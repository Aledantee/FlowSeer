BAD-MIB DEFINITIONS ::= BEGIN

acme OBJECT IDENTIFIER ::= { iso org(3) dod(6) internet(1) private(4) enterprises(1) 47100 }

shuffled OBJECT-TYPE
    SYNTAX      Integer32
    MAX-ACCESS  read-only
    DESCRIPTION "The description comes before the status."
    STATUS      current
    ::= { acme 1 }

END
