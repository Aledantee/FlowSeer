-- A fixture module for the mibgen diagnostic baseline gate. Every
-- deviation below is deliberate: the gate can only be shown to bite
-- against a module that actually raises something.
--
-- It raises four diagnostics: a display hint on each of two Gauge32
-- conventions, a range wider than its base type, and a repeated STATUS
-- clause. The sibling directories hold variants that move, add or
-- relocate one of them.

BASELINE-MIB DEFINITIONS ::= BEGIN

IMPORTS
    MODULE-IDENTITY, OBJECT-TYPE, Gauge32, Integer32
        FROM SNMPv2-SMI
    TEXTUAL-CONVENTION
        FROM SNMPv2-TC;

baselineMIB MODULE-IDENTITY
    LAST-UPDATED "202608300000Z"
    ORGANIZATION "FlowSeer"
    CONTACT-INFO "FlowSeer test fixtures."
    DESCRIPTION  "Fixture module for the diagnostic baseline gate."
    ::= { 1 3 6 1 4 1 99999 1 }

HintedGauge ::= TEXTUAL-CONVENTION
    DISPLAY-HINT "d-2"
    STATUS       current
    DESCRIPTION  "A gauge carrying a display hint RFC 2579 does not allow."
    SYNTAX       Gauge32

SecondHintedGauge ::= TEXTUAL-CONVENTION
    DISPLAY-HINT "d-3"
    STATUS       current
    DESCRIPTION  "A second gauge carrying a display hint."
    SYNTAX       Gauge32

WideRange ::= TEXTUAL-CONVENTION
    STATUS       current
    DESCRIPTION  "A range wider than the base type can hold."
    SYNTAX       Integer32 (0..4294967295)

RepeatedStatus ::= TEXTUAL-CONVENTION
    STATUS       current
    STATUS       current
    DESCRIPTION  "A convention that writes STATUS twice."
    SYNTAX       Integer32

baselineBroken OBJECT-TYPE
    SYNTAX      NoSuchSyntax
    MAX-ACCESS  read-only
    STATUS      current
    DESCRIPTION "An object whose SYNTAX names a type nothing defines."
    ::= { baselineMIB 1 }

END
