BAD-MIB DEFINITIONS ::= BEGIN

acme OBJECT IDENTIFIER ::= { iso org(3) dod(6) internet(1) private(4) enterprises(1) 47100 }

cipherSuite OBJECT-TYPE
    SYNTAX      INTEGER { tls_rsa(1), tls_dhe(2) }
    MAX-ACCESS  read-only
    STATUS      current
    DESCRIPTION "An object."
    ::= { acme 1 }

END
