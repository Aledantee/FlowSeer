BAD-MIB DEFINITIONS ::= BEGIN

acme OBJECT IDENTIFIER ::= { iso org(3) dod(6) internet(1) private(4) enterprises(1) 47100 }

misplacedUnits OBJECT-IDENTITY
    UNITS       "seconds"
    STATUS      current
    DESCRIPTION "A naming node with an object's clause on it."
    ::= { acme 1 }

END
