BAD-MIB DEFINITIONS ::= BEGIN

acme OBJECT IDENTIFIER ::= { iso org(3) dod(6) internet(1) private(4) enterprises(1) 47100 }

negativeLength OBJECT-TYPE
    SYNTAX      OCTET STRING (SIZE (-1..4))
    MAX-ACCESS  read-only
    STATUS      current
    DESCRIPTION "An object."
    ::= { acme 1 }

END
