BAD-MIB DEFINITIONS ::= BEGIN

acme OBJECT IDENTIFIER ::= { iso org(3) dod(6) internet(1) private(4) enterprises(1) 47100 }

shortOctet OBJECT-TYPE
    SYNTAX      OCTET STRING
    MAX-ACCESS  read-only
    STATUS      current
    DESCRIPTION "An object."
    DEFVAL      { '10101'B }
    ::= { acme 1 }

END
