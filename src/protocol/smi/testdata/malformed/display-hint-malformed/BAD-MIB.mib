BAD-MIB DEFINITIONS ::= BEGIN

acme OBJECT IDENTIFIER ::= { iso org(3) dod(6) internet(1) private(4) enterprises(1) 47100 }

BadHint ::= TEXTUAL-CONVENTION
    DISPLAY-HINT "255z"
    STATUS       current
    DESCRIPTION  "A hint naming a format nothing renders."
    SYNTAX       OCTET STRING

END
