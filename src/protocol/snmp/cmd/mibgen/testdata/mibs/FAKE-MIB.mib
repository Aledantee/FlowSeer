FAKE-MIB DEFINITIONS ::= BEGIN
IMPORTS
    OBJECT-TYPE, MODULE-IDENTITY, Integer32, Counter32, Counter64, TimeTicks, IpAddress
        FROM SNMPv2-SMI
    DisplayString, MacAddress, TEXTUAL-CONVENTION
        FROM SNMPv2-TC
    FakeKeyIndex, fakeKeyEntry
        FROM FAKE-KEYS-MIB;

fakeMIB MODULE-IDENTITY
    LAST-UPDATED "202605120000Z"
    ORGANIZATION "FlowSeer Test"
    CONTACT-INFO "test"
    DESCRIPTION  "Hand-crafted MIB for mibgen golden tests."
    ::= { 1 3 6 1 4 1 99999 1 }

fakeScalar OBJECT-TYPE
    SYNTAX      Integer32
    MAX-ACCESS  read-only
    STATUS      current
    DESCRIPTION "A simple scalar."
    ::= { fakeMIB 1 }

fakeStatus OBJECT-TYPE
    SYNTAX      INTEGER {
        up(1),
        down(2),
        testing(3)
    }
    MAX-ACCESS  read-only
    STATUS      current
    DESCRIPTION "An enum-typed scalar."
    ::= { fakeMIB 2 }

FakeCapabilities ::= TEXTUAL-CONVENTION
    STATUS      current
    DESCRIPTION "A named BITS convention. Bit positions follow
                 declaration order; the emitter names each one as an
                 snmp.BitPos constant and decodes values of this type
                 to an snmp.BitSet."
    SYNTAX      BITS {
        alpha(0),
        beta(1),
        gamma(2)
    }

fakeCaps OBJECT-TYPE
    SYNTAX      FakeCapabilities
    MAX-ACCESS  read-only
    STATUS      current
    DESCRIPTION "A BITS-typed scalar."
    ::= { fakeMIB 6 }

fakeLegacyMac OBJECT-TYPE
    SYNTAX      MacAddress
    MAX-ACCESS  read-only
    STATUS      obsolete
    DESCRIPTION "An obsolete scalar with a natural textual-convention decoder."
    ::= { fakeMIB 18 }

fakeSoloTable OBJECT-TYPE
    SYNTAX      SEQUENCE OF FakeSoloEntry
    MAX-ACCESS  not-accessible
    STATUS      deprecated
    DESCRIPTION "A deprecated table with one readable column."
    ::= { fakeMIB 19 }

fakeSoloEntry OBJECT-TYPE
    SYNTAX      FakeSoloEntry
    MAX-ACCESS  not-accessible
    STATUS      current
    DESCRIPTION "A row in fakeSoloTable."
    INDEX { fakeSoloIndex }
    ::= { fakeSoloTable 1 }

FakeSoloEntry ::= SEQUENCE {
    fakeSoloIndex       Integer32,
    fakeSoloLastChange  Counter32
}

fakeSoloIndex OBJECT-TYPE
    SYNTAX      Integer32 (1..2147483647)
    MAX-ACCESS  not-accessible
    STATUS      current
    DESCRIPTION "Row index."
    ::= { fakeSoloEntry 1 }

fakeSoloLastChange OBJECT-TYPE
    SYNTAX      Counter32
    MAX-ACCESS  read-only
    STATUS      current
    DESCRIPTION "The table's single readable column and change indicator."
    ::= { fakeSoloEntry 2 }

fakeTable OBJECT-TYPE
    SYNTAX      SEQUENCE OF FakeEntry
    MAX-ACCESS  not-accessible
    STATUS      current
    DESCRIPTION "A table."
    ::= { fakeMIB 3 }

fakeEntry OBJECT-TYPE
    SYNTAX      FakeEntry
    MAX-ACCESS  not-accessible
    STATUS      current
    DESCRIPTION "A row in fakeTable."
    INDEX { fakeIndex }
    ::= { fakeTable 1 }

FakeEntry ::= SEQUENCE {
    fakeIndex       Integer32,
    fakeName        DisplayString,
    fakeMac         MacAddress,
    fakeOctets      Counter64,
    fakeLastChange  TimeTicks,
    fakeFlags       FakeCapabilities,
    fakeRef         FakeKeyIndex,
    fakeMode        INTEGER,
    fakeDeprecated  Counter32
}

fakeIndex OBJECT-TYPE
    SYNTAX      Integer32 (1..2147483647)
    MAX-ACCESS  not-accessible
    STATUS      current
    DESCRIPTION "Row index."
    ::= { fakeEntry 1 }

fakeName OBJECT-TYPE
    SYNTAX      DisplayString
    MAX-ACCESS  read-only
    STATUS      current
    DESCRIPTION "Name."
    ::= { fakeEntry 2 }

fakeMac OBJECT-TYPE
    SYNTAX      MacAddress
    MAX-ACCESS  read-only
    STATUS      current
    DESCRIPTION "MAC address."
    ::= { fakeEntry 3 }

fakeOctets OBJECT-TYPE
    SYNTAX      Counter64
    MAX-ACCESS  read-only
    STATUS      current
    DESCRIPTION "Counter."
    ::= { fakeEntry 4 }

fakeLastChange OBJECT-TYPE
    SYNTAX      TimeTicks
    MAX-ACCESS  read-only
    STATUS      current
    DESCRIPTION "Per-row change indicator. The name-suffix heuristic
                 classifies this column as TierIndicator at codegen
                 time and structural discovery binds it to fakeTable."
    ::= { fakeEntry 5 }

fakeFlags OBJECT-TYPE
    SYNTAX      FakeCapabilities
    MAX-ACCESS  read-only
    STATUS      current
    DESCRIPTION "A BITS-typed column. Covers the row-struct, watch-
                 equality, and observation paths for set-valued
                 columns."
    ::= { fakeEntry 6 }

fakeRef OBJECT-TYPE
    SYNTAX      FakeKeyIndex
    MAX-ACCESS  read-only
    STATUS      current
    DESCRIPTION "A reference to a row of fakeKeyTable in FAKE-KEYS-MIB.
                 Covers the cross-package keyed-convention path and its
                 degraded form when that module is not configured."
    ::= { fakeEntry 7 }

fakeMode OBJECT-TYPE
    SYNTAX      INTEGER {
        only(1)
    }
    MAX-ACCESS  read-only
    STATUS      current
    DESCRIPTION "A one-member enum column."
    ::= { fakeEntry 8 }

fakeDeprecated OBJECT-TYPE
    SYNTAX      Counter32
    MAX-ACCESS  read-only
    STATUS      deprecated
    DESCRIPTION "A deprecated counter column."
    ::= { fakeEntry 9 }

-- fakeStackTable has no per-row indicator column, so structural
-- per-row discovery cannot bind it. Its indicator is the module-level
-- fakeStackLastChange scalar below, reachable only through the
-- name-prefix rule: "fakeStack" (the table name minus its trailing
-- "Table") plus the "LastChange" suffix. This pair is the golden
-- fixture's coverage for discoverNamePrefixScalarIndicator.

fakeStackTable OBJECT-TYPE
    SYNTAX      SEQUENCE OF FakeStackEntry
    MAX-ACCESS  not-accessible
    STATUS      current
    DESCRIPTION "A table whose change indicator is a sibling scalar."
    ::= { fakeMIB 4 }

fakeStackEntry OBJECT-TYPE
    SYNTAX      FakeStackEntry
    MAX-ACCESS  not-accessible
    STATUS      current
    DESCRIPTION "A row in fakeStackTable."
    INDEX { fakeStackIndex }
    ::= { fakeStackTable 1 }

FakeStackEntry ::= SEQUENCE {
    fakeStackIndex  Integer32,
    fakeStackName   DisplayString
}

fakeStackIndex OBJECT-TYPE
    SYNTAX      Integer32 (1..2147483647)
    MAX-ACCESS  not-accessible
    STATUS      current
    DESCRIPTION "Row index."
    ::= { fakeStackEntry 1 }

fakeStackName OBJECT-TYPE
    SYNTAX      DisplayString
    MAX-ACCESS  read-only
    STATUS      current
    DESCRIPTION "Name."
    ::= { fakeStackEntry 2 }

fakeStackLastChange OBJECT-TYPE
    SYNTAX      TimeTicks
    MAX-ACCESS  read-only
    STATUS      current
    DESCRIPTION "Scalar change indicator covering fakeStackTable. Bound
                 by the name-prefix structural rule, not by per-row
                 discovery."
    ::= { fakeMIB 5 }

-- The tables below exist for their INDEX shapes: a two-part key with a
-- length-prefixed string, an IMPLIED string, an IpAddress, an OBJECT
-- IDENTIFIER, a row that AUGMENTS fakeEntry, and after those the
-- shapes the emitter has to fall back or reach through on: an INDEX
-- part nothing declares, a row augmenting another module's row, a row
-- augmenting an augmenting row, a row augmenting an index-only table,
-- and an index column that refines the imported convention.

fakePairTable OBJECT-TYPE
    SYNTAX      SEQUENCE OF FakePairEntry
    MAX-ACCESS  not-accessible
    STATUS      current
    DESCRIPTION "A table keyed by an integer and a string."
    ::= { fakeMIB 7 }

fakePairEntry OBJECT-TYPE
    SYNTAX      FakePairEntry
    MAX-ACCESS  not-accessible
    STATUS      current
    DESCRIPTION "A row in fakePairTable."
    INDEX { fakePairSlot, fakePairName }
    ::= { fakePairTable 1 }

FakePairEntry ::= SEQUENCE {
    fakePairSlot    Integer32,
    fakePairName    OCTET STRING,
    fakePairValue   Integer32
}

fakePairSlot OBJECT-TYPE
    SYNTAX      Integer32 (1..64)
    MAX-ACCESS  not-accessible
    STATUS      current
    DESCRIPTION "First index part."
    ::= { fakePairEntry 1 }

fakePairName OBJECT-TYPE
    SYNTAX      OCTET STRING (SIZE (1..32))
    MAX-ACCESS  not-accessible
    STATUS      current
    DESCRIPTION "Second index part, length-prefixed in the instance OID."
    ::= { fakePairEntry 2 }

fakePairValue OBJECT-TYPE
    SYNTAX      Integer32
    MAX-ACCESS  read-only
    STATUS      current
    DESCRIPTION "Value."
    ::= { fakePairEntry 3 }

fakeImpliedTable OBJECT-TYPE
    SYNTAX      SEQUENCE OF FakeImpliedEntry
    MAX-ACCESS  not-accessible
    STATUS      current
    DESCRIPTION "A table keyed by an IMPLIED string."
    ::= { fakeMIB 8 }

fakeImpliedEntry OBJECT-TYPE
    SYNTAX      FakeImpliedEntry
    MAX-ACCESS  not-accessible
    STATUS      current
    DESCRIPTION "A row in fakeImpliedTable."
    INDEX { IMPLIED fakeImpliedName }
    ::= { fakeImpliedTable 1 }

FakeImpliedEntry ::= SEQUENCE {
    fakeImpliedName     OCTET STRING,
    fakeImpliedValue    Integer32
}

fakeImpliedName OBJECT-TYPE
    SYNTAX      OCTET STRING (SIZE (1..64))
    MAX-ACCESS  not-accessible
    STATUS      current
    DESCRIPTION "Index part without a length arc."
    ::= { fakeImpliedEntry 1 }

fakeImpliedValue OBJECT-TYPE
    SYNTAX      Integer32
    MAX-ACCESS  read-only
    STATUS      current
    DESCRIPTION "Value."
    ::= { fakeImpliedEntry 2 }

fakeAddrTable OBJECT-TYPE
    SYNTAX      SEQUENCE OF FakeAddrEntry
    MAX-ACCESS  not-accessible
    STATUS      current
    DESCRIPTION "A table keyed by an IpAddress."
    ::= { fakeMIB 9 }

fakeAddrEntry OBJECT-TYPE
    SYNTAX      FakeAddrEntry
    MAX-ACCESS  not-accessible
    STATUS      current
    DESCRIPTION "A row in fakeAddrTable."
    INDEX { fakeAddrIp }
    ::= { fakeAddrTable 1 }

FakeAddrEntry ::= SEQUENCE {
    fakeAddrIp      IpAddress,
    fakeAddrLabel   DisplayString
}

fakeAddrIp OBJECT-TYPE
    SYNTAX      IpAddress
    MAX-ACCESS  not-accessible
    STATUS      current
    DESCRIPTION "Index part: four arcs."
    ::= { fakeAddrEntry 1 }

fakeAddrLabel OBJECT-TYPE
    SYNTAX      DisplayString
    MAX-ACCESS  read-only
    STATUS      current
    DESCRIPTION "Label."
    ::= { fakeAddrEntry 2 }

fakeOidTable OBJECT-TYPE
    SYNTAX      SEQUENCE OF FakeOidEntry
    MAX-ACCESS  not-accessible
    STATUS      current
    DESCRIPTION "A table keyed by an OBJECT IDENTIFIER."
    ::= { fakeMIB 10 }

fakeOidEntry OBJECT-TYPE
    SYNTAX      FakeOidEntry
    MAX-ACCESS  not-accessible
    STATUS      current
    DESCRIPTION "A row in fakeOidTable."
    INDEX { fakeOidPath }
    ::= { fakeOidTable 1 }

FakeOidEntry ::= SEQUENCE {
    fakeOidPath     OBJECT IDENTIFIER,
    fakeOidLabel    DisplayString
}

fakeOidPath OBJECT-TYPE
    SYNTAX      OBJECT IDENTIFIER
    MAX-ACCESS  not-accessible
    STATUS      current
    DESCRIPTION "Index part: a length arc followed by the OID arcs."
    ::= { fakeOidEntry 1 }

fakeOidLabel OBJECT-TYPE
    SYNTAX      DisplayString
    MAX-ACCESS  read-only
    STATUS      current
    DESCRIPTION "Label."
    ::= { fakeOidEntry 2 }

fakeAugTable OBJECT-TYPE
    SYNTAX      SEQUENCE OF FakeAugEntry
    MAX-ACCESS  not-accessible
    STATUS      current
    DESCRIPTION "A table whose rows extend fakeTable rows."
    ::= { fakeMIB 11 }

fakeAugEntry OBJECT-TYPE
    SYNTAX      FakeAugEntry
    MAX-ACCESS  not-accessible
    STATUS      current
    DESCRIPTION "A row in fakeAugTable, keyed like fakeEntry."
    AUGMENTS { fakeEntry }
    ::= { fakeAugTable 1 }

FakeAugEntry ::= SEQUENCE {
    fakeAugExtra    Integer32
}

fakeAugExtra OBJECT-TYPE
    SYNTAX      Integer32
    MAX-ACCESS  read-only
    STATUS      current
    DESCRIPTION "Extra value."
    ::= { fakeAugEntry 1 }

fakeUnresolvedTable OBJECT-TYPE
    SYNTAX      SEQUENCE OF FakeUnresolvedEntry
    MAX-ACCESS  not-accessible
    STATUS      current
    DESCRIPTION "A table whose INDEX names a column nothing declares."
    ::= { fakeMIB 12 }

fakeUnresolvedEntry OBJECT-TYPE
    SYNTAX      FakeUnresolvedEntry
    MAX-ACCESS  not-accessible
    STATUS      current
    DESCRIPTION "A row in fakeUnresolvedTable, keyed by the raw suffix
                 since its INDEX part does not resolve."
    INDEX { fakeNowhere }
    ::= { fakeUnresolvedTable 1 }

FakeUnresolvedEntry ::= SEQUENCE {
    fakeUnresolvedValue Integer32
}

fakeUnresolvedValue OBJECT-TYPE
    SYNTAX      Integer32
    MAX-ACCESS  read-only
    STATUS      current
    DESCRIPTION "Value."
    ::= { fakeUnresolvedEntry 1 }

fakeKeyAugTable OBJECT-TYPE
    SYNTAX      SEQUENCE OF FakeKeyAugEntry
    MAX-ACCESS  not-accessible
    STATUS      current
    DESCRIPTION "A table whose rows extend fakeKeyTable rows of FAKE-KEYS-MIB."
    ::= { fakeMIB 13 }

fakeKeyAugEntry OBJECT-TYPE
    SYNTAX      FakeKeyAugEntry
    MAX-ACCESS  not-accessible
    STATUS      current
    DESCRIPTION "A row in fakeKeyAugTable, keyed like fakeKeyEntry."
    AUGMENTS { fakeKeyEntry }
    ::= { fakeKeyAugTable 1 }

FakeKeyAugEntry ::= SEQUENCE {
    fakeKeyAugExtra Integer32
}

fakeKeyAugExtra OBJECT-TYPE
    SYNTAX      Integer32
    MAX-ACCESS  read-only
    STATUS      current
    DESCRIPTION "Extra value."
    ::= { fakeKeyAugEntry 1 }

fakeChainTable OBJECT-TYPE
    SYNTAX      SEQUENCE OF FakeChainEntry
    MAX-ACCESS  not-accessible
    STATUS      current
    DESCRIPTION "A table whose rows extend fakeAugTable rows, which
                 themselves extend fakeTable rows."
    ::= { fakeMIB 14 }

fakeChainEntry OBJECT-TYPE
    SYNTAX      FakeChainEntry
    MAX-ACCESS  not-accessible
    STATUS      current
    DESCRIPTION "A row in fakeChainTable, keyed like fakeEntry through
                 fakeAugEntry."
    AUGMENTS { fakeAugEntry }
    ::= { fakeChainTable 1 }

FakeChainEntry ::= SEQUENCE {
    fakeChainExtra  Integer32
}

fakeChainExtra OBJECT-TYPE
    SYNTAX      Integer32
    MAX-ACCESS  read-only
    STATUS      current
    DESCRIPTION "Extra value."
    ::= { fakeChainEntry 1 }

fakeBareTable OBJECT-TYPE
    SYNTAX      SEQUENCE OF FakeBareEntry
    MAX-ACCESS  not-accessible
    STATUS      current
    DESCRIPTION "A table whose only column is its index."
    ::= { fakeMIB 15 }

fakeBareEntry OBJECT-TYPE
    SYNTAX      FakeBareEntry
    MAX-ACCESS  not-accessible
    STATUS      current
    DESCRIPTION "A row in fakeBareTable."
    INDEX { fakeBareIndex }
    ::= { fakeBareTable 1 }

FakeBareEntry ::= SEQUENCE {
    fakeBareIndex   Integer32
}

fakeBareIndex OBJECT-TYPE
    SYNTAX      Integer32 (1..16)
    MAX-ACCESS  not-accessible
    STATUS      current
    DESCRIPTION "Row index."
    ::= { fakeBareEntry 1 }

fakeBareAugTable OBJECT-TYPE
    SYNTAX      SEQUENCE OF FakeBareAugEntry
    MAX-ACCESS  not-accessible
    STATUS      current
    DESCRIPTION "A table whose rows extend the index-only fakeBareTable."
    ::= { fakeMIB 16 }

fakeBareAugEntry OBJECT-TYPE
    SYNTAX      FakeBareAugEntry
    MAX-ACCESS  not-accessible
    STATUS      current
    DESCRIPTION "A row in fakeBareAugTable, keyed like fakeBareEntry."
    AUGMENTS { fakeBareEntry }
    ::= { fakeBareAugTable 1 }

FakeBareAugEntry ::= SEQUENCE {
    fakeBareAugExtra    Integer32
}

fakeBareAugExtra OBJECT-TYPE
    SYNTAX      Integer32
    MAX-ACCESS  read-only
    STATUS      current
    DESCRIPTION "Extra value."
    ::= { fakeBareAugEntry 1 }

fakeRefinedTable OBJECT-TYPE
    SYNTAX      SEQUENCE OF FakeRefinedEntry
    MAX-ACCESS  not-accessible
    STATUS      current
    DESCRIPTION "A table keyed by a refinement of the imported convention."
    ::= { fakeMIB 17 }

fakeRefinedEntry OBJECT-TYPE
    SYNTAX      FakeRefinedEntry
    MAX-ACCESS  not-accessible
    STATUS      current
    DESCRIPTION "A row in fakeRefinedTable."
    INDEX { fakeRefinedIndex }
    ::= { fakeRefinedTable 1 }

FakeRefinedEntry ::= SEQUENCE {
    fakeRefinedIndex    FakeKeyIndex,
    fakeRefinedValue    Integer32
}

fakeRefinedIndex OBJECT-TYPE
    SYNTAX      FakeKeyIndex (1..10)
    MAX-ACCESS  not-accessible
    STATUS      current
    DESCRIPTION "Row index: a fakeKeyTable row, restricted to the first ten."
    ::= { fakeRefinedEntry 1 }

fakeRefinedValue OBJECT-TYPE
    SYNTAX      Integer32
    MAX-ACCESS  read-only
    STATUS      current
    DESCRIPTION "Value."
    ::= { fakeRefinedEntry 2 }

END
