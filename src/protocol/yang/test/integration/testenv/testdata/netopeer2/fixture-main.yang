module fixture-main {
  yang-version 1.1;
  namespace "urn:flowseer:fixture-main";
  prefix fm;

  import fixture-types {
    prefix ft;
  }

  import fixture-grp {
    prefix fg;
  }

  include fixture-main-sub;

  revision 2026-01-02 {
    description "Fixture baseline.";
  }

  container servers {
    list server {
      key "name";
      leaf name {
        type string;
      }
      leaf port {
        type ft:port-number;
      }
      leaf listen {
        type ft:port-or-name;
        description "Union leaf.";
      }
      leaf proto {
        type identityref {
          base ft:protocol;
        }
      }
      leaf ratio {
        type decimal64 {
          fraction-digits 3;
        }
      }
      leaf legacy-flag {
        type boolean;
        description "Deviated away by fixture-dev.";
      }
      container tls {
        presence "TLS termination enabled";
        leaf min-version {
          type enumeration {
            enum tls12;
            enum tls13;
          }
        }
      }
      container key {
        description "Child container whose joined name collides with the server companion key struct.";
        leaf id {
          type string;
        }
      }
      list endpoint {
        key "address port";
        description "Nested list with a compound key; flattened rows
          carry the parent server's key (KTD4).";
        leaf address {
          type string;
        }
        leaf port {
          type ft:port-number;
        }
        leaf enabled {
          type boolean;
        }
      }
    }
    container server-schema {
      description "Sibling of server whose joined name equals the server schema var.";
      leaf note {
        type string;
      }
    }
    container schema {
      description "Child container whose joined name collides with the servers companion schema var.";
      leaf version {
        type string;
      }
    }
  }

  container bindings {
    list binding {
      key "server-ref";
      description "List keyed by a leafref, resolved to its target
        type at generation time.";
      leaf server-ref {
        type leafref {
          path "/fm:servers/fm:server/fm:name";
        }
      }
      leaf weight {
        type uint8;
      }
    }
  }

  container alarm-state {
    description "Collides with alarmState under naive mangling.";
    leaf count {
      type uint32;
    }
  }

  container alarmState {
    description "Collides with alarm-state under naive mangling.";
    leaf count {
      type uint32;
    }
  }

  container primary-group {
    uses fg:endpoint-settings;
    uses fg:peer-list;
  }

  container secondary-group {
    uses fg:endpoint-settings;
    uses fg:peer-list;
  }

  container shape-probe {
    description "Pairs of same-named nodes that differ in one property the
      codecs read, so they must not share a generated type.";
    container by-type-a {
      container setting {
        leaf value {
          type uint32;
        }
      }
    }
    container by-type-b {
      container setting {
        leaf value {
          type string;
        }
      }
    }
    container by-presence-a {
      container marker {
        leaf value {
          type uint32;
        }
      }
    }
    container by-presence-b {
      container marker {
        presence "Enables the marker.";
        leaf value {
          type uint32;
        }
      }
    }
    container by-module-a {
      container slot {
        leaf value {
          type uint32;
        }
      }
    }
    container by-module-b {
      container slot {
        description "fixture-aug augments this container's only leaf.";
      }
    }
    container by-owner-a {
      container flag;
    }
    container by-owner-b {
      description "fixture-aug augments an empty flag container here.";
    }
  }
}
