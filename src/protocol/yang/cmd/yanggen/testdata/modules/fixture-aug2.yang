module fixture-aug2 {
  yang-version 1.1;
  namespace "urn:flowseer:fixture-aug2";
  prefix fa2;

  import fixture-main {
    prefix fm;
  }

  revision 2026-01-05 {
    description "Second augment fixture.";
  }

  augment "/fm:servers/fm:server" {
    leaf owner {
      type uint8;
    }
    leaf port {
      type string;
    }
  }

  augment "/fm:servers" {
    list mirror {
      key "id";
      leaf id {
        type string;
      }
    }
  }
}
