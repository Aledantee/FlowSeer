--  *****************************************************************
--  DLINKSW-LOOPBACK-TEST-MIB.mib : Loopback Test MIB
-- 
--  Copyright (c) 2013 D-Link Corporation, all rights reserved.
--   
--  *****************************************************************

DLINKSW-LOOPBACK-TEST-MIB DEFINITIONS ::= BEGIN

    IMPORTS
        MODULE-IDENTITY,
		OBJECT-TYPE,
		Integer32,
		Counter32
                        FROM SNMPv2-SMI
        dlinkIndustrialCommon		
						FROM DLINK-ID-REC-MIB
        ifIndex
						FROM IF-MIB;
		
    	
    dlinkSwLoopbackTestMIB MODULE-IDENTITY
		LAST-UPDATED "201511230000Z"
		ORGANIZATION "D-Link Corp."
		CONTACT-INFO
			"         D-Link Corporation
             Postal: No. 289, Sinhu 3rd Rd., Neihu District,
                     Taipei City 114, Taiwan, R.O.C
             Tel:    +886-2-66000123
             E-mail: tsd@dlink.com.tw
            "
		DESCRIPTION
			"This MIB module defines objects for loopback test."
		REVISION "201511230000Z"
        DESCRIPTION
            "This is the first version of the MIB file."
    ::= { dlinkIndustrialCommon 189 }

	
	dLoopbackTestMIBNotifications 			OBJECT IDENTIFIER ::= { dlinkSwLoopbackTestMIB 0 }
	dLoopbackTestMIBObjects 			OBJECT IDENTIFIER ::= { dlinkSwLoopbackTestMIB 1 }
	dLoopbackTestMIBConformance		    	OBJECT IDENTIFIER ::= { dlinkSwLoopbackTestMIB 2 }

-- -----------------------------------------------------------------------------
-- dLoopbackTestMIBNotifications
-- -----------------------------------------------------------------------------


-- -----------------------------------------------------------------------------
-- dLoopbackTestMIBObjects
-- -----------------------------------------------------------------------------

    dLoopbackTestConfigTabe OBJECT-TYPE
        SYNTAX  	SEQUENCE OF DLoopbackTestConfigEntry
        MAX-ACCESS  not-accessible
        STATUS  	current
        DESCRIPTION
            "This table contains the configuration of local loopback."
        ::= { dLoopbackTestMIBObjects 1 }

    dLoopbackTestConfigEntry OBJECT-TYPE
        SYNTAX  	DLoopbackTestConfigEntry
        MAX-ACCESS  not-accessible
        STATUS  	current
        DESCRIPTION
            "This is an entry of the dLoopbackTestConfigTabe."
        INDEX  { ifIndex }
        ::= { dLoopbackTestConfigTabe 1 }

    DLoopbackTestConfigEntry ::=
        SEQUENCE {
            dLoopbackTestMode
                INTEGER,
            dLoopbackTestLayer
            	INTEGER,
            dLoopbackTestState
            	INTEGER
        }

    dLoopbackTestMode OBJECT-TYPE
        SYNTAX  INTEGER{
                other(1),
                internal(2),
                external(3)
                }
        MAX-ACCESS  read-write
        STATUS  	current
        DESCRIPTION
            "This object indicates the method of loopback.
            Note: This object and dLoopbackTestLayer must be set together."
        ::= { dLoopbackTestConfigEntry 1 }

    dLoopbackTestLayer OBJECT-TYPE
        SYNTAX  INTEGER{
                other(1),
                mac(2),
                phycopper(3),
                phyfiber(4)
                }
        MAX-ACCESS  read-write
        STATUS  	current
        DESCRIPTION
            "This object indicates the mode of loopback.
            Note: This object and dLoopbackTestMode must be set together."
        ::= { dLoopbackTestConfigEntry 2 }


    dLoopbackTestState OBJECT-TYPE
        SYNTAX  INTEGER{
                enabled(1),
                disabled(2)
                }
        MAX-ACCESS  read-write
        STATUS  	current
        DESCRIPTION
            "This object indicates the state of loopback.

            enabled (1): for internal loopback, start loopback test;
            for external loopback, set port(s) to external loopback mode.
            disabled (2): for internal loopback, stop loopback test;
            for external loopback, recover port(s) from external loopback mode.
            "
        ::= { dLoopbackTestConfigEntry 3 }
        
    dLoopbackTestResultTable OBJECT-TYPE
        SYNTAX  SEQUENCE OF DLoopbackTestResultEntry
        MAX-ACCESS  not-accessible
        STATUS  current
        DESCRIPTION
            "This table contains the result of local loopback."
        ::= { dLoopbackTestMIBObjects 2 }

    dLoopbackTestResultEntry OBJECT-TYPE
        SYNTAX  DLoopbackTestResultEntry
        MAX-ACCESS  not-accessible
        STATUS  current
        DESCRIPTION
            "This is an entry of the dLoopbackTestResultTable."
        INDEX  { ifIndex }
        ::= { dLoopbackTestResultTable 1 }

    DLoopbackTestResultEntry ::=
        SEQUENCE {
            dLoopbackTest64Tx
                Counter32,
            dLoopbackTest64Rx
                Counter32,
            dLoopbackTest512Tx
                Counter32,
            dLoopbackTest512Rx
                Counter32,
            dLoopbackTest1024Tx
            	Counter32,
            dLoopbackTest1024Rx
            	Counter32,
            dLoopbackTest1536Tx
            	Counter32,
            dLoopbackTest1536Rx
            	Counter32,
            dLoopbackTestStatus
            	INTEGER       	
        }
        
    dLoopbackTest64Tx OBJECT-TYPE
        SYNTAX  Counter32
        MAX-ACCESS  read-only
        STATUS  current
        DESCRIPTION
            "This object indicates the 64-byte packets of loopback Tx."
        ::= { dLoopbackTestResultEntry 1 }

    dLoopbackTest64Rx OBJECT-TYPE
        SYNTAX  Counter32
        MAX-ACCESS  read-only
        STATUS  current
        DESCRIPTION
            "This object indicates the 64-byte packets of loopback Rx."
        ::= { dLoopbackTestResultEntry 2 }
        
    dLoopbackTest512Tx OBJECT-TYPE
        SYNTAX  Counter32
        MAX-ACCESS  read-only
        STATUS  current
        DESCRIPTION
            "This object indicates the 512-byte packets of loopback Tx."
        ::= { dLoopbackTestResultEntry 3 }

    dLoopbackTest512Rx OBJECT-TYPE
        SYNTAX  Counter32
        MAX-ACCESS  read-only
        STATUS  current
        DESCRIPTION
            "This object indicates the 512-byte packets of loopback Rx."
        ::= { dLoopbackTestResultEntry 4 }

    dLoopbackTest1024Tx OBJECT-TYPE
        SYNTAX  Counter32
        MAX-ACCESS  read-only
        STATUS  current
        DESCRIPTION
            "This object indicates the 1024-byte packets of loopback Tx."
        ::= { dLoopbackTestResultEntry 5 }
        
    dLoopbackTest1024Rx OBJECT-TYPE
        SYNTAX  Counter32
        MAX-ACCESS  read-only
        STATUS  current
        DESCRIPTION
            "This object indicates the 1024-byte packets of loopback Rx."
        ::= { dLoopbackTestResultEntry 6 }
        
    dLoopbackTest1536Tx OBJECT-TYPE
        SYNTAX  Counter32
        MAX-ACCESS  read-only
        STATUS  current
        DESCRIPTION
            "This object indicates the 1536-byte packets of loopback Tx."
        ::= { dLoopbackTestResultEntry 7 }

    dLoopbackTest1536Rx OBJECT-TYPE
        SYNTAX  Counter32
        MAX-ACCESS  read-only
        STATUS  current
        DESCRIPTION
            "This object indicates the 1536-byte packets of loopback Rx."
        ::= { dLoopbackTestResultEntry 8 }

    dLoopbackTestStatus OBJECT-TYPE
        SYNTAX  INTEGER{
                other(1),
				testing(2),
                success(3),
                fail(4)
                }
        MAX-ACCESS  read-only
        STATUS  current
        DESCRIPTION
            "This object indicates the status of loopback."
        ::= { dLoopbackTestResultEntry 9 }
		
    	     	
-- -----------------------------------------------------------------------------
-- dLoopbackTestMIBConformance
-- -----------------------------------------------------------------------------

		dLoopbackTestCompliances OBJECT IDENTIFIER ::= { dLoopbackTestMIBConformance 1 }
		
		dLoopbackTestCompliance MODULE-COMPLIANCE
			STATUS current
			DESCRIPTION 
				"The compliance statement for entities which implement the 
				DLINKSW-LOOPBACK-TEST-MIB."
			MODULE -- this module
			MANDATORY-GROUPS { 
				dLoopbackConfigGroup,
				dLoopbackTestResultGroup       		   
			}						
		::= { dLoopbackTestCompliances 1 }
		
		dLoopbackTestGroups OBJECT IDENTIFIER ::= { dLoopbackTestMIBConformance 2 }
		
		dLoopbackConfigGroup	OBJECT-GROUP
			OBJECTS {
			dLoopbackTestMode,
            dLoopbackTestLayer,
            dLoopbackTestState									
		}
		STATUS current
		DESCRIPTION 
			"A collection of objects provides LOOPBACKTEST config information."
		::= { dLoopbackTestGroups 1 }

		
    dLoopbackTestResultGroup OBJECT-GROUP
		OBJECTS { 
            dLoopbackTest64Tx,
            dLoopbackTest64Rx,
            dLoopbackTest512Tx,
            dLoopbackTest512Rx,
            dLoopbackTest1024Tx,
            dLoopbackTest1024Rx,
            dLoopbackTest1536Tx,
            dLoopbackTest1536Rx,
            dLoopbackTestStatus		
		}
		STATUS current
		DESCRIPTION 
			"A collection of objects provides LOOPBACKTEST result information."
		::= { dLoopbackTestGroups 2 }     
END
