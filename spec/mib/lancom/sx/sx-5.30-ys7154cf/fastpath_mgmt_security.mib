FASTPATH-MGMT-SECURITY-MIB DEFINITIONS ::= BEGIN

-- Broadcom FastPath Mgmt Security MIB
-- Copyright 2016-2022 Broadcom.
-- This SNMP Management Information Specification
-- embodies Broadcom's confidential and proprietary
-- intellectual property.  Broadcom retains all title
-- and ownership in the Specification including any revisions.

-- This Specification is supplied "AS IS", Broadcom 
-- makes no warranty, either expressed or implied,
-- as to the use, operation, condition, or performance of the
-- Specification.


IMPORTS
    MODULE-IDENTITY, OBJECT-TYPE, NOTIFICATION-TYPE, 
    IpAddress, Integer32, Unsigned32    FROM SNMPv2-SMI
    fastPath                            FROM LANCOM-REF-MIB
    DisplayString                       FROM RFC1213-MIB
    TruthValue, RowStatus               FROM SNMPv2-TC;

    fastPathMgmtSecurity MODULE-IDENTITY
        LAST-UPDATED "202212150000Z" -- 15 Dec 2022 12:00:00 GMT
        ORGANIZATION "Broadcom "
        CONTACT-INFO
          "                      Customer Support
          Postal:                Broadcom 
                                 1030 Swabia Court
                                 Suite 400
                                 Durham, NC 27703
          Tel:                   +1 919 865 2700"
        DESCRIPTION
          "The Broadcom Private MIB for FastPath Security"

        -- Revision history.
        REVISION
          "202212150000Z" -- 15 Dec 2022 12:00:00 GMT
        DESCRIPTION
          "Added ecdhe-rsa-chacha-poly-sha2(10) cipher to agentSSLIpHttpSecureCiphersuite."
        REVISION
          "202209210000Z" -- 21 Sep 2022 12:00:00 GMT
        DESCRIPTION
          "Added agentSSHHostKeyAlgorithmsConfigGroup to agentSSHConfigGroup."
        REVISION
          "202209130000Z" -- 13 Sep 2022 12:00:00 GMT
        DESCRIPTION
          "agentSSLProtocolLevel object has been obsoleted by agentSSLSecureProtocol."
        REVISION
          "202206100000Z" -- 10 Jun 2022 12:00:00 GMT
        DESCRIPTION
          "Added agentSSLOperationalMode in agentSSLConfigGroup."
        REVISION
          "202111220000Z" -- 22 Nov 2021 12:00:00 GMT
        DESCRIPTION
          "Added rsa-dsa(7),rsa-ecdsa(8) and dsa-ecdsa(9) to agentSSHKeysPresent and agentSSHKeyGenerationStatus."
        REVISION
          "202109210000Z" -- 21 Sep 2021 12:00:00 GMT
        DESCRIPTION
          "Added agentSSLIpHttpSecureCiphersuite to agentSSLConfigGroup.
           Added agentSSHDsaKeyLen and agentSSHRsaKeyLen to agentSSHConfigGroup.
           Added agentSSHAuthenticationRetries to agentSSHConfigGroup.
           Added agentSSHEncryptionAlgorithmsConfigGroup, agentSSHMacAlgorithmsConfigGroup and 
           agentSSHKexAlgorithmsConfigGroup to agentSSHConfigGroup."
        REVISION
          "202102080000Z" -- 08 Feb 2021 12:00:00 GMT
        DESCRIPTION
          "Added object agentSSLCryptoDhParam."
        REVISION
          "202006150000Z" -- 15 June 2020 12:00:00 GMT
        DESCRIPTION
          "tls12 option is added in agentSSLProtocolLevel object."
        REVISION
          "201907110000Z" -- 11 July 2019 12:00:00 GMT
        DESCRIPTION
          "Added MIB objects for Outbound SSH."
        REVISION
          "201812050000Z" -- 05 Dec 2018 12:00:00 GMT
        DESCRIPTION
          "Added object agentSSHEcdsaKeyControl, agentSSHEcdsaKeyLen to agentSSHConfigGroup."
        REVISION
          "201707110000Z" -- 11 Jul 2017 12:00:00 GMT
        DESCRIPTION
          "Modified the description of the object agentSSHProtocolLevel."
        REVISION
          "201705180000Z" -- 18 May 2017 12:00:00 GMT
        DESCRIPTION
          "Added objects agentScpServerAdminMode."
        REVISION
          "201703100000Z" -- 10 Mar 2017 12:00:00 GMT
        DESCRIPTION
          "Added objects agentAccountingUpdateNewinfo, agentAccountingUpdatePeriodic."
        REVISION
          "201311110000Z" -- 11 Nov 2013 12:00:00 GMT
        DESCRIPTION
          "Fixed allowed integer range for object agentSSLSecurePort."
        REVISION
          "201308270000Z" -- 27 Aug 2013 12:00:00 GMT
        DESCRIPTION
          "Added object agentSSHMgmtPortNum to agentSSHConfigGroup."
        REVISION
          "201101260000Z" -- 26 Jan 2011 12:00:00 GMT
        DESCRIPTION
          "Postal address updated."
        REVISION
          "200705230000Z" -- 23 May 2007 12:00:00 GMT
        DESCRIPTION
          "Broadcom branding related changes."
        REVISION
          "200311210000Z" -- 21 Nov 2003 12:00:00 GMT
        DESCRIPTION
          "Initial revision."

    ::= { fastPath 11 }

    --**************************************************************************************
    -- agentSSLConfigGroup
    --
    --**************************************************************************************

    agentSSLConfigGroup                        OBJECT IDENTIFIER ::= { fastPathMgmtSecurity 1 }

    agentSSLAdminMode OBJECT-TYPE
         SYNTAX      INTEGER {
                     enable(1),
                     disable(2)
                     }
         MAX-ACCESS  read-write
         STATUS      current
         DESCRIPTION
                     "Configures whether the SSL service is enabled on this switch.  The
                      default value is disable(2)."
         ::= { agentSSLConfigGroup 1 }

    agentSSLSecurePort OBJECT-TYPE
         SYNTAX      Integer32 (443|1025..65535)
         MAX-ACCESS  read-write
         STATUS      current
         DESCRIPTION
                     "Configures the port the SSL service will respond on.  The default
                      value is 443."
         ::= { agentSSLConfigGroup 2 }

    agentSSLProtocolLevel OBJECT-TYPE
         SYNTAX      INTEGER {
                     ssl30(1), -- SSL 3.0
                     tls10(2), -- TSL 1.0
                     both(3),
                     tls12(4) -- TLS 1.2
                     }
         MAX-ACCESS  read-only
         STATUS      obsolete
         DESCRIPTION
                     "Indicates which protocol versions of SSL are enabled on this
                     switch. The default value is tls12(4). This object has been obsoleted
                     by agentSSLSecureProtocol."
         ::= { agentSSLConfigGroup 3 }

    agentSSLMaxSessions OBJECT-TYPE
         SYNTAX      Integer32 (0..16)
         MAX-ACCESS  read-write
         STATUS      current
         DESCRIPTION
                     "Configures the maximum number of allowable SSL sessions.  The default
                      value is 16."
         ::= { agentSSLConfigGroup 4 }

    agentSSLHardTimeout OBJECT-TYPE
         SYNTAX      Integer32 (1..168)
         MAX-ACCESS  read-write
         STATUS      current
         DESCRIPTION
                     "Configures the hard timeout for SSL sessions in hours.  The default
                      value is 24 hours."
         ::= { agentSSLConfigGroup 5 }

    agentSSLSoftTimeout OBJECT-TYPE
         SYNTAX      Integer32 (1..60)
         MAX-ACCESS  read-write
         STATUS      current
         DESCRIPTION
                     "Configures the soft (activity) timeout for SSL sessions in minutes.
                      The default value is 5 minutes."
         ::= { agentSSLConfigGroup 6 }

    agentSSLCertificatePresent OBJECT-TYPE
         SYNTAX      TruthValue
         MAX-ACCESS  read-only
         STATUS      current
         DESCRIPTION
                     "Boolean value indicating whether SSL certificate files exist on the device."
         ::= { agentSSLConfigGroup 7 }

    agentSSLCertificateControl OBJECT-TYPE
         SYNTAX      INTEGER {
                     noop(1),
                     generate(2),
                     delete(3)
                     }
         MAX-ACCESS  read-write
         STATUS      current
         DESCRIPTION
                     "Controls certificate generation and deletion. Always returns noop(1)."
         ::= { agentSSLConfigGroup 8 }

    agentSSLCertificateGenerationStatus OBJECT-TYPE
         SYNTAX      TruthValue
         MAX-ACCESS  read-only
         STATUS      current
         DESCRIPTION
                     "Indicates whether certificate files are currently being generated."
         ::= { agentSSLConfigGroup 9 }

    agentSSLCryptoDhParam OBJECT-TYPE
         SYNTAX      INTEGER {
                     dh1024(1),
                     dh2048(2)
                     }
         MAX-ACCESS  read-write
         STATUS      current
         DESCRIPTION
                     "Configures the Diffie-Hellman to be used for SSL tunnel."
         ::= { agentSSLConfigGroup 10 }

    agentSSLIpHttpSecureCiphersuite OBJECT-TYPE
         SYNTAX      BITS {
                     undefined(0),
                     aes128-cbc-sha(1),
                     aes256-cbc-sha(2),
                     dhe-aes128-cbc-sha(3),
                     dhe-aes-cbc-sha2(4),
                     dhe-aes-gcm-sha2(5),
                     ecdhe-rsa-aes-cbc-sha2(6),
                     ecdhe-rsa-aes-gcm-sha2(7),
                     rsa-aes-cbc-sha2(8),
                     rsa-aes-gcm-sha2(9),
                     ecdhe-rsa-chacha-poly-sha2(10)
                     }
         MAX-ACCESS  read-write
         STATUS      current
         DESCRIPTION
                     "Specifies ciphersuites to be used for SSL tunnel.
                      This object is being used for assigning specified Secure Ciphersuite list.
                      Bit mask value is being used for configuring Secure Ciphersuites."
         ::= { agentSSLConfigGroup 11 }

    agentSSLOperationalMode OBJECT-TYPE
         SYNTAX      INTEGER {
                     enabled(1),
                     disabled(2)
                     }
         MAX-ACCESS  read-only
         STATUS      current
         DESCRIPTION
                     "HTTPS Operational Status."
         ::= { agentSSLConfigGroup 12 }

    agentSSLSecureProtocol OBJECT-TYPE
         SYNTAX      BITS {
                     undefined(0),
                     tls10(1),
                     tls11(2),
                     tls12(3),
                     tls13(4)
                     }
         MAX-ACCESS  read-write
         STATUS      current
         DESCRIPTION
                     "Specifies secure protocol to be used for SSL tunnel.
                      This object is being used for assigning specified secure protocol.
                      Bit mask value is being used for configuring secure protocols."
         ::= { agentSSLConfigGroup 13 }


    --**************************************************************************************
    -- agentSSHConfigGroup
    --
    --**************************************************************************************

    agentSSHConfigGroup                        OBJECT IDENTIFIER ::= { fastPathMgmtSecurity 2 }

    agentSSHAdminMode OBJECT-TYPE
         SYNTAX      INTEGER {
                     enable(1),
                     disable(2)
                     }
         MAX-ACCESS  read-write
         STATUS      current
         DESCRIPTION
                     "Configures whether the SSH service is enabled on this switch.  The
                      default value is disable(2)."
         ::= { agentSSHConfigGroup 1 }

    agentSSHProtocolLevel OBJECT-TYPE
         SYNTAX      INTEGER {
                     ssh10(1), -- deprecated, SSH 1.0 no longer supported
                     ssh20(2), -- SSH 2.0
                     both(3)   -- deprecated, SSH 1.0 no longer supported 
                     }
         MAX-ACCESS  read-only
         STATUS      current
         DESCRIPTION
                     "Indicates the protocol version of SSH enabled on this switch.
                      Starting with the use of OpenSSH version 7.5P1,
                      SSH Protocol Version 1.0 is no longer supported."
         DEFVAL { ssh20}
         ::= { agentSSHConfigGroup 2 }

    agentSSHSessionsCount OBJECT-TYPE
         SYNTAX      Integer32
         MAX-ACCESS  read-only
         STATUS      current
         DESCRIPTION
                     "Current number of active SSH sessions on this switch."
         ::= { agentSSHConfigGroup 3 }

   agentSSHMaxSessionsCount OBJECT-TYPE
         SYNTAX       Integer32 (0..5)
         MAX-ACCESS   read-write
         STATUS       current
         DESCRIPTION
                     "Max number of SSH sessions permitted on this switch."
         ::= { agentSSHConfigGroup 4 }

   agentSSHSessionTimeout OBJECT-TYPE
         SYNTAX       Integer32 (1..160)
         MAX-ACCESS   read-write
         STATUS       current
         DESCRIPTION
                     "ssh idle timeout value for this switch im minutes."
         ::= { agentSSHConfigGroup 5 }

    agentSSHKeysPresent OBJECT-TYPE
         SYNTAX      INTEGER {
                     dsa(1),
                     rsa(2),
                     both(3),   --deprecated
                     none(4),
                     ecdsa(5),
                     all(6),
                     rsa-dsa(7),
                     rsa-ecdsa(8),
                     dsa-ecdsa(9)
                     }
         MAX-ACCESS  read-only
         STATUS      current
         DESCRIPTION
                     "Indicates what key files are present on the device, if any."
         ::= { agentSSHConfigGroup 6 }

    agentSSHKeyGenerationStatus OBJECT-TYPE
         SYNTAX      INTEGER {
                     dsa(1),
                     rsa(2),
                     both(3),   --deprecated
                     none(4),
                     ecdsa(5),
                     all(6),
                     rsa-dsa(7),
                     rsa-ecdsa(8),
                     dsa-ecdsa(9)
                     }
         MAX-ACCESS  read-only
         STATUS      current
         DESCRIPTION
                     "Indicates what key files are currently being generated, if any."
         ::= { agentSSHConfigGroup 7 }

    agentSSHRSAKeyControl OBJECT-TYPE
         SYNTAX      INTEGER {
                     noop(1),
                     generate(2),
                     delete(3)
                     }
         MAX-ACCESS  read-write
         STATUS      current
         DESCRIPTION
                     "Controls RSA key generation and deletion.  A read of this object always returns noop(1)."
         ::= { agentSSHConfigGroup 8 }

    agentSSHDSAKeyControl OBJECT-TYPE
         SYNTAX      INTEGER {
                     noop(1),
                     generate(2),
                     delete(3)
                     }
         MAX-ACCESS  read-write
         STATUS      current
         DESCRIPTION
                     "Controls DSA key generation and deletion.  A read of this object always returns noop(1)."
         ::= { agentSSHConfigGroup 9 }

   agentSSHMgmtPortNum OBJECT-TYPE
         SYNTAX      Integer32 (1..65535)
         MAX-ACCESS  read-write
         STATUS      current
         DESCRIPTION
                     "Get/Set the TCP port number that the SSH server listens to for incoming
                     requests. The port number is an integer value from 1 to 65535. Before setting
                     this object, check your system (e.g. using 'netstat') to make sure the desired
                     port number is not currently being used by any other service. The default
                     value for this object is 22.

                     Note that existing SSH login sessions are not affected by a change in value of
                     this object, although establishment of any new SSH sessions must use the new 
                     port number."
         ::= { agentSSHConfigGroup 10 }

    agentScpServerAdminMode OBJECT-TYPE
         SYNTAX      INTEGER {
                     enable(1),
                     disable(2)
                     }
         MAX-ACCESS  read-write
         STATUS      current
         DESCRIPTION
                     "Configures SCP server admin mode to download files to the switch.
                      The default value is disable(2)."
         DEFVAL { disable }        
         ::= { agentSSHConfigGroup 11 }

    agentSSHEcdsaKeyControl OBJECT-TYPE
         SYNTAX      INTEGER {
                     noop(1),
                     generate(2),
                     delete(3)
                     }
         MAX-ACCESS  read-write
         STATUS      current
         DESCRIPTION
                     "Controls ECDSA key generation and deletion.  A read of this object always returns noop(1)."
         ::= { agentSSHConfigGroup 12 }

    agentSSHEcdsaKeyLen OBJECT-TYPE
         SYNTAX      Integer32
         MAX-ACCESS  read-write
         STATUS      current
         DESCRIPTION
                     "Get/Set ECDSA key length. Supported Key lengths are 256, 384 and 521 bits."
         ::= { agentSSHConfigGroup 13 }

    agentSSHDsaKeyLen OBJECT-TYPE
         SYNTAX      Integer32
         MAX-ACCESS  read-write
         STATUS      current
         DESCRIPTION
                     "Get/Set DSA key length. Supported Key length is 1024 bits."
         DEFVAL { 1024 }
         ::= { agentSSHConfigGroup 14 }

    agentSSHRsaKeyLen OBJECT-TYPE
         SYNTAX      Integer32
         MAX-ACCESS  read-write
         STATUS      current
         DESCRIPTION
                     "Get/Set RSA key length. Supported Key lengths are 1024, 2048 and 3072 bits."
         DEFVAL { 1024 }
         ::= { agentSSHConfigGroup 15 }

    agentSSHAuthenticationRetries OBJECT-TYPE
         SYNTAX      Unsigned32 (0..5)
         MAX-ACCESS  read-write
         STATUS      current
         DESCRIPTION
                     "To configure the maximum authentication retries allowed per SSH connection."
         DEFVAL { 3 }

         ::= { agentSSHConfigGroup 16 }

    --**************************************************************************************
    -- agentSSHEncryptionAlgorithmsConfigGroup
    --
    --**************************************************************************************

    agentSSHEncryptionAlgorithmsConfigGroup                        OBJECT IDENTIFIER ::= { agentSSHConfigGroup 17 }

    agentSSHServerEncryptionAlgorithmsTable OBJECT-TYPE
         SYNTAX      SEQUENCE OF AgentSSHServerEncryptionAlgorithmsEntry  
         MAX-ACCESS  not-accessible
         STATUS      current
         DESCRIPTION
                     "Specifies SSH encryption algorithms to be used."
         ::= { agentSSHEncryptionAlgorithmsConfigGroup 1 }


    agentSSHServerEncryptionAlgorithmsEntry OBJECT-TYPE
         SYNTAX      AgentSSHServerEncryptionAlgorithmsEntry 
         MAX-ACCESS  not-accessible
         STATUS      current
         DESCRIPTION
                     "Config entry for SSH encryption algorithms."
         INDEX       { agentSSHServerEncryptionIndex }
         ::= { agentSSHServerEncryptionAlgorithmsTable 1 }

    AgentSSHServerEncryptionAlgorithmsEntry ::= SEQUENCE {
                          agentSSHServerEncryptionIndex 
                           Unsigned32,
                          agentSSHServerEncryptionAlgorithms 
                           INTEGER 
           }

    agentSSHServerEncryptionIndex OBJECT-TYPE
         SYNTAX     Unsigned32 (1..4) 
         MAX-ACCESS not-accessible 
         STATUS      current
         DESCRIPTION
                     "The index of the SSH encryption configuration order." 

         ::= { agentSSHServerEncryptionAlgorithmsEntry 1 }

    agentSSHServerEncryptionAlgorithms OBJECT-TYPE
         SYNTAX      INTEGER {
                       undefined(0),
                       aes128-ctr(1),
                       aes192-ctr(2),
                       aes256-ctr(3),
                       chacha20-poly1305(4)
                     }
         MAX-ACCESS  read-create
         STATUS      current
         DESCRIPTION
                     "Specifies encryption algorithm to be used for SSH.

                      Abbreviation used.
                      - chacha20-poly1305(4) is used for chacha20-poly1305@openssh.com.   
                      " 
         DEFVAL { undefined }

         ::= { agentSSHServerEncryptionAlgorithmsEntry 2 }

    agentSSHServerEncryptionRefresh OBJECT-TYPE
         SYNTAX     INTEGER {
                    enable(1),
                    disable(2)
                    }
         MAX-ACCESS read-write 
         STATUS     current
         DESCRIPTION
                    "When set to enable(1), configuration of agentSSHServerEncryptionAlgorithmsEntry will be configured
                     and refresh ssh process. The value is write-only.
                     Attempt to read will return disable(2)."

         ::= { agentSSHEncryptionAlgorithmsConfigGroup 2 }

    --**************************************************************************************
    -- agentSSHMacAlgorithmsConfigGroup 
    --
    --**************************************************************************************

    agentSSHMacAlgorithmsConfigGroup                    OBJECT IDENTIFIER ::= { agentSSHConfigGroup 18 }

    agentSSHServerMacAlgorithmsTable OBJECT-TYPE
         SYNTAX      SEQUENCE OF AgentSSHServerMacAlgorithmsEntry  
         MAX-ACCESS  not-accessible
         STATUS      current
         DESCRIPTION
                     "Specifies SSH mac algorithms to be used."
         ::= { agentSSHMacAlgorithmsConfigGroup 1 }


    agentSSHServerMacAlgorithmsEntry OBJECT-TYPE
         SYNTAX      AgentSSHServerMacAlgorithmsEntry 
         MAX-ACCESS  not-accessible
         STATUS      current
         DESCRIPTION
                     "Config entry for SSH mac algorithms."
         INDEX       { agentSSHServerMacIndex }
         ::= { agentSSHServerMacAlgorithmsTable 1 }

    AgentSSHServerMacAlgorithmsEntry ::= SEQUENCE {
                          agentSSHServerMacIndex 
                           Unsigned32,
                          agentSSHServerMacAlgorithms 
                           INTEGER
           }

    agentSSHServerMacIndex OBJECT-TYPE
         SYNTAX     Unsigned32 (1..10) 
         MAX-ACCESS not-accessible 
         STATUS      current
         DESCRIPTION
                     "The index of the SSH mac algorithms configuration order." 

         ::= { agentSSHServerMacAlgorithmsEntry 1 }

    agentSSHServerMacAlgorithms OBJECT-TYPE
         SYNTAX      INTEGER {
                       undefined(0),
                       hmac-sha1(1),
                       hmac-sha1-etm(2),
                       hmac-md5-etm(3),
                       hmac-sha2-256(4),
                       hmac-sha2-512(5),
                       hmac-sha1-96-etm(6),
                       hmac-md5-96-etm(7),
                       hmac-md5(8),
                       hmac-sha2-256-etm(9),
                       hmac-sha2-512-etm(10)
                     }
         MAX-ACCESS  read-create
         STATUS      current
         DESCRIPTION
                     "Specifies MAC algorithm to be used for SSH.

                      Abbreviation used.
                      - hmac-sha1-etm(2) is used for hmac-sha1-etm@openssh.com
                      - hmac-md5-etm(3) is used for hmac-md5-etm@openssh.com
                      - hmac-sha1-96-etm(6) is used for hmac-sha1-96-etm@openssh.com
                      - hmac-md5-96-etm(7) is used for hmac-md5-96-etm@openssh.com
                      - hmac-sha2-256-etm(9) is used for hmac-sha2-256-etm@openssh.com
                      - hmac-sha2-512-etm(10) is used for hmac-sha2-512-etm@openssh.com

                     " 
         DEFVAL { undefined }

         ::= { agentSSHServerMacAlgorithmsEntry 2 }

    agentSSHServerMacRefresh OBJECT-TYPE
         SYNTAX     INTEGER {
                    enable(1),
                    disable(2)
                    }
         MAX-ACCESS read-write 
         STATUS     current
         DESCRIPTION
                    "When set to enable(1), configuration of agentSSHServerMacAlgorithmsEntry will be configured
                     and refresh ssh process. The value is write-only.
                     Attempt to read will return disable(2)."

         ::= { agentSSHMacAlgorithmsConfigGroup 2 }

    --**************************************************************************************
    -- agentSSHKexAlgorithmsConfigGroup 
    --
    --**************************************************************************************

    agentSSHKexAlgorithmsConfigGroup                    OBJECT IDENTIFIER ::= { agentSSHConfigGroup 19 }

    agentSSHServerKexAlgorithmsTable OBJECT-TYPE
         SYNTAX      SEQUENCE OF AgentSSHServerKexAlgorithmsEntry  
         MAX-ACCESS  not-accessible
         STATUS      current
         DESCRIPTION
                     "Specifies SSH kex algorithms to be used."
         ::= { agentSSHKexAlgorithmsConfigGroup 1 }


    agentSSHServerKexAlgorithmsEntry OBJECT-TYPE
         SYNTAX      AgentSSHServerKexAlgorithmsEntry 
         MAX-ACCESS  not-accessible
         STATUS      current
         DESCRIPTION
                     "Config entry for SSH kex algorithms."
         INDEX       { agentSSHServerKexIndex }
         ::= { agentSSHServerKexAlgorithmsTable 1 }

    AgentSSHServerKexAlgorithmsEntry ::= SEQUENCE {
                          agentSSHServerKexIndex 
                           Unsigned32,
                          agentSSHServerKexAlgorithms 
                           INTEGER
           }

    agentSSHServerKexIndex OBJECT-TYPE
         SYNTAX     Unsigned32 (1..10) 
         MAX-ACCESS not-accessible 
         STATUS      current
         DESCRIPTION
                     "The index of the SSH kex algorithms configuration order." 

         ::= { agentSSHServerKexAlgorithmsEntry 1 }

    agentSSHServerKexAlgorithms OBJECT-TYPE
         SYNTAX      INTEGER {
                       undefined(0),
                       curve25519-sha256(1),
                       curve25519-sha256-libssh(2),
                       ecdh-sha2-nistp256(3),
                       ecdh-sha2-nistp384(4),
                       ecdh-sha2-nistp521(5),
                       diffie-hellman-group-exchange-sha256(6),
                       diffie-hellman-group16-sha512(7),
                       diffie-hellman-group18-sha512(8),
                       diffie-hellman-group14-sha256(9),
                       diffie-hellman-group14-sha1(10)
                     }
         MAX-ACCESS  read-create
         STATUS      current
         DESCRIPTION
                     "Specifies KEX algorithm to be used for SSH.

                      Abbreviation used.
                      - curve25519-sha256-libssh(2) is used for curve25519-sha256@libssh.org
                     " 
         DEFVAL { undefined }

         ::= { agentSSHServerKexAlgorithmsEntry 2 }

    agentSSHServerKexRefresh OBJECT-TYPE
         SYNTAX     INTEGER {
                    enable(1),
                    disable(2)
                    }
         MAX-ACCESS read-write 
         STATUS     current
         DESCRIPTION
                    "When set to enable(1), configuration of agentSSHServerKexAlgorithmsEntry will be configured
                     and refresh ssh process. The value is write-only.
                     Attempt to read will return disable(2)."

         ::= { agentSSHKexAlgorithmsConfigGroup 2 }

    --**************************************************************************************
    -- agentSSHHostKeyAlgorithmsConfigGroup
    --
    --**************************************************************************************

    agentSSHHostKeyAlgorithmsConfigGroup                    OBJECT IDENTIFIER ::= { agentSSHConfigGroup 20 }

    agentSSHServerHostKeyAlgorithmsTable OBJECT-TYPE
         SYNTAX      SEQUENCE OF AgentSSHServerHostKeyAlgorithmsEntry
         MAX-ACCESS  not-accessible
         STATUS      current
         DESCRIPTION
                     "Specifies SSH host key algorithms to be used."
         ::= { agentSSHHostKeyAlgorithmsConfigGroup 1 }

    agentSSHServerHostKeyAlgorithmsEntry OBJECT-TYPE
         SYNTAX      AgentSSHServerHostKeyAlgorithmsEntry
         MAX-ACCESS  not-accessible
         STATUS      current
         DESCRIPTION
                     "Config entry for SSH host key algorithms."
         INDEX       { agentSSHServerHostKeyIndex }
         ::= { agentSSHServerHostKeyAlgorithmsTable 1 }

    AgentSSHServerHostKeyAlgorithmsEntry ::= SEQUENCE {
                          agentSSHServerHostKeyIndex
                           Unsigned32,
                          agentSSHServerHostKeyAlgorithms
                           INTEGER
           }

    agentSSHServerHostKeyIndex OBJECT-TYPE
         SYNTAX     Unsigned32 (1..4)
         MAX-ACCESS not-accessible
         STATUS      current
         DESCRIPTION
                     "The index of the SSH host key algorithms configuration order."

         ::= { agentSSHServerHostKeyAlgorithmsEntry 1 }

    agentSSHServerHostKeyAlgorithms OBJECT-TYPE
         SYNTAX      INTEGER {
                       undefined(0),
                       ssh-rsa(1),
                       rsa-sha2-256(2),
                       rsa-sha2-512(3),
                       ecdsa-sha2-nistp256(4),
                       ecdsa-sha2-nistp384(5),
                       ecdsa-sha2-nistp521(6)
                     }
         MAX-ACCESS  read-create
         STATUS      current
         DESCRIPTION
                     "Specifies host key algorithm to be used for SSH."

         DEFVAL { undefined }

         ::= { agentSSHServerHostKeyAlgorithmsEntry 2 }


    agentSSHServerHostKeyRefresh OBJECT-TYPE
         SYNTAX     INTEGER {
                    enable(1),
                    disable(2)
                    }
         MAX-ACCESS read-write
         STATUS     current
         DESCRIPTION
                    "When set to enable(1), configuration of agentSSHServerHostKeyAlgorithmsEntry will be configured
                     and refresh ssh process. The value is write-only.
                     Attempt to read will return disable(2)."

         ::= { agentSSHHostKeyAlgorithmsConfigGroup 2 }


    --************************************************************************************
    -- agentListAuthenticationGroup
    --
    --************************************************************************************

    agentListAuthenticationGroup                   OBJECT IDENTIFIER ::= { fastPathMgmtSecurity 3 }

    agentListAuthenticationTable OBJECT-TYPE
         SYNTAX SEQUENCE OF AgentListAuthenticationEntry
         MAX-ACCESS         not-accessible
         STATUS             current
         DESCRIPTION
                            "This table contains sets of authentication lists."
         ::= { agentListAuthenticationGroup 1 }

    agentListAuthenticationEntry OBJECT-TYPE
         SYNTAX        AgentListAuthenticationEntry
         MAX-ACCESS    not-accessible
         STATUS        current
         DESCRIPTION
                       "Specifies objects for agentListAuthenticationTable table."
         INDEX         { agentListAuthenticationAccessLevel, 
                         agentListAuthenticationIndex }
         ::= { agentListAuthenticationTable 1 }

    AgentListAuthenticationEntry ::= SEQUENCE {
         agentListAuthenticationAccessLevel
             INTEGER,
         agentListAuthenticationIndex
             Unsigned32,
         agentListAuthenticationName
             DisplayString,
         agentListAuthenticationAccessLine
             BITS,
         agentListAuthenticationRowStatus
             RowStatus
         }

    agentListAuthenticationAccessLevel OBJECT-TYPE
         SYNTAX       INTEGER {
                      login(0),
                      enable(1)
                      }
         MAX-ACCESS   not-accessible
         STATUS       current
         DESCRIPTION
                      "Specifies access level of authentication list, login(0) or enable(1)."
         ::= { agentListAuthenticationEntry 1 }

    agentListAuthenticationIndex OBJECT-TYPE
         SYNTAX       Unsigned32
         MAX-ACCESS   not-accessible
         STATUS       current
         DESCRIPTION
                      "Index of authentication list. Maximum allowed value for login is 5.
                       Maximum allowed value for enable is 5."
         ::= { agentListAuthenticationEntry 2 }

    agentListAuthenticationName OBJECT-TYPE
         SYNTAX       DisplayString (SIZE(1..15))
         MAX-ACCESS   read-write
         STATUS       current
         DESCRIPTION
                      "Name of selected authentication list. Setting a value for an empty row 
                       prevents creating a new row in the table. Value must not be empty."
         ::= { agentListAuthenticationEntry 3 }

    agentListAuthenticationAccessLine OBJECT-TYPE
         SYNTAX       BITS {
                      undefined(0),
                      console(1),
                      telnet(2),
                      ssh(3)
                      }
         MAX-ACCESS   read-write
         STATUS       current
         DESCRIPTION
                      "This object is being used for assigning specified authentication list to 
                       access line. One list can be assigned to different access lines at one time. 
                       Bit mask value is being used for configuring and has values as follows:
                       - undefined(0) - show that list is not assigned. Used for clearing any 
                                        assigned value;
                       - console(1) - assign specified list to console access line;
                       - telnet(2) - assign specified list to telnet access line;
                       - ssh(3) - assign specified list to ssh access line.
                       Before configuring this field authentication methods must be configured for 
                       specified list."
         ::= { agentListAuthenticationEntry 4 }

    agentListAuthenticationRowStatus OBJECT-TYPE
         SYNTAX       RowStatus
         MAX-ACCESS   read-write
         STATUS       current
         DESCRIPTION
                      "Status of authentication list entry row.
                       active(1) - Shows that configured row is operational.
                       notReady(3) - Shows that configured row doesn't have configured methods in 
                                     the table agentListAuthenticationMethodsTable
                       destroy(6) - Delete specified row from table. For default list, default
                                    method sets will be restored."
         ::= { agentListAuthenticationEntry 5 }

    agentListAuthenticationMethodsGroup            OBJECT IDENTIFIER ::= { agentListAuthenticationGroup 2 }

    agentListAuthenticationMethodsTable OBJECT-TYPE
         SYNTAX SEQUENCE OF AgentListAuthenticationMethodsEntry
         MAX-ACCESS         not-accessible
         STATUS             current
         DESCRIPTION
                            "This table contains set of methods for specified authentication list 
                             and is child table for agentListAuthenticationTable. When a row in 
                             parent table is removed, the same row in this table is removed."
         ::= { agentListAuthenticationMethodsGroup 1 }

    agentListAuthenticationMethodsEntry OBJECT-TYPE
         SYNTAX        AgentListAuthenticationMethodsEntry
         MAX-ACCESS    not-accessible
         STATUS        current
         DESCRIPTION
                       "Specify objects for agentListAuthenticationMethodsTable."
         INDEX         { agentListAuthenticationAccessLevel, 
                         agentListAuthenticationIndex,
                         agentListAuthenticationMethodsIndex }
         ::= { agentListAuthenticationMethodsTable 1 }

    AgentListAuthenticationMethodsEntry ::= SEQUENCE {
         agentListAuthenticationMethodsIndex
             Unsigned32,
         agentListAuthenticationMethodsValue
             INTEGER
         }

    agentListAuthenticationMethodsIndex OBJECT-TYPE
         SYNTAX       Unsigned32
         MAX-ACCESS   not-accessible
         STATUS       current
         DESCRIPTION
                      "Index of method in specified authentication list."
         ::= { agentListAuthenticationMethodsEntry 1 }

    agentListAuthenticationMethodsValue OBJECT-TYPE
         SYNTAX       INTEGER {
                      undefined(0),
                      enable(1),
                      line(2),
                      local(3),
                      none(4),
                      radius(5),
                      tacacs(6),
                      deny(7)
                      }
         MAX-ACCESS   read-write
         STATUS       current
         DESCRIPTION
                      "Value of specified method. For login and enable access lines
                       set of method values are different and are as follows:
                       * login access line: enable(1), line(2), local(3), none(4),
                                            radius(5), tacacs(6);
                       * enable access line: enable(1), line(2), none(4), radius(5),
                                             tacacs(6), deny(7).
                       Undefined(0) value is used for displaying empty method. Setting
                       this value will clear configured method from the list. A list
                       of authentication methods may not be modified once associated
                       to an access line."
         ::= { agentListAuthenticationMethodsEntry 2 }

    --************************************************************************************
    -- agentListAutorizationGroup
    --
    --************************************************************************************

    agentListAutorizationGroup                   OBJECT IDENTIFIER ::= { fastPathMgmtSecurity 4 }

    agentListAutorizationTable OBJECT-TYPE
         SYNTAX SEQUENCE OF AgentListAutorizationEntry
         MAX-ACCESS         not-accessible
         STATUS             current
         DESCRIPTION
                            "This table contains sets of authorization lists."
         ::= { agentListAutorizationGroup 1 }

    agentListAutorizationEntry OBJECT-TYPE
         SYNTAX        AgentListAutorizationEntry
         MAX-ACCESS    not-accessible
         STATUS        current
         DESCRIPTION
                       "Specifies objects for agentListAutorizationTable table."
         INDEX         { agentListAutorizationType, 
                         agentListAutorizationIndex }
         ::= { agentListAutorizationTable 1 }

    AgentListAutorizationEntry ::= SEQUENCE {
         agentListAutorizationType
             INTEGER,
         agentListAutorizationIndex
             Unsigned32,
         agentListAutorizationName
             DisplayString,
         agentListAutorizationAccessLine
             BITS,
         agentListAutorizationRowStatus
             RowStatus
         }

    agentListAutorizationType OBJECT-TYPE
         SYNTAX       INTEGER {
                      command(0),
                      exec(1)
                      }
         MAX-ACCESS   not-accessible
         STATUS       current
         DESCRIPTION
                      "Specify type of authorization list, command(0) or exec(1)."
         ::= { agentListAutorizationEntry 1 }

    agentListAutorizationIndex OBJECT-TYPE
         SYNTAX       Unsigned32
         MAX-ACCESS   not-accessible
         STATUS       current
         DESCRIPTION
                      "Index of authorization list. Maximum value is 5."
         ::= { agentListAutorizationEntry 2 }

    agentListAutorizationName OBJECT-TYPE
         SYNTAX       DisplayString (SIZE(1..20))
         MAX-ACCESS   read-write
         STATUS       current
         DESCRIPTION
                      "Name of selected authorization list. Setting a value for an empty row 
                       prevents creating a new row in the table. Value must not be empty."
         ::= { agentListAutorizationEntry 3 }

    agentListAutorizationAccessLine OBJECT-TYPE
         SYNTAX       BITS {
                      undefined(0),
                      console(1),
                      telnet(2),
                      ssh(3)
                      }
         MAX-ACCESS   read-write
         STATUS       current
         DESCRIPTION
                      "This object is being used for assigning specified authorization list to 
                       an access line. One list can be assigned to different access lines. Bit 
                       mask value is being used for configuring and has values as follows:
                       - undefined(0) - show that list isn't assigned, used for clearing any 
                                        assigned value;
                       - console(1) - assign specified list to console access line;
                       - telnet(2) - assign specified list to telnet access line;
                       - ssh(3) - assign specified list to ssh access line.
                       Before configuring this field, authorization methods must be configured 
                       for specified list."
         ::= { agentListAutorizationEntry 4 }

    agentListAutorizationRowStatus OBJECT-TYPE
         SYNTAX       RowStatus
         MAX-ACCESS   read-write
         STATUS       current
         DESCRIPTION
                      "Status of authorization list entry row.
                       active(1) - Shows that configured row is operational.
                       notReady(3) - Shows that configured row doesn't have configured methods in 
                                     the table agentListAutorizationMethodsTable.
                       destroy(6) - Delete specified row from table. For default list, default
                                    method sets will be restored."

         ::= { agentListAutorizationEntry 5 }

    agentListAutorizationMethodsGroup            OBJECT IDENTIFIER ::= { agentListAutorizationGroup 2 }

    agentListAutorizationMethodsTable OBJECT-TYPE
         SYNTAX SEQUENCE OF AgentListAutorizationMethodsEntry
         MAX-ACCESS         not-accessible
         STATUS             current
         DESCRIPTION
                            "This table contains set of methods for specified authorization list 
                             and is a child table for agentListAuthorizationTable. When a row in
                             parent table is removed, the same row in this table is removed."
         ::= { agentListAutorizationMethodsGroup 1 }

    agentListAutorizationMethodsEntry OBJECT-TYPE
         SYNTAX        AgentListAutorizationMethodsEntry
         MAX-ACCESS    not-accessible
         STATUS        current
         DESCRIPTION
                       "Specify objects for agentListAutorizationMethodsTable."
         INDEX         { agentListAutorizationType, 
                         agentListAutorizationIndex,
                         agentListAutorizationMethodsIndex }
         ::= { agentListAutorizationMethodsTable 1 }

    AgentListAutorizationMethodsEntry ::= SEQUENCE {
         agentListAutorizationMethodsIndex
             Unsigned32,
         agentListAutorizationMethodsValue
             INTEGER
         }

    agentListAutorizationMethodsIndex OBJECT-TYPE
         SYNTAX       Unsigned32
         MAX-ACCESS   not-accessible
         STATUS       current
         DESCRIPTION
                      "Index of method in specified authorization list."
         ::= { agentListAutorizationMethodsEntry 1 }

    agentListAutorizationMethodsValue OBJECT-TYPE
         SYNTAX       INTEGER {
                      undefined(0),
                      tacacs(1),
                      radius(2),
                      local(3),
                      none(4)
                      }
         MAX-ACCESS   read-write
         STATUS       current
         DESCRIPTION
                      "Value of specified method. For command and exec authorization types, 
                       set of method values are different and are as follows:
                       * command: tacacs(1), radius(2), none(4);
                       * exec: tacacs(1), radius(2), local(3), none(4).
                       Undefined(0) value is being used for displaying empty method. Setting
                       this object to undefined will clear configured method from the list.
                       A list of authentication methods may not be modified once associated 
                       to an access line."
         ::= { agentListAutorizationMethodsEntry 2 }

    --************************************************************************************
    -- agentListAccountingGroup
    --
    --************************************************************************************

    agentListAccountingGroup                   OBJECT IDENTIFIER ::= { fastPathMgmtSecurity 5 }

    agentListAccountingTable OBJECT-TYPE
         SYNTAX SEQUENCE OF AgentListAccountingEntry
         MAX-ACCESS         not-accessible
         STATUS             current
         DESCRIPTION
                            "This table contains sets of accounting lists."
         ::= { agentListAccountingGroup 1 }

    agentListAccountingEntry OBJECT-TYPE
         SYNTAX        AgentListAccountingEntry
         MAX-ACCESS    not-accessible
         STATUS        current
         DESCRIPTION
                       "Specify objects for agentListAccountingTable."
         INDEX         { agentListAccountingType, 
                         agentListAccountingIndex }
         ::= { agentListAccountingTable 1 }

    AgentListAccountingEntry ::= SEQUENCE {
         agentListAccountingType
             INTEGER,
         agentListAccountingIndex
             Unsigned32,
         agentListAccountingName
             DisplayString,
         agentListAccountingRecordType
             INTEGER,
         agentListAccountingAccessLine
             BITS,
         agentListAccountingRowStatus
             RowStatus
         }

    agentListAccountingType OBJECT-TYPE
         SYNTAX       INTEGER {
                      command(0),
                      exec(1)
                      }
         MAX-ACCESS   not-accessible
         STATUS       current
         DESCRIPTION
                      "Specify type of accounting list, command(0) or exec(1)."
         ::= { agentListAccountingEntry 1 }

    agentListAccountingIndex OBJECT-TYPE
         SYNTAX       Unsigned32
         MAX-ACCESS   not-accessible
         STATUS       current
         DESCRIPTION
                      "Index of accounting list. Maximum value is 5."
         ::= { agentListAccountingEntry 2 }

    agentListAccountingName OBJECT-TYPE
         SYNTAX       DisplayString (SIZE(1..15))
         MAX-ACCESS   read-write
         STATUS       current
         DESCRIPTION
                      "Name of selected accounting list. Setting a value for an empty row 
                       prevents creating a new row in the table. Value must not be empty."
         ::= { agentListAccountingEntry 3 }

    agentListAccountingRecordType OBJECT-TYPE
         SYNTAX       INTEGER {
                      undefined(0),
                      start-stop(1),
                      stop-only(2),
                      none(3)
                      }
         MAX-ACCESS   read-write
         STATUS       current
         DESCRIPTION
                      "Specify record type of accounting list, start-stop(1), stop-only(2) or 
                       none(3)."
         ::= { agentListAccountingEntry 4 }

    agentListAccountingAccessLine OBJECT-TYPE
         SYNTAX       BITS {
                      undefined(0),
                      console(1),
                      telnet(2),
                      ssh(3)
                      }
         MAX-ACCESS   read-write
         STATUS       current
         DESCRIPTION
                      "This object is being used for assigning specified accounting list to an 
                       access line. One list can be assigned to different access lines. Bit mask 
                       value is being used for configuring and has values as follows:
                       - undefined(0) - show that list isn't assigned, used for clearing any 
                                        assigned value;
                       - console(1) - assign specified list to console access line;
                       - telnet(2) - assign specified list to telnet access line;
                       - ssh(3) - assign specified list to ssh access line.
                       Before configuring this field, accounting methods must be configured for 
                       specified list."
         ::= { agentListAccountingEntry 5 }

    agentListAccountingRowStatus OBJECT-TYPE
         SYNTAX       RowStatus
         MAX-ACCESS   read-write
         STATUS       current
         DESCRIPTION
                      "Status of accounting list entry row.
                       active(1) - Shows that configured row is operational.
                       notReady(3) - Shows that configured row doesn't have configured methods in 
                                     the table agentListAccountingMethodsTable or record type 
                                     is not configured.
                       destroy(6) - Delete specified row from table. For default list default
                                    method sets will be restored."

         ::= { agentListAccountingEntry 6 }

    agentListAccountingMethodsGroup            OBJECT IDENTIFIER ::= { agentListAccountingGroup 2 }

    agentListAccountingMethodsTable OBJECT-TYPE
         SYNTAX SEQUENCE OF AgentListAccountingMethodsEntry
         MAX-ACCESS         not-accessible
         STATUS             current
         DESCRIPTION
                            "This table contains set of methods for specified accounting list."
         ::= { agentListAccountingMethodsGroup 1 }

    agentListAccountingMethodsEntry OBJECT-TYPE
         SYNTAX        AgentListAccountingMethodsEntry
         MAX-ACCESS    not-accessible
         STATUS        current
         DESCRIPTION
                       "This table contains set of methods for specified accounting list and is 
                        a child table for agentListAccountingTable. When a row in parent table is
                        removed, the same row in this table is removed."
         INDEX         { agentListAccountingType, 
                         agentListAccountingIndex,
                         agentListAccountingMethodsIndex }
         ::= { agentListAccountingMethodsTable 1 }

    AgentListAccountingMethodsEntry ::= SEQUENCE {
         agentListAccountingMethodsIndex
             Unsigned32,
         agentListAccountingMethodsValue
             INTEGER
         }

    agentListAccountingMethodsIndex OBJECT-TYPE
         SYNTAX       Unsigned32
         MAX-ACCESS   not-accessible
         STATUS       current
         DESCRIPTION
                      "Index of method in specified accounting list."
         ::= { agentListAccountingMethodsEntry 1 }

    agentListAccountingMethodsValue OBJECT-TYPE
         SYNTAX       INTEGER {
                      undefined(0),
                      tacacs(1),
                      radius(2)
                      }
         MAX-ACCESS   read-write
         STATUS       current
         DESCRIPTION
                      "Value of specified method. For command and exec authorization types
                       set of method values are as follows:
                       * command: tacacs(1);
                       * exec: tacacs(1), radius(2).
                       Undefined(0) value is being used for displaying empty method. Setting
                       this object to undefined will clear configured method from the list.
                       A list of authentication methods may not be modified once associated 
                       to an access line."
         ::= { agentListAccountingMethodsEntry 2 }

    agentAccountingUpdateConfigGroup            OBJECT IDENTIFIER ::= { agentListAccountingGroup 3 }

    agentAccountingUpdateNewinfo OBJECT-TYPE
        SYNTAX      INTEGER {
                    enable(1),
                    disable(2)
                    }
        MAX-ACCESS  read-write
        STATUS      current
        DESCRIPTION
                    "Configures interim accounting record to be sent to the
                     accounting server, whenever there is new accounting
                     information to be reported. By default sending newinfo
                     to accouting servers is disabled."
        ::= { agentAccountingUpdateConfigGroup 1 }

    agentAccountingUpdatePeriodic OBJECT-TYPE
        SYNTAX       Integer32 (0..200)
        MAX-ACCESS  read-write
        STATUS      current
        DESCRIPTION
                    "Configures interim accounting record to be sent to the
                     accounting server periodically. By default the periodic
                     timeout is 0 and no interim accouting record is sent to
                     accouting servers."
        ::= { agentAccountingUpdateConfigGroup 2 }


    --**************************************************************************************
    -- agentOutboundSSHGroup -> contains MIB objects displaying various properties 
    --                          of a Outbound SSH
    --
    --**************************************************************************************

    agentOutboundSSHGroup       OBJECT IDENTIFIER ::= { fastPathMgmtSecurity 6}

    agentOutboundSSHAdminMode OBJECT-TYPE
      SYNTAX      INTEGER {
                  enable(1),
                  disable(2)
                  }
      MAX-ACCESS read-write
      STATUS     current
      DESCRIPTION
       " Admin-mode of the Outbound SSH."
      DEFVAL { disable }
    ::= { agentOutboundSSHGroup 1 }

    agentOutboundSSHMaxSessions OBJECT-TYPE
      SYNTAX     INTEGER (0..5)
      MAX-ACCESS read-write
      STATUS     current
      DESCRIPTION
       " The maximum no. of Outbound SSH sessions allowed."
      DEFVAL { 5 }
    ::= { agentOutboundSSHGroup 2 }

    agentOutboundSSHActiveSessions OBJECT-TYPE
         SYNTAX      Integer32
         MAX-ACCESS  read-only
         STATUS      current
         DESCRIPTION
                     "Get the number of active outgoing SSH sessions."
         ::= { agentOutboundSSHGroup 3 }


    agentOutboundSSHTimeout OBJECT-TYPE
      SYNTAX     INTEGER (0..160)
      MAX-ACCESS read-write
      STATUS     current
      DESCRIPTION
       " The login inactivity timeout value for Outbound SSH."
      DEFVAL { 5 }
    ::= { agentOutboundSSHGroup 4 }


END
