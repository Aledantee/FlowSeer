LCOS-MIB DEFINITIONS ::= BEGIN

IMPORTS
    Integer32, OBJECT-TYPE, NOTIFICATION-TYPE, TimeTicks,
    Counter64, Unsigned32, enterprises, MODULE-IDENTITY,
    Gauge32, IpAddress, Counter32
            FROM SNMPv2-SMI
    sysName, sysDescr
            FROM RFC1213-MIB
    DisplayString, MacAddress
            FROM SNMPv2-TC
    CounterBasedGauge64
            FROM HCNUM-TC;

lcos MODULE-IDENTITY
    LAST-UPDATED "201912211059Z"  -- December 21, 2019
    ORGANIZATION
            "LANCOM Systems GmbH"
    CONTACT-INFO
            " 
            Adenauerstrasse 20 / B2
            52146 Wuerselen
            Germany
            
            Phone:  +49 (0)2405 49 93 6 0
            Fax:    +49 (0)2405 49 93 6 99
            E-Mail: info@lancom.eu"
    DESCRIPTION
            "LANCOM Operating System unified manangement information base (MIB)"
    REVISION "201912211059Z"  -- December 21, 2019
    DESCRIPTION
            "The latest version of this MIB module."
    REVISION "201912040905Z"  -- December 4, 2019
    DESCRIPTION
            "lcsStatusWlanMngmtApConf entries change to read-only"
    REVISION "201911201248Z"  -- November 20, 2019
    DESCRIPTION
            "lcsStatusIpRouterLoadBalancerConnectionsEntryTcpIpSessions change type
            from Integer32 to Unsigned32"
    REVISION "201910250925Z"  -- October 25, 2019
    DESCRIPTION
            "lcsSetupIeee80211uHotspot20Hotspot20ProfilesEntry fix typo
            Remame csSetupIeee80211uHotspot20Hotspot20ProfilesEtryConnectCapabil
            to csSetupIeee80211uHotspot20Hotspot20ProfilesEntryConnectCapabil"
    REVISION "201904040000Z"  -- April 4, 2019
    DESCRIPTION
            "lcsStatusConfigAntiTheftProtectionState fix typo in enumeration"
    REVISION "201904030000Z"  -- April 3, 2019
    DESCRIPTION
            "Setup/Interfaces/Mobile/Profiles/Profiles size reduced to 15.
            Rename lcsSetupIpv6Dhcpv6ServerReservationsEntryClientId to
            lcsSetupIpv6Dhcpv6ServerReservationsEntryClient-ID.
            lcsStatusVcCllMngrUsersEntryIfc new values.
            lcsSetupVcCllMngrUsersAnalogUserUsersEntryIfc type change Enumeration to BITS."
    REVISION "201902191145Z"  -- February 19, 2019
    DESCRIPTION
            "Setup/IPv6/Router-Advertisement/Prefix-Pools change index"
    REVISION "201902191144Z"  -- February 19, 2019
    DESCRIPTION
            "Replace VDSL profile e17b with e35b"
    REVISION "201901180942Z"  -- January 18, 2019
    DESCRIPTION
            "First release (10.30)"
    ::= { enterprises lancom-systems(2356) 11 }

--
-- NODES
--
-- {NODE} 1.3.6.1.4.1.2356.11.0
lcsTrapGrp OBJECT IDENTIFIER ::= { lcos 0 }

-- {NODE} 1.3.6.1.4.1.2356.11.0.0
lcsTraps OBJECT IDENTIFIER ::= { lcsTrapGrp 0 }

-- {NODE} 1.3.6.1.4.1.2356.11.1
lcsStatus OBJECT IDENTIFIER ::= { lcos 1 }

-- {SCALAR} 1.3.6.1.4.1.2356.11.1.2
lcsStatusOperatingTime OBJECT-TYPE
    SYNTAX     DisplayString
    MAX-ACCESS read-only
    STATUS     current
    DESCRIPTION
            ""
    ::= { lcsStatus 2 }

-- {NODE} 1.3.6.1.4.1.2356.11.1.3
lcsStatusWlan OBJECT IDENTIFIER ::= { lcsStatus 3 }

-- {SCALAR} 1.3.6.1.4.1.2356.11.1.3.11
lcsStatusWlanDeleteValues OBJECT-TYPE
    SYNTAX     DisplayString
    MAX-ACCESS read-write
    STATUS     current
    DESCRIPTION
            ""
    ::= { lcsStatusWlan 11 }

-- {TABLE} 1.3.6.1.4.1.2356.11.1.3.32
lcsStatusWlanStationTableTable OBJECT-TYPE
    SYNTAX     SEQUENCE OF LcsStatusWlanStationTableEntry
    MAX-ACCESS not-accessible
    STATUS     current
    DESCRIPTION
            ""
    ::= { lcsStatusWlan 32 }

-- {ROW} 1.3.6.1.4.1.2356.11.1.3.32.1
lcsStatusWlanStationTableEntry OBJECT-TYPE
    SYNTAX     LcsStatusWlanStationTableEntry
    MAX-ACCESS not-accessible
    STATUS     current
    DESCRIPTION
            ""
    INDEX {
            lcsStatusWlanStationTableEntryIndex
          }
    ::= { lcsStatusWlanStationTableTable 1 }

LcsStatusWlanStationTableEntry ::= SEQUENCE {
            lcsStatusWlanStationTableEntryIndex Integer32,
            lcsStatusWlanStationTableEntryMacAddress MacAddress,
            lcsStatusWlanStationTableEntryTxBytes Counter64,
            lcsStatusWlanStationTableEntryRxBytes Counter64,
            lcsStatusWlanStationTableEntryIdentification DisplayString,
            lcsStatusWlanStationTableEntryState INTEGER,
            lcsStatusWlanStationTableEntryRxRate INTEGER,
            lcsStatusWlanStationTableEntryKeyType INTEGER,
            lcsStatusWlanStationTableEntryInterface INTEGER,
            lcsStatusWlanStationTableEntryPowerSaving INTEGER,
            lcsStatusWlanStationTableEntryListenInterval Integer32,
            lcsStatusWlanStationTableEntryConnectTime Integer32,
            lcsStatusWlanStationTableEntryAid Integer32,
            lcsStatusWlanStationTableEntryThroughput DisplayString,
            lcsStatusWlanStationTableEntryShortSlotTime INTEGER,
            lcsStatusWlanStationTableEntryShortPreamble INTEGER,
            lcsStatusWlanStationTableEntryNetwork INTEGER,
            lcsStatusWlanStationTableEntryPhySignal Integer32,
            lcsStatusWlanStationTableEntryIpv4Address IpAddress,
            lcsStatusWlanStationTableEntryTxRate INTEGER,
            lcsStatusWlanStationTableEntryMaxThroughput DisplayString,
            lcsStatusWlanStationTableEntryBytesThroughput Integer32,
            lcsStatusWlanStationTableEntryBytesMaxThroughput Integer32,
            lcsStatusWlanStationTableEntryClBrgSupport INTEGER,
            lcsStatusWlanStationTableEntryWpaVersion INTEGER,
            lcsStatusWlanStationTableEntryLastEvent INTEGER,
            lcsStatusWlanStationTableEntryTxLimit Integer32,
            lcsStatusWlanStationTableEntryRxLimit Integer32,
            lcsStatusWlanStationTableEntryQos INTEGER,
            lcsStatusWlanStationTableEntryVlanId Integer32,
            lcsStatusWlanStationTableEntryUserName DisplayString,
            lcsStatusWlanStationTableEntryMacCheck INTEGER,
            lcsStatusWlanStationTableEntryTxPackets Counter32,
            lcsStatusWlanStationTableEntryRxPackets Counter32,
            lcsStatusWlanStationTableEntryIdleTimeout Integer32,
            lcsStatusWlanStationTableEntryLastError INTEGER,
            lcsStatusWlanStationTableEntryShortGuardInterval INTEGER,
            lcsStatusWlanStationTableEntry40mhzMode INTEGER,
            lcsStatusWlanStationTableEntry40mhzIntolerant INTEGER,
            lcsStatusWlanStationTableEntryMaxAMsduLen Integer32,
            lcsStatusWlanStationTableEntryMaxAMpduLen Integer32,
            lcsStatusWlanStationTableEntryEffTxRate Integer32,
            lcsStatusWlanStationTableEntryEffRxRate Integer32,
            lcsStatusWlanStationTableEntryApsd BITS,
            lcsStatusWlanStationTableEntryIpv6Address IpAddress,
            lcsStatusWlanStationTableEntrySmPwrsave INTEGER,
            lcsStatusWlanStationTableEntryTxErrors Integer32,
            lcsStatusWlanStationTableEntryTotalRetries Integer32,
            lcsStatusWlanStationTableEntryAlarmState INTEGER,
            lcsStatusWlanStationTableEntry40mhzCoexistence INTEGER,
            lcsStatusWlanStationTableEntry20mhzRequested INTEGER,
            lcsStatusWlanStationTableEntryRxStbc INTEGER,
            lcsStatusWlanStationTableEntryLdpc INTEGER,
            lcsStatusWlanStationTableEntryAutowds INTEGER,
            lcsStatusWlanStationTableEntryFastRoaming INTEGER,
            lcsStatusWlanStationTableEntryWpa2KeyManagement INTEGER,
            lcsStatusWlanStationTableEntrySGIMask BITS,
            lcsStatusWlanStationTableEntryChannelBandwidths BITS,
            lcsStatusWlanStationTableEntryProtMgmtFrames INTEGER,
            lcsStatusWlanStationTableEntryRxStbcHt INTEGER,
            lcsStatusWlanStationTableEntryRxStbcVht INTEGER,
            lcsStatusWlanStationTableEntryLDPCMask BITS,
            lcsStatusWlanStationTableEntryOperationMode INTEGER,
            lcsStatusWlanStationTableEntryBlockackTestResult INTEGER,
            lcsStatusWlanStationTableEntryTxChannelwidth INTEGER,
            lcsStatusWlanStationTableEntryTxShortGi INTEGER,
            lcsStatusWlanStationTableEntryRxChannelwidth INTEGER,
            lcsStatusWlanStationTableEntryRxShortGi INTEGER,
            lcsStatusWlanStationTableEntryTxMcs Integer32,
            lcsStatusWlanStationTableEntryRxMcs Integer32,
            lcsStatusWlanStationTableEntry11acBeamforming BITS,
            lcsStatusWlanStationTableEntryDhcpHostname DisplayString,
            lcsStatusWlanStationTableEntryRadioMeasurements BITS,
            lcsStatusWlanStationTableEntryBssTransition INTEGER,
            lcsStatusWlanStationTableEntryMaxSpatialStreams Integer32,
            lcsStatusWlanStationTableEntryLastFrameReceived Integer32,
            lcsStatusWlanStationTableEntrySteeringFriendly INTEGER,
            lcsStatusWlanStationTableEntryLastSteering Integer32,
            lcsStatusWlanStationTableEntryLepsU INTEGER,
            lcsStatusWlanStationTableEntryWpaAuthType INTEGER,
            lcsStatusWlanStationTableEntryHotspot20Release INTEGER,
            lcsStatusWlanStationTableEntryQosMapping INTEGER,
            lcsStatusWlanStationTableEntrySessionTimeout Integer32,
            lcsStatusWlanStationTableEntryIpv6AddressTxt DisplayString
    }

-- {COLUMN} 1.3.6.1.4.1.2356.11.1.3.32.1.1
lcsStatusWlanStationTableEntryIndex OBJECT-TYPE
    SYNTAX     Integer32 (0..65535)
    MAX-ACCESS read-only
    STATUS     current
    DESCRIPTION
            ""
    ::= { lcsStatusWlanStationTableEntry 1 }

-- {COLUMN} 1.3.6.1.4.1.2356.11.1.3.32.1.4
lcsStatusWlanStationTableEntryMacAddress OBJECT-TYPE
    SYNTAX     MacAddress
    MAX-ACCESS read-only
    STATUS     current
    DESCRIPTION
            ""
    ::= { lcsStatusWlanStationTableEntry 4 }

-- {COLUMN} 1.3.6.1.4.1.2356.11.1.3.32.1.6
lcsStatusWlanStationTableEntryTxBytes OBJECT-TYPE
    SYNTAX     Counter64
    MAX-ACCESS read-only
    STATUS     current
    DESCRIPTION
            ""
    ::= { lcsStatusWlanStationTableEntry 6 }

-- {COLUMN} 1.3.6.1.4.1.2356.11.1.3.32.1.7
lcsStatusWlanStationTableEntryRxBytes OBJECT-TYPE
    SYNTAX     Counter64
    MAX-ACCESS read-only
    STATUS     current
    DESCRIPTION
            ""
    ::= { lcsStatusWlanStationTableEntry 7 }

-- {COLUMN} 1.3.6.1.4.1.2356.11.1.3.32.1.9
lcsStatusWlanStationTableEntryIdentification OBJECT-TYPE
    SYNTAX     DisplayString (SIZE(0..32))
    MAX-ACCESS read-only
    STATUS     current
    DESCRIPTION
            ""
    ::= { lcsStatusWlanStationTableEntry 9 }

-- {COLUMN} 1.3.6.1.4.1.2356.11.1.3.32.1.10
lcsStatusWlanStationTableEntryState OBJECT-TYPE
    SYNTAX     INTEGER {
                  eNone (0),
                  eAdhoc (1),
                  eAuthenticated (2),
                  eConnected (3),
                  eMacCheck (4),
                  eKeyHandshake (8),
                  eAssociated (9),
                  e1xNegotiation (10)
            }
    MAX-ACCESS read-only
    STATUS     current
    DESCRIPTION
            ""
    ::= { lcsStatusWlanStationTableEntry 10 }

-- {COLUMN} 1.3.6.1.4.1.2356.11.1.3.32.1.13
lcsStatusWlanStationTableEntryRxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            ""
    ::= { lcsStatusWlanStationTableEntry 13 }

-- {COLUMN} 1.3.6.1.4.1.2356.11.1.3.32.1.14
lcsStatusWlanStationTableEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eAesCcmp256 (67),
                  eBip (68),
                  eBipCmac256 (69),
                  eAesGcmp128 (70),
                  eAesGcmp256 (71),
                  eBipGmac128 (72),
                  eBipGmac256 (73)
            }
    MAX-ACCESS read-only
    STATUS     current
    DESCRIPTION
            ""
    ::= { lcsStatusWlanStationTableEntry 14 }

-- {COLUMN} 1.3.6.1.4.1.2356.11.1.3.32.1.15
lcsStatusWlanStationTableEntryInterface OBJECT-TYPE
    SYNTAX     INTEGER {
                  eWlan1 (0),
                  eWlan2 (1),
                  eWlan3 (2),
                  eWlan4 (3)
            }
    MAX-ACCESS read-only
    STATUS     current
    DESCRIPTION
            ""
    ::= { lcsStatusWlanStationTableEntry 15 }

-- {COLUMN} 1.3.6.1.4.1.2356.11.1.3.32.1.16
lcsStatusWlanStationTableEntryPowerSaving OBJECT-TYPE
    SYNTAX     INTEGER {
                  eUnknown (0),
                  eInactive (1),
                  eActive (2)
            }
    MAX-ACCESS read-only
    STATUS     current
    DESCRIPTION
            ""
    ::= { lcsStatusWlanStationTableEntry 16 }

-- {COLUMN} 1.3.6.1.4.1.2356.11.1.3.32.1.17
lcsStatusWlanStationTableEntryListenInterval OBJECT-TYPE
    SYNTAX     Integer32 (0..65535)
    MAX-ACCESS read-only
    STATUS     current
    DESCRIPTION
            ""
    ::= { lcsStatusWlanStationTableEntry 17 }

-- {COLUMN} 1.3.6.1.4.1.2356.11.1.3.32.1.18
lcsStatusWlanStationTableEntryConnectTime OBJECT-TYPE
    SYNTAX     Integer32 (0..2147483647)
    MAX-ACCESS read-only
    STATUS     current
    DESCRIPTION
            ""
    ::= { lcsStatusWlanStationTableEntry 18 }

-- {COLUMN} 1.3.6.1.4.1.2356.11.1.3.32.1.19
lcsStatusWlanStationTableEntryAid OBJECT-TYPE
    SYNTAX     Integer32 (0..65535)
    MAX-ACCESS read-only
    STATUS     current
    DESCRIPTION
            ""
    ::= { lcsStatusWlanStationTableEntry 19 }

-- {COLUMN} 1.3.6.1.4.1.2356.11.1.3.32.1.20
lcsStatusWlanStationTableEntryThroughput OBJECT-TYPE
    SYNTAX     DisplayString (SIZE(0..255))
    MAX-ACCESS read-only
    STATUS     current
    DESCRIPTION
            ""
    ::= { lcsStatusWlanStationTableEntry 20 }

-- {COLUMN} 1.3.6.1.4.1.2356.11.1.3.32.1.21
lcsStatusWlanStationTableEntryShortSlotTime OBJECT-TYPE
    SYNTAX     INTEGER {
                  eNo (0),
                  eYes (1)
            }
    MAX-ACCESS read-only
    STATUS     current
    DESCRIPTION
            ""
    ::= { lcsStatusWlanStationTableEntry 21 }

-- {COLUMN} 1.3.6.1.4.1.2356.11.1.3.32.1.23
lcsStatusWlanStationTableEntryShortPreamble OBJECT-TYPE
    SYNTAX     INTEGER {
                  eNo (0),
                  eYes (1)
            }
    MAX-ACCESS read-only
    STATUS     current
    DESCRIPTION
            ""
    ::= { lcsStatusWlanStationTableEntry 23 }

-- {COLUMN} 1.3.6.1.4.1.2356.11.1.3.32.1.25
lcsStatusWlanStationTableEntryNetwork OBJECT-TYPE
    SYNTAX     INTEGER {
                  e1 (0),
                  e2 (1),
                  e3 (2),
                  e4 (3),
                  e5 (4),
                  e6 (5),
                  e7 (6),
                  e8 (7),
                  e9 (8),
                  e10 (9),
                  e11 (10),
                  e12 (11),
                  e13 (12),
                  e14 (13),
                  e15 (14),
                  e16 (15)
            }
    MAX-ACCESS read-only
    STATUS     current
    DESCRIPTION
            ""
    ::= { lcsStatusWlanStationTableEntry 25 }

-- {COLUMN} 1.3.6.1.4.1.2356.11.1.3.32.1.26
lcsStatusWlanStationTableEntryPhySignal OBJECT-TYPE
    SYNTAX     Integer32 (0..65535)
    MAX-ACCESS read-only
    STATUS     current
    DESCRIPTION
            ""
    ::= { lcsStatusWlanStationTableEntry 26 }

-- {COLUMN} 1.3.6.1.4.1.2356.11.1.3.32.1.27
lcsStatusWlanStationTableEntryIpv4Address OBJECT-TYPE
    SYNTAX     IpAddress
    MAX-ACCESS read-only
    STATUS     current
    DESCRIPTION
            ""
    ::= { lcsStatusWlanStationTableEntry 27 }

-- {COLUMN} 1.3.6.1.4.1.2356.11.1.3.32.1.28
lcsStatusWlanStationTableEntryTxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            ""
    ::= { lcsStatusWlanStationTableEntry 28 }

-- {COLUMN} 1.3.6.1.4.1.2356.11.1.3.32.1.29
lcsStatusWlanStationTableEntryMaxThroughput OBJECT-TYPE
    SYNTAX     DisplayString (SIZE(0..255))
    MAX-ACCESS read-only
    STATUS     current
    DESCRIPTION
            ""
    ::= { lcsStatusWlanStationTableEntry 29 }

-- {COLUMN} 1.3.6.1.4.1.2356.11.1.3.32.1.30
lcsStatusWlanStationTableEntryBytesThroughput OBJECT-TYPE
    SYNTAX     Integer32 (0..2147483647)
    MAX-ACCESS read-only
    STATUS     current
    DESCRIPTION
            ""
    ::= { lcsStatusWlanStationTableEntry 30 }

-- {COLUMN} 1.3.6.1.4.1.2356.11.1.3.32.1.31
lcsStatusWlanStationTableEntryBytesMaxThroughput OBJECT-TYPE
    SYNTAX     Integer32 (0..2147483647)
    MAX-ACCESS read-only
    STATUS     current
    DESCRIPTION
            ""
    ::= { lcsStatusWlanStationTableEntry 31 }

-- {COLUMN} 1.3.6.1.4.1.2356.11.1.3.32.1.32
lcsStatusWlanStationTableEntryClBrgSupport OBJECT-TYPE
    SYNTAX     INTEGER {
                  eNo (0),
                  eYes (1)
            }
    MAX-ACCESS read-only
    STATUS     current
    DESCRIPTION
            ""
    ::= { lcsStatusWlanStationTableEntry 32 }

-- {COLUMN} 1.3.6.1.4.1.2356.11.1.3.32.1.33
lcsStatusWlanStationTableEntryWpaVersion OBJECT-TYPE
    SYNTAX     INTEGER {
                  eNone (0),
                  eWpa1 (1),
                  eWpa2 (2),
                  eWpa3 (3)
            }
    MAX-ACCESS read-only
    STATUS     current
    DESCRIPTION
            ""
    ::= { lcsStatusWlanStationTableEntry 33 }

-- {COLUMN} 1.3.6.1.4.1.2356.11.1.3.32.1.34
lcsStatusWlanStationTableEntryLastEvent OBJECT-TYPE
    SYNTAX     INTEGER {
                  eNone (0),
                  eAuthSuccess (1),
                  eDeauth (2),
                  eAssocSuccess (3),
                  eReassocSuccess (4),
                  eDisassoc (5),
                  eRadiusSuccess (6),
                  eAuthReject (7),
                  eAssocReject (8),
                  eKeyhandshakeSuccess (9),
                  eKeyhandshakeTimeout (10),
                  eKeyhandshakeFailure (11),
                  eRadiusReject (12),
                  eSupervision (13),
                  e8021xSuccess (14),
                  e8021xFailure (15),
                  eIdleTimeout (16),
                  eAdminDeassoc (17),
                  eRoamed (18)
            }
    MAX-ACCESS read-only
    STATUS     current
    DESCRIPTION
            ""
    ::= { lcsStatusWlanStationTableEntry 34 }

-- {COLUMN} 1.3.6.1.4.1.2356.11.1.3.32.1.35
lcsStatusWlanStationTableEntryTxLimit OBJECT-TYPE
    SYNTAX     Integer32 (0..2147483647)
    MAX-ACCESS read-only
    STATUS     current
    DESCRIPTION
            ""
    ::= { lcsStatusWlanStationTableEntry 35 }

-- {COLUMN} 1.3.6.1.4.1.2356.11.1.3.32.1.36
lcsStatusWlanStationTableEntryRxLimit OBJECT-TYPE
    SYNTAX     Integer32 (0..2147483647)
    MAX-ACCESS read-only
    STATUS     current
    DESCRIPTION
            ""
    ::= { lcsStatusWlanStationTableEntry 36 }

-- {COLUMN} 1.3.6.1.4.1.2356.11.1.3.32.1.37
lcsStatusWlanStationTableEntryQos OBJECT-TYPE
    SYNTAX     INTEGER {
                  eNo (0),
                  eYes (1)
            }
    MAX-ACCESS read-only
    STATUS     current
    DESCRIPTION
            ""
    ::= { lcsStatusWlanStationTableEntry 37 }

-- {COLUMN} 1.3.6.1.4.1.2356.11.1.3.32.1.38
lcsStatusWlanStationTableEntryVlanId OBJECT-TYPE
    SYNTAX     Integer32 (0..65535)
    MAX-ACCESS read-only
    STATUS     current
    DESCRIPTION
            ""
    ::= { lcsStatusWlanStationTableEntry 38 }

-- {COLUMN} 1.3.6.1.4.1.2356.11.1.3.32.1.39
lcsStatusWlanStationTableEntryUserName OBJECT-TYPE
    SYNTAX     DisplayString (SIZE(0..255))
    MAX-ACCESS read-only
    STATUS     current
    DESCRIPTION
            ""
    ::= { lcsStatusWlanStationTableEntry 39 }

-- {COLUMN} 1.3.6.1.4.1.2356.11.1.3.32.1.40
lcsStatusWlanStationTableEntryMacCheck OBJECT-TYPE
    SYNTAX     INTEGER {
                  eNone (0),
                  eLocal (1),
                  eRadius (2)
            }
    MAX-ACCESS read-only
    STATUS     current
    DESCRIPTION
            ""
    ::= { lcsStatusWlanStationTableEntry 40 }

-- {COLUMN} 1.3.6.1.4.1.2356.11.1.3.32.1.41
lcsStatusWlanStationTableEntryTxPackets OBJECT-TYPE
    SYNTAX     Counter32
    MAX-ACCESS read-only
    STATUS     current
    DESCRIPTION
            ""
    ::= { lcsStatusWlanStationTableEntry 41 }

-- {COLUMN} 1.3.6.1.4.1.2356.11.1.3.32.1.42
lcsStatusWlanStationTableEntryRxPackets OBJECT-TYPE
    SYNTAX     Counter32
    MAX-ACCESS read-only
    STATUS     current
    DESCRIPTION
            ""
    ::= { lcsStatusWlanStationTableEntry 42 }

-- {COLUMN} 1.3.6.1.4.1.2356.11.1.3.32.1.43
lcsStatusWlanStationTableEntryIdleTimeout OBJECT-TYPE
    SYNTAX     Integer32 (0..2147483647)
    MAX-ACCESS read-only
    STATUS     current
    DESCRIPTION
            ""
    ::= { lcsStatusWlanStationTableEntry 43 }

-- {COLUMN} 1.3.6.1.4.1.2356.11.1.3.32.1.44
lcsStatusWlanStationTableEntryLastError OBJECT-TYPE
    SYNTAX     INTEGER {
                  eNone (0),
                  eAuthSuccess (1),
                  eDeauth (2),
                  eAssocSuccess (3),
                  eReassocSuccess (4),
                  eDisassoc (5),
                  eRadiusSuccess (6),
                  eAuthReject (7),
                  eAssocReject (8),
                  eKeyhandshakeSuccess (9),
                  eKeyhandshakeTimeout (10),
                  eKeyhandshakeFailure (11),
                  eRadiusReject (12),
                  eSupervision (13),
                  e8021xSuccess (14),
                  e8021xFailure (15),
                  eIdleTimeout (16),
                  eAdminDeassoc (17),
                  eRoamed (18)
            }
    MAX-ACCESS read-only
    STATUS     current
    DESCRIPTION
            ""
    ::= { lcsStatusWlanStationTableEntry 44 }

-- {COLUMN} 1.3.6.1.4.1.2356.11.1.3.32.1.45
lcsStatusWlanStationTableEntryShortGuardInterval OBJECT-TYPE
    SYNTAX     INTEGER {
                  eNo (0),
                  e20mhz (1),
                  e40mhz (2),
                  e2040mhz (3)
            }
    MAX-ACCESS read-only
    STATUS     current
    DESCRIPTION
            ""
    ::= { lcsStatusWlanStationTableEntry 45 }

-- {COLUMN} 1.3.6.1.4.1.2356.11.1.3.32.1.46
lcsStatusWlanStationTableEntry40mhzMode OBJECT-TYPE
    SYNTAX     INTEGER {
                  eNo (0),
                  eYes (1)
            }
    MAX-ACCESS read-only
    STATUS     current
    DESCRIPTION
            ""
    ::= { lcsStatusWlanStationTableEntry 46 }

-- {COLUMN} 1.3.6.1.4.1.2356.11.1.3.32.1.47
lcsStatusWlanStationTableEntry40mhzIntolerant OBJECT-TYPE
    SYNTAX     INTEGER {
                  eNo (0),
                  eYes (1)
            }
    MAX-ACCESS read-only
    STATUS     current
    DESCRIPTION
            ""
    ::= { lcsStatusWlanStationTableEntry 47 }

-- {COLUMN} 1.3.6.1.4.1.2356.11.1.3.32.1.48
lcsStatusWlanStationTableEntryMaxAMsduLen OBJECT-TYPE
    SYNTAX     Integer32 (0..2147483647)
    MAX-ACCESS read-only
    STATUS     current
    DESCRIPTION
            ""
    ::= { lcsStatusWlanStationTableEntry 48 }

-- {COLUMN} 1.3.6.1.4.1.2356.11.1.3.32.1.49
lcsStatusWlanStationTableEntryMaxAMpduLen OBJECT-TYPE
    SYNTAX     Integer32 (0..2147483647)
    MAX-ACCESS read-only
    STATUS     current
    DESCRIPTION
            ""
    ::= { lcsStatusWlanStationTableEntry 49 }

-- {COLUMN} 1.3.6.1.4.1.2356.11.1.3.32.1.50
lcsStatusWlanStationTableEntryEffTxRate OBJECT-TYPE
    SYNTAX     Integer32 (0..2147483647)
    MAX-ACCESS read-only
    STATUS     current
    DESCRIPTION
            ""
    ::= { lcsStatusWlanStationTableEntry 50 }

-- {COLUMN} 1.3.6.1.4.1.2356.11.1.3.32.1.51
lcsStatusWlanStationTableEntryEffRxRate OBJECT-TYPE
    SYNTAX     Integer32 (0..2147483647)
    MAX-ACCESS read-only
    STATUS     current
    DESCRIPTION
            ""
    ::= { lcsStatusWlanStationTableEntry 51 }

-- {COLUMN} 1.3.6.1.4.1.2356.11.1.3.32.1.52
lcsStatusWlanStationTableEntryApsd OBJECT-TYPE
    SYNTAX     BITS {
                  eNo (0),
                  eVo (4),
                  eVi (5),
                  eBk (6),
                  eBe (7)
            }
    MAX-ACCESS read-only
    STATUS     current
    DESCRIPTION
            ""
    ::= { lcsStatusWlanStationTableEntry 52 }

-- {COLUMN} 1.3.6.1.4.1.2356.11.1.3.32.1.53
lcsStatusWlanStationTableEntryIpv6Address OBJECT-TYPE
    SYNTAX     IpAddress
    MAX-ACCESS read-only
    STATUS     current
    DESCRIPTION
            ""
    ::= { lcsStatusWlanStationTableEntry 53 }

-- {COLUMN} 1.3.6.1.4.1.2356.11.1.3.32.1.54
lcsStatusWlanStationTableEntrySmPwrsave OBJECT-TYPE
    SYNTAX     INTEGER {
                  eInactive (0),
                  eStatic (1),
                  eDynamic (2)
            }
    MAX-ACCESS read-only
    STATUS     current
    DESCRIPTION
            ""
    ::= { lcsStatusWlanStationTableEntry 54 }

-- {COLUMN} 1.3.6.1.4.1.2356.11.1.3.32.1.55
lcsStatusWlanStationTableEntryTxErrors OBJECT-TYPE
    SYNTAX     Integer32 (0..2147483647)
    MAX-ACCESS read-only
    STATUS     current
    DESCRIPTION
            ""
    ::= { lcsStatusWlanStationTableEntry 55 }

-- {COLUMN} 1.3.6.1.4.1.2356.11.1.3.32.1.56
lcsStatusWlanStationTableEntryTotalRetries OBJECT-TYPE
    SYNTAX     Integer32 (0..2147483647)
    MAX-ACCESS read-only
    STATUS     current
    DESCRIPTION
            ""
    ::= { lcsStatusWlanStationTableEntry 56 }

-- {COLUMN} 1.3.6.1.4.1.2356.11.1.3.32.1.57
lcsStatusWlanStationTableEntryAlarmState OBJECT-TYPE
    SYNTAX     INTEGER {
                  eNo (0),
                  ePhySignal (1),
                  eTotalRetries (2),
                  eTxErrors (4)
            }
    MAX-ACCESS read-only
    STATUS     current
    DESCRIPTION
            ""
    ::= { lcsStatusWlanStationTableEntry 57 }

-- {COLUMN} 1.3.6.1.4.1.2356.11.1.3.32.1.58
lcsStatusWlanStationTableEntry40mhzCoexistence OBJECT-TYPE
    SYNTAX     INTEGER {
                  eNo (0),
                  eYes (1)
            }
    MAX-ACCESS read-only
    STATUS     current
    DESCRIPTION
            "-- empty --"
    ::= { lcsStatusWlanStationTableEntry 58 }

-- {COLUMN} 1.3.6.1.4.1.2356.11.1.3.32.1.59
lcsStatusWlanStationTableEntry20mhzRequested OBJECT-TYPE
    SYNTAX     INTEGER {
                  eNo (0),
                  eYes (1)
            }
    MAX-ACCESS read-only
    STATUS     current
    DESCRIPTION
            "-- empty --"
    ::= { lcsStatusWlanStationTableEntry 59 }

-- {COLUMN} 1.3.6.1.4.1.2356.11.1.3.32.1.60
lcsStatusWlanStationTableEntryRxStbc OBJECT-TYPE
    SYNTAX     INTEGER {
                  eNone (0),
                  eOne (1),
                  eTwo (2),
                  eThree (3)
            }
    MAX-ACCESS read-only
    STATUS     current
    DESCRIPTION
            "-- empty --"
    ::= { lcsStatusWlanStationTableEntry 60 }

-- {COLUMN} 1.3.6.1.4.1.2356.11.1.3.32.1.61
lcsStatusWlanStationTableEntryLdpc OBJECT-TYPE
    SYNTAX     INTEGER {
                  eNo (0),
                  eYes (1)
            }
    MAX-ACCESS read-only
    STATUS     current
    DESCRIPTION
            "-- empty --"
    ::= { lcsStatusWlanStationTableEntry 61 }

-- {COLUMN} 1.3.6.1.4.1.2356.11.1.3.32.1.62
lcsStatusWlanStationTableEntryAutowds OBJECT-TYPE
    SYNTAX     INTEGER {
                  eNone (0),
                  eExpress (1),
                  ePreconfigured (2)
            }
    MAX-ACCESS read-only
    STATUS     current
    DESCRIPTION
            "-- empty --"
    ::= { lcsStatusWlanStationTableEntry 62 }

-- {COLUMN} 1.3.6.1.4.1.2356.11.1.3.32.1.63
lcsStatusWlanStationTableEntryFastRoaming OBJECT-TYPE
    SYNTAX     INTEGER {
                  eNo (0),
                  eYes (1)
            }
    MAX-ACCESS read-only
    STATUS     current
    DESCRIPTION
            "-- empty --"
    ::= { lcsStatusWlanStationTableEntry 63 }

-- {COLUMN} 1.3.6.1.4.1.2356.11.1.3.32.1.64
lcsStatusWlanStationTableEntryWpa2KeyManagement OBJECT-TYPE
    SYNTAX     INTEGER {
                  eStandard (0),
                  eFastRoaming (1),
                  eSha256 (2),
                  eSha384 (3),
                  eFastRoamingSha384 (4),
                  eNone (255)
            }
    MAX-ACCESS read-only
    STATUS     current
    DESCRIPTION
            "-- empty --"
    ::= { lcsStatusWlanStationTableEntry 64 }

-- {COLUMN} 1.3.6.1.4.1.2356.11.1.3.32.1.65
lcsStatusWlanStationTableEntrySGIMask OBJECT-TYPE
    SYNTAX     BITS {
                  eNo (0),
                  e160mhz (28),
                  e80mhz (29),
                  e40mhz (30),
                  e20mhz (31)
            }
    MAX-ACCESS read-only
    STATUS     current
    DESCRIPTION
            "Bit mask of short guard interval support per-CBW"
    ::= { lcsStatusWlanStationTableEntry 65 }

-- {COLUMN} 1.3.6.1.4.1.2356.11.1.3.32.1.66
lcsStatusWlanStationTableEntryChannelBandwidths OBJECT-TYPE
    SYNTAX     BITS {
                  eT40mhz (26),
                  e80Plus80mhz (27),
                  e160mhz (28),
                  e80mhz (29),
                  e40mhz (30),
                  e20mhz (31)
            }
    MAX-ACCESS read-only
    STATUS     current
    DESCRIPTION
            "-- empty --"
    ::= { lcsStatusWlanStationTableEntry 66 }

-- {COLUMN} 1.3.6.1.4.1.2356.11.1.3.32.1.67
lcsStatusWlanStationTableEntryProtMgmtFrames OBJECT-TYPE
    SYNTAX     INTEGER {
                  eNo (0),
                  eYes (1)
            }
    MAX-ACCESS read-only
    STATUS     current
    DESCRIPTION
            "-- empty --"
    ::= { lcsStatusWlanStationTableEntry 67 }

-- {COLUMN} 1.3.6.1.4.1.2356.11.1.3.32.1.68
lcsStatusWlanStationTableEntryRxStbcHt OBJECT-TYPE
    SYNTAX     INTEGER {
                  eNone (0),
                  eOne (1),
                  eTwo (2),
                  eThree (3)
            }
    MAX-ACCESS read-only
    STATUS     current
    DESCRIPTION
            "-- empty --"
    ::= { lcsStatusWlanStationTableEntry 68 }

-- {COLUMN} 1.3.6.1.4.1.2356.11.1.3.32.1.69
lcsStatusWlanStationTableEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { lcsStatusWlanStationTableEntry 69 }

-- {COLUMN} 1.3.6.1.4.1.2356.11.1.3.32.1.70
lcsStatusWlanStationTableEntryLDPCMask OBJECT-TYPE
    SYNTAX     BITS {
                  eVht (30),
                  eHt (31)
            }
    MAX-ACCESS read-only
    STATUS     current
    DESCRIPTION
            "Bit mask of LDPC support per-PHY-Type"
    ::= { lcsStatusWlanStationTableEntry 70 }

-- {COLUMN} 1.3.6.1.4.1.2356.11.1.3.32.1.71
lcsStatusWlanStationTableEntryOperationMode OBJECT-TYPE
    SYNTAX     INTEGER {
                  eUnknown (0),
                  e11b (1),
                  e11g (2),
                  e11a (3),
                  e11n (4),
                  e11ac (5)
            }
    MAX-ACCESS read-only
    STATUS     current
    DESCRIPTION
            "-- empty --"
    ::= { lcsStatusWlanStationTableEntry 71 }

-- {COLUMN} 1.3.6.1.4.1.2356.11.1.3.32.1.72
lcsStatusWlanStationTableEntryBlockackTestResult OBJECT-TYPE
    SYNTAX     INTEGER {
                  eUnknown (0),
                  eOk (1),
                  eNotOk (2),
                  eNotApplicable (3)
            }
    MAX-ACCESS read-only
    STATUS     current
    DESCRIPTION
            "-- empty --"
    ::= { lcsStatusWlanStationTableEntry 72 }

-- {COLUMN} 1.3.6.1.4.1.2356.11.1.3.32.1.73
lcsStatusWlanStationTableEntryTxChannelwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanStationTableEntry 73 }

-- {COLUMN} 1.3.6.1.4.1.2356.11.1.3.32.1.74
lcsStatusWlanStationTableEntryTxShortGi OBJECT-TYPE
    SYNTAX     INTEGER {
                  eNo (0),
                  eYes (1)
            }
    MAX-ACCESS read-only
    STATUS     current
    DESCRIPTION
            "-- empty --"
    ::= { lcsStatusWlanStationTableEntry 74 }

-- {COLUMN} 1.3.6.1.4.1.2356.11.1.3.32.1.75
lcsStatusWlanStationTableEntryRxChannelwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanStationTableEntry 75 }

-- {COLUMN} 1.3.6.1.4.1.2356.11.1.3.32.1.76
lcsStatusWlanStationTableEntryRxShortGi OBJECT-TYPE
    SYNTAX     INTEGER {
                  eNo (0),
                  eYes (1)
            }
    MAX-ACCESS read-only
    STATUS     current
    DESCRIPTION
            "-- empty --"
    ::= { lcsStatusWlanStationTableEntry 76 }

-- {COLUMN} 1.3.6.1.4.1.2356.11.1.3.32.1.77
lcsStatusWlanStationTableEntryTxMcs OBJECT-TYPE
    SYNTAX     Integer32 (0..255)
    MAX-ACCESS read-only
    STATUS     current
    DESCRIPTION
            "-- empty --"
    ::= { lcsStatusWlanStationTableEntry 77 }

-- {COLUMN} 1.3.6.1.4.1.2356.11.1.3.32.1.78
lcsStatusWlanStationTableEntryRxMcs OBJECT-TYPE
    SYNTAX     Integer32 (0..255)
    MAX-ACCESS read-only
    STATUS     current
    DESCRIPTION
            "-- empty --"
    ::= { lcsStatusWlanStationTableEntry 78 }

-- {COLUMN} 1.3.6.1.4.1.2356.11.1.3.32.1.79
lcsStatusWlanStationTableEntry11acBeamforming OBJECT-TYPE
    SYNTAX     BITS {
                  eMuBfee (28),
                  eMuBfer (29),
                  eSuBfee (30),
                  eSuBfer (31)
            }
    MAX-ACCESS read-only
    STATUS     current
    DESCRIPTION
            "-- empty --"
    ::= { lcsStatusWlanStationTableEntry 79 }

-- {COLUMN} 1.3.6.1.4.1.2356.11.1.3.32.1.80
lcsStatusWlanStationTableEntryDhcpHostname OBJECT-TYPE
    SYNTAX     DisplayString (SIZE(0..255))
    MAX-ACCESS read-only
    STATUS     current
    DESCRIPTION
            "-- empty --"
    ::= { lcsStatusWlanStationTableEntry 80 }

-- {COLUMN} 1.3.6.1.4.1.2356.11.1.3.32.1.81
lcsStatusWlanStationTableEntryRadioMeasurements OBJECT-TYPE
    SYNTAX     BITS {
                  eOther (26),
                  eApcr (27),
                  eNocm (28),
                  eBtm (29),
                  eBam (30),
                  eBpm (31)
            }
    MAX-ACCESS read-only
    STATUS     current
    DESCRIPTION
            "-- empty --"
    ::= { lcsStatusWlanStationTableEntry 81 }

-- {COLUMN} 1.3.6.1.4.1.2356.11.1.3.32.1.82
lcsStatusWlanStationTableEntryBssTransition OBJECT-TYPE
    SYNTAX     INTEGER {
                  eNo (0),
                  eYes (1)
            }
    MAX-ACCESS read-only
    STATUS     current
    DESCRIPTION
            "-- empty --"
    ::= { lcsStatusWlanStationTableEntry 82 }

-- {COLUMN} 1.3.6.1.4.1.2356.11.1.3.32.1.83
lcsStatusWlanStationTableEntryMaxSpatialStreams OBJECT-TYPE
    SYNTAX     Integer32 (0..255)
    MAX-ACCESS read-only
    STATUS     current
    DESCRIPTION
            "-- empty --"
    ::= { lcsStatusWlanStationTableEntry 83 }

-- {COLUMN} 1.3.6.1.4.1.2356.11.1.3.32.1.84
lcsStatusWlanStationTableEntryLastFrameReceived OBJECT-TYPE
    SYNTAX     Integer32 (0..2147483647)
    MAX-ACCESS read-only
    STATUS     current
    DESCRIPTION
            "-- empty --"
    ::= { lcsStatusWlanStationTableEntry 84 }

-- {COLUMN} 1.3.6.1.4.1.2356.11.1.3.32.1.85
lcsStatusWlanStationTableEntrySteeringFriendly OBJECT-TYPE
    SYNTAX     INTEGER {
                  eNo (0),
                  eYes (16777216)
            }
    MAX-ACCESS read-only
    STATUS     current
    DESCRIPTION
            "-- empty --"
    ::= { lcsStatusWlanStationTableEntry 85 }

-- {COLUMN} 1.3.6.1.4.1.2356.11.1.3.32.1.86
lcsStatusWlanStationTableEntryLastSteering OBJECT-TYPE
    SYNTAX     Integer32 (0..2147483647)
    MAX-ACCESS read-only
    STATUS     current
    DESCRIPTION
            "-- empty --"
    ::= { lcsStatusWlanStationTableEntry 86 }

-- {COLUMN} 1.3.6.1.4.1.2356.11.1.3.32.1.87
lcsStatusWlanStationTableEntryLepsU OBJECT-TYPE
    SYNTAX     INTEGER {
                  eNo (0),
                  eYes (1)
            }
    MAX-ACCESS read-only
    STATUS     current
    DESCRIPTION
            "-- empty --"
    ::= { lcsStatusWlanStationTableEntry 87 }

-- {COLUMN} 1.3.6.1.4.1.2356.11.1.3.32.1.88
lcsStatusWlanStationTableEntryWpaAuthType OBJECT-TYPE
    SYNTAX     INTEGER {
                  eNone (0),
                  ePsk (1),
                  e8021x (2),
                  eOwe (7),
                  eSae (8)
            }
    MAX-ACCESS read-only
    STATUS     current
    DESCRIPTION
            "-- empty --"
    ::= { lcsStatusWlanStationTableEntry 88 }

-- {COLUMN} 1.3.6.1.4.1.2356.11.1.3.32.1.89
lcsStatusWlanStationTableEntryHotspot20Release OBJECT-TYPE
    SYNTAX     INTEGER {
                  eNone (0),
                  eRelease1 (1),
                  eRelease2 (2),
                  eRelease3 (3)
            }
    MAX-ACCESS read-only
    STATUS     current
    DESCRIPTION
            "-- empty --"
    ::= { lcsStatusWlanStationTableEntry 89 }

-- {COLUMN} 1.3.6.1.4.1.2356.11.1.3.32.1.90
lcsStatusWlanStationTableEntryQosMapping OBJECT-TYPE
    SYNTAX     INTEGER {
                  eNo (0),
                  eYes (1)
            }
    MAX-ACCESS read-only
    STATUS     current
    DESCRIPTION
            "-- empty --"
    ::= { lcsStatusWlanStationTableEntry 90 }

-- {COLUMN} 1.3.6.1.4.1.2356.11.1.3.32.1.91
lcsStatusWlanStationTableEntrySessionTimeout OBJECT-TYPE
    SYNTAX     Integer32 (0..2147483647)
    MAX-ACCESS read-only
    STATUS     current
    DESCRIPTION
            "-- empty --"
    ::= { lcsStatusWlanStationTableEntry 91 }

-- {COLUMN} 1.3.6.1.4.1.2356.11.1.3.32.1.565
lcsStatusWlanStationTableEntryIpv6AddressTxt OBJECT-TYPE
    SYNTAX     DisplayString (SIZE(0..255))
    MAX-ACCESS read-only
    STATUS     current
    DESCRIPTION
            "-- empty --"
    ::= { lcsStatusWlanStationTableEntry 565 }

-- {TABLE} 1.3.6.1.4.1.2356.11.1.3.34
lcsStatusWlanScanResultsTable OBJECT-TYPE
    SYNTAX     SEQUENCE OF LcsStatusWlanScanResultsEntry
    MAX-ACCESS not-accessible
    STATUS     current
    DESCRIPTION
            ""
    ::= { lcsStatusWlan 34 }

-- {ROW} 1.3.6.1.4.1.2356.11.1.3.34.1
lcsStatusWlanScanResultsEntry OBJECT-TYPE
    SYNTAX     LcsStatusWlanScanResultsEntry
    MAX-ACCESS not-accessible
    STATUS     current
    DESCRIPTION
            ""
    INDEX {
            lcsStatusWlanScanResultsEntryBssid,
            lcsStatusWlanScanResultsEntryInterface
          }
    ::= { lcsStatusWlanScanResultsTable 1 }

LcsStatusWlanScanResultsEntry ::= SEQUENCE {
            lcsStatusWlanScanResultsEntryBssid MacAddress,
            lcsStatusWlanScanResultsEntryNetworkName DisplayString,
            lcsStatusWlanScanResultsEntryOperationMode INTEGER,
            lcsStatusWlanScanResultsEntryBeaconPeriod Integer32,
            lcsStatusWlanScanResultsEntryDtimPeriod Integer32,
            lcsStatusWlanScanResultsEntryRadioChannel Integer32,
            lcsStatusWlanScanResultsEntryPhySignal Integer32,
            lcsStatusWlanScanResultsEntryNoiseLevel Integer32,
            lcsStatusWlanScanResultsEntryLoad DisplayString,
            lcsStatusWlanScanResultsEntryEncryption INTEGER,
            lcsStatusWlanScanResultsEntryShortPreamble INTEGER,
            lcsStatusWlanScanResultsEntryInterface INTEGER,
            lcsStatusWlanScanResultsEntryRadioBand INTEGER,
            lcsStatusWlanScanResultsEntry108mbpsMode INTEGER,
            lcsStatusWlanScanResultsEntryShortSlotTime INTEGER,
            lcsStatusWlanScanResultsEntryRate INTEGER,
            lcsStatusWlanScanResultsEntryNonerpPresent INTEGER,
            lcsStatusWlanScanResultsEntryCompression INTEGER,
            lcsStatusWlanScanResultsEntryPcfFunctionality INTEGER,
            lcsStatusWlanScanResultsEntryIdentification DisplayString,
            lcsStatusWlanScanResultsEntryQos INTEGER,
            lcsStatusWlanScanResultsEntryAge Integer32,
            lcsStatusWlanScanResultsEntrySignalLevel Integer32,
            lcsStatusWlanScanResultsEntryShortGuardInterval INTEGER,
            lcsStatusWlanScanResultsEntryExtChannel INTEGER,
            lcsStatusWlanScanResultsEntry40mhzMode INTEGER,
            lcsStatusWlanScanResultsEntry40mhzIntolerant INTEGER,
            lcsStatusWlanScanResultsEntryInterpointPeerName DisplayString,
            lcsStatusWlanScanResultsEntryMaxAMpduLen Integer32,
            lcsStatusWlanScanResultsEntryMaxAMsduLen Integer32,
            lcsStatusWlanScanResultsEntryVendor DisplayString,
            lcsStatusWlanScanResultsEntryEffRate Integer32,
            lcsStatusWlanScanResultsEntry40mhzCoexistence INTEGER,
            lcsStatusWlanScanResultsEntryPreAuthentication INTEGER,
            lcsStatusWlanScanResultsEntryTxStbc INTEGER,
            lcsStatusWlanScanResultsEntryRxStbc INTEGER,
            lcsStatusWlanScanResultsEntryEapolPreauthFailed INTEGER,
            lcsStatusWlanScanResultsEntryLdpc INTEGER,
            lcsStatusWlanScanResultsEntryAutowds INTEGER,
            lcsStatusWlanScanResultsEntrySGIMask BITS,
            lcsStatusWlanScanResultsEntryChannelBandwidths BITS,
            lcsStatusWlanScanResultsEntryChannelBandwidth INTEGER,
            lcsStatusWlanScanResultsEntryClBrgSupport INTEGER,
            lcsStatusWlanScanResultsEntryProtMgmtFrames INTEGER,
            lcsStatusWlanScanResultsEntryTxPowerLimit DisplayString,
            lcsStatusWlanScanResultsEntryTxSTBCMask BITS,
            lcsStatusWlanScanResultsEntryRxStbcHt INTEGER,
            lcsStatusWlanScanResultsEntryRxStbcVht INTEGER,
            lcsStatusWlanScanResultsEntryLDPCMask BITS,
            lcsStatusWlanScanResultsEntryUuid DisplayString,
            lcsStatusWlanScanResultsEntry11acBeamforming BITS,
            lcsStatusWlanScanResultsEntrySecondaryChannel Integer32,
            lcsStatusWlanScanResultsEntryTransitionalMode INTEGER,
            lcsStatusWlanScanResultsEntryTransitionalSsid DisplayString,
            lcsStatusWlanScanResultsEntryTransitionalBssid MacAddress,
            lcsStatusWlanScanResultsEntryQosMapping INTEGER
    }

-- {COLUMN} 1.3.6.1.4.1.2356.11.1.3.34.1.1
lcsStatusWlanScanResultsEntryBssid OBJECT-TYPE
    SYNTAX     MacAddress
    MAX-ACCESS read-only
    STATUS     current
    DESCRIPTION
            ""
    ::= { lcsStatusWlanScanResultsEntry 1 }

-- {COLUMN} 1.3.6.1.4.1.2356.11.1.3.34.1.2
lcsStatusWlanScanResultsEntryNetworkName OBJECT-TYPE
    SYNTAX     DisplayString (SIZE(0..255))
    MAX-ACCESS read-only
    STATUS     current
    DESCRIPTION
            ""
    ::= { lcsStatusWlanScanResultsEntry 2 }

-- {COLUMN} 1.3.6.1.4.1.2356.11.1.3.34.1.3
lcsStatusWlanScanResultsEntryOperationMode OBJECT-TYPE
    SYNTAX     INTEGER {
                  eNone (0),
                  eAdhoc (1),
                  eInfrastructure (2)
            }
    MAX-ACCESS read-only
    STATUS     current
    DESCRIPTION
            "lancom's description of operation mode"
    ::= { lcsStatusWlanScanResultsEntry 3 }

-- {COLUMN} 1.3.6.1.4.1.2356.11.1.3.34.1.6
lcsStatusWlanScanResultsEntryBeaconPeriod OBJECT-TYPE
    SYNTAX     Integer32 (0..65535)
    MAX-ACCESS read-only
    STATUS     current
    DESCRIPTION
            ""
    ::= { lcsStatusWlanScanResultsEntry 6 }

-- {COLUMN} 1.3.6.1.4.1.2356.11.1.3.34.1.7
lcsStatusWlanScanResultsEntryDtimPeriod OBJECT-TYPE
    SYNTAX     Integer32 (0..65535)
    MAX-ACCESS read-only
    STATUS     current
    DESCRIPTION
            ""
    ::= { lcsStatusWlanScanResultsEntry 7 }

-- {COLUMN} 1.3.6.1.4.1.2356.11.1.3.34.1.8
lcsStatusWlanScanResultsEntryRadioChannel OBJECT-TYPE
    SYNTAX     Integer32 (0..255)
    MAX-ACCESS read-only
    STATUS     current
    DESCRIPTION
            ""
    ::= { lcsStatusWlanScanResultsEntry 8 }

-- {COLUMN} 1.3.6.1.4.1.2356.11.1.3.34.1.10
lcsStatusWlanScanResultsEntryPhySignal OBJECT-TYPE
    SYNTAX     Integer32 (0..65535)
    MAX-ACCESS read-only
    STATUS     current
    DESCRIPTION
            ""
    ::= { lcsStatusWlanScanResultsEntry 10 }

-- {COLUMN} 1.3.6.1.4.1.2356.11.1.3.34.1.11
lcsStatusWlanScanResultsEntryNoiseLevel OBJECT-TYPE
    SYNTAX     Integer32 (-128..127)
    MAX-ACCESS read-only
    STATUS     current
    DESCRIPTION
            ""
    ::= { lcsStatusWlanScanResultsEntry 11 }

-- {COLUMN} 1.3.6.1.4.1.2356.11.1.3.34.1.12
lcsStatusWlanScanResultsEntryLoad OBJECT-TYPE
    SYNTAX     DisplayString (SIZE(0..255))
    MAX-ACCESS read-only
    STATUS     current
    DESCRIPTION
            ""
    ::= { lcsStatusWlanScanResultsEntry 12 }

-- {COLUMN} 1.3.6.1.4.1.2356.11.1.3.34.1.13
lcsStatusWlanScanResultsEntryEncryption OBJECT-TYPE
    SYNTAX     INTEGER {
                  eNone (0),
                  eWep (1),
                  eTkip (2),
                  eAes (3),
                  eAesPlusTkip (4)
            }
    MAX-ACCESS read-only
    STATUS     current
    DESCRIPTION
            ""
    ::= { lcsStatusWlanScanResultsEntry 13 }

-- {COLUMN} 1.3.6.1.4.1.2356.11.1.3.34.1.14
lcsStatusWlanScanResultsEntryShortPreamble OBJECT-TYPE
    SYNTAX     INTEGER {
                  eNo (0),
                  eYes (1)
            }
    MAX-ACCESS read-only
    STATUS     current
    DESCRIPTION
            ""
    ::= { lcsStatusWlanScanResultsEntry 14 }

-- {COLUMN} 1.3.6.1.4.1.2356.11.1.3.34.1.15
lcsStatusWlanScanResultsEntryInterface OBJECT-TYPE
    SYNTAX     INTEGER {
                  eWlan1 (0),
                  eWlan2 (1),
                  eWlan3 (2),
                  eWlan4 (3)
            }
    MAX-ACCESS read-only
    STATUS     current
    DESCRIPTION
            ""
    ::= { lcsStatusWlanScanResultsEntry 15 }

-- {COLUMN} 1.3.6.1.4.1.2356.11.1.3.34.1.16
lcsStatusWlanScanResultsEntryRadioBand OBJECT-TYPE
    SYNTAX     INTEGER {
                  eUnknown (0),
                  e24ghz (1),
                  e5ghz (2),
                  e24ghz5ghz (3)
            }
    MAX-ACCESS read-only
    STATUS     current
    DESCRIPTION
            ""
    ::= { lcsStatusWlanScanResultsEntry 16 }

-- {COLUMN} 1.3.6.1.4.1.2356.11.1.3.34.1.17
lcsStatusWlanScanResultsEntry108mbpsMode OBJECT-TYPE
    SYNTAX     INTEGER {
                  eNo (0),
                  eYes (1)
            }
    MAX-ACCESS read-only
    STATUS     current
    DESCRIPTION
            ""
    ::= { lcsStatusWlanScanResultsEntry 17 }

-- {COLUMN} 1.3.6.1.4.1.2356.11.1.3.34.1.18
lcsStatusWlanScanResultsEntryShortSlotTime OBJECT-TYPE
    SYNTAX     INTEGER {
                  eNo (0),
                  eYes (1)
            }
    MAX-ACCESS read-only
    STATUS     current
    DESCRIPTION
            ""
    ::= { lcsStatusWlanScanResultsEntry 18 }

-- {COLUMN} 1.3.6.1.4.1.2356.11.1.3.34.1.19
lcsStatusWlanScanResultsEntryRate OBJECT-TYPE
    SYNTAX     INTEGER {
                  eUnknown (0),
                  e1M (1),
                  e2M (2),
                  e5M (3),
                  e5M5 (4),
                  e8M (5),
                  e11M (6),
                  e6M (12),
                  e9M (13),
                  e12M (14),
                  e18M (15),
                  e24M (16),
                  e36M (17),
                  e48M (18),
                  e54M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eHT4S26M (52),
                  eHT4S52M (53),
                  eHT4S78M (54),
                  eHT4S104M (55),
                  eHT4S156M (56),
                  eHT4S208M (57),
                  eHT4S234M (58),
                  eHT4S260M (59),
                  eHTDUP6M (60),
                  eHtMcs33 (61),
                  eHtMcs34 (62),
                  eHtMcs35 (63),
                  eHtMcs36 (64),
                  eHtMcs37 (65),
                  eHtMcs38 (66),
                  eHtMcs39 (67),
                  eHtMcs40 (68),
                  eHtMcs41 (69),
                  eHtMcs42 (70),
                  eHtMcs43 (71),
                  eHtMcs44 (72),
                  eHtMcs45 (73),
                  eHtMcs46 (74),
                  eHtMcs47 (75),
                  eHtMcs48 (76),
                  eHtMcs49 (77),
                  eHtMcs50 (78),
                  eHtMcs51 (79),
                  eHtMcs52 (80),
                  eHtMcs53 (81),
                  eHtMcs54 (82),
                  eHtMcs55 (83),
                  eHtMcs56 (84),
                  eHtMcs57 (85),
                  eHtMcs58 (86),
                  eHtMcs59 (87),
                  eHtMcs60 (88),
                  eHtMcs61 (89),
                  eHtMcs62 (90),
                  eHtMcs63 (91),
                  eHtMcs64 (92),
                  eHtMcs65 (93),
                  eHtMcs66 (94),
                  eHtMcs67 (95),
                  eHtMcs68 (96),
                  eHtMcs69 (97),
                  eHtMcs70 (98),
                  eHtMcs71 (99),
                  eHtMcs72 (100),
                  eHtMcs73 (101),
                  eHtMcs74 (102),
                  eHtMcs75 (103),
                  eHtMcs76 (104),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            ""
    ::= { lcsStatusWlanScanResultsEntry 19 }

-- {COLUMN} 1.3.6.1.4.1.2356.11.1.3.34.1.20
lcsStatusWlanScanResultsEntryNonerpPresent OBJECT-TYPE
    SYNTAX     INTEGER {
                  eNo (0),
                  eYes (1)
            }
    MAX-ACCESS read-only
    STATUS     current
    DESCRIPTION
            ""
    ::= { lcsStatusWlanScanResultsEntry 20 }

-- {COLUMN} 1.3.6.1.4.1.2356.11.1.3.34.1.21
lcsStatusWlanScanResultsEntryCompression OBJECT-TYPE
    SYNTAX     INTEGER {
                  eNo (0),
                  eYes (1)
            }
    MAX-ACCESS read-only
    STATUS     current
    DESCRIPTION
            ""
    ::= { lcsStatusWlanScanResultsEntry 21 }

-- {COLUMN} 1.3.6.1.4.1.2356.11.1.3.34.1.22
lcsStatusWlanScanResultsEntryPcfFunctionality OBJECT-TYPE
    SYNTAX     INTEGER {
                  eNone (0),
                  eDelivery (1),
                  eDeliveryPlusPolling (2)
            }
    MAX-ACCESS read-only
    STATUS     current
    DESCRIPTION
            ""
    ::= { lcsStatusWlanScanResultsEntry 22 }

-- {COLUMN} 1.3.6.1.4.1.2356.11.1.3.34.1.23
lcsStatusWlanScanResultsEntryIdentification OBJECT-TYPE
    SYNTAX     DisplayString (SIZE(0..16))
    MAX-ACCESS read-only
    STATUS     current
    DESCRIPTION
            ""
    ::= { lcsStatusWlanScanResultsEntry 23 }

-- {COLUMN} 1.3.6.1.4.1.2356.11.1.3.34.1.24
lcsStatusWlanScanResultsEntryQos OBJECT-TYPE
    SYNTAX     INTEGER {
                  eNo (0),
                  eYes (1)
            }
    MAX-ACCESS read-only
    STATUS     current
    DESCRIPTION
            ""
    ::= { lcsStatusWlanScanResultsEntry 24 }

-- {COLUMN} 1.3.6.1.4.1.2356.11.1.3.34.1.25
lcsStatusWlanScanResultsEntryAge OBJECT-TYPE
    SYNTAX     Integer32 (0..2147483647)
    MAX-ACCESS read-only
    STATUS     current
    DESCRIPTION
            ""
    ::= { lcsStatusWlanScanResultsEntry 25 }

-- {COLUMN} 1.3.6.1.4.1.2356.11.1.3.34.1.26
lcsStatusWlanScanResultsEntrySignalLevel OBJECT-TYPE
    SYNTAX     Integer32 (-32768..32767)
    MAX-ACCESS read-only
    STATUS     current
    DESCRIPTION
            ""
    ::= { lcsStatusWlanScanResultsEntry 26 }

-- {COLUMN} 1.3.6.1.4.1.2356.11.1.3.34.1.27
lcsStatusWlanScanResultsEntryShortGuardInterval OBJECT-TYPE
    SYNTAX     INTEGER {
                  eNo (0),
                  e20mhz (1),
                  e40mhz (2),
                  e2040mhz (3)
            }
    MAX-ACCESS read-only
    STATUS     current
    DESCRIPTION
            ""
    ::= { lcsStatusWlanScanResultsEntry 27 }

-- {COLUMN} 1.3.6.1.4.1.2356.11.1.3.34.1.28
lcsStatusWlanScanResultsEntryExtChannel OBJECT-TYPE
    SYNTAX     INTEGER {
                  eNone (0),
                  eAbove (1),
                  eBelow (3)
            }
    MAX-ACCESS read-only
    STATUS     current
    DESCRIPTION
            ""
    ::= { lcsStatusWlanScanResultsEntry 28 }

-- {COLUMN} 1.3.6.1.4.1.2356.11.1.3.34.1.29
lcsStatusWlanScanResultsEntry40mhzMode OBJECT-TYPE
    SYNTAX     INTEGER {
                  eNo (0),
                  eYes (1)
            }
    MAX-ACCESS read-only
    STATUS     current
    DESCRIPTION
            ""
    ::= { lcsStatusWlanScanResultsEntry 29 }

-- {COLUMN} 1.3.6.1.4.1.2356.11.1.3.34.1.30
lcsStatusWlanScanResultsEntry40mhzIntolerant OBJECT-TYPE
    SYNTAX     INTEGER {
                  eNo (0),
                  eYes (1)
            }
    MAX-ACCESS read-only
    STATUS     current
    DESCRIPTION
            ""
    ::= { lcsStatusWlanScanResultsEntry 30 }

-- {COLUMN} 1.3.6.1.4.1.2356.11.1.3.34.1.31
lcsStatusWlanScanResultsEntryInterpointPeerName OBJECT-TYPE
    SYNTAX     DisplayString (SIZE(0..24))
    MAX-ACCESS read-only
    STATUS     current
    DESCRIPTION
            ""
    ::= { lcsStatusWlanScanResultsEntry 31 }

-- {COLUMN} 1.3.6.1.4.1.2356.11.1.3.34.1.32
lcsStatusWlanScanResultsEntryMaxAMpduLen OBJECT-TYPE
    SYNTAX     Integer32 (0..2147483647)
    MAX-ACCESS read-only
    STATUS     current
    DESCRIPTION
            ""
    ::= { lcsStatusWlanScanResultsEntry 32 }

-- {COLUMN} 1.3.6.1.4.1.2356.11.1.3.34.1.33
lcsStatusWlanScanResultsEntryMaxAMsduLen OBJECT-TYPE
    SYNTAX     Integer32 (0..2147483647)
    MAX-ACCESS read-only
    STATUS     current
    DESCRIPTION
            ""
    ::= { lcsStatusWlanScanResultsEntry 33 }

-- {COLUMN} 1.3.6.1.4.1.2356.11.1.3.34.1.34
lcsStatusWlanScanResultsEntryVendor OBJECT-TYPE
    SYNTAX     DisplayString (SIZE(0..255))
    MAX-ACCESS read-only
    STATUS     current
    DESCRIPTION
            ""
    ::= { lcsStatusWlanScanResultsEntry 34 }

-- {COLUMN} 1.3.6.1.4.1.2356.11.1.3.34.1.35
lcsStatusWlanScanResultsEntryEffRate OBJECT-TYPE
    SYNTAX     Integer32 (0..2147483647)
    MAX-ACCESS read-only
    STATUS     current
    DESCRIPTION
            ""
    ::= { lcsStatusWlanScanResultsEntry 35 }

-- {COLUMN} 1.3.6.1.4.1.2356.11.1.3.34.1.36
lcsStatusWlanScanResultsEntry40mhzCoexistence OBJECT-TYPE
    SYNTAX     INTEGER {
                  eNo (0),
                  eYes (1)
            }
    MAX-ACCESS read-only
    STATUS     current
    DESCRIPTION
            "-- empty --"
    ::= { lcsStatusWlanScanResultsEntry 36 }

-- {COLUMN} 1.3.6.1.4.1.2356.11.1.3.34.1.37
lcsStatusWlanScanResultsEntryPreAuthentication OBJECT-TYPE
    SYNTAX     INTEGER {
                  eNo (0),
                  eYes (1)
            }
    MAX-ACCESS read-only
    STATUS     current
    DESCRIPTION
            "-- empty --"
    ::= { lcsStatusWlanScanResultsEntry 37 }

-- {COLUMN} 1.3.6.1.4.1.2356.11.1.3.34.1.38
lcsStatusWlanScanResultsEntryTxStbc OBJECT-TYPE
    SYNTAX     INTEGER {
                  eNo (0),
                  eYes (1)
            }
    MAX-ACCESS read-only
    STATUS     current
    DESCRIPTION
            "-- empty --"
    ::= { lcsStatusWlanScanResultsEntry 38 }

-- {COLUMN} 1.3.6.1.4.1.2356.11.1.3.34.1.39
lcsStatusWlanScanResultsEntryRxStbc OBJECT-TYPE
    SYNTAX     INTEGER {
                  eNone (0),
                  eOne (1),
                  eTwo (2),
                  eThree (3)
            }
    MAX-ACCESS read-only
    STATUS     current
    DESCRIPTION
            "-- empty --"
    ::= { lcsStatusWlanScanResultsEntry 39 }

-- {COLUMN} 1.3.6.1.4.1.2356.11.1.3.34.1.40
lcsStatusWlanScanResultsEntryEapolPreauthFailed OBJECT-TYPE
    SYNTAX     INTEGER {
                  eNo (0),
                  eYes (1)
            }
    MAX-ACCESS read-only
    STATUS     current
    DESCRIPTION
            "-- empty --"
    ::= { lcsStatusWlanScanResultsEntry 40 }

-- {COLUMN} 1.3.6.1.4.1.2356.11.1.3.34.1.41
lcsStatusWlanScanResultsEntryLdpc OBJECT-TYPE
    SYNTAX     INTEGER {
                  eNo (0),
                  eYes (1)
            }
    MAX-ACCESS read-only
    STATUS     current
    DESCRIPTION
            "-- empty --"
    ::= { lcsStatusWlanScanResultsEntry 41 }

-- {COLUMN} 1.3.6.1.4.1.2356.11.1.3.34.1.42
lcsStatusWlanScanResultsEntryAutowds OBJECT-TYPE
    SYNTAX     INTEGER {
                  eNo (0),
                  eYes (1)
            }
    MAX-ACCESS read-only
    STATUS     current
    DESCRIPTION
            "-- empty --"
    ::= { lcsStatusWlanScanResultsEntry 42 }

-- {COLUMN} 1.3.6.1.4.1.2356.11.1.3.34.1.43
lcsStatusWlanScanResultsEntrySGIMask OBJECT-TYPE
    SYNTAX     BITS {
                  eNo (0),
                  e160mhz (28),
                  e80mhz (29),
                  e40mhz (30),
                  e20mhz (31)
            }
    MAX-ACCESS read-only
    STATUS     current
    DESCRIPTION
            "Bit mask of short guard interval support per-CBW"
    ::= { lcsStatusWlanScanResultsEntry 43 }

-- {COLUMN} 1.3.6.1.4.1.2356.11.1.3.34.1.44
lcsStatusWlanScanResultsEntryChannelBandwidths OBJECT-TYPE
    SYNTAX     BITS {
                  eT40mhz (26),
                  e80Plus80mhz (27),
                  e160mhz (28),
                  e80mhz (29),
                  e40mhz (30),
                  e20mhz (31)
            }
    MAX-ACCESS read-only
    STATUS     current
    DESCRIPTION
            "-- empty --"
    ::= { lcsStatusWlanScanResultsEntry 44 }

-- {COLUMN} 1.3.6.1.4.1.2356.11.1.3.34.1.45
lcsStatusWlanScanResultsEntryChannelBandwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanScanResultsEntry 45 }

-- {COLUMN} 1.3.6.1.4.1.2356.11.1.3.34.1.46
lcsStatusWlanScanResultsEntryClBrgSupport OBJECT-TYPE
    SYNTAX     INTEGER {
                  eNo (0),
                  eYes (1)
            }
    MAX-ACCESS read-only
    STATUS     current
    DESCRIPTION
            "-- empty --"
    ::= { lcsStatusWlanScanResultsEntry 46 }

-- {COLUMN} 1.3.6.1.4.1.2356.11.1.3.34.1.47
lcsStatusWlanScanResultsEntryProtMgmtFrames OBJECT-TYPE
    SYNTAX     INTEGER {
                  eNo (0),
                  eOptional (1),
                  eMandatory (2)
            }
    MAX-ACCESS read-only
    STATUS     current
    DESCRIPTION
            "-- empty --"
    ::= { lcsStatusWlanScanResultsEntry 47 }

-- {COLUMN} 1.3.6.1.4.1.2356.11.1.3.34.1.48
lcsStatusWlanScanResultsEntryTxPowerLimit OBJECT-TYPE
    SYNTAX     DisplayString (SIZE(0..255))
    MAX-ACCESS read-only
    STATUS     current
    DESCRIPTION
            "-- empty --"
    ::= { lcsStatusWlanScanResultsEntry 48 }

-- {COLUMN} 1.3.6.1.4.1.2356.11.1.3.34.1.49
lcsStatusWlanScanResultsEntryTxSTBCMask OBJECT-TYPE
    SYNTAX     BITS {
                  eVht (30),
                  eHt (31)
            }
    MAX-ACCESS read-only
    STATUS     current
    DESCRIPTION
            "Bit mask of Tx STBC support per-PHY-Type"
    ::= { lcsStatusWlanScanResultsEntry 49 }

-- {COLUMN} 1.3.6.1.4.1.2356.11.1.3.34.1.50
lcsStatusWlanScanResultsEntryRxStbcHt OBJECT-TYPE
    SYNTAX     INTEGER {
                  eNone (0),
                  eOne (1),
                  eTwo (2),
                  eThree (3)
            }
    MAX-ACCESS read-only
    STATUS     current
    DESCRIPTION
            "-- empty --"
    ::= { lcsStatusWlanScanResultsEntry 50 }

-- {COLUMN} 1.3.6.1.4.1.2356.11.1.3.34.1.51
lcsStatusWlanScanResultsEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { lcsStatusWlanScanResultsEntry 51 }

-- {COLUMN} 1.3.6.1.4.1.2356.11.1.3.34.1.52
lcsStatusWlanScanResultsEntryLDPCMask OBJECT-TYPE
    SYNTAX     BITS {
                  eVht (30),
                  eHt (31)
            }
    MAX-ACCESS read-only
    STATUS     current
    DESCRIPTION
            "Bit mask of LDPC support per-PHY-Type"
    ::= { lcsStatusWlanScanResultsEntry 52 }

-- {COLUMN} 1.3.6.1.4.1.2356.11.1.3.34.1.53
lcsStatusWlanScanResultsEntryUuid OBJECT-TYPE
    SYNTAX     DisplayString (SIZE(0..255))
    MAX-ACCESS read-only
    STATUS     current
    DESCRIPTION
            "-- empty --"
    ::= { lcsStatusWlanScanResultsEntry 53 }

-- {COLUMN} 1.3.6.1.4.1.2356.11.1.3.34.1.54
lcsStatusWlanScanResultsEntry11acBeamforming OBJECT-TYPE
    SYNTAX     BITS {
                  eMuBfee (28),
                  eMuBfer (29),
                  eSuBfee (30),
                  eSuBfer (31)
            }
    MAX-ACCESS read-only
    STATUS     current
    DESCRIPTION
            "-- empty --"
    ::= { lcsStatusWlanScanResultsEntry 54 }

-- {COLUMN} 1.3.6.1.4.1.2356.11.1.3.34.1.55
lcsStatusWlanScanResultsEntrySecondaryChannel OBJECT-TYPE
    SYNTAX     Integer32 (0..255)
    MAX-ACCESS read-only
    STATUS     current
    DESCRIPTION
            "-- empty --"
    ::= { lcsStatusWlanScanResultsEntry 55 }

-- {COLUMN} 1.3.6.1.4.1.2356.11.1.3.34.1.56
lcsStatusWlanScanResultsEntryTransitionalMode OBJECT-TYPE
    SYNTAX     INTEGER {
                  eNo (0),
                  eYes (1)
            }
    MAX-ACCESS read-only
    STATUS     current
    DESCRIPTION
            "-- empty --"
    ::= { lcsStatusWlanScanResultsEntry 56 }

-- {COLUMN} 1.3.6.1.4.1.2356.11.1.3.34.1.57
lcsStatusWlanScanResultsEntryTransitionalSsid OBJECT-TYPE
    SYNTAX     DisplayString (SIZE(0..255))
    MAX-ACCESS read-only
    STATUS     current
    DESCRIPTION
            "-- empty --"
    ::= { lcsStatusWlanScanResultsEntry 57 }

-- {COLUMN} 1.3.6.1.4.1.2356.11.1.3.34.1.58
lcsStatusWlanScanResultsEntryTransitionalBssid OBJECT-TYPE
    SYNTAX     MacAddress
    MAX-ACCESS read-only
    STATUS     current
    DESCRIPTION
            "-- empty --"
    ::= { lcsStatusWlanScanResultsEntry 58 }

-- {COLUMN} 1.3.6.1.4.1.2356.11.1.3.34.1.59
lcsStatusWlanScanResultsEntryQosMapping OBJECT-TYPE
    SYNTAX     INTEGER {
                  eNo (0),
                  eYes (1)
            }
    MAX-ACCESS read-only
    STATUS     current
    DESCRIPTION
            "-- empty --"
    ::= { lcsStatusWlanScanResultsEntry 59 }

-- {NODE} 1.3.6.1.4.1.2356.11.1.3.36
lcsStatusWlanInterpoints OBJECT IDENTIFIER ::= { lcsStatusWlan 36 }

-- {TABLE} 1.3.6.1.4.1.2356.11.1.3.36.1
lcsStatusWlanInterpointsAccesspointListTable OBJECT-TYPE
    SYNTAX     SEQUENCE OF LcsStatusWlanInterpointsAccesspointListEntry
    MAX-ACCESS not-accessible
    STATUS     current
    DESCRIPTION
            ""
    ::= { lcsStatusWlanInterpoints 1 }

-- {ROW} 1.3.6.1.4.1.2356.11.1.3.36.1.1
lcsStatusWlanInterpointsAccesspointListEntry OBJECT-TYPE
    SYNTAX     LcsStatusWlanInterpointsAccesspointListEntry
    MAX-ACCESS not-accessible
    STATUS     current
    DESCRIPTION
            ""
    INDEX {
            lcsStatusWlanInterpointsAccesspointListEntryIndex
          }
    ::= { lcsStatusWlanInterpointsAccesspointListTable 1 }

LcsStatusWlanInterpointsAccesspointListEntry ::= SEQUENCE {
            lcsStatusWlanInterpointsAccesspointListEntryIndex INTEGER,
            lcsStatusWlanInterpointsAccesspointListEntryMacAddress MacAddress,
            lcsStatusWlanInterpointsAccesspointListEntryRxRate INTEGER,
            lcsStatusWlanInterpointsAccesspointListEntryTxBytes Counter64,
            lcsStatusWlanInterpointsAccesspointListEntryRxBytes Counter64,
            lcsStatusWlanInterpointsAccesspointListEntryThroughput DisplayString,
            lcsStatusWlanInterpointsAccesspointListEntryKeyingState INTEGER,
            lcsStatusWlanInterpointsAccesspointListEntryRxPhySignal Integer32,
            lcsStatusWlanInterpointsAccesspointListEntryLinkPhySignal Integer32,
            lcsStatusWlanInterpointsAccesspointListEntryIdentification DisplayString,
            lcsStatusWlanInterpointsAccesspointListEntryTxRate INTEGER,
            lcsStatusWlanInterpointsAccesspointListEntryMaxThroughput DisplayString,
            lcsStatusWlanInterpointsAccesspointListEntryBytesThroughput Integer32,
            lcsStatusWlanInterpointsAccesspointListEntryBytesMaxThroughput Integer32,
            lcsStatusWlanInterpointsAccesspointListEntryWpaVersion INTEGER,
            lcsStatusWlanInterpointsAccesspointListEntryTxLimit Integer32,
            lcsStatusWlanInterpointsAccesspointListEntryRxLimit Integer32,
            lcsStatusWlanInterpointsAccesspointListEntryKeyHandshakeRole INTEGER,
            lcsStatusWlanInterpointsAccesspointListEntryTxPackets Integer32,
            lcsStatusWlanInterpointsAccesspointListEntryRxPackets Integer32,
            lcsStatusWlanInterpointsAccesspointListEntryQos INTEGER,
            lcsStatusWlanInterpointsAccesspointListEntryInterpointPeerName DisplayString,
            lcsStatusWlanInterpointsAccesspointListEntryMaxAMsduLen Integer32,
            lcsStatusWlanInterpointsAccesspointListEntryMaxAMpduLen Integer32,
            lcsStatusWlanInterpointsAccesspointListEntry40mhzMode INTEGER,
            lcsStatusWlanInterpointsAccesspointListEntryShortPreamble INTEGER,
            lcsStatusWlanInterpointsAccesspointListEntryShortGuardInterval INTEGER,
            lcsStatusWlanInterpointsAccesspointListEntryEffTxRate Integer32,
            lcsStatusWlanInterpointsAccesspointListEntryEffRxRate Integer32,
            lcsStatusWlanInterpointsAccesspointListEntryKeyType INTEGER,
            lcsStatusWlanInterpointsAccesspointListEntryTxErrors Integer32,
            lcsStatusWlanInterpointsAccesspointListEntryTotalRetries Integer32,
            lcsStatusWlanInterpointsAccesspointListEntryAlarmState BITS,
            lcsStatusWlanInterpointsAccesspointListEntryLinkActive INTEGER,
            lcsStatusWlanInterpointsAccesspointListEntryRxStbc INTEGER,
            lcsStatusWlanInterpointsAccesspointListEntryLdpc INTEGER,
            lcsStatusWlanInterpointsAccesspointListEntryRemoteStatus INTEGER,
            lcsStatusWlanInterpointsAccesspointListEntryWpa2KeyManagement INTEGER,
            lcsStatusWlanInterpointsAccesspointListEntrySGIMask BITS,
            lcsStatusWlanInterpointsAccesspointListEntryChannelBandwidths BITS,
            lcsStatusWlanInterpointsAccesspointListEntryProtMgmtFrames INTEGER,
            lcsStatusWlanInterpointsAccesspointListEntryRxStbcHt INTEGER,
            lcsStatusWlanInterpointsAccesspointListEntryRxStbcVht INTEGER,
            lcsStatusWlanInterpointsAccesspointListEntryLDPCMask BITS,
            lcsStatusWlanInterpointsAccesspointListEntryOperationMode INTEGER,
            lcsStatusWlanInterpointsAccesspointListEntryTxChannelwidth INTEGER,
            lcsStatusWlanInterpointsAccesspointListEntryTxShortGi INTEGER,
            lcsStatusWlanInterpointsAccesspointListEntryRxChannelwidth INTEGER,
            lcsStatusWlanInterpointsAccesspointListEntryRxShortGi INTEGER,
            lcsStatusWlanInterpointsAccesspointListEntryTxMcs Integer32,
            lcsStatusWlanInterpointsAccesspointListEntryRxMcs Integer32,
            lcsStatusWlanInterpointsAccesspointListEntryWpaAuthType INTEGER,
            lcsStatusWlanInterpointsAccesspointListEntryQosMapping INTEGER
    }

-- {COLUMN} 1.3.6.1.4.1.2356.11.1.3.36.1.1.1
lcsStatusWlanInterpointsAccesspointListEntryIndex OBJECT-TYPE
    SYNTAX     INTEGER {
                  eP2p11 (1),
                  eP2p12 (2),
                  eP2p13 (3),
                  eP2p14 (4),
                  eP2p15 (5),
                  eP2p16 (6),
                  eP2p21 (7),
                  eP2p22 (8),
                  eP2p23 (9),
                  eP2p24 (10),
                  eP2p25 (11),
                  eP2p26 (12),
                  eP2p17 (32),
                  eP2p18 (33),
                  eP2p19 (34),
                  eP2p110 (35),
                  eP2p111 (36),
                  eP2p112 (37),
                  eP2p113 (38),
                  eP2p114 (39),
                  eP2p115 (40),
                  eP2p116 (41),
                  eP2p27 (64),
                  eP2p28 (65),
                  eP2p29 (66),
                  eP2p210 (67),
                  eP2p211 (68),
                  eP2p212 (69),
                  eP2p213 (70),
                  eP2p214 (71),
                  eP2p215 (72),
                  eP2p216 (73)
            }
    MAX-ACCESS read-only
    STATUS     current
    DESCRIPTION
            ""
    ::= { lcsStatusWlanInterpointsAccesspointListEntry 1 }

-- {COLUMN} 1.3.6.1.4.1.2356.11.1.3.36.1.1.2
lcsStatusWlanInterpointsAccesspointListEntryMacAddress OBJECT-TYPE
    SYNTAX     MacAddress
    MAX-ACCESS read-only
    STATUS     current
    DESCRIPTION
            ""
    ::= { lcsStatusWlanInterpointsAccesspointListEntry 2 }

-- {COLUMN} 1.3.6.1.4.1.2356.11.1.3.36.1.1.5
lcsStatusWlanInterpointsAccesspointListEntryRxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            ""
    ::= { lcsStatusWlanInterpointsAccesspointListEntry 5 }

-- {COLUMN} 1.3.6.1.4.1.2356.11.1.3.36.1.1.6
lcsStatusWlanInterpointsAccesspointListEntryTxBytes OBJECT-TYPE
    SYNTAX     Counter64
    MAX-ACCESS read-only
    STATUS     current
    DESCRIPTION
            ""
    ::= { lcsStatusWlanInterpointsAccesspointListEntry 6 }

-- {COLUMN} 1.3.6.1.4.1.2356.11.1.3.36.1.1.7
lcsStatusWlanInterpointsAccesspointListEntryRxBytes OBJECT-TYPE
    SYNTAX     Counter64
    MAX-ACCESS read-only
    STATUS     current
    DESCRIPTION
            ""
    ::= { lcsStatusWlanInterpointsAccesspointListEntry 7 }

-- {COLUMN} 1.3.6.1.4.1.2356.11.1.3.36.1.1.8
lcsStatusWlanInterpointsAccesspointListEntryThroughput OBJECT-TYPE
    SYNTAX     DisplayString (SIZE(0..255))
    MAX-ACCESS read-only
    STATUS     current
    DESCRIPTION
            ""
    ::= { lcsStatusWlanInterpointsAccesspointListEntry 8 }

-- {COLUMN} 1.3.6.1.4.1.2356.11.1.3.36.1.1.12
lcsStatusWlanInterpointsAccesspointListEntryKeyingState OBJECT-TYPE
    SYNTAX     INTEGER {
                  eIdle (0),
                  ePending (1),
                  eDone (2),
                  eSaePending (3)
            }
    MAX-ACCESS read-only
    STATUS     current
    DESCRIPTION
            ""
    ::= { lcsStatusWlanInterpointsAccesspointListEntry 12 }

-- {COLUMN} 1.3.6.1.4.1.2356.11.1.3.36.1.1.13
lcsStatusWlanInterpointsAccesspointListEntryRxPhySignal OBJECT-TYPE
    SYNTAX     Integer32 (0..65535)
    MAX-ACCESS read-only
    STATUS     current
    DESCRIPTION
            ""
    ::= { lcsStatusWlanInterpointsAccesspointListEntry 13 }

-- {COLUMN} 1.3.6.1.4.1.2356.11.1.3.36.1.1.14
lcsStatusWlanInterpointsAccesspointListEntryLinkPhySignal OBJECT-TYPE
    SYNTAX     Integer32 (0..65535)
    MAX-ACCESS read-only
    STATUS     current
    DESCRIPTION
            ""
    ::= { lcsStatusWlanInterpointsAccesspointListEntry 14 }

-- {COLUMN} 1.3.6.1.4.1.2356.11.1.3.36.1.1.15
lcsStatusWlanInterpointsAccesspointListEntryIdentification OBJECT-TYPE
    SYNTAX     DisplayString (SIZE(0..32))
    MAX-ACCESS read-only
    STATUS     current
    DESCRIPTION
            ""
    ::= { lcsStatusWlanInterpointsAccesspointListEntry 15 }

-- {COLUMN} 1.3.6.1.4.1.2356.11.1.3.36.1.1.16
lcsStatusWlanInterpointsAccesspointListEntryTxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            ""
    ::= { lcsStatusWlanInterpointsAccesspointListEntry 16 }

-- {COLUMN} 1.3.6.1.4.1.2356.11.1.3.36.1.1.17
lcsStatusWlanInterpointsAccesspointListEntryMaxThroughput OBJECT-TYPE
    SYNTAX     DisplayString (SIZE(0..255))
    MAX-ACCESS read-only
    STATUS     current
    DESCRIPTION
            ""
    ::= { lcsStatusWlanInterpointsAccesspointListEntry 17 }

-- {COLUMN} 1.3.6.1.4.1.2356.11.1.3.36.1.1.19
lcsStatusWlanInterpointsAccesspointListEntryBytesThroughput OBJECT-TYPE
    SYNTAX     Integer32 (0..2147483647)
    MAX-ACCESS read-only
    STATUS     current
    DESCRIPTION
            ""
    ::= { lcsStatusWlanInterpointsAccesspointListEntry 19 }

-- {COLUMN} 1.3.6.1.4.1.2356.11.1.3.36.1.1.20
lcsStatusWlanInterpointsAccesspointListEntryBytesMaxThroughput OBJECT-TYPE
    SYNTAX     Integer32 (0..2147483647)
    MAX-ACCESS read-only
    STATUS     current
    DESCRIPTION
            ""
    ::= { lcsStatusWlanInterpointsAccesspointListEntry 20 }

-- {COLUMN} 1.3.6.1.4.1.2356.11.1.3.36.1.1.21
lcsStatusWlanInterpointsAccesspointListEntryWpaVersion OBJECT-TYPE
    SYNTAX     INTEGER {
                  eNone (0),
                  eWpa1 (1),
                  eWpa2 (2),
                  eWpa3 (3)
            }
    MAX-ACCESS read-only
    STATUS     current
    DESCRIPTION
            ""
    ::= { lcsStatusWlanInterpointsAccesspointListEntry 21 }

-- {COLUMN} 1.3.6.1.4.1.2356.11.1.3.36.1.1.22
lcsStatusWlanInterpointsAccesspointListEntryTxLimit OBJECT-TYPE
    SYNTAX     Integer32 (0..2147483647)
    MAX-ACCESS read-only
    STATUS     current
    DESCRIPTION
            ""
    ::= { lcsStatusWlanInterpointsAccesspointListEntry 22 }

-- {COLUMN} 1.3.6.1.4.1.2356.11.1.3.36.1.1.23
lcsStatusWlanInterpointsAccesspointListEntryRxLimit OBJECT-TYPE
    SYNTAX     Integer32 (0..2147483647)
    MAX-ACCESS read-only
    STATUS     current
    DESCRIPTION
            ""
    ::= { lcsStatusWlanInterpointsAccesspointListEntry 23 }

-- {COLUMN} 1.3.6.1.4.1.2356.11.1.3.36.1.1.24
lcsStatusWlanInterpointsAccesspointListEntryKeyHandshakeRole OBJECT-TYPE
    SYNTAX     INTEGER {
                  eNone (0),
                  eSupplicant (1),
                  eAuthenticator (2)
            }
    MAX-ACCESS read-only
    STATUS     current
    DESCRIPTION
            ""
    ::= { lcsStatusWlanInterpointsAccesspointListEntry 24 }

-- {COLUMN} 1.3.6.1.4.1.2356.11.1.3.36.1.1.25
lcsStatusWlanInterpointsAccesspointListEntryTxPackets OBJECT-TYPE
    SYNTAX     Integer32 (0..2147483647)
    MAX-ACCESS read-only
    STATUS     current
    DESCRIPTION
            ""
    ::= { lcsStatusWlanInterpointsAccesspointListEntry 25 }

-- {COLUMN} 1.3.6.1.4.1.2356.11.1.3.36.1.1.26
lcsStatusWlanInterpointsAccesspointListEntryRxPackets OBJECT-TYPE
    SYNTAX     Integer32 (0..2147483647)
    MAX-ACCESS read-only
    STATUS     current
    DESCRIPTION
            ""
    ::= { lcsStatusWlanInterpointsAccesspointListEntry 26 }

-- {COLUMN} 1.3.6.1.4.1.2356.11.1.3.36.1.1.27
lcsStatusWlanInterpointsAccesspointListEntryQos OBJECT-TYPE
    SYNTAX     INTEGER {
                  eNo (0),
                  eYes (1)
            }
    MAX-ACCESS read-only
    STATUS     current
    DESCRIPTION
            ""
    ::= { lcsStatusWlanInterpointsAccesspointListEntry 27 }

-- {COLUMN} 1.3.6.1.4.1.2356.11.1.3.36.1.1.28
lcsStatusWlanInterpointsAccesspointListEntryInterpointPeerName OBJECT-TYPE
    SYNTAX     DisplayString (SIZE(0..24))
    MAX-ACCESS read-only
    STATUS     current
    DESCRIPTION
            ""
    ::= { lcsStatusWlanInterpointsAccesspointListEntry 28 }

-- {COLUMN} 1.3.6.1.4.1.2356.11.1.3.36.1.1.29
lcsStatusWlanInterpointsAccesspointListEntryMaxAMsduLen OBJECT-TYPE
    SYNTAX     Integer32 (0..2147483647)
    MAX-ACCESS read-only
    STATUS     current
    DESCRIPTION
            ""
    ::= { lcsStatusWlanInterpointsAccesspointListEntry 29 }

-- {COLUMN} 1.3.6.1.4.1.2356.11.1.3.36.1.1.30
lcsStatusWlanInterpointsAccesspointListEntryMaxAMpduLen OBJECT-TYPE
    SYNTAX     Integer32 (0..2147483647)
    MAX-ACCESS read-only
    STATUS     current
    DESCRIPTION
            ""
    ::= { lcsStatusWlanInterpointsAccesspointListEntry 30 }

-- {COLUMN} 1.3.6.1.4.1.2356.11.1.3.36.1.1.31
lcsStatusWlanInterpointsAccesspointListEntry40mhzMode OBJECT-TYPE
    SYNTAX     INTEGER {
                  eNo (0),
                  eYes (1)
            }
    MAX-ACCESS read-only
    STATUS     current
    DESCRIPTION
            ""
    ::= { lcsStatusWlanInterpointsAccesspointListEntry 31 }

-- {COLUMN} 1.3.6.1.4.1.2356.11.1.3.36.1.1.32
lcsStatusWlanInterpointsAccesspointListEntryShortPreamble OBJECT-TYPE
    SYNTAX     INTEGER {
                  eNo (0),
                  eYes (1)
            }
    MAX-ACCESS read-only
    STATUS     current
    DESCRIPTION
            ""
    ::= { lcsStatusWlanInterpointsAccesspointListEntry 32 }

-- {COLUMN} 1.3.6.1.4.1.2356.11.1.3.36.1.1.33
lcsStatusWlanInterpointsAccesspointListEntryShortGuardInterval OBJECT-TYPE
    SYNTAX     INTEGER {
                  eNo (0),
                  e20mhz (1),
                  e40mhz (2),
                  e2040mhz (3)
            }
    MAX-ACCESS read-only
    STATUS     current
    DESCRIPTION
            ""
    ::= { lcsStatusWlanInterpointsAccesspointListEntry 33 }

-- {COLUMN} 1.3.6.1.4.1.2356.11.1.3.36.1.1.34
lcsStatusWlanInterpointsAccesspointListEntryEffTxRate OBJECT-TYPE
    SYNTAX     Integer32 (0..2147483647)
    MAX-ACCESS read-only
    STATUS     current
    DESCRIPTION
            ""
    ::= { lcsStatusWlanInterpointsAccesspointListEntry 34 }

-- {COLUMN} 1.3.6.1.4.1.2356.11.1.3.36.1.1.35
lcsStatusWlanInterpointsAccesspointListEntryEffRxRate OBJECT-TYPE
    SYNTAX     Integer32 (0..2147483647)
    MAX-ACCESS read-only
    STATUS     current
    DESCRIPTION
            ""
    ::= { lcsStatusWlanInterpointsAccesspointListEntry 35 }

-- {COLUMN} 1.3.6.1.4.1.2356.11.1.3.36.1.1.36
lcsStatusWlanInterpointsAccesspointListEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eAesCcmp256 (67),
                  eBip (68),
                  eBipCmac256 (69),
                  eAesGcmp128 (70),
                  eAesGcmp256 (71),
                  eBipGmac128 (72),
                  eBipGmac256 (73)
            }
    MAX-ACCESS read-only
    STATUS     current
    DESCRIPTION
            ""
    ::= { lcsStatusWlanInterpointsAccesspointListEntry 36 }

-- {COLUMN} 1.3.6.1.4.1.2356.11.1.3.36.1.1.37
lcsStatusWlanInterpointsAccesspointListEntryTxErrors OBJECT-TYPE
    SYNTAX     Integer32 (0..2147483647)
    MAX-ACCESS read-only
    STATUS     current
    DESCRIPTION
            ""
    ::= { lcsStatusWlanInterpointsAccesspointListEntry 37 }

-- {COLUMN} 1.3.6.1.4.1.2356.11.1.3.36.1.1.38
lcsStatusWlanInterpointsAccesspointListEntryTotalRetries OBJECT-TYPE
    SYNTAX     Integer32 (0..2147483647)
    MAX-ACCESS read-only
    STATUS     current
    DESCRIPTION
            ""
    ::= { lcsStatusWlanInterpointsAccesspointListEntry 38 }

-- {COLUMN} 1.3.6.1.4.1.2356.11.1.3.36.1.1.39
lcsStatusWlanInterpointsAccesspointListEntryAlarmState OBJECT-TYPE
    SYNTAX     BITS {
                  eNo (0),
                  eTxErrors (29),
                  eTotalRetries (30),
                  ePhySignal (31)
            }
    MAX-ACCESS read-only
    STATUS     current
    DESCRIPTION
            ""
    ::= { lcsStatusWlanInterpointsAccesspointListEntry 39 }

-- {COLUMN} 1.3.6.1.4.1.2356.11.1.3.36.1.1.40
lcsStatusWlanInterpointsAccesspointListEntryLinkActive OBJECT-TYPE
    SYNTAX     INTEGER {
                  eNo (0),
                  eYes (1)
            }
    MAX-ACCESS read-only
    STATUS     current
    DESCRIPTION
            "-- empty --"
    ::= { lcsStatusWlanInterpointsAccesspointListEntry 40 }

-- {COLUMN} 1.3.6.1.4.1.2356.11.1.3.36.1.1.41
lcsStatusWlanInterpointsAccesspointListEntryRxStbc OBJECT-TYPE
    SYNTAX     INTEGER {
                  eNone (0),
                  eOne (1),
                  eTwo (2),
                  eThree (3)
            }
    MAX-ACCESS read-only
    STATUS     current
    DESCRIPTION
            "-- empty --"
    ::= { lcsStatusWlanInterpointsAccesspointListEntry 41 }

-- {COLUMN} 1.3.6.1.4.1.2356.11.1.3.36.1.1.42
lcsStatusWlanInterpointsAccesspointListEntryLdpc OBJECT-TYPE
    SYNTAX     INTEGER {
                  eNo (0),
                  eYes (1)
            }
    MAX-ACCESS read-only
    STATUS     current
    DESCRIPTION
            "-- empty --"
    ::= { lcsStatusWlanInterpointsAccesspointListEntry 42 }

-- {COLUMN} 1.3.6.1.4.1.2356.11.1.3.36.1.1.43
lcsStatusWlanInterpointsAccesspointListEntryRemoteStatus OBJECT-TYPE
    SYNTAX     INTEGER {
                  eUnknown (0),
                  eNotOk (1),
                  eOk (2)
            }
    MAX-ACCESS read-only
    STATUS     current
    DESCRIPTION
            "-- empty --"
    ::= { lcsStatusWlanInterpointsAccesspointListEntry 43 }

-- {COLUMN} 1.3.6.1.4.1.2356.11.1.3.36.1.1.44
lcsStatusWlanInterpointsAccesspointListEntryWpa2KeyManagement OBJECT-TYPE
    SYNTAX     INTEGER {
                  eStandard (0),
                  eFastRoaming (1),
                  eSha256 (2),
                  eSha384 (3),
                  eFastRoamingSha384 (4),
                  eNone (255)
            }
    MAX-ACCESS read-only
    STATUS     current
    DESCRIPTION
            "-- empty --"
    ::= { lcsStatusWlanInterpointsAccesspointListEntry 44 }

-- {COLUMN} 1.3.6.1.4.1.2356.11.1.3.36.1.1.45
lcsStatusWlanInterpointsAccesspointListEntrySGIMask OBJECT-TYPE
    SYNTAX     BITS {
                  eNo (0),
                  e160mhz (28),
                  e80mhz (29),
                  e40mhz (30),
                  e20mhz (31)
            }
    MAX-ACCESS read-only
    STATUS     current
    DESCRIPTION
            "Bit mask of short guard interval support per-CBW"
    ::= { lcsStatusWlanInterpointsAccesspointListEntry 45 }

-- {COLUMN} 1.3.6.1.4.1.2356.11.1.3.36.1.1.46
lcsStatusWlanInterpointsAccesspointListEntryChannelBandwidths OBJECT-TYPE
    SYNTAX     BITS {
                  eT40mhz (26),
                  e80Plus80mhz (27),
                  e160mhz (28),
                  e80mhz (29),
                  e40mhz (30),
                  e20mhz (31)
            }
    MAX-ACCESS read-only
    STATUS     current
    DESCRIPTION
            "-- empty --"
    ::= { lcsStatusWlanInterpointsAccesspointListEntry 46 }

-- {COLUMN} 1.3.6.1.4.1.2356.11.1.3.36.1.1.47
lcsStatusWlanInterpointsAccesspointListEntryProtMgmtFrames OBJECT-TYPE
    SYNTAX     INTEGER {
                  eNo (0),
                  eYes (1)
            }
    MAX-ACCESS read-only
    STATUS     current
    DESCRIPTION
            "-- empty --"
    ::= { lcsStatusWlanInterpointsAccesspointListEntry 47 }

-- {COLUMN} 1.3.6.1.4.1.2356.11.1.3.36.1.1.48
lcsStatusWlanInterpointsAccesspointListEntryRxStbcHt OBJECT-TYPE
    SYNTAX     INTEGER {
                  eNone (0),
                  eOne (1),
                  eTwo (2),
                  eThree (3)
            }
    MAX-ACCESS read-only
    STATUS     current
    DESCRIPTION
            "-- empty --"
    ::= { lcsStatusWlanInterpointsAccesspointListEntry 48 }

-- {COLUMN} 1.3.6.1.4.1.2356.11.1.3.36.1.1.49
lcsStatusWlanInterpointsAccesspointListEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { lcsStatusWlanInterpointsAccesspointListEntry 49 }

-- {COLUMN} 1.3.6.1.4.1.2356.11.1.3.36.1.1.50
lcsStatusWlanInterpointsAccesspointListEntryLDPCMask OBJECT-TYPE
    SYNTAX     BITS {
                  eVht (30),
                  eHt (31)
            }
    MAX-ACCESS read-only
    STATUS     current
    DESCRIPTION
            "Bit mask of LDPC support per-PHY-Type"
    ::= { lcsStatusWlanInterpointsAccesspointListEntry 50 }

-- {COLUMN} 1.3.6.1.4.1.2356.11.1.3.36.1.1.51
lcsStatusWlanInterpointsAccesspointListEntryOperationMode OBJECT-TYPE
    SYNTAX     INTEGER {
                  eUnknown (0),
                  e11b (1),
                  e11g (2),
                  e11a (3),
                  e11n (4),
                  e11ac (5)
            }
    MAX-ACCESS read-only
    STATUS     current
    DESCRIPTION
            "-- empty --"
    ::= { lcsStatusWlanInterpointsAccesspointListEntry 51 }

-- {COLUMN} 1.3.6.1.4.1.2356.11.1.3.36.1.1.52
lcsStatusWlanInterpointsAccesspointListEntryTxChannelwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanInterpointsAccesspointListEntry 52 }

-- {COLUMN} 1.3.6.1.4.1.2356.11.1.3.36.1.1.53
lcsStatusWlanInterpointsAccesspointListEntryTxShortGi OBJECT-TYPE
    SYNTAX     INTEGER {
                  eNo (0),
                  eYes (1)
            }
    MAX-ACCESS read-only
    STATUS     current
    DESCRIPTION
            "-- empty --"
    ::= { lcsStatusWlanInterpointsAccesspointListEntry 53 }

-- {COLUMN} 1.3.6.1.4.1.2356.11.1.3.36.1.1.54
lcsStatusWlanInterpointsAccesspointListEntryRxChannelwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanInterpointsAccesspointListEntry 54 }

-- {COLUMN} 1.3.6.1.4.1.2356.11.1.3.36.1.1.55
lcsStatusWlanInterpointsAccesspointListEntryRxShortGi OBJECT-TYPE
    SYNTAX     INTEGER {
                  eNo (0),
                  eYes (1)
            }
    MAX-ACCESS read-only
    STATUS     current
    DESCRIPTION
            "-- empty --"
    ::= { lcsStatusWlanInterpointsAccesspointListEntry 55 }

-- {COLUMN} 1.3.6.1.4.1.2356.11.1.3.36.1.1.56
lcsStatusWlanInterpointsAccesspointListEntryTxMcs OBJECT-TYPE
    SYNTAX     Integer32 (0..255)
    MAX-ACCESS read-only
    STATUS     current
    DESCRIPTION
            "-- empty --"
    ::= { lcsStatusWlanInterpointsAccesspointListEntry 56 }

-- {COLUMN} 1.3.6.1.4.1.2356.11.1.3.36.1.1.57
lcsStatusWlanInterpointsAccesspointListEntryRxMcs OBJECT-TYPE
    SYNTAX     Integer32 (0..255)
    MAX-ACCESS read-only
    STATUS     current
    DESCRIPTION
            "-- empty --"
    ::= { lcsStatusWlanInterpointsAccesspointListEntry 57 }

-- {COLUMN} 1.3.6.1.4.1.2356.11.1.3.36.1.1.58
lcsStatusWlanInterpointsAccesspointListEntryWpaAuthType OBJECT-TYPE
    SYNTAX     INTEGER {
                  eNone (0),
                  ePsk (1),
                  e8021x (2),
                  eOwe (7),
                  eSae (8)
            }
    MAX-ACCESS read-only
    STATUS     current
    DESCRIPTION
            "-- empty --"
    ::= { lcsStatusWlanInterpointsAccesspointListEntry 58 }

-- {COLUMN} 1.3.6.1.4.1.2356.11.1.3.36.1.1.59
lcsStatusWlanInterpointsAccesspointListEntryQosMapping OBJECT-TYPE
    SYNTAX     INTEGER {
                  eNo (0),
                  eYes (1)
            }
    MAX-ACCESS read-only
    STATUS     current
    DESCRIPTION
            "-- empty --"
    ::= { lcsStatusWlanInterpointsAccesspointListEntry 59 }

-- {TABLE} 1.3.6.1.4.1.2356.11.1.3.36.3
lcsStatusWlanInterpointsKeyListTable OBJECT-TYPE
    SYNTAX     SEQUENCE OF LcsStatusWlanInterpointsKeyListEntry
    MAX-ACCESS not-accessible
    STATUS     current
    DESCRIPTION
            ""
    ::= { lcsStatusWlanInterpoints 3 }

-- {ROW} 1.3.6.1.4.1.2356.11.1.3.36.3.1
lcsStatusWlanInterpointsKeyListEntry OBJECT-TYPE
    SYNTAX     LcsStatusWlanInterpointsKeyListEntry
    MAX-ACCESS not-accessible
    STATUS     current
    DESCRIPTION
            ""
    INDEX {
            lcsStatusWlanInterpointsKeyListEntryIndex
          }
    ::= { lcsStatusWlanInterpointsKeyListTable 1 }

LcsStatusWlanInterpointsKeyListEntry ::= SEQUENCE {
            lcsStatusWlanInterpointsKeyListEntryIndex INTEGER,
            lcsStatusWlanInterpointsKeyListEntrySource INTEGER,
            lcsStatusWlanInterpointsKeyListEntryKeyType INTEGER,
            lcsStatusWlanInterpointsKeyListEntryKeyValue DisplayString,
            lcsStatusWlanInterpointsKeyListEntryTsc DisplayString,
            lcsStatusWlanInterpointsKeyListEntryAge Integer32,
            lcsStatusWlanInterpointsKeyListEntryIvSequenceErrors Integer32,
            lcsStatusWlanInterpointsKeyListEntryRscBe DisplayString,
            lcsStatusWlanInterpointsKeyListEntryRscBk DisplayString,
            lcsStatusWlanInterpointsKeyListEntryRscEe DisplayString,
            lcsStatusWlanInterpointsKeyListEntryRscCl DisplayString,
            lcsStatusWlanInterpointsKeyListEntryRscVi DisplayString,
            lcsStatusWlanInterpointsKeyListEntryRscVo DisplayString,
            lcsStatusWlanInterpointsKeyListEntryRscNc DisplayString,
            lcsStatusWlanInterpointsKeyListEntryRscMgmt DisplayString
    }

-- {COLUMN} 1.3.6.1.4.1.2356.11.1.3.36.3.1.1
lcsStatusWlanInterpointsKeyListEntryIndex OBJECT-TYPE
    SYNTAX     INTEGER {
                  eP2p11 (1),
                  eP2p12 (2),
                  eP2p13 (3),
                  eP2p14 (4),
                  eP2p15 (5),
                  eP2p16 (6),
                  eP2p21 (7),
                  eP2p22 (8),
                  eP2p23 (9),
                  eP2p24 (10),
                  eP2p25 (11),
                  eP2p26 (12),
                  eP2p17 (32),
                  eP2p18 (33),
                  eP2p19 (34),
                  eP2p110 (35),
                  eP2p111 (36),
                  eP2p112 (37),
                  eP2p113 (38),
                  eP2p114 (39),
                  eP2p115 (40),
                  eP2p116 (41),
                  eP2p27 (64),
                  eP2p28 (65),
                  eP2p29 (66),
                  eP2p210 (67),
                  eP2p211 (68),
                  eP2p212 (69),
                  eP2p213 (70),
                  eP2p214 (71),
                  eP2p215 (72),
                  eP2p216 (73)
            }
    MAX-ACCESS read-only
    STATUS     current
    DESCRIPTION
            ""
    ::= { lcsStatusWlanInterpointsKeyListEntry 1 }

-- {COLUMN} 1.3.6.1.4.1.2356.11.1.3.36.3.1.2
lcsStatusWlanInterpointsKeyListEntrySource OBJECT-TYPE
    SYNTAX     INTEGER {
                  eNone (0),
                  eStatic (1),
                  eDynamic (2)
            }
    MAX-ACCESS read-only
    STATUS     current
    DESCRIPTION
            ""
    ::= { lcsStatusWlanInterpointsKeyListEntry 2 }

-- {COLUMN} 1.3.6.1.4.1.2356.11.1.3.36.3.1.3
lcsStatusWlanInterpointsKeyListEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eAesCcmp256 (67),
                  eBip (68),
                  eBipCmac256 (69),
                  eAesGcmp128 (70),
                  eAesGcmp256 (71),
                  eBipGmac128 (72),
                  eBipGmac256 (73)
            }
    MAX-ACCESS read-only
    STATUS     current
    DESCRIPTION
            ""
    ::= { lcsStatusWlanInterpointsKeyListEntry 3 }

-- {COLUMN} 1.3.6.1.4.1.2356.11.1.3.36.3.1.4
lcsStatusWlanInterpointsKeyListEntryKeyValue OBJECT-TYPE
    SYNTAX     DisplayString (SIZE(0..255))
    MAX-ACCESS read-only
    STATUS     current
    DESCRIPTION
            ""
    ::= { lcsStatusWlanInterpointsKeyListEntry 4 }

-- {COLUMN} 1.3.6.1.4.1.2356.11.1.3.36.3.1.5
lcsStatusWlanInterpointsKeyListEntryTsc OBJECT-TYPE
    SYNTAX     DisplayString (SIZE(0..255))
    MAX-ACCESS read-only
    STATUS     current
    DESCRIPTION
            ""
    ::= { lcsStatusWlanInterpointsKeyListEntry 5 }

-- {COLUMN} 1.3.6.1.4.1.2356.11.1.3.36.3.1.7
lcsStatusWlanInterpointsKeyListEntryAge OBJECT-TYPE
    SYNTAX     Integer32 (0..2147483647)
    MAX-ACCESS read-only
    STATUS     current
    DESCRIPTION
            ""
    ::= { lcsStatusWlanInterpointsKeyListEntry 7 }

-- {COLUMN} 1.3.6.1.4.1.2356.11.1.3.36.3.1.8
lcsStatusWlanInterpointsKeyListEntryIvSequenceErrors OBJECT-TYPE
    SYNTAX     Integer32 (0..2147483647)
    MAX-ACCESS read-only
    STATUS     current
    DESCRIPTION
            ""
    ::= { lcsStatusWlanInterpointsKeyListEntry 8 }

-- {COLUMN} 1.3.6.1.4.1.2356.11.1.3.36.3.1.16
lcsStatusWlanInterpointsKeyListEntryRscBe OBJECT-TYPE
    SYNTAX     DisplayString (SIZE(0..255))
    MAX-ACCESS read-only
    STATUS     current
    DESCRIPTION
            ""
    ::= { lcsStatusWlanInterpointsKeyListEntry 16 }

-- {COLUMN} 1.3.6.1.4.1.2356.11.1.3.36.3.1.17
lcsStatusWlanInterpointsKeyListEntryRscBk OBJECT-TYPE
    SYNTAX     DisplayString (SIZE(0..255))
    MAX-ACCESS read-only
    STATUS     current
    DESCRIPTION
            ""
    ::= { lcsStatusWlanInterpointsKeyListEntry 17 }

-- {COLUMN} 1.3.6.1.4.1.2356.11.1.3.36.3.1.19
lcsStatusWlanInterpointsKeyListEntryRscEe OBJECT-TYPE
    SYNTAX     DisplayString (SIZE(0..255))
    MAX-ACCESS read-only
    STATUS     current
    DESCRIPTION
            ""
    ::= { lcsStatusWlanInterpointsKeyListEntry 19 }

-- {COLUMN} 1.3.6.1.4.1.2356.11.1.3.36.3.1.20
lcsStatusWlanInterpointsKeyListEntryRscCl OBJECT-TYPE
    SYNTAX     DisplayString (SIZE(0..255))
    MAX-ACCESS read-only
    STATUS     current
    DESCRIPTION
            ""
    ::= { lcsStatusWlanInterpointsKeyListEntry 20 }

-- {COLUMN} 1.3.6.1.4.1.2356.11.1.3.36.3.1.21
lcsStatusWlanInterpointsKeyListEntryRscVi OBJECT-TYPE
    SYNTAX     DisplayString (SIZE(0..255))
    MAX-ACCESS read-only
    STATUS     current
    DESCRIPTION
            ""
    ::= { lcsStatusWlanInterpointsKeyListEntry 21 }

-- {COLUMN} 1.3.6.1.4.1.2356.11.1.3.36.3.1.22
lcsStatusWlanInterpointsKeyListEntryRscVo OBJECT-TYPE
    SYNTAX     DisplayString (SIZE(0..255))
    MAX-ACCESS read-only
    STATUS     current
    DESCRIPTION
            ""
    ::= { lcsStatusWlanInterpointsKeyListEntry 22 }

-- {COLUMN} 1.3.6.1.4.1.2356.11.1.3.36.3.1.23
lcsStatusWlanInterpointsKeyListEntryRscNc OBJECT-TYPE
    SYNTAX     DisplayString (SIZE(0..255))
    MAX-ACCESS read-only
    STATUS     current
    DESCRIPTION
            ""
    ::= { lcsStatusWlanInterpointsKeyListEntry 23 }

-- {COLUMN} 1.3.6.1.4.1.2356.11.1.3.36.3.1.24
lcsStatusWlanInterpointsKeyListEntryRscMgmt OBJECT-TYPE
    SYNTAX     DisplayString (SIZE(0..255))
    MAX-ACCESS read-only
    STATUS     current
    DESCRIPTION
            "-- empty --"
    ::= { lcsStatusWlanInterpointsKeyListEntry 24 }

-- {SCALAR} 1.3.6.1.4.1.2356.11.1.3.37
lcsStatusWlanDeassocStation OBJECT-TYPE
    SYNTAX     DisplayString
    MAX-ACCESS read-write
    STATUS     current
    DESCRIPTION
            ""
    ::= { lcsStatusWlan 37 }

-- {TABLE} 1.3.6.1.4.1.2356.11.1.3.38
lcsStatusWlanIappTableTable OBJECT-TYPE
    SYNTAX     SEQUENCE OF LcsStatusWlanIappTableEntry
    MAX-ACCESS not-accessible
    STATUS     current
    DESCRIPTION
            ""
    ::= { lcsStatusWlan 38 }

-- {ROW} 1.3.6.1.4.1.2356.11.1.3.38.1
lcsStatusWlanIappTableEntry OBJECT-TYPE
    SYNTAX     LcsStatusWlanIappTableEntry
    MAX-ACCESS not-accessible
    STATUS     current
    DESCRIPTION
            ""
    INDEX {
            lcsStatusWlanIappTableEntryBssid,
            lcsStatusWlanIappTableEntryIpAddress,
            lcsStatusWlanIappTableEntryNetworkName
          }
    ::= { lcsStatusWlanIappTableTable 1 }

LcsStatusWlanIappTableEntry ::= SEQUENCE {
            lcsStatusWlanIappTableEntryIpAddress IpAddress,
            lcsStatusWlanIappTableEntryBssid MacAddress,
            lcsStatusWlanIappTableEntryTimer Integer32,
            lcsStatusWlanIappTableEntryTimeout Integer32,
            lcsStatusWlanIappTableEntryCapabilities BITS,
            lcsStatusWlanIappTableEntryNetworkName DisplayString,
            lcsStatusWlanIappTableEntrySsid DisplayString,
            lcsStatusWlanIappTableEntryRadioChannel Integer32,
            lcsStatusWlanIappTableEntryDomainId DisplayString,
            lcsStatusWlanIappTableEntryLoad DisplayString,
            lcsStatusWlanIappTableEntryNeighbor INTEGER,
            lcsStatusWlanIappTableEntryPhyType INTEGER
    }

-- {COLUMN} 1.3.6.1.4.1.2356.11.1.3.38.1.1
lcsStatusWlanIappTableEntryIpAddress OBJECT-TYPE
    SYNTAX     IpAddress
    MAX-ACCESS read-only
    STATUS     current
    DESCRIPTION
            ""
    ::= { lcsStatusWlanIappTableEntry 1 }

-- {COLUMN} 1.3.6.1.4.1.2356.11.1.3.38.1.2
lcsStatusWlanIappTableEntryBssid OBJECT-TYPE
    SYNTAX     MacAddress
    MAX-ACCESS read-only
    STATUS     current
    DESCRIPTION
            ""
    ::= { lcsStatusWlanIappTableEntry 2 }

-- {COLUMN} 1.3.6.1.4.1.2356.11.1.3.38.1.3
lcsStatusWlanIappTableEntryTimer OBJECT-TYPE
    SYNTAX     Integer32 (0..65535)
    MAX-ACCESS read-only
    STATUS     current
    DESCRIPTION
            ""
    ::= { lcsStatusWlanIappTableEntry 3 }

-- {COLUMN} 1.3.6.1.4.1.2356.11.1.3.38.1.4
lcsStatusWlanIappTableEntryTimeout OBJECT-TYPE
    SYNTAX     Integer32 (0..65535)
    MAX-ACCESS read-only
    STATUS     current
    DESCRIPTION
            ""
    ::= { lcsStatusWlanIappTableEntry 4 }

-- {COLUMN} 1.3.6.1.4.1.2356.11.1.3.38.1.5
lcsStatusWlanIappTableEntryCapabilities OBJECT-TYPE
    SYNTAX     BITS {
                  eForward (1),
                  ePrivacy (2)
            }
    MAX-ACCESS read-only
    STATUS     current
    DESCRIPTION
            ""
    ::= { lcsStatusWlanIappTableEntry 5 }

-- {COLUMN} 1.3.6.1.4.1.2356.11.1.3.38.1.6
lcsStatusWlanIappTableEntryNetworkName OBJECT-TYPE
    SYNTAX     DisplayString (SIZE(0..16))
    MAX-ACCESS read-only
    STATUS     current
    DESCRIPTION
            ""
    ::= { lcsStatusWlanIappTableEntry 6 }

-- {COLUMN} 1.3.6.1.4.1.2356.11.1.3.38.1.7
lcsStatusWlanIappTableEntrySsid OBJECT-TYPE
    SYNTAX     DisplayString (SIZE(0..32))
    MAX-ACCESS read-only
    STATUS     current
    DESCRIPTION
            "-- empty --"
    ::= { lcsStatusWlanIappTableEntry 7 }

-- {COLUMN} 1.3.6.1.4.1.2356.11.1.3.38.1.8
lcsStatusWlanIappTableEntryRadioChannel OBJECT-TYPE
    SYNTAX     Integer32 (0..65535)
    MAX-ACCESS read-only
    STATUS     current
    DESCRIPTION
            "-- empty --"
    ::= { lcsStatusWlanIappTableEntry 8 }

-- {COLUMN} 1.3.6.1.4.1.2356.11.1.3.38.1.9
lcsStatusWlanIappTableEntryDomainId OBJECT-TYPE
    SYNTAX     DisplayString (SIZE(0..255))
    MAX-ACCESS read-only
    STATUS     current
    DESCRIPTION
            "-- empty --"
    ::= { lcsStatusWlanIappTableEntry 9 }

-- {COLUMN} 1.3.6.1.4.1.2356.11.1.3.38.1.10
lcsStatusWlanIappTableEntryLoad OBJECT-TYPE
    SYNTAX     DisplayString (SIZE(0..255))
    MAX-ACCESS read-only
    STATUS     current
    DESCRIPTION
            "-- empty --"
    ::= { lcsStatusWlanIappTableEntry 10 }

-- {COLUMN} 1.3.6.1.4.1.2356.11.1.3.38.1.11
lcsStatusWlanIappTableEntryNeighbor OBJECT-TYPE
    SYNTAX     INTEGER {
                  eNo (0),
                  eYes (1)
            }
    MAX-ACCESS read-only
    STATUS     current
    DESCRIPTION
            "-- empty --"
    ::= { lcsStatusWlanIappTableEntry 11 }

-- {COLUMN} 1.3.6.1.4.1.2356.11.1.3.38.1.12
lcsStatusWlanIappTableEntryPhyType OBJECT-TYPE
    SYNTAX     INTEGER {
                  eProprietary (0),
                  eFhss (1),
                  eDsss (2),
                  eInfrared (3),
                  eOfdm (4),
                  eHrDsss (5),
                  eErp (6),
                  eHt (7),
                  eVht (9),
                  eTvht (10),
                  eS1g (11),
                  eCdmg (12),
                  eCmmg (13),
                  eHe (14),
                  ePbcc (254)
            }
    MAX-ACCESS read-only
    STATUS     current
    DESCRIPTION
            "-- empty --"
    ::= { lcsStatusWlanIappTableEntry 12 }

-- {TABLE} 1.3.6.1.4.1.2356.11.1.3.40
lcsStatusWlanForeignStationsTable OBJECT-TYPE
    SYNTAX     SEQUENCE OF LcsStatusWlanForeignStationsEntry
    MAX-ACCESS not-accessible
    STATUS     current
    DESCRIPTION
            ""
    ::= { lcsStatusWlan 40 }

-- {ROW} 1.3.6.1.4.1.2356.11.1.3.40.1
lcsStatusWlanForeignStationsEntry OBJECT-TYPE
    SYNTAX     LcsStatusWlanForeignStationsEntry
    MAX-ACCESS not-accessible
    STATUS     current
    DESCRIPTION
            ""
    INDEX {
            lcsStatusWlanForeignStationsEntryMacAddress
          }
    ::= { lcsStatusWlanForeignStationsTable 1 }

LcsStatusWlanForeignStationsEntry ::= SEQUENCE {
            lcsStatusWlanForeignStationsEntryMacAddress MacAddress,
            lcsStatusWlanForeignStationsEntryBssid MacAddress,
            lcsStatusWlanForeignStationsEntryNetworkName DisplayString
    }

-- {COLUMN} 1.3.6.1.4.1.2356.11.1.3.40.1.1
lcsStatusWlanForeignStationsEntryMacAddress OBJECT-TYPE
    SYNTAX     MacAddress
    MAX-ACCESS read-only
    STATUS     current
    DESCRIPTION
            ""
    ::= { lcsStatusWlanForeignStationsEntry 1 }

-- {COLUMN} 1.3.6.1.4.1.2356.11.1.3.40.1.2
lcsStatusWlanForeignStationsEntryBssid OBJECT-TYPE
    SYNTAX     MacAddress
    MAX-ACCESS read-only
    STATUS     current
    DESCRIPTION
            ""
    ::= { lcsStatusWlanForeignStationsEntry 2 }

-- {COLUMN} 1.3.6.1.4.1.2356.11.1.3.40.1.3
lcsStatusWlanForeignStationsEntryNetworkName OBJECT-TYPE
    SYNTAX     DisplayString (SIZE(0..255))
    MAX-ACCESS read-only
    STATUS     current
    DESCRIPTION
            ""
    ::= { lcsStatusWlanForeignStationsEntry 3 }

-- {TABLE} 1.3.6.1.4.1.2356.11.1.3.41
lcsStatusWlanGroupEncryptionKeysTable OBJECT-TYPE
    SYNTAX     SEQUENCE OF LcsStatusWlanGroupEncryptionKeysEntry
    MAX-ACCESS not-accessible
    STATUS     current
    DESCRIPTION
            ""
    ::= { lcsStatusWlan 41 }

-- {ROW} 1.3.6.1.4.1.2356.11.1.3.41.1
lcsStatusWlanGroupEncryptionKeysEntry OBJECT-TYPE
    SYNTAX     LcsStatusWlanGroupEncryptionKeysEntry
    MAX-ACCESS not-accessible
    STATUS     current
    DESCRIPTION
            ""
    INDEX {
            lcsStatusWlanGroupEncryptionKeysEntryIndex
          }
    ::= { lcsStatusWlanGroupEncryptionKeysTable 1 }

LcsStatusWlanGroupEncryptionKeysEntry ::= SEQUENCE {
            lcsStatusWlanGroupEncryptionKeysEntryIndex DisplayString,
            lcsStatusWlanGroupEncryptionKeysEntrySource INTEGER,
            lcsStatusWlanGroupEncryptionKeysEntryKeyType INTEGER,
            lcsStatusWlanGroupEncryptionKeysEntryKeyValue DisplayString,
            lcsStatusWlanGroupEncryptionKeysEntryTsc DisplayString,
            lcsStatusWlanGroupEncryptionKeysEntryAge Integer32,
            lcsStatusWlanGroupEncryptionKeysEntryIvSequenceErrors Integer32,
            lcsStatusWlanGroupEncryptionKeysEntryRscBe DisplayString,
            lcsStatusWlanGroupEncryptionKeysEntryRscBk DisplayString,
            lcsStatusWlanGroupEncryptionKeysEntryRscEe DisplayString,
            lcsStatusWlanGroupEncryptionKeysEntryRscCl DisplayString,
            lcsStatusWlanGroupEncryptionKeysEntryRscVi DisplayString,
            lcsStatusWlanGroupEncryptionKeysEntryRscVo DisplayString,
            lcsStatusWlanGroupEncryptionKeysEntryRscNc DisplayString,
            lcsStatusWlanGroupEncryptionKeysEntryRscMgmt DisplayString
    }

-- {COLUMN} 1.3.6.1.4.1.2356.11.1.3.41.1.1
lcsStatusWlanGroupEncryptionKeysEntryIndex OBJECT-TYPE
    SYNTAX     DisplayString (SIZE(0..255))
    MAX-ACCESS read-only
    STATUS     current
    DESCRIPTION
            ""
    ::= { lcsStatusWlanGroupEncryptionKeysEntry 1 }

-- {COLUMN} 1.3.6.1.4.1.2356.11.1.3.41.1.2
lcsStatusWlanGroupEncryptionKeysEntrySource OBJECT-TYPE
    SYNTAX     INTEGER {
                  eNone (0),
                  eStatic (1),
                  eDynamic (2)
            }
    MAX-ACCESS read-only
    STATUS     current
    DESCRIPTION
            ""
    ::= { lcsStatusWlanGroupEncryptionKeysEntry 2 }

-- {COLUMN} 1.3.6.1.4.1.2356.11.1.3.41.1.3
lcsStatusWlanGroupEncryptionKeysEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eAesCcmp256 (67),
                  eBip (68),
                  eBipCmac256 (69),
                  eAesGcmp128 (70),
                  eAesGcmp256 (71),
                  eBipGmac128 (72),
                  eBipGmac256 (73)
            }
    MAX-ACCESS read-only
    STATUS     current
    DESCRIPTION
            ""
    ::= { lcsStatusWlanGroupEncryptionKeysEntry 3 }

-- {COLUMN} 1.3.6.1.4.1.2356.11.1.3.41.1.4
lcsStatusWlanGroupEncryptionKeysEntryKeyValue OBJECT-TYPE
    SYNTAX     DisplayString (SIZE(0..255))
    MAX-ACCESS read-only
    STATUS     current
    DESCRIPTION
            ""
    ::= { lcsStatusWlanGroupEncryptionKeysEntry 4 }

-- {COLUMN} 1.3.6.1.4.1.2356.11.1.3.41.1.5
lcsStatusWlanGroupEncryptionKeysEntryTsc OBJECT-TYPE
    SYNTAX     DisplayString (SIZE(0..255))
    MAX-ACCESS read-only
    STATUS     current
    DESCRIPTION
            ""
    ::= { lcsStatusWlanGroupEncryptionKeysEntry 5 }

-- {COLUMN} 1.3.6.1.4.1.2356.11.1.3.41.1.7
lcsStatusWlanGroupEncryptionKeysEntryAge OBJECT-TYPE
    SYNTAX     Integer32 (0..2147483647)
    MAX-ACCESS read-only
    STATUS     current
    DESCRIPTION
            ""
    ::= { lcsStatusWlanGroupEncryptionKeysEntry 7 }

-- {COLUMN} 1.3.6.1.4.1.2356.11.1.3.41.1.8
lcsStatusWlanGroupEncryptionKeysEntryIvSequenceErrors OBJECT-TYPE
    SYNTAX     Integer32 (0..2147483647)
    MAX-ACCESS read-only
    STATUS     current
    DESCRIPTION
            ""
    ::= { lcsStatusWlanGroupEncryptionKeysEntry 8 }

-- {COLUMN} 1.3.6.1.4.1.2356.11.1.3.41.1.16
lcsStatusWlanGroupEncryptionKeysEntryRscBe OBJECT-TYPE
    SYNTAX     DisplayString (SIZE(0..255))
    MAX-ACCESS read-only
    STATUS     current
    DESCRIPTION
            ""
    ::= { lcsStatusWlanGroupEncryptionKeysEntry 16 }

-- {COLUMN} 1.3.6.1.4.1.2356.11.1.3.41.1.17
lcsStatusWlanGroupEncryptionKeysEntryRscBk OBJECT-TYPE
    SYNTAX     DisplayString (SIZE(0..255))
    MAX-ACCESS read-only
    STATUS     current
    DESCRIPTION
            ""
    ::= { lcsStatusWlanGroupEncryptionKeysEntry 17 }

-- {COLUMN} 1.3.6.1.4.1.2356.11.1.3.41.1.19
lcsStatusWlanGroupEncryptionKeysEntryRscEe OBJECT-TYPE
    SYNTAX     DisplayString (SIZE(0..255))
    MAX-ACCESS read-only
    STATUS     current
    DESCRIPTION
            ""
    ::= { lcsStatusWlanGroupEncryptionKeysEntry 19 }

-- {COLUMN} 1.3.6.1.4.1.2356.11.1.3.41.1.20
lcsStatusWlanGroupEncryptionKeysEntryRscCl OBJECT-TYPE
    SYNTAX     DisplayString (SIZE(0..255))
    MAX-ACCESS read-only
    STATUS     current
    DESCRIPTION
            ""
    ::= { lcsStatusWlanGroupEncryptionKeysEntry 20 }

-- {COLUMN} 1.3.6.1.4.1.2356.11.1.3.41.1.21
lcsStatusWlanGroupEncryptionKeysEntryRscVi OBJECT-TYPE
    SYNTAX     DisplayString (SIZE(0..255))
    MAX-ACCESS read-only
    STATUS     current
    DESCRIPTION
            ""
    ::= { lcsStatusWlanGroupEncryptionKeysEntry 21 }

-- {COLUMN} 1.3.6.1.4.1.2356.11.1.3.41.1.22
lcsStatusWlanGroupEncryptionKeysEntryRscVo OBJECT-TYPE
    SYNTAX     DisplayString (SIZE(0..255))
    MAX-ACCESS read-only
    STATUS     current
    DESCRIPTION
            ""
    ::= { lcsStatusWlanGroupEncryptionKeysEntry 22 }

-- {COLUMN} 1.3.6.1.4.1.2356.11.1.3.41.1.23
lcsStatusWlanGroupEncryptionKeysEntryRscNc OBJECT-TYPE
    SYNTAX     DisplayString (SIZE(0..255))
    MAX-ACCESS read-only
    STATUS     current
    DESCRIPTION
            ""
    ::= { lcsStatusWlanGroupEncryptionKeysEntry 23 }

-- {COLUMN} 1.3.6.1.4.1.2356.11.1.3.41.1.24
lcsStatusWlanGroupEncryptionKeysEntryRscMgmt OBJECT-TYPE
    SYNTAX     DisplayString (SIZE(0..255))
    MAX-ACCESS read-only
    STATUS     current
    DESCRIPTION
            "-- empty --"
    ::= { lcsStatusWlanGroupEncryptionKeysEntry 24 }

-- {TABLE} 1.3.6.1.4.1.2356.11.1.3.42
lcsStatusWlanChannelScanResultsTable OBJECT-TYPE
    SYNTAX     SEQUENCE OF LcsStatusWlanChannelScanResultsEntry
    MAX-ACCESS not-accessible
    STATUS     current
    DESCRIPTION
            ""
    ::= { lcsStatusWlan 42 }

-- {ROW} 1.3.6.1.4.1.2356.11.1.3.42.1
lcsStatusWlanChannelScanResultsEntry OBJECT-TYPE
    SYNTAX     LcsStatusWlanChannelScanResultsEntry
    MAX-ACCESS not-accessible
    STATUS     current
    DESCRIPTION
            ""
    INDEX {
            lcsStatusWlanChannelScanResultsEntryRadioBand,
            lcsStatusWlanChannelScanResultsEntryRadioChannel,
            lcsStatusWlanChannelScanResultsEntryInterface
          }
    ::= { lcsStatusWlanChannelScanResultsTable 1 }

LcsStatusWlanChannelScanResultsEntry ::= SEQUENCE {
            lcsStatusWlanChannelScanResultsEntryRadioChannel Integer32,
            lcsStatusWlanChannelScanResultsEntryInterface INTEGER,
            lcsStatusWlanChannelScanResultsEntryScanned INTEGER,
            lcsStatusWlanChannelScanResultsEntryNoiseLevel Integer32,
            lcsStatusWlanChannelScanResultsEntryNumBss Integer32,
            lcsStatusWlanChannelScanResultsEntryRadarDetected INTEGER,
            lcsStatusWlanChannelScanResultsEntry108mbpsMode INTEGER,
            lcsStatusWlanChannelScanResultsEntryRadioBand INTEGER,
            lcsStatusWlanChannelScanResultsEntryPulseCount Integer32,
            lcsStatusWlanChannelScanResultsEntryRemTime Integer32,
            lcsStatusWlanChannelScanResultsEntryDfsState INTEGER,
            lcsStatusWlanChannelScanResultsEntryRadarPattern DisplayString,
            lcsStatusWlanChannelScanResultsEntryDfsScheme INTEGER,
            lcsStatusWlanChannelScanResultsEntryUsage BITS,
            lcsStatusWlanChannelScanResultsEntryScanAge Integer32,
            lcsStatusWlanChannelScanResultsEntryNonHtBss INTEGER,
            lcsStatusWlanChannelScanResultsEntryNonHtBssAge Integer32,
            lcsStatusWlanChannelScanResultsEntry40mIntolerantBss INTEGER,
            lcsStatusWlanChannelScanResultsEntry40mIntolerantBssAge Integer32,
            lcsStatusWlanChannelScanResultsEntry40mIntolerantBssReported INTEGER,
            lcsStatusWlanChannelScanResultsEntry40mIntolerantBssReportedAge Integer32,
            lcsStatusWlanChannelScanResultsEntryChannelBandwidth INTEGER,
            lcsStatusWlanChannelScanResultsEntryAdaptiveRfTimeout Integer32,
            lcsStatusWlanChannelScanResultsEntryHasNeighbors INTEGER
    }

-- {COLUMN} 1.3.6.1.4.1.2356.11.1.3.42.1.1
lcsStatusWlanChannelScanResultsEntryRadioChannel OBJECT-TYPE
    SYNTAX     Integer32 (0..255)
    MAX-ACCESS read-only
    STATUS     current
    DESCRIPTION
            ""
    ::= { lcsStatusWlanChannelScanResultsEntry 1 }

-- {COLUMN} 1.3.6.1.4.1.2356.11.1.3.42.1.2
lcsStatusWlanChannelScanResultsEntryInterface OBJECT-TYPE
    SYNTAX     INTEGER {
                  eWlan1 (0),
                  eWlan2 (1),
                  eWlan3 (2),
                  eWlan4 (3)
            }
    MAX-ACCESS read-only
    STATUS     current
    DESCRIPTION
            ""
    ::= { lcsStatusWlanChannelScanResultsEntry 2 }

-- {COLUMN} 1.3.6.1.4.1.2356.11.1.3.42.1.3
lcsStatusWlanChannelScanResultsEntryScanned OBJECT-TYPE
    SYNTAX     INTEGER {
                  eNo (0),
                  eYes (1)
            }
    MAX-ACCESS read-only
    STATUS     current
    DESCRIPTION
            ""
    ::= { lcsStatusWlanChannelScanResultsEntry 3 }

-- {COLUMN} 1.3.6.1.4.1.2356.11.1.3.42.1.4
lcsStatusWlanChannelScanResultsEntryNoiseLevel OBJECT-TYPE
    SYNTAX     Integer32 (-128..127)
    MAX-ACCESS read-only
    STATUS     current
    DESCRIPTION
            ""
    ::= { lcsStatusWlanChannelScanResultsEntry 4 }

-- {COLUMN} 1.3.6.1.4.1.2356.11.1.3.42.1.6
lcsStatusWlanChannelScanResultsEntryNumBss OBJECT-TYPE
    SYNTAX     Integer32 (0..65535)
    MAX-ACCESS read-only
    STATUS     current
    DESCRIPTION
            ""
    ::= { lcsStatusWlanChannelScanResultsEntry 6 }

-- {COLUMN} 1.3.6.1.4.1.2356.11.1.3.42.1.7
lcsStatusWlanChannelScanResultsEntryRadarDetected OBJECT-TYPE
    SYNTAX     INTEGER {
                  eNo (0),
                  eYes (1)
            }
    MAX-ACCESS read-only
    STATUS     current
    DESCRIPTION
            ""
    ::= { lcsStatusWlanChannelScanResultsEntry 7 }

-- {COLUMN} 1.3.6.1.4.1.2356.11.1.3.42.1.8
lcsStatusWlanChannelScanResultsEntry108mbpsMode OBJECT-TYPE
    SYNTAX     INTEGER {
                  eNo (0),
                  eYes (1)
            }
    MAX-ACCESS read-only
    STATUS     current
    DESCRIPTION
            ""
    ::= { lcsStatusWlanChannelScanResultsEntry 8 }

-- {COLUMN} 1.3.6.1.4.1.2356.11.1.3.42.1.9
lcsStatusWlanChannelScanResultsEntryRadioBand OBJECT-TYPE
    SYNTAX     INTEGER {
                  eUnknown (0),
                  e24ghz (1),
                  e5ghz (2),
                  e24ghz5ghz (3)
            }
    MAX-ACCESS read-only
    STATUS     current
    DESCRIPTION
            ""
    ::= { lcsStatusWlanChannelScanResultsEntry 9 }

-- {COLUMN} 1.3.6.1.4.1.2356.11.1.3.42.1.10
lcsStatusWlanChannelScanResultsEntryPulseCount OBJECT-TYPE
    SYNTAX     Integer32 (0..2147483647)
    MAX-ACCESS read-only
    STATUS     current
    DESCRIPTION
            ""
    ::= { lcsStatusWlanChannelScanResultsEntry 10 }

-- {COLUMN} 1.3.6.1.4.1.2356.11.1.3.42.1.11
lcsStatusWlanChannelScanResultsEntryRemTime OBJECT-TYPE
    SYNTAX     Integer32 (0..2147483647)
    MAX-ACCESS read-only
    STATUS     current
    DESCRIPTION
            ""
    ::= { lcsStatusWlanChannelScanResultsEntry 11 }

-- {COLUMN} 1.3.6.1.4.1.2356.11.1.3.42.1.12
lcsStatusWlanChannelScanResultsEntryDfsState OBJECT-TYPE
    SYNTAX     INTEGER {
                  eClear (0),
                  eBlocked (1),
                  eUnknown (2)
            }
    MAX-ACCESS read-only
    STATUS     current
    DESCRIPTION
            ""
    ::= { lcsStatusWlanChannelScanResultsEntry 12 }

-- {COLUMN} 1.3.6.1.4.1.2356.11.1.3.42.1.13
lcsStatusWlanChannelScanResultsEntryRadarPattern OBJECT-TYPE
    SYNTAX     DisplayString (SIZE(0..40))
    MAX-ACCESS read-only
    STATUS     current
    DESCRIPTION
            ""
    ::= { lcsStatusWlanChannelScanResultsEntry 13 }

-- {COLUMN} 1.3.6.1.4.1.2356.11.1.3.42.1.14
lcsStatusWlanChannelScanResultsEntryDfsScheme OBJECT-TYPE
    SYNTAX     INTEGER {
                  eNone (0),
                  eEn301893V12 (1),
                  eEn301893V13 (2),
                  eEn302502 (4),
                  eFcc (8),
                  eJapan (16),
                  eEn301893V15 (32),
                  eEn301893V16 (64),
                  eEn301893V17 (256),
                  eEn301893V21 (512)
            }
    MAX-ACCESS read-only
    STATUS     current
    DESCRIPTION
            ""
    ::= { lcsStatusWlanChannelScanResultsEntry 14 }

-- {COLUMN} 1.3.6.1.4.1.2356.11.1.3.42.1.15
lcsStatusWlanChannelScanResultsEntryUsage OBJECT-TYPE
    SYNTAX     BITS {
                  eNone (0),
                  eEnvironmentScan (28),
                  eOverlapScan (29),
                  eBackgroundScan (30),
                  eOperation (31)
            }
    MAX-ACCESS read-only
    STATUS     current
    DESCRIPTION
            "-- empty --"
    ::= { lcsStatusWlanChannelScanResultsEntry 15 }

-- {COLUMN} 1.3.6.1.4.1.2356.11.1.3.42.1.16
lcsStatusWlanChannelScanResultsEntryScanAge OBJECT-TYPE
    SYNTAX     Integer32 (0..2147483647)
    MAX-ACCESS read-only
    STATUS     current
    DESCRIPTION
            "-- empty --"
    ::= { lcsStatusWlanChannelScanResultsEntry 16 }

-- {COLUMN} 1.3.6.1.4.1.2356.11.1.3.42.1.17
lcsStatusWlanChannelScanResultsEntryNonHtBss OBJECT-TYPE
    SYNTAX     INTEGER {
                  eNo (0),
                  eYes (1)
            }
    MAX-ACCESS read-only
    STATUS     current
    DESCRIPTION
            "-- empty --"
    ::= { lcsStatusWlanChannelScanResultsEntry 17 }

-- {COLUMN} 1.3.6.1.4.1.2356.11.1.3.42.1.18
lcsStatusWlanChannelScanResultsEntryNonHtBssAge OBJECT-TYPE
    SYNTAX     Integer32 (0..2147483647)
    MAX-ACCESS read-only
    STATUS     current
    DESCRIPTION
            "-- empty --"
    ::= { lcsStatusWlanChannelScanResultsEntry 18 }

-- {COLUMN} 1.3.6.1.4.1.2356.11.1.3.42.1.19
lcsStatusWlanChannelScanResultsEntry40mIntolerantBss OBJECT-TYPE
    SYNTAX     INTEGER {
                  eNo (0),
                  eYes (1)
            }
    MAX-ACCESS read-only
    STATUS     current
    DESCRIPTION
            "-- empty --"
    ::= { lcsStatusWlanChannelScanResultsEntry 19 }

-- {COLUMN} 1.3.6.1.4.1.2356.11.1.3.42.1.20
lcsStatusWlanChannelScanResultsEntry40mIntolerantBssAge OBJECT-TYPE
    SYNTAX     Integer32 (0..2147483647)
    MAX-ACCESS read-only
    STATUS     current
    DESCRIPTION
            "-- empty --"
    ::= { lcsStatusWlanChannelScanResultsEntry 20 }

-- {COLUMN} 1.3.6.1.4.1.2356.11.1.3.42.1.21
lcsStatusWlanChannelScanResultsEntry40mIntolerantBssReported OBJECT-TYPE
    SYNTAX     INTEGER {
                  eNo (0),
                  eYes (1)
            }
    MAX-ACCESS read-only
    STATUS     current
    DESCRIPTION
            "-- empty --"
    ::= { lcsStatusWlanChannelScanResultsEntry 21 }

-- {COLUMN} 1.3.6.1.4.1.2356.11.1.3.42.1.22
lcsStatusWlanChannelScanResultsEntry40mIntolerantBssReportedAge OBJECT-TYPE
    SYNTAX     Integer32 (0..2147483647)
    MAX-ACCESS read-only
    STATUS     current
    DESCRIPTION
            "-- empty --"
    ::= { lcsStatusWlanChannelScanResultsEntry 22 }

-- {COLUMN} 1.3.6.1.4.1.2356.11.1.3.42.1.23
lcsStatusWlanChannelScanResultsEntryChannelBandwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanChannelScanResultsEntry 23 }

-- {COLUMN} 1.3.6.1.4.1.2356.11.1.3.42.1.24
lcsStatusWlanChannelScanResultsEntryAdaptiveRfTimeout OBJECT-TYPE
    SYNTAX     Integer32 (0..2147483647)
    MAX-ACCESS read-only
    STATUS     current
    DESCRIPTION
            "-- empty --"
    ::= { lcsStatusWlanChannelScanResultsEntry 24 }

-- {COLUMN} 1.3.6.1.4.1.2356.11.1.3.42.1.25
lcsStatusWlanChannelScanResultsEntryHasNeighbors OBJECT-TYPE
    SYNTAX     INTEGER {
                  eNo (0),
                  eYes (1)
            }
    MAX-ACCESS read-only
    STATUS     current
    DESCRIPTION
            "-- empty --"
    ::= { lcsStatusWlanChannelScanResultsEntry 25 }

-- {NODE} 1.3.6.1.4.1.2356.11.1.3.43
lcsStatusWlanClient OBJECT IDENTIFIER ::= { lcsStatusWlan 43 }

-- {TABLE} 1.3.6.1.4.1.2356.11.1.3.43.1
lcsStatusWlanClientIpv4TranslationTableTable OBJECT-TYPE
    SYNTAX     SEQUENCE OF LcsStatusWlanClientIpv4TranslationTableEntry
    MAX-ACCESS not-accessible
    STATUS     current
    DESCRIPTION
            ""
    ::= { lcsStatusWlanClient 1 }

-- {ROW} 1.3.6.1.4.1.2356.11.1.3.43.1.1
lcsStatusWlanClientIpv4TranslationTableEntry OBJECT-TYPE
    SYNTAX     LcsStatusWlanClientIpv4TranslationTableEntry
    MAX-ACCESS not-accessible
    STATUS     current
    DESCRIPTION
            ""
    INDEX {
            lcsStatusWlanClientIpv4TranslationTableEntryIpAddress
          }
    ::= { lcsStatusWlanClientIpv4TranslationTableTable 1 }

LcsStatusWlanClientIpv4TranslationTableEntry ::= SEQUENCE {
            lcsStatusWlanClientIpv4TranslationTableEntryIpAddress IpAddress,
            lcsStatusWlanClientIpv4TranslationTableEntryMacAddress MacAddress,
            lcsStatusWlanClientIpv4TranslationTableEntryAge Integer32,
            lcsStatusWlanClientIpv4TranslationTableEntryInternal INTEGER
    }

-- {COLUMN} 1.3.6.1.4.1.2356.11.1.3.43.1.1.1
lcsStatusWlanClientIpv4TranslationTableEntryIpAddress OBJECT-TYPE
    SYNTAX     IpAddress
    MAX-ACCESS read-only
    STATUS     current
    DESCRIPTION
            ""
    ::= { lcsStatusWlanClientIpv4TranslationTableEntry 1 }

-- {COLUMN} 1.3.6.1.4.1.2356.11.1.3.43.1.1.2
lcsStatusWlanClientIpv4TranslationTableEntryMacAddress OBJECT-TYPE
    SYNTAX     MacAddress
    MAX-ACCESS read-only
    STATUS     current
    DESCRIPTION
            ""
    ::= { lcsStatusWlanClientIpv4TranslationTableEntry 2 }

-- {COLUMN} 1.3.6.1.4.1.2356.11.1.3.43.1.1.3
lcsStatusWlanClientIpv4TranslationTableEntryAge OBJECT-TYPE
    SYNTAX     Integer32 (0..2147483647)
    MAX-ACCESS read-only
    STATUS     current
    DESCRIPTION
            ""
    ::= { lcsStatusWlanClientIpv4TranslationTableEntry 3 }

-- {COLUMN} 1.3.6.1.4.1.2356.11.1.3.43.1.1.4
lcsStatusWlanClientIpv4TranslationTableEntryInternal OBJECT-TYPE
    SYNTAX     INTEGER {
                  eNo (0),
                  eYes (1)
            }
    MAX-ACCESS read-only
    STATUS     current
    DESCRIPTION
            "-- empty --"
    ::= { lcsStatusWlanClientIpv4TranslationTableEntry 4 }

-- {TABLE} 1.3.6.1.4.1.2356.11.1.3.43.10
lcsStatusWlanClientPppoeIdTranslationTableTable OBJECT-TYPE
    SYNTAX     SEQUENCE OF LcsStatusWlanClientPppoeIdTranslationTableEntry
    MAX-ACCESS not-accessible
    STATUS     current
    DESCRIPTION
            ""
    ::= { lcsStatusWlanClient 10 }

-- {ROW} 1.3.6.1.4.1.2356.11.1.3.43.10.1
lcsStatusWlanClientPppoeIdTranslationTableEntry OBJECT-TYPE
    SYNTAX     LcsStatusWlanClientPppoeIdTranslationTableEntry
    MAX-ACCESS not-accessible
    STATUS     current
    DESCRIPTION
            ""
    INDEX {
            lcsStatusWlanClientPppoeIdTranslationTableEntrySessionId
          }
    ::= { lcsStatusWlanClientPppoeIdTranslationTableTable 1 }

LcsStatusWlanClientPppoeIdTranslationTableEntry ::= SEQUENCE {
            lcsStatusWlanClientPppoeIdTranslationTableEntrySessionId Integer32,
            lcsStatusWlanClientPppoeIdTranslationTableEntryMacAddress MacAddress,
            lcsStatusWlanClientPppoeIdTranslationTableEntryAge Integer32
    }

-- {COLUMN} 1.3.6.1.4.1.2356.11.1.3.43.10.1.1
lcsStatusWlanClientPppoeIdTranslationTableEntrySessionId OBJECT-TYPE
    SYNTAX     Integer32 (0..65535)
    MAX-ACCESS read-only
    STATUS     current
    DESCRIPTION
            ""
    ::= { lcsStatusWlanClientPppoeIdTranslationTableEntry 1 }

-- {COLUMN} 1.3.6.1.4.1.2356.11.1.3.43.10.1.2
lcsStatusWlanClientPppoeIdTranslationTableEntryMacAddress OBJECT-TYPE
    SYNTAX     MacAddress
    MAX-ACCESS read-only
    STATUS     current
    DESCRIPTION
            ""
    ::= { lcsStatusWlanClientPppoeIdTranslationTableEntry 2 }

-- {COLUMN} 1.3.6.1.4.1.2356.11.1.3.43.10.1.3
lcsStatusWlanClientPppoeIdTranslationTableEntryAge OBJECT-TYPE
    SYNTAX     Integer32 (0..2147483647)
    MAX-ACCESS read-only
    STATUS     current
    DESCRIPTION
            ""
    ::= { lcsStatusWlanClientPppoeIdTranslationTableEntry 3 }

-- {TABLE} 1.3.6.1.4.1.2356.11.1.3.43.11
lcsStatusWlanClientPppoeUniqTranslationTableTable OBJECT-TYPE
    SYNTAX     SEQUENCE OF LcsStatusWlanClientPppoeUniqTranslationTableEntry
    MAX-ACCESS not-accessible
    STATUS     current
    DESCRIPTION
            ""
    ::= { lcsStatusWlanClient 11 }

-- {ROW} 1.3.6.1.4.1.2356.11.1.3.43.11.1
lcsStatusWlanClientPppoeUniqTranslationTableEntry OBJECT-TYPE
    SYNTAX     LcsStatusWlanClientPppoeUniqTranslationTableEntry
    MAX-ACCESS not-accessible
    STATUS     current
    DESCRIPTION
            ""
    INDEX {
            lcsStatusWlanClientPppoeUniqTranslationTableEntryHostUniqLen,
            lcsStatusWlanClientPppoeUniqTranslationTableEntryHostUniq
          }
    ::= { lcsStatusWlanClientPppoeUniqTranslationTableTable 1 }

LcsStatusWlanClientPppoeUniqTranslationTableEntry ::= SEQUENCE {
            lcsStatusWlanClientPppoeUniqTranslationTableEntryHostUniqLen Integer32,
            lcsStatusWlanClientPppoeUniqTranslationTableEntryHostUniq DisplayString,
            lcsStatusWlanClientPppoeUniqTranslationTableEntryMacAddress MacAddress,
            lcsStatusWlanClientPppoeUniqTranslationTableEntryAge Integer32
    }

-- {COLUMN} 1.3.6.1.4.1.2356.11.1.3.43.11.1.1
lcsStatusWlanClientPppoeUniqTranslationTableEntryHostUniqLen OBJECT-TYPE
    SYNTAX     Integer32 (0..65535)
    MAX-ACCESS read-only
    STATUS     current
    DESCRIPTION
            ""
    ::= { lcsStatusWlanClientPppoeUniqTranslationTableEntry 1 }

-- {COLUMN} 1.3.6.1.4.1.2356.11.1.3.43.11.1.2
lcsStatusWlanClientPppoeUniqTranslationTableEntryHostUniq OBJECT-TYPE
    SYNTAX     DisplayString (SIZE(0..255))
    MAX-ACCESS read-only
    STATUS     current
    DESCRIPTION
            ""
    ::= { lcsStatusWlanClientPppoeUniqTranslationTableEntry 2 }

-- {COLUMN} 1.3.6.1.4.1.2356.11.1.3.43.11.1.3
lcsStatusWlanClientPppoeUniqTranslationTableEntryMacAddress OBJECT-TYPE
    SYNTAX     MacAddress
    MAX-ACCESS read-only
    STATUS     current
    DESCRIPTION
            ""
    ::= { lcsStatusWlanClientPppoeUniqTranslationTableEntry 3 }

-- {COLUMN} 1.3.6.1.4.1.2356.11.1.3.43.11.1.4
lcsStatusWlanClientPppoeUniqTranslationTableEntryAge OBJECT-TYPE
    SYNTAX     Integer32 (0..2147483647)
    MAX-ACCESS read-only
    STATUS     current
    DESCRIPTION
            ""
    ::= { lcsStatusWlanClientPppoeUniqTranslationTableEntry 4 }

-- {TABLE} 1.3.6.1.4.1.2356.11.1.3.43.12
lcsStatusWlanClientIpv6TranslationTableTable OBJECT-TYPE
    SYNTAX     SEQUENCE OF LcsStatusWlanClientIpv6TranslationTableEntry
    MAX-ACCESS not-accessible
    STATUS     current
    DESCRIPTION
            ""
    ::= { lcsStatusWlanClient 12 }

-- {ROW} 1.3.6.1.4.1.2356.11.1.3.43.12.1
lcsStatusWlanClientIpv6TranslationTableEntry OBJECT-TYPE
    SYNTAX     LcsStatusWlanClientIpv6TranslationTableEntry
    MAX-ACCESS not-accessible
    STATUS     current
    DESCRIPTION
            ""
    INDEX {
            lcsStatusWlanClientIpv6TranslationTableEntryIpAddress
          }
    ::= { lcsStatusWlanClientIpv6TranslationTableTable 1 }

LcsStatusWlanClientIpv6TranslationTableEntry ::= SEQUENCE {
            lcsStatusWlanClientIpv6TranslationTableEntryIpAddress IpAddress,
            lcsStatusWlanClientIpv6TranslationTableEntryMacAddress MacAddress,
            lcsStatusWlanClientIpv6TranslationTableEntryAge Integer32,
            lcsStatusWlanClientIpv6TranslationTableEntryInternal INTEGER
    }

-- {COLUMN} 1.3.6.1.4.1.2356.11.1.3.43.12.1.1
lcsStatusWlanClientIpv6TranslationTableEntryIpAddress OBJECT-TYPE
    SYNTAX     IpAddress
    MAX-ACCESS read-only
    STATUS     current
    DESCRIPTION
            ""
    ::= { lcsStatusWlanClientIpv6TranslationTableEntry 1 }

-- {COLUMN} 1.3.6.1.4.1.2356.11.1.3.43.12.1.2
lcsStatusWlanClientIpv6TranslationTableEntryMacAddress OBJECT-TYPE
    SYNTAX     MacAddress
    MAX-ACCESS read-only
    STATUS     current
    DESCRIPTION
            ""
    ::= { lcsStatusWlanClientIpv6TranslationTableEntry 2 }

-- {COLUMN} 1.3.6.1.4.1.2356.11.1.3.43.12.1.3
lcsStatusWlanClientIpv6TranslationTableEntryAge OBJECT-TYPE
    SYNTAX     Integer32 (0..2147483647)
    MAX-ACCESS read-only
    STATUS     current
    DESCRIPTION
            ""
    ::= { lcsStatusWlanClientIpv6TranslationTableEntry 3 }

-- {COLUMN} 1.3.6.1.4.1.2356.11.1.3.43.12.1.4
lcsStatusWlanClientIpv6TranslationTableEntryInternal OBJECT-TYPE
    SYNTAX     INTEGER {
                  eNo (0),
                  eYes (1)
            }
    MAX-ACCESS read-only
    STATUS     current
    DESCRIPTION
            "-- empty --"
    ::= { lcsStatusWlanClientIpv6TranslationTableEntry 4 }

-- {TABLE} 1.3.6.1.4.1.2356.11.1.3.43.51
lcsStatusWlanClientIfcsTable OBJECT-TYPE
    SYNTAX     SEQUENCE OF LcsStatusWlanClientIfcsEntry
    MAX-ACCESS not-accessible
    STATUS     current
    DESCRIPTION
            ""
    ::= { lcsStatusWlanClient 51 }

-- {ROW} 1.3.6.1.4.1.2356.11.1.3.43.51.1
lcsStatusWlanClientIfcsEntry OBJECT-TYPE
    SYNTAX     LcsStatusWlanClientIfcsEntry
    MAX-ACCESS not-accessible
    STATUS     current
    DESCRIPTION
            ""
    INDEX {
            lcsStatusWlanClientIfcsEntryIfc
          }
    ::= { lcsStatusWlanClientIfcsTable 1 }

LcsStatusWlanClientIfcsEntry ::= SEQUENCE {
            lcsStatusWlanClientIfcsEntryIfc DisplayString,
            lcsStatusWlanClientIfcsEntryState INTEGER,
            lcsStatusWlanClientIfcsEntryStationMode INTEGER,
            lcsStatusWlanClientIfcsEntryRxRate INTEGER,
            lcsStatusWlanClientIfcsEntryThroughput DisplayString,
            lcsStatusWlanClientIfcsEntryPhySignal Integer32,
            lcsStatusWlanClientIfcsEntryTxRate INTEGER,
            lcsStatusWlanClientIfcsEntryMaxThroughput DisplayString,
            lcsStatusWlanClientIfcsEntryTxBytes Counter64,
            lcsStatusWlanClientIfcsEntryRxBytes Counter64,
            lcsStatusWlanClientIfcsEntryBytesThroughput Integer32,
            lcsStatusWlanClientIfcsEntryBytesMaxThroughput Integer32,
            lcsStatusWlanClientIfcsEntryClBrgSupport INTEGER,
            lcsStatusWlanClientIfcsEntryWpaVersion INTEGER,
            lcsStatusWlanClientIfcsEntryTxLimit Integer32,
            lcsStatusWlanClientIfcsEntryRxLimit Integer32,
            lcsStatusWlanClientIfcsEntryQos INTEGER,
            lcsStatusWlanClientIfcsEntryTxPackets Counter32,
            lcsStatusWlanClientIfcsEntryRxPackets Counter32,
            lcsStatusWlanClientIfcsEntryLinkPhySignal Integer32,
            lcsStatusWlanClientIfcsEntryAid Integer32,
            lcsStatusWlanClientIfcsEntryIdentification DisplayString,
            lcsStatusWlanClientIfcsEntryConnectTime Integer32,
            lcsStatusWlanClientIfcsEntryLinkSignalLevel Integer32,
            lcsStatusWlanClientIfcsEntryMaxAMpduLen Integer32,
            lcsStatusWlanClientIfcsEntryMaxAMsduLen Integer32,
            lcsStatusWlanClientIfcsEntryEffTxRate Integer32,
            lcsStatusWlanClientIfcsEntryEffRxRate Integer32,
            lcsStatusWlanClientIfcsEntryKeyType INTEGER,
            lcsStatusWlanClientIfcsEntryTxErrors Integer32,
            lcsStatusWlanClientIfcsEntryTotalRetries Integer32,
            lcsStatusWlanClientIfcsEntryAlarmState INTEGER,
            lcsStatusWlanClientIfcsEntryAllow40mhz INTEGER,
            lcsStatusWlanClientIfcsEntryExtChannel INTEGER,
            lcsStatusWlanClientIfcsEntry40mhzCoexistence INTEGER,
            lcsStatusWlanClientIfcsEntryRxStbc INTEGER,
            lcsStatusWlanClientIfcsEntryLdpc INTEGER,
            lcsStatusWlanClientIfcsEntryWpa2KeyManagement INTEGER,
            lcsStatusWlanClientIfcsEntryProtMgmtFrames INTEGER,
            lcsStatusWlanClientIfcsEntryRxStbcHt INTEGER,
            lcsStatusWlanClientIfcsEntryRxStbcVht INTEGER,
            lcsStatusWlanClientIfcsEntryLDPCMask BITS,
            lcsStatusWlanClientIfcsEntryOperationMode INTEGER,
            lcsStatusWlanClientIfcsEntryTxChannelwidth INTEGER,
            lcsStatusWlanClientIfcsEntryTxShortGi INTEGER,
            lcsStatusWlanClientIfcsEntryRxChannelwidth INTEGER,
            lcsStatusWlanClientIfcsEntryRxShortGi INTEGER,
            lcsStatusWlanClientIfcsEntryTxMcs Integer32,
            lcsStatusWlanClientIfcsEntryRxMcs Integer32,
            lcsStatusWlanClientIfcsEntry11acBeamforming BITS,
            lcsStatusWlanClientIfcsEntryNetworkName DisplayString,
            lcsStatusWlanClientIfcsEntryBssid MacAddress,
            lcsStatusWlanClientIfcsEntryWpaAuthType INTEGER,
            lcsStatusWlanClientIfcsEntryQosMapping INTEGER
    }

-- {COLUMN} 1.3.6.1.4.1.2356.11.1.3.43.51.1.1
lcsStatusWlanClientIfcsEntryIfc OBJECT-TYPE
    SYNTAX     DisplayString (SIZE(0..255))
    MAX-ACCESS read-only
    STATUS     current
    DESCRIPTION
            ""
    ::= { lcsStatusWlanClientIfcsEntry 1 }

-- {COLUMN} 1.3.6.1.4.1.2356.11.1.3.43.51.1.2
lcsStatusWlanClientIfcsEntryState OBJECT-TYPE
    SYNTAX     INTEGER {
                  eNone (0),
                  eAuthenticated (2),
                  eConnected (3),
                  eJoined (5),
                  eScanning (6),
                  eChallenge (7),
                  eKeyHandshake (8),
                  eAssociated (9),
                  e1xNegotiation (10),
                  eWaitPmkCache (11)
            }
    MAX-ACCESS read-only
    STATUS     current
    DESCRIPTION
            ""
    ::= { lcsStatusWlanClientIfcsEntry 2 }

-- {COLUMN} 1.3.6.1.4.1.2356.11.1.3.43.51.1.3
lcsStatusWlanClientIfcsEntryStationMode OBJECT-TYPE
    SYNTAX     INTEGER {
                  eNone (0),
                  eAdhoc (1),
                  eInfrastructure (2)
            }
    MAX-ACCESS read-only
    STATUS     current
    DESCRIPTION
            ""
    ::= { lcsStatusWlanClientIfcsEntry 3 }

-- {COLUMN} 1.3.6.1.4.1.2356.11.1.3.43.51.1.5
lcsStatusWlanClientIfcsEntryRxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            ""
    ::= { lcsStatusWlanClientIfcsEntry 5 }

-- {COLUMN} 1.3.6.1.4.1.2356.11.1.3.43.51.1.6
lcsStatusWlanClientIfcsEntryThroughput OBJECT-TYPE
    SYNTAX     DisplayString (SIZE(0..255))
    MAX-ACCESS read-only
    STATUS     current
    DESCRIPTION
            ""
    ::= { lcsStatusWlanClientIfcsEntry 6 }

-- {COLUMN} 1.3.6.1.4.1.2356.11.1.3.43.51.1.7
lcsStatusWlanClientIfcsEntryPhySignal OBJECT-TYPE
    SYNTAX     Integer32 (0..65535)
    MAX-ACCESS read-only
    STATUS     current
    DESCRIPTION
            ""
    ::= { lcsStatusWlanClientIfcsEntry 7 }

-- {COLUMN} 1.3.6.1.4.1.2356.11.1.3.43.51.1.9
lcsStatusWlanClientIfcsEntryTxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            ""
    ::= { lcsStatusWlanClientIfcsEntry 9 }

-- {COLUMN} 1.3.6.1.4.1.2356.11.1.3.43.51.1.10
lcsStatusWlanClientIfcsEntryMaxThroughput OBJECT-TYPE
    SYNTAX     DisplayString (SIZE(0..255))
    MAX-ACCESS read-only
    STATUS     current
    DESCRIPTION
            ""
    ::= { lcsStatusWlanClientIfcsEntry 10 }

-- {COLUMN} 1.3.6.1.4.1.2356.11.1.3.43.51.1.11
lcsStatusWlanClientIfcsEntryTxBytes OBJECT-TYPE
    SYNTAX     Counter64
    MAX-ACCESS read-only
    STATUS     current
    DESCRIPTION
            ""
    ::= { lcsStatusWlanClientIfcsEntry 11 }

-- {COLUMN} 1.3.6.1.4.1.2356.11.1.3.43.51.1.12
lcsStatusWlanClientIfcsEntryRxBytes OBJECT-TYPE
    SYNTAX     Counter64
    MAX-ACCESS read-only
    STATUS     current
    DESCRIPTION
            ""
    ::= { lcsStatusWlanClientIfcsEntry 12 }

-- {COLUMN} 1.3.6.1.4.1.2356.11.1.3.43.51.1.13
lcsStatusWlanClientIfcsEntryBytesThroughput OBJECT-TYPE
    SYNTAX     Integer32 (0..2147483647)
    MAX-ACCESS read-only
    STATUS     current
    DESCRIPTION
            ""
    ::= { lcsStatusWlanClientIfcsEntry 13 }

-- {COLUMN} 1.3.6.1.4.1.2356.11.1.3.43.51.1.14
lcsStatusWlanClientIfcsEntryBytesMaxThroughput OBJECT-TYPE
    SYNTAX     Integer32 (0..2147483647)
    MAX-ACCESS read-only
    STATUS     current
    DESCRIPTION
            ""
    ::= { lcsStatusWlanClientIfcsEntry 14 }

-- {COLUMN} 1.3.6.1.4.1.2356.11.1.3.43.51.1.15
lcsStatusWlanClientIfcsEntryClBrgSupport OBJECT-TYPE
    SYNTAX     INTEGER {
                  eNo (0),
                  eYes (1)
            }
    MAX-ACCESS read-only
    STATUS     current
    DESCRIPTION
            ""
    ::= { lcsStatusWlanClientIfcsEntry 15 }

-- {COLUMN} 1.3.6.1.4.1.2356.11.1.3.43.51.1.16
lcsStatusWlanClientIfcsEntryWpaVersion OBJECT-TYPE
    SYNTAX     INTEGER {
                  eNone (0),
                  eWpa1 (1),
                  eWpa2 (2),
                  eWpa3 (3)
            }
    MAX-ACCESS read-only
    STATUS     current
    DESCRIPTION
            ""
    ::= { lcsStatusWlanClientIfcsEntry 16 }

-- {COLUMN} 1.3.6.1.4.1.2356.11.1.3.43.51.1.17
lcsStatusWlanClientIfcsEntryTxLimit OBJECT-TYPE
    SYNTAX     Integer32 (0..2147483647)
    MAX-ACCESS read-only
    STATUS     current
    DESCRIPTION
            ""
    ::= { lcsStatusWlanClientIfcsEntry 17 }

-- {COLUMN} 1.3.6.1.4.1.2356.11.1.3.43.51.1.18
lcsStatusWlanClientIfcsEntryRxLimit OBJECT-TYPE
    SYNTAX     Integer32 (0..2147483647)
    MAX-ACCESS read-only
    STATUS     current
    DESCRIPTION
            ""
    ::= { lcsStatusWlanClientIfcsEntry 18 }

-- {COLUMN} 1.3.6.1.4.1.2356.11.1.3.43.51.1.19
lcsStatusWlanClientIfcsEntryQos OBJECT-TYPE
    SYNTAX     INTEGER {
                  eNo (0),
                  eYes (1)
            }
    MAX-ACCESS read-only
    STATUS     current
    DESCRIPTION
            ""
    ::= { lcsStatusWlanClientIfcsEntry 19 }

-- {COLUMN} 1.3.6.1.4.1.2356.11.1.3.43.51.1.20
lcsStatusWlanClientIfcsEntryTxPackets OBJECT-TYPE
    SYNTAX     Counter32
    MAX-ACCESS read-only
    STATUS     current
    DESCRIPTION
            ""
    ::= { lcsStatusWlanClientIfcsEntry 20 }

-- {COLUMN} 1.3.6.1.4.1.2356.11.1.3.43.51.1.21
lcsStatusWlanClientIfcsEntryRxPackets OBJECT-TYPE
    SYNTAX     Counter32
    MAX-ACCESS read-only
    STATUS     current
    DESCRIPTION
            ""
    ::= { lcsStatusWlanClientIfcsEntry 21 }

-- {COLUMN} 1.3.6.1.4.1.2356.11.1.3.43.51.1.22
lcsStatusWlanClientIfcsEntryLinkPhySignal OBJECT-TYPE
    SYNTAX     Integer32 (0..65535)
    MAX-ACCESS read-only
    STATUS     current
    DESCRIPTION
            ""
    ::= { lcsStatusWlanClientIfcsEntry 22 }

-- {COLUMN} 1.3.6.1.4.1.2356.11.1.3.43.51.1.23
lcsStatusWlanClientIfcsEntryAid OBJECT-TYPE
    SYNTAX     Integer32 (0..65535)
    MAX-ACCESS read-only
    STATUS     current
    DESCRIPTION
            ""
    ::= { lcsStatusWlanClientIfcsEntry 23 }

-- {COLUMN} 1.3.6.1.4.1.2356.11.1.3.43.51.1.24
lcsStatusWlanClientIfcsEntryIdentification OBJECT-TYPE
    SYNTAX     DisplayString (SIZE(0..32))
    MAX-ACCESS read-only
    STATUS     current
    DESCRIPTION
            ""
    ::= { lcsStatusWlanClientIfcsEntry 24 }

-- {COLUMN} 1.3.6.1.4.1.2356.11.1.3.43.51.1.25
lcsStatusWlanClientIfcsEntryConnectTime OBJECT-TYPE
    SYNTAX     Integer32 (0..2147483647)
    MAX-ACCESS read-only
    STATUS     current
    DESCRIPTION
            ""
    ::= { lcsStatusWlanClientIfcsEntry 25 }

-- {COLUMN} 1.3.6.1.4.1.2356.11.1.3.43.51.1.26
lcsStatusWlanClientIfcsEntryLinkSignalLevel OBJECT-TYPE
    SYNTAX     Integer32 (-32768..32767)
    MAX-ACCESS read-only
    STATUS     current
    DESCRIPTION
            ""
    ::= { lcsStatusWlanClientIfcsEntry 26 }

-- {COLUMN} 1.3.6.1.4.1.2356.11.1.3.43.51.1.27
lcsStatusWlanClientIfcsEntryMaxAMpduLen OBJECT-TYPE
    SYNTAX     Integer32 (0..2147483647)
    MAX-ACCESS read-only
    STATUS     current
    DESCRIPTION
            ""
    ::= { lcsStatusWlanClientIfcsEntry 27 }

-- {COLUMN} 1.3.6.1.4.1.2356.11.1.3.43.51.1.28
lcsStatusWlanClientIfcsEntryMaxAMsduLen OBJECT-TYPE
    SYNTAX     Integer32 (0..2147483647)
    MAX-ACCESS read-only
    STATUS     current
    DESCRIPTION
            ""
    ::= { lcsStatusWlanClientIfcsEntry 28 }

-- {COLUMN} 1.3.6.1.4.1.2356.11.1.3.43.51.1.29
lcsStatusWlanClientIfcsEntryEffTxRate OBJECT-TYPE
    SYNTAX     Integer32 (0..2147483647)
    MAX-ACCESS read-only
    STATUS     current
    DESCRIPTION
            ""
    ::= { lcsStatusWlanClientIfcsEntry 29 }

-- {COLUMN} 1.3.6.1.4.1.2356.11.1.3.43.51.1.30
lcsStatusWlanClientIfcsEntryEffRxRate OBJECT-TYPE
    SYNTAX     Integer32 (0..2147483647)
    MAX-ACCESS read-only
    STATUS     current
    DESCRIPTION
            ""
    ::= { lcsStatusWlanClientIfcsEntry 30 }

-- {COLUMN} 1.3.6.1.4.1.2356.11.1.3.43.51.1.31
lcsStatusWlanClientIfcsEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eAesCcmp256 (67),
                  eBip (68),
                  eBipCmac256 (69),
                  eAesGcmp128 (70),
                  eAesGcmp256 (71),
                  eBipGmac128 (72),
                  eBipGmac256 (73)
            }
    MAX-ACCESS read-only
    STATUS     current
    DESCRIPTION
            ""
    ::= { lcsStatusWlanClientIfcsEntry 31 }

-- {COLUMN} 1.3.6.1.4.1.2356.11.1.3.43.51.1.32
lcsStatusWlanClientIfcsEntryTxErrors OBJECT-TYPE
    SYNTAX     Integer32 (0..2147483647)
    MAX-ACCESS read-only
    STATUS     current
    DESCRIPTION
            ""
    ::= { lcsStatusWlanClientIfcsEntry 32 }

-- {COLUMN} 1.3.6.1.4.1.2356.11.1.3.43.51.1.33
lcsStatusWlanClientIfcsEntryTotalRetries OBJECT-TYPE
    SYNTAX     Integer32 (0..2147483647)
    MAX-ACCESS read-only
    STATUS     current
    DESCRIPTION
            ""
    ::= { lcsStatusWlanClientIfcsEntry 33 }

-- {COLUMN} 1.3.6.1.4.1.2356.11.1.3.43.51.1.34
lcsStatusWlanClientIfcsEntryAlarmState OBJECT-TYPE
    SYNTAX     INTEGER {
                  eNo (0),
                  ePhySignal (1),
                  eTotalRetries (2),
                  eTxErrors (4)
            }
    MAX-ACCESS read-only
    STATUS     current
    DESCRIPTION
            ""
    ::= { lcsStatusWlanClientIfcsEntry 34 }

-- {COLUMN} 1.3.6.1.4.1.2356.11.1.3.43.51.1.35
lcsStatusWlanClientIfcsEntryAllow40mhz OBJECT-TYPE
    SYNTAX     INTEGER {
                  eNo (0),
                  eYes (1)
            }
    MAX-ACCESS read-only
    STATUS     current
    DESCRIPTION
            "-- empty --"
    ::= { lcsStatusWlanClientIfcsEntry 35 }

-- {COLUMN} 1.3.6.1.4.1.2356.11.1.3.43.51.1.36
lcsStatusWlanClientIfcsEntryExtChannel OBJECT-TYPE
    SYNTAX     INTEGER {
                  eNone (0),
                  eAbove (1),
                  eBelow (3)
            }
    MAX-ACCESS read-only
    STATUS     current
    DESCRIPTION
            "-- empty --"
    ::= { lcsStatusWlanClientIfcsEntry 36 }

-- {COLUMN} 1.3.6.1.4.1.2356.11.1.3.43.51.1.37
lcsStatusWlanClientIfcsEntry40mhzCoexistence OBJECT-TYPE
    SYNTAX     INTEGER {
                  eNo (0),
                  eYes (1)
            }
    MAX-ACCESS read-only
    STATUS     current
    DESCRIPTION
            "-- empty --"
    ::= { lcsStatusWlanClientIfcsEntry 37 }

-- {COLUMN} 1.3.6.1.4.1.2356.11.1.3.43.51.1.38
lcsStatusWlanClientIfcsEntryRxStbc OBJECT-TYPE
    SYNTAX     INTEGER {
                  eNone (0),
                  eOne (1),
                  eTwo (2),
                  eThree (3)
            }
    MAX-ACCESS read-only
    STATUS     current
    DESCRIPTION
            "-- empty --"
    ::= { lcsStatusWlanClientIfcsEntry 38 }

-- {COLUMN} 1.3.6.1.4.1.2356.11.1.3.43.51.1.39
lcsStatusWlanClientIfcsEntryLdpc OBJECT-TYPE
    SYNTAX     INTEGER {
                  eNo (0),
                  eYes (1)
            }
    MAX-ACCESS read-only
    STATUS     current
    DESCRIPTION
            "-- empty --"
    ::= { lcsStatusWlanClientIfcsEntry 39 }

-- {COLUMN} 1.3.6.1.4.1.2356.11.1.3.43.51.1.40
lcsStatusWlanClientIfcsEntryWpa2KeyManagement OBJECT-TYPE
    SYNTAX     INTEGER {
                  eStandard (0),
                  eFastRoaming (1),
                  eSha256 (2),
                  eSha384 (3),
                  eFastRoamingSha384 (4),
                  eNone (255)
            }
    MAX-ACCESS read-only
    STATUS     current
    DESCRIPTION
            "-- empty --"
    ::= { lcsStatusWlanClientIfcsEntry 40 }

-- {COLUMN} 1.3.6.1.4.1.2356.11.1.3.43.51.1.41
lcsStatusWlanClientIfcsEntryProtMgmtFrames OBJECT-TYPE
    SYNTAX     INTEGER {
                  eNo (0),
                  eYes (1)
            }
    MAX-ACCESS read-only
    STATUS     current
    DESCRIPTION
            "-- empty --"
    ::= { lcsStatusWlanClientIfcsEntry 41 }

-- {COLUMN} 1.3.6.1.4.1.2356.11.1.3.43.51.1.42
lcsStatusWlanClientIfcsEntryRxStbcHt OBJECT-TYPE
    SYNTAX     INTEGER {
                  eNone (0),
                  eOne (1),
                  eTwo (2),
                  eThree (3)
            }
    MAX-ACCESS read-only
    STATUS     current
    DESCRIPTION
            "-- empty --"
    ::= { lcsStatusWlanClientIfcsEntry 42 }

-- {COLUMN} 1.3.6.1.4.1.2356.11.1.3.43.51.1.43
lcsStatusWlanClientIfcsEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { lcsStatusWlanClientIfcsEntry 43 }

-- {COLUMN} 1.3.6.1.4.1.2356.11.1.3.43.51.1.44
lcsStatusWlanClientIfcsEntryLDPCMask OBJECT-TYPE
    SYNTAX     BITS {
                  eVht (30),
                  eHt (31)
            }
    MAX-ACCESS read-only
    STATUS     current
    DESCRIPTION
            "Bit mask of LDPC support per-PHY-Type"
    ::= { lcsStatusWlanClientIfcsEntry 44 }

-- {COLUMN} 1.3.6.1.4.1.2356.11.1.3.43.51.1.45
lcsStatusWlanClientIfcsEntryOperationMode OBJECT-TYPE
    SYNTAX     INTEGER {
                  eUnknown (0),
                  e11b (1),
                  e11g (2),
                  e11a (3),
                  e11n (4),
                  e11ac (5)
            }
    MAX-ACCESS read-only
    STATUS     current
    DESCRIPTION
            "-- empty --"
    ::= { lcsStatusWlanClientIfcsEntry 45 }

-- {COLUMN} 1.3.6.1.4.1.2356.11.1.3.43.51.1.46
lcsStatusWlanClientIfcsEntryTxChannelwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanClientIfcsEntry 46 }

-- {COLUMN} 1.3.6.1.4.1.2356.11.1.3.43.51.1.47
lcsStatusWlanClientIfcsEntryTxShortGi OBJECT-TYPE
    SYNTAX     INTEGER {
                  eNo (0),
                  eYes (1)
            }
    MAX-ACCESS read-only
    STATUS     current
    DESCRIPTION
            "-- empty --"
    ::= { lcsStatusWlanClientIfcsEntry 47 }

-- {COLUMN} 1.3.6.1.4.1.2356.11.1.3.43.51.1.48
lcsStatusWlanClientIfcsEntryRxChannelwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanClientIfcsEntry 48 }

-- {COLUMN} 1.3.6.1.4.1.2356.11.1.3.43.51.1.49
lcsStatusWlanClientIfcsEntryRxShortGi OBJECT-TYPE
    SYNTAX     INTEGER {
                  eNo (0),
                  eYes (1)
            }
    MAX-ACCESS read-only
    STATUS     current
    DESCRIPTION
            "-- empty --"
    ::= { lcsStatusWlanClientIfcsEntry 49 }

-- {COLUMN} 1.3.6.1.4.1.2356.11.1.3.43.51.1.50
lcsStatusWlanClientIfcsEntryTxMcs OBJECT-TYPE
    SYNTAX     Integer32 (0..255)
    MAX-ACCESS read-only
    STATUS     current
    DESCRIPTION
            "-- empty --"
    ::= { lcsStatusWlanClientIfcsEntry 50 }

-- {COLUMN} 1.3.6.1.4.1.2356.11.1.3.43.51.1.51
lcsStatusWlanClientIfcsEntryRxMcs OBJECT-TYPE
    SYNTAX     Integer32 (0..255)
    MAX-ACCESS read-only
    STATUS     current
    DESCRIPTION
            "-- empty --"
    ::= { lcsStatusWlanClientIfcsEntry 51 }

-- {COLUMN} 1.3.6.1.4.1.2356.11.1.3.43.51.1.52
lcsStatusWlanClientIfcsEntry11acBeamforming OBJECT-TYPE
    SYNTAX     BITS {
                  eMuBfee (28),
                  eMuBfer (29),
                  eSuBfee (30),
                  eSuBfer (31)
            }
    MAX-ACCESS read-only
    STATUS     current
    DESCRIPTION
            "-- empty --"
    ::= { lcsStatusWlanClientIfcsEntry 52 }

-- {COLUMN} 1.3.6.1.4.1.2356.11.1.3.43.51.1.53
lcsStatusWlanClientIfcsEntryNetworkName OBJECT-TYPE
    SYNTAX     DisplayString (SIZE(0..255))
    MAX-ACCESS read-only
    STATUS     current
    DESCRIPTION
            "-- empty --"
    ::= { lcsStatusWlanClientIfcsEntry 53 }

-- {COLUMN} 1.3.6.1.4.1.2356.11.1.3.43.51.1.54
lcsStatusWlanClientIfcsEntryBssid OBJECT-TYPE
    SYNTAX     MacAddress
    MAX-ACCESS read-only
    STATUS     current
    DESCRIPTION
            "-- empty --"
    ::= { lcsStatusWlanClientIfcsEntry 54 }

-- {COLUMN} 1.3.6.1.4.1.2356.11.1.3.43.51.1.55
lcsStatusWlanClientIfcsEntryWpaAuthType OBJECT-TYPE
    SYNTAX     INTEGER {
                  eNone (0),
                  ePsk (1),
                  e8021x (2),
                  eOwe (7),
                  eSae (8)
            }
    MAX-ACCESS read-only
    STATUS     current
    DESCRIPTION
            "-- empty --"
    ::= { lcsStatusWlanClientIfcsEntry 55 }

-- {COLUMN} 1.3.6.1.4.1.2356.11.1.3.43.51.1.59
lcsStatusWlanClientIfcsEntryQosMapping OBJECT-TYPE
    SYNTAX     INTEGER {
                  eNo (0),
                  eYes (1)
            }
    MAX-ACCESS read-only
    STATUS     current
    DESCRIPTION
            "-- empty --"
    ::= { lcsStatusWlanClientIfcsEntry 59 }

-- {TABLE} 1.3.6.1.4.1.2356.11.1.3.43.52
lcsStatusWlanClientConnectionRejectsTable OBJECT-TYPE
    SYNTAX     SEQUENCE OF LcsStatusWlanClientConnectionRejectsEntry
    MAX-ACCESS not-accessible
    STATUS     current
    DESCRIPTION
            ""
    ::= { lcsStatusWlanClient 52 }

-- {ROW} 1.3.6.1.4.1.2356.11.1.3.43.52.1
lcsStatusWlanClientConnectionRejectsEntry OBJECT-TYPE
    SYNTAX     LcsStatusWlanClientConnectionRejectsEntry
    MAX-ACCESS not-accessible
    STATUS     current
    DESCRIPTION
            ""
    INDEX {
            lcsStatusWlanClientConnectionRejectsEntryBssid,
            lcsStatusWlanClientConnectionRejectsEntryInterface
          }
    ::= { lcsStatusWlanClientConnectionRejectsTable 1 }

LcsStatusWlanClientConnectionRejectsEntry ::= SEQUENCE {
            lcsStatusWlanClientConnectionRejectsEntryBssid MacAddress,
            lcsStatusWlanClientConnectionRejectsEntryInterface INTEGER,
            lcsStatusWlanClientConnectionRejectsEntryAge Integer32,
            lcsStatusWlanClientConnectionRejectsEntryEvent INTEGER,
            lcsStatusWlanClientConnectionRejectsEntryStatusOrReason Integer32
    }

-- {COLUMN} 1.3.6.1.4.1.2356.11.1.3.43.52.1.1
lcsStatusWlanClientConnectionRejectsEntryBssid OBJECT-TYPE
    SYNTAX     MacAddress
    MAX-ACCESS read-only
    STATUS     current
    DESCRIPTION
            ""
    ::= { lcsStatusWlanClientConnectionRejectsEntry 1 }

-- {COLUMN} 1.3.6.1.4.1.2356.11.1.3.43.52.1.2
lcsStatusWlanClientConnectionRejectsEntryInterface OBJECT-TYPE
    SYNTAX     INTEGER {
                  eWlan1 (1),
                  eWlan2 (2)
            }
    MAX-ACCESS read-only
    STATUS     current
    DESCRIPTION
            ""
    ::= { lcsStatusWlanClientConnectionRejectsEntry 2 }

-- {COLUMN} 1.3.6.1.4.1.2356.11.1.3.43.52.1.3
lcsStatusWlanClientConnectionRejectsEntryAge OBJECT-TYPE
    SYNTAX     Integer32 (0..2147483647)
    MAX-ACCESS read-only
    STATUS     current
    DESCRIPTION
            ""
    ::= { lcsStatusWlanClientConnectionRejectsEntry 3 }

-- {COLUMN} 1.3.6.1.4.1.2356.11.1.3.43.52.1.4
lcsStatusWlanClientConnectionRejectsEntryEvent OBJECT-TYPE
    SYNTAX     INTEGER {
                  eDeauthenticate (1),
                  eDisassociate (2),
                  eAuthenticateReject (3),
                  eAssociateReject (4)
            }
    MAX-ACCESS read-only
    STATUS     current
    DESCRIPTION
            ""
    ::= { lcsStatusWlanClientConnectionRejectsEntry 4 }

-- {COLUMN} 1.3.6.1.4.1.2356.11.1.3.43.52.1.5
lcsStatusWlanClientConnectionRejectsEntryStatusOrReason OBJECT-TYPE
    SYNTAX     Integer32 (0..65535)
    MAX-ACCESS read-only
    STATUS     current
    DESCRIPTION
            ""
    ::= { lcsStatusWlanClientConnectionRejectsEntry 5 }

-- {TABLE} 1.3.6.1.4.1.2356.11.1.3.44
lcsStatusWlanCompetingNetworksTable OBJECT-TYPE
    SYNTAX     SEQUENCE OF LcsStatusWlanCompetingNetworksEntry
    MAX-ACCESS not-accessible
    STATUS     current
    DESCRIPTION
            ""
    ::= { lcsStatusWlan 44 }

-- {ROW} 1.3.6.1.4.1.2356.11.1.3.44.1
lcsStatusWlanCompetingNetworksEntry OBJECT-TYPE
    SYNTAX     LcsStatusWlanCompetingNetworksEntry
    MAX-ACCESS not-accessible
    STATUS     current
    DESCRIPTION
            ""
    INDEX {
            lcsStatusWlanCompetingNetworksEntryBssid,
            lcsStatusWlanCompetingNetworksEntryInterface
          }
    ::= { lcsStatusWlanCompetingNetworksTable 1 }

LcsStatusWlanCompetingNetworksEntry ::= SEQUENCE {
            lcsStatusWlanCompetingNetworksEntryBssid MacAddress,
            lcsStatusWlanCompetingNetworksEntryNetworkName DisplayString,
            lcsStatusWlanCompetingNetworksEntryOperationMode INTEGER,
            lcsStatusWlanCompetingNetworksEntryBeaconPeriod Integer32,
            lcsStatusWlanCompetingNetworksEntryDtimPeriod Integer32,
            lcsStatusWlanCompetingNetworksEntryRadioChannel Integer32,
            lcsStatusWlanCompetingNetworksEntryPhySignal Integer32,
            lcsStatusWlanCompetingNetworksEntryNoiseLevel Integer32,
            lcsStatusWlanCompetingNetworksEntryLoad DisplayString,
            lcsStatusWlanCompetingNetworksEntryEncryption INTEGER,
            lcsStatusWlanCompetingNetworksEntryShortPreamble INTEGER,
            lcsStatusWlanCompetingNetworksEntryInterface INTEGER,
            lcsStatusWlanCompetingNetworksEntryRadioBand INTEGER,
            lcsStatusWlanCompetingNetworksEntry108mbpsMode INTEGER,
            lcsStatusWlanCompetingNetworksEntryShortSlotTime INTEGER,
            lcsStatusWlanCompetingNetworksEntryRate INTEGER,
            lcsStatusWlanCompetingNetworksEntryNonerpPresent INTEGER,
            lcsStatusWlanCompetingNetworksEntryCompression INTEGER,
            lcsStatusWlanCompetingNetworksEntryPcfFunctionality INTEGER,
            lcsStatusWlanCompetingNetworksEntryIdentification DisplayString,
            lcsStatusWlanCompetingNetworksEntryQos INTEGER,
            lcsStatusWlanCompetingNetworksEntryAge Integer32,
            lcsStatusWlanCompetingNetworksEntrySignalLevel Integer32,
            lcsStatusWlanCompetingNetworksEntryShortGuardInterval INTEGER,
            lcsStatusWlanCompetingNetworksEntryExtChannel INTEGER,
            lcsStatusWlanCompetingNetworksEntry40mhzMode INTEGER,
            lcsStatusWlanCompetingNetworksEntry40mhzIntolerant INTEGER,
            lcsStatusWlanCompetingNetworksEntryInterpointPeerName DisplayString,
            lcsStatusWlanCompetingNetworksEntryMaxAMpduLen Integer32,
            lcsStatusWlanCompetingNetworksEntryMaxAMsduLen Integer32,
            lcsStatusWlanCompetingNetworksEntryVendor DisplayString,
            lcsStatusWlanCompetingNetworksEntryEffRate Integer32,
            lcsStatusWlanCompetingNetworksEntry40mhzCoexistence INTEGER,
            lcsStatusWlanCompetingNetworksEntryPreAuthentication INTEGER,
            lcsStatusWlanCompetingNetworksEntryTxStbc INTEGER,
            lcsStatusWlanCompetingNetworksEntryRxStbc INTEGER,
            lcsStatusWlanCompetingNetworksEntryEapolPreauthFailed INTEGER,
            lcsStatusWlanCompetingNetworksEntryLdpc INTEGER,
            lcsStatusWlanCompetingNetworksEntryAutowds INTEGER,
            lcsStatusWlanCompetingNetworksEntrySGIMask BITS,
            lcsStatusWlanCompetingNetworksEntryChannelBandwidths BITS,
            lcsStatusWlanCompetingNetworksEntryChannelBandwidth INTEGER,
            lcsStatusWlanCompetingNetworksEntryClBrgSupport INTEGER,
            lcsStatusWlanCompetingNetworksEntryProtMgmtFrames INTEGER,
            lcsStatusWlanCompetingNetworksEntryTxPowerLimit DisplayString,
            lcsStatusWlanCompetingNetworksEntryTxSTBCMask BITS,
            lcsStatusWlanCompetingNetworksEntryRxStbcHt INTEGER,
            lcsStatusWlanCompetingNetworksEntryRxStbcVht INTEGER,
            lcsStatusWlanCompetingNetworksEntryLDPCMask BITS,
            lcsStatusWlanCompetingNetworksEntryUuid DisplayString,
            lcsStatusWlanCompetingNetworksEntry11acBeamforming BITS,
            lcsStatusWlanCompetingNetworksEntrySecondaryChannel Integer32,
            lcsStatusWlanCompetingNetworksEntryTransitionalMode INTEGER,
            lcsStatusWlanCompetingNetworksEntryTransitionalSsid DisplayString,
            lcsStatusWlanCompetingNetworksEntryTransitionalBssid MacAddress,
            lcsStatusWlanCompetingNetworksEntryQosMapping INTEGER
    }

-- {COLUMN} 1.3.6.1.4.1.2356.11.1.3.44.1.1
lcsStatusWlanCompetingNetworksEntryBssid OBJECT-TYPE
    SYNTAX     MacAddress
    MAX-ACCESS read-only
    STATUS     current
    DESCRIPTION
            ""
    ::= { lcsStatusWlanCompetingNetworksEntry 1 }

-- {COLUMN} 1.3.6.1.4.1.2356.11.1.3.44.1.2
lcsStatusWlanCompetingNetworksEntryNetworkName OBJECT-TYPE
    SYNTAX     DisplayString (SIZE(0..255))
    MAX-ACCESS read-only
    STATUS     current
    DESCRIPTION
            ""
    ::= { lcsStatusWlanCompetingNetworksEntry 2 }

-- {COLUMN} 1.3.6.1.4.1.2356.11.1.3.44.1.3
lcsStatusWlanCompetingNetworksEntryOperationMode OBJECT-TYPE
    SYNTAX     INTEGER {
                  eNone (0),
                  eAdhoc (1),
                  eInfrastructure (2)
            }
    MAX-ACCESS read-only
    STATUS     current
    DESCRIPTION
            "lancom's description of operation mode"
    ::= { lcsStatusWlanCompetingNetworksEntry 3 }

-- {COLUMN} 1.3.6.1.4.1.2356.11.1.3.44.1.6
lcsStatusWlanCompetingNetworksEntryBeaconPeriod OBJECT-TYPE
    SYNTAX     Integer32 (0..65535)
    MAX-ACCESS read-only
    STATUS     current
    DESCRIPTION
            ""
    ::= { lcsStatusWlanCompetingNetworksEntry 6 }

-- {COLUMN} 1.3.6.1.4.1.2356.11.1.3.44.1.7
lcsStatusWlanCompetingNetworksEntryDtimPeriod OBJECT-TYPE
    SYNTAX     Integer32 (0..65535)
    MAX-ACCESS read-only
    STATUS     current
    DESCRIPTION
            ""
    ::= { lcsStatusWlanCompetingNetworksEntry 7 }

-- {COLUMN} 1.3.6.1.4.1.2356.11.1.3.44.1.8
lcsStatusWlanCompetingNetworksEntryRadioChannel OBJECT-TYPE
    SYNTAX     Integer32 (0..255)
    MAX-ACCESS read-only
    STATUS     current
    DESCRIPTION
            ""
    ::= { lcsStatusWlanCompetingNetworksEntry 8 }

-- {COLUMN} 1.3.6.1.4.1.2356.11.1.3.44.1.10
lcsStatusWlanCompetingNetworksEntryPhySignal OBJECT-TYPE
    SYNTAX     Integer32 (0..65535)
    MAX-ACCESS read-only
    STATUS     current
    DESCRIPTION
            ""
    ::= { lcsStatusWlanCompetingNetworksEntry 10 }

-- {COLUMN} 1.3.6.1.4.1.2356.11.1.3.44.1.11
lcsStatusWlanCompetingNetworksEntryNoiseLevel OBJECT-TYPE
    SYNTAX     Integer32 (-128..127)
    MAX-ACCESS read-only
    STATUS     current
    DESCRIPTION
            ""
    ::= { lcsStatusWlanCompetingNetworksEntry 11 }

-- {COLUMN} 1.3.6.1.4.1.2356.11.1.3.44.1.12
lcsStatusWlanCompetingNetworksEntryLoad OBJECT-TYPE
    SYNTAX     DisplayString (SIZE(0..255))
    MAX-ACCESS read-only
    STATUS     current
    DESCRIPTION
            ""
    ::= { lcsStatusWlanCompetingNetworksEntry 12 }

-- {COLUMN} 1.3.6.1.4.1.2356.11.1.3.44.1.13
lcsStatusWlanCompetingNetworksEntryEncryption OBJECT-TYPE
    SYNTAX     INTEGER {
                  eNone (0),
                  eWep (1),
                  eTkip (2),
                  eAes (3),
                  eAesPlusTkip (4)
            }
    MAX-ACCESS read-only
    STATUS     current
    DESCRIPTION
            ""
    ::= { lcsStatusWlanCompetingNetworksEntry 13 }

-- {COLUMN} 1.3.6.1.4.1.2356.11.1.3.44.1.14
lcsStatusWlanCompetingNetworksEntryShortPreamble OBJECT-TYPE
    SYNTAX     INTEGER {
                  eNo (0),
                  eYes (1)
            }
    MAX-ACCESS read-only
    STATUS     current
    DESCRIPTION
            ""
    ::= { lcsStatusWlanCompetingNetworksEntry 14 }

-- {COLUMN} 1.3.6.1.4.1.2356.11.1.3.44.1.15
lcsStatusWlanCompetingNetworksEntryInterface OBJECT-TYPE
    SYNTAX     INTEGER {
                  eWlan1 (0),
                  eWlan2 (1),
                  eWlan3 (2),
                  eWlan4 (3)
            }
    MAX-ACCESS read-only
    STATUS     current
    DESCRIPTION
            ""
    ::= { lcsStatusWlanCompetingNetworksEntry 15 }

-- {COLUMN} 1.3.6.1.4.1.2356.11.1.3.44.1.16
lcsStatusWlanCompetingNetworksEntryRadioBand OBJECT-TYPE
    SYNTAX     INTEGER {
                  eUnknown (0),
                  e24ghz (1),
                  e5ghz (2),
                  e24ghz5ghz (3)
            }
    MAX-ACCESS read-only
    STATUS     current
    DESCRIPTION
            ""
    ::= { lcsStatusWlanCompetingNetworksEntry 16 }

-- {COLUMN} 1.3.6.1.4.1.2356.11.1.3.44.1.17
lcsStatusWlanCompetingNetworksEntry108mbpsMode OBJECT-TYPE
    SYNTAX     INTEGER {
                  eNo (0),
                  eYes (1)
            }
    MAX-ACCESS read-only
    STATUS     current
    DESCRIPTION
            ""
    ::= { lcsStatusWlanCompetingNetworksEntry 17 }

-- {COLUMN} 1.3.6.1.4.1.2356.11.1.3.44.1.18
lcsStatusWlanCompetingNetworksEntryShortSlotTime OBJECT-TYPE
    SYNTAX     INTEGER {
                  eNo (0),
                  eYes (1)
            }
    MAX-ACCESS read-only
    STATUS     current
    DESCRIPTION
            ""
    ::= { lcsStatusWlanCompetingNetworksEntry 18 }

-- {COLUMN} 1.3.6.1.4.1.2356.11.1.3.44.1.19
lcsStatusWlanCompetingNetworksEntryRate OBJECT-TYPE
    SYNTAX     INTEGER {
                  eUnknown (0),
                  e1M (1),
                  e2M (2),
                  e5M (3),
                  e5M5 (4),
                  e8M (5),
                  e11M (6),
                  e6M (12),
                  e9M (13),
                  e12M (14),
                  e18M (15),
                  e24M (16),
                  e36M (17),
                  e48M (18),
                  e54M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eHT4S26M (52),
                  eHT4S52M (53),
                  eHT4S78M (54),
                  eHT4S104M (55),
                  eHT4S156M (56),
                  eHT4S208M (57),
                  eHT4S234M (58),
                  eHT4S260M (59),
                  eHTDUP6M (60),
                  eHtMcs33 (61),
                  eHtMcs34 (62),
                  eHtMcs35 (63),
                  eHtMcs36 (64),
                  eHtMcs37 (65),
                  eHtMcs38 (66),
                  eHtMcs39 (67),
                  eHtMcs40 (68),
                  eHtMcs41 (69),
                  eHtMcs42 (70),
                  eHtMcs43 (71),
                  eHtMcs44 (72),
                  eHtMcs45 (73),
                  eHtMcs46 (74),
                  eHtMcs47 (75),
                  eHtMcs48 (76),
                  eHtMcs49 (77),
                  eHtMcs50 (78),
                  eHtMcs51 (79),
                  eHtMcs52 (80),
                  eHtMcs53 (81),
                  eHtMcs54 (82),
                  eHtMcs55 (83),
                  eHtMcs56 (84),
                  eHtMcs57 (85),
                  eHtMcs58 (86),
                  eHtMcs59 (87),
                  eHtMcs60 (88),
                  eHtMcs61 (89),
                  eHtMcs62 (90),
                  eHtMcs63 (91),
                  eHtMcs64 (92),
                  eHtMcs65 (93),
                  eHtMcs66 (94),
                  eHtMcs67 (95),
                  eHtMcs68 (96),
                  eHtMcs69 (97),
                  eHtMcs70 (98),
                  eHtMcs71 (99),
                  eHtMcs72 (100),
                  eHtMcs73 (101),
                  eHtMcs74 (102),
                  eHtMcs75 (103),
                  eHtMcs76 (104),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            ""
    ::= { lcsStatusWlanCompetingNetworksEntry 19 }

-- {COLUMN} 1.3.6.1.4.1.2356.11.1.3.44.1.20
lcsStatusWlanCompetingNetworksEntryNonerpPresent OBJECT-TYPE
    SYNTAX     INTEGER {
                  eNo (0),
                  eYes (1)
            }
    MAX-ACCESS read-only
    STATUS     current
    DESCRIPTION
            ""
    ::= { lcsStatusWlanCompetingNetworksEntry 20 }

-- {COLUMN} 1.3.6.1.4.1.2356.11.1.3.44.1.21
lcsStatusWlanCompetingNetworksEntryCompression OBJECT-TYPE
    SYNTAX     INTEGER {
                  eNo (0),
                  eYes (1)
            }
    MAX-ACCESS read-only
    STATUS     current
    DESCRIPTION
            ""
    ::= { lcsStatusWlanCompetingNetworksEntry 21 }

-- {COLUMN} 1.3.6.1.4.1.2356.11.1.3.44.1.22
lcsStatusWlanCompetingNetworksEntryPcfFunctionality OBJECT-TYPE
    SYNTAX     INTEGER {
                  eNone (0),
                  eDelivery (1),
                  eDeliveryPlusPolling (2)
            }
    MAX-ACCESS read-only
    STATUS     current
    DESCRIPTION
            ""
    ::= { lcsStatusWlanCompetingNetworksEntry 22 }

-- {COLUMN} 1.3.6.1.4.1.2356.11.1.3.44.1.23
lcsStatusWlanCompetingNetworksEntryIdentification OBJECT-TYPE
    SYNTAX     DisplayString (SIZE(0..16))
    MAX-ACCESS read-only
    STATUS     current
    DESCRIPTION
            ""
    ::= { lcsStatusWlanCompetingNetworksEntry 23 }

-- {COLUMN} 1.3.6.1.4.1.2356.11.1.3.44.1.24
lcsStatusWlanCompetingNetworksEntryQos OBJECT-TYPE
    SYNTAX     INTEGER {
                  eNo (0),
                  eYes (1)
            }
    MAX-ACCESS read-only
    STATUS     current
    DESCRIPTION
            ""
    ::= { lcsStatusWlanCompetingNetworksEntry 24 }

-- {COLUMN} 1.3.6.1.4.1.2356.11.1.3.44.1.25
lcsStatusWlanCompetingNetworksEntryAge OBJECT-TYPE
    SYNTAX     Integer32 (0..2147483647)
    MAX-ACCESS read-only
    STATUS     current
    DESCRIPTION
            ""
    ::= { lcsStatusWlanCompetingNetworksEntry 25 }

-- {COLUMN} 1.3.6.1.4.1.2356.11.1.3.44.1.26
lcsStatusWlanCompetingNetworksEntrySignalLevel OBJECT-TYPE
    SYNTAX     Integer32 (-32768..32767)
    MAX-ACCESS read-only
    STATUS     current
    DESCRIPTION
            ""
    ::= { lcsStatusWlanCompetingNetworksEntry 26 }

-- {COLUMN} 1.3.6.1.4.1.2356.11.1.3.44.1.27
lcsStatusWlanCompetingNetworksEntryShortGuardInterval OBJECT-TYPE
    SYNTAX     INTEGER {
                  eNo (0),
                  e20mhz (1),
                  e40mhz (2),
                  e2040mhz (3)
            }
    MAX-ACCESS read-only
    STATUS     current
    DESCRIPTION
            ""
    ::= { lcsStatusWlanCompetingNetworksEntry 27 }

-- {COLUMN} 1.3.6.1.4.1.2356.11.1.3.44.1.28
lcsStatusWlanCompetingNetworksEntryExtChannel OBJECT-TYPE
    SYNTAX     INTEGER {
                  eNone (0),
                  eAbove (1),
                  eBelow (3)
            }
    MAX-ACCESS read-only
    STATUS     current
    DESCRIPTION
            ""
    ::= { lcsStatusWlanCompetingNetworksEntry 28 }

-- {COLUMN} 1.3.6.1.4.1.2356.11.1.3.44.1.29
lcsStatusWlanCompetingNetworksEntry40mhzMode OBJECT-TYPE
    SYNTAX     INTEGER {
                  eNo (0),
                  eYes (1)
            }
    MAX-ACCESS read-only
    STATUS     current
    DESCRIPTION
            ""
    ::= { lcsStatusWlanCompetingNetworksEntry 29 }

-- {COLUMN} 1.3.6.1.4.1.2356.11.1.3.44.1.30
lcsStatusWlanCompetingNetworksEntry40mhzIntolerant OBJECT-TYPE
    SYNTAX     INTEGER {
                  eNo (0),
                  eYes (1)
            }
    MAX-ACCESS read-only
    STATUS     current
    DESCRIPTION
            ""
    ::= { lcsStatusWlanCompetingNetworksEntry 30 }

-- {COLUMN} 1.3.6.1.4.1.2356.11.1.3.44.1.31
lcsStatusWlanCompetingNetworksEntryInterpointPeerName OBJECT-TYPE
    SYNTAX     DisplayString (SIZE(0..24))
    MAX-ACCESS read-only
    STATUS     current
    DESCRIPTION
            ""
    ::= { lcsStatusWlanCompetingNetworksEntry 31 }

-- {COLUMN} 1.3.6.1.4.1.2356.11.1.3.44.1.32
lcsStatusWlanCompetingNetworksEntryMaxAMpduLen OBJECT-TYPE
    SYNTAX     Integer32 (0..2147483647)
    MAX-ACCESS read-only
    STATUS     current
    DESCRIPTION
            ""
    ::= { lcsStatusWlanCompetingNetworksEntry 32 }

-- {COLUMN} 1.3.6.1.4.1.2356.11.1.3.44.1.33
lcsStatusWlanCompetingNetworksEntryMaxAMsduLen OBJECT-TYPE
    SYNTAX     Integer32 (0..2147483647)
    MAX-ACCESS read-only
    STATUS     current
    DESCRIPTION
            ""
    ::= { lcsStatusWlanCompetingNetworksEntry 33 }

-- {COLUMN} 1.3.6.1.4.1.2356.11.1.3.44.1.34
lcsStatusWlanCompetingNetworksEntryVendor OBJECT-TYPE
    SYNTAX     DisplayString (SIZE(0..255))
    MAX-ACCESS read-only
    STATUS     current
    DESCRIPTION
            ""
    ::= { lcsStatusWlanCompetingNetworksEntry 34 }

-- {COLUMN} 1.3.6.1.4.1.2356.11.1.3.44.1.35
lcsStatusWlanCompetingNetworksEntryEffRate OBJECT-TYPE
    SYNTAX     Integer32 (0..2147483647)
    MAX-ACCESS read-only
    STATUS     current
    DESCRIPTION
            ""
    ::= { lcsStatusWlanCompetingNetworksEntry 35 }

-- {COLUMN} 1.3.6.1.4.1.2356.11.1.3.44.1.36
lcsStatusWlanCompetingNetworksEntry40mhzCoexistence OBJECT-TYPE
    SYNTAX     INTEGER {
                  eNo (0),
                  eYes (1)
            }
    MAX-ACCESS read-only
    STATUS     current
    DESCRIPTION
            "-- empty --"
    ::= { lcsStatusWlanCompetingNetworksEntry 36 }

-- {COLUMN} 1.3.6.1.4.1.2356.11.1.3.44.1.37
lcsStatusWlanCompetingNetworksEntryPreAuthentication OBJECT-TYPE
    SYNTAX     INTEGER {
                  eNo (0),
                  eYes (1)
            }
    MAX-ACCESS read-only
    STATUS     current
    DESCRIPTION
            "-- empty --"
    ::= { lcsStatusWlanCompetingNetworksEntry 37 }

-- {COLUMN} 1.3.6.1.4.1.2356.11.1.3.44.1.38
lcsStatusWlanCompetingNetworksEntryTxStbc OBJECT-TYPE
    SYNTAX     INTEGER {
                  eNo (0),
                  eYes (1)
            }
    MAX-ACCESS read-only
    STATUS     current
    DESCRIPTION
            "-- empty --"
    ::= { lcsStatusWlanCompetingNetworksEntry 38 }

-- {COLUMN} 1.3.6.1.4.1.2356.11.1.3.44.1.39
lcsStatusWlanCompetingNetworksEntryRxStbc OBJECT-TYPE
    SYNTAX     INTEGER {
                  eNone (0),
                  eOne (1),
                  eTwo (2),
                  eThree (3)
            }
    MAX-ACCESS read-only
    STATUS     current
    DESCRIPTION
            "-- empty --"
    ::= { lcsStatusWlanCompetingNetworksEntry 39 }

-- {COLUMN} 1.3.6.1.4.1.2356.11.1.3.44.1.40
lcsStatusWlanCompetingNetworksEntryEapolPreauthFailed OBJECT-TYPE
    SYNTAX     INTEGER {
                  eNo (0),
                  eYes (1)
            }
    MAX-ACCESS read-only
    STATUS     current
    DESCRIPTION
            "-- empty --"
    ::= { lcsStatusWlanCompetingNetworksEntry 40 }

-- {COLUMN} 1.3.6.1.4.1.2356.11.1.3.44.1.41
lcsStatusWlanCompetingNetworksEntryLdpc OBJECT-TYPE
    SYNTAX     INTEGER {
                  eNo (0),
                  eYes (1)
            }
    MAX-ACCESS read-only
    STATUS     current
    DESCRIPTION
            "-- empty --"
    ::= { lcsStatusWlanCompetingNetworksEntry 41 }

-- {COLUMN} 1.3.6.1.4.1.2356.11.1.3.44.1.42
lcsStatusWlanCompetingNetworksEntryAutowds OBJECT-TYPE
    SYNTAX     INTEGER {
                  eNo (0),
                  eYes (1)
            }
    MAX-ACCESS read-only
    STATUS     current
    DESCRIPTION
            "-- empty --"
    ::= { lcsStatusWlanCompetingNetworksEntry 42 }

-- {COLUMN} 1.3.6.1.4.1.2356.11.1.3.44.1.43
lcsStatusWlanCompetingNetworksEntrySGIMask OBJECT-TYPE
    SYNTAX     BITS {
                  eNo (0),
                  e160mhz (28),
                  e80mhz (29),
                  e40mhz (30),
                  e20mhz (31)
            }
    MAX-ACCESS read-only
    STATUS     current
    DESCRIPTION
            "Bit mask of short guard interval support per-CBW"
    ::= { lcsStatusWlanCompetingNetworksEntry 43 }

-- {COLUMN} 1.3.6.1.4.1.2356.11.1.3.44.1.44
lcsStatusWlanCompetingNetworksEntryChannelBandwidths OBJECT-TYPE
    SYNTAX     BITS {
                  eT40mhz (26),
                  e80Plus80mhz (27),
                  e160mhz (28),
                  e80mhz (29),
                  e40mhz (30),
                  e20mhz (31)
            }
    MAX-ACCESS read-only
    STATUS     current
    DESCRIPTION
            "-- empty --"
    ::= { lcsStatusWlanCompetingNetworksEntry 44 }

-- {COLUMN} 1.3.6.1.4.1.2356.11.1.3.44.1.45
lcsStatusWlanCompetingNetworksEntryChannelBandwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanCompetingNetworksEntry 45 }

-- {COLUMN} 1.3.6.1.4.1.2356.11.1.3.44.1.46
lcsStatusWlanCompetingNetworksEntryClBrgSupport OBJECT-TYPE
    SYNTAX     INTEGER {
                  eNo (0),
                  eYes (1)
            }
    MAX-ACCESS read-only
    STATUS     current
    DESCRIPTION
            "-- empty --"
    ::= { lcsStatusWlanCompetingNetworksEntry 46 }

-- {COLUMN} 1.3.6.1.4.1.2356.11.1.3.44.1.47
lcsStatusWlanCompetingNetworksEntryProtMgmtFrames OBJECT-TYPE
    SYNTAX     INTEGER {
                  eNo (0),
                  eOptional (1),
                  eMandatory (2)
            }
    MAX-ACCESS read-only
    STATUS     current
    DESCRIPTION
            "-- empty --"
    ::= { lcsStatusWlanCompetingNetworksEntry 47 }

-- {COLUMN} 1.3.6.1.4.1.2356.11.1.3.44.1.48
lcsStatusWlanCompetingNetworksEntryTxPowerLimit OBJECT-TYPE
    SYNTAX     DisplayString (SIZE(0..255))
    MAX-ACCESS read-only
    STATUS     current
    DESCRIPTION
            "-- empty --"
    ::= { lcsStatusWlanCompetingNetworksEntry 48 }

-- {COLUMN} 1.3.6.1.4.1.2356.11.1.3.44.1.49
lcsStatusWlanCompetingNetworksEntryTxSTBCMask OBJECT-TYPE
    SYNTAX     BITS {
                  eVht (30),
                  eHt (31)
            }
    MAX-ACCESS read-only
    STATUS     current
    DESCRIPTION
            "Bit mask of Tx STBC support per-PHY-Type"
    ::= { lcsStatusWlanCompetingNetworksEntry 49 }

-- {COLUMN} 1.3.6.1.4.1.2356.11.1.3.44.1.50
lcsStatusWlanCompetingNetworksEntryRxStbcHt OBJECT-TYPE
    SYNTAX     INTEGER {
                  eNone (0),
                  eOne (1),
                  eTwo (2),
                  eThree (3)
            }
    MAX-ACCESS read-only
    STATUS     current
    DESCRIPTION
            "-- empty --"
    ::= { lcsStatusWlanCompetingNetworksEntry 50 }

-- {COLUMN} 1.3.6.1.4.1.2356.11.1.3.44.1.51
lcsStatusWlanCompetingNetworksEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { lcsStatusWlanCompetingNetworksEntry 51 }

-- {COLUMN} 1.3.6.1.4.1.2356.11.1.3.44.1.52
lcsStatusWlanCompetingNetworksEntryLDPCMask OBJECT-TYPE
    SYNTAX     BITS {
                  eVht (30),
                  eHt (31)
            }
    MAX-ACCESS read-only
    STATUS     current
    DESCRIPTION
            "Bit mask of LDPC support per-PHY-Type"
    ::= { lcsStatusWlanCompetingNetworksEntry 52 }

-- {COLUMN} 1.3.6.1.4.1.2356.11.1.3.44.1.53
lcsStatusWlanCompetingNetworksEntryUuid OBJECT-TYPE
    SYNTAX     DisplayString (SIZE(0..255))
    MAX-ACCESS read-only
    STATUS     current
    DESCRIPTION
            "-- empty --"
    ::= { lcsStatusWlanCompetingNetworksEntry 53 }

-- {COLUMN} 1.3.6.1.4.1.2356.11.1.3.44.1.54
lcsStatusWlanCompetingNetworksEntry11acBeamforming OBJECT-TYPE
    SYNTAX     BITS {
                  eMuBfee (28),
                  eMuBfer (29),
                  eSuBfee (30),
                  eSuBfer (31)
            }
    MAX-ACCESS read-only
    STATUS     current
    DESCRIPTION
            "-- empty --"
    ::= { lcsStatusWlanCompetingNetworksEntry 54 }

-- {COLUMN} 1.3.6.1.4.1.2356.11.1.3.44.1.55
lcsStatusWlanCompetingNetworksEntrySecondaryChannel OBJECT-TYPE
    SYNTAX     Integer32 (0..255)
    MAX-ACCESS read-only
    STATUS     current
    DESCRIPTION
            "-- empty --"
    ::= { lcsStatusWlanCompetingNetworksEntry 55 }

-- {COLUMN} 1.3.6.1.4.1.2356.11.1.3.44.1.56
lcsStatusWlanCompetingNetworksEntryTransitionalMode OBJECT-TYPE
    SYNTAX     INTEGER {
                  eNo (0),
                  eYes (1)
            }
    MAX-ACCESS read-only
    STATUS     current
    DESCRIPTION
            "-- empty --"
    ::= { lcsStatusWlanCompetingNetworksEntry 56 }

-- {COLUMN} 1.3.6.1.4.1.2356.11.1.3.44.1.57
lcsStatusWlanCompetingNetworksEntryTransitionalSsid OBJECT-TYPE
    SYNTAX     DisplayString (SIZE(0..255))
    MAX-ACCESS read-only
    STATUS     current
    DESCRIPTION
            "-- empty --"
    ::= { lcsStatusWlanCompetingNetworksEntry 57 }

-- {COLUMN} 1.3.6.1.4.1.2356.11.1.3.44.1.58
lcsStatusWlanCompetingNetworksEntryTransitionalBssid OBJECT-TYPE
    SYNTAX     MacAddress
    MAX-ACCESS read-only
    STATUS     current
    DESCRIPTION
            "-- empty --"
    ::= { lcsStatusWlanCompetingNetworksEntry 58 }

-- {COLUMN} 1.3.6.1.4.1.2356.11.1.3.44.1.59
lcsStatusWlanCompetingNetworksEntryQosMapping OBJECT-TYPE
    SYNTAX     INTEGER {
                  eNo (0),
                  eYes (1)
            }
    MAX-ACCESS read-only
    STATUS     current
    DESCRIPTION
            "-- empty --"
    ::= { lcsStatusWlanCompetingNetworksEntry 59 }

-- {TABLE} 1.3.6.1.4.1.2356.11.1.3.45
lcsStatusWlanSeenClientsTable OBJECT-TYPE
    SYNTAX     SEQUENCE OF LcsStatusWlanSeenClientsEntry
    MAX-ACCESS not-accessible
    STATUS     current
    DESCRIPTION
            ""
    ::= { lcsStatusWlan 45 }

-- {ROW} 1.3.6.1.4.1.2356.11.1.3.45.1
lcsStatusWlanSeenClientsEntry OBJECT-TYPE
    SYNTAX     LcsStatusWlanSeenClientsEntry
    MAX-ACCESS not-accessible
    STATUS     current
    DESCRIPTION
            ""
    INDEX {
            lcsStatusWlanSeenClientsEntryMacAddress,
            lcsStatusWlanSeenClientsEntryInterface
          }
    ::= { lcsStatusWlanSeenClientsTable 1 }

LcsStatusWlanSeenClientsEntry ::= SEQUENCE {
            lcsStatusWlanSeenClientsEntryMacAddress MacAddress,
            lcsStatusWlanSeenClientsEntryInterface INTEGER,
            lcsStatusWlanSeenClientsEntrySignalLevel Integer32,
            lcsStatusWlanSeenClientsEntryAge Integer32,
            lcsStatusWlanSeenClientsEntryNetworkName DisplayString,
            lcsStatusWlanSeenClientsEntryRxPhySignal Integer32,
            lcsStatusWlanSeenClientsEntryNumProbes Counter32,
            lcsStatusWlanSeenClientsEntryVendor DisplayString,
            lcsStatusWlanSeenClientsEntryNumProberspOk Counter32,
            lcsStatusWlanSeenClientsEntryNumProberspBad Counter32,
            lcsStatusWlanSeenClientsEntryRadioBand INTEGER,
            lcsStatusWlanSeenClientsEntryNumProberspSuppressed Counter32
    }

-- {COLUMN} 1.3.6.1.4.1.2356.11.1.3.45.1.1
lcsStatusWlanSeenClientsEntryMacAddress OBJECT-TYPE
    SYNTAX     MacAddress
    MAX-ACCESS read-only
    STATUS     current
    DESCRIPTION
            ""
    ::= { lcsStatusWlanSeenClientsEntry 1 }

-- {COLUMN} 1.3.6.1.4.1.2356.11.1.3.45.1.2
lcsStatusWlanSeenClientsEntryInterface OBJECT-TYPE
    SYNTAX     INTEGER {
                  eWlan1 (0),
                  eWlan2 (1),
                  eWlan3 (2),
                  eWlan4 (3)
            }
    MAX-ACCESS read-only
    STATUS     current
    DESCRIPTION
            ""
    ::= { lcsStatusWlanSeenClientsEntry 2 }

-- {COLUMN} 1.3.6.1.4.1.2356.11.1.3.45.1.3
lcsStatusWlanSeenClientsEntrySignalLevel OBJECT-TYPE
    SYNTAX     Integer32 (-128..127)
    MAX-ACCESS read-only
    STATUS     current
    DESCRIPTION
            ""
    ::= { lcsStatusWlanSeenClientsEntry 3 }

-- {COLUMN} 1.3.6.1.4.1.2356.11.1.3.45.1.4
lcsStatusWlanSeenClientsEntryAge OBJECT-TYPE
    SYNTAX     Integer32 (0..2147483647)
    MAX-ACCESS read-only
    STATUS     current
    DESCRIPTION
            ""
    ::= { lcsStatusWlanSeenClientsEntry 4 }

-- {COLUMN} 1.3.6.1.4.1.2356.11.1.3.45.1.5
lcsStatusWlanSeenClientsEntryNetworkName OBJECT-TYPE
    SYNTAX     DisplayString (SIZE(0..32))
    MAX-ACCESS read-only
    STATUS     current
    DESCRIPTION
            ""
    ::= { lcsStatusWlanSeenClientsEntry 5 }

-- {COLUMN} 1.3.6.1.4.1.2356.11.1.3.45.1.6
lcsStatusWlanSeenClientsEntryRxPhySignal OBJECT-TYPE
    SYNTAX     Integer32 (0..65535)
    MAX-ACCESS read-only
    STATUS     current
    DESCRIPTION
            ""
    ::= { lcsStatusWlanSeenClientsEntry 6 }

-- {COLUMN} 1.3.6.1.4.1.2356.11.1.3.45.1.7
lcsStatusWlanSeenClientsEntryNumProbes OBJECT-TYPE
    SYNTAX     Counter32
    MAX-ACCESS read-only
    STATUS     current
    DESCRIPTION
            ""
    ::= { lcsStatusWlanSeenClientsEntry 7 }

-- {COLUMN} 1.3.6.1.4.1.2356.11.1.3.45.1.8
lcsStatusWlanSeenClientsEntryVendor OBJECT-TYPE
    SYNTAX     DisplayString (SIZE(0..255))
    MAX-ACCESS read-only
    STATUS     current
    DESCRIPTION
            ""
    ::= { lcsStatusWlanSeenClientsEntry 8 }

-- {COLUMN} 1.3.6.1.4.1.2356.11.1.3.45.1.9
lcsStatusWlanSeenClientsEntryNumProberspOk OBJECT-TYPE
    SYNTAX     Counter32
    MAX-ACCESS read-only
    STATUS     current
    DESCRIPTION
            "-- empty --"
    ::= { lcsStatusWlanSeenClientsEntry 9 }

-- {COLUMN} 1.3.6.1.4.1.2356.11.1.3.45.1.10
lcsStatusWlanSeenClientsEntryNumProberspBad OBJECT-TYPE
    SYNTAX     Counter32
    MAX-ACCESS read-only
    STATUS     current
    DESCRIPTION
            "-- empty --"
    ::= { lcsStatusWlanSeenClientsEntry 10 }

-- {COLUMN} 1.3.6.1.4.1.2356.11.1.3.45.1.11
lcsStatusWlanSeenClientsEntryRadioBand OBJECT-TYPE
    SYNTAX     INTEGER {
                  eUnknown (0),
                  e24ghz (1),
                  e5ghz (2)
            }
    MAX-ACCESS read-only
    STATUS     current
    DESCRIPTION
            "-- empty --"
    ::= { lcsStatusWlanSeenClientsEntry 11 }

-- {COLUMN} 1.3.6.1.4.1.2356.11.1.3.45.1.12
lcsStatusWlanSeenClientsEntryNumProberspSuppressed OBJECT-TYPE
    SYNTAX     Counter32
    MAX-ACCESS read-only
    STATUS     current
    DESCRIPTION
            "-- empty --"
    ::= { lcsStatusWlanSeenClientsEntry 12 }

-- {TABLE} 1.3.6.1.4.1.2356.11.1.3.46
lcsStatusWlanLogTableTable OBJECT-TYPE
    SYNTAX     SEQUENCE OF LcsStatusWlanLogTableEntry
    MAX-ACCESS not-accessible
    STATUS     current
    DESCRIPTION
            ""
    ::= { lcsStatusWlan 46 }

-- {ROW} 1.3.6.1.4.1.2356.11.1.3.46.1
lcsStatusWlanLogTableEntry OBJECT-TYPE
    SYNTAX     LcsStatusWlanLogTableEntry
    MAX-ACCESS not-accessible
    STATUS     current
    DESCRIPTION
            ""
    INDEX {
            lcsStatusWlanLogTableEntryIndex
          }
    ::= { lcsStatusWlanLogTableTable 1 }

LcsStatusWlanLogTableEntry ::= SEQUENCE {
            lcsStatusWlanLogTableEntryIndex Integer32,
            lcsStatusWlanLogTableEntryTime DisplayString,
            lcsStatusWlanLogTableEntryInterface INTEGER,
            lcsStatusWlanLogTableEntryEvent DisplayString,
            lcsStatusWlanLogTableEntryAddress MacAddress,
            lcsStatusWlanLogTableEntryReason DisplayString
    }

-- {COLUMN} 1.3.6.1.4.1.2356.11.1.3.46.1.1
lcsStatusWlanLogTableEntryIndex OBJECT-TYPE
    SYNTAX     Integer32 (0..2147483647)
    MAX-ACCESS read-only
    STATUS     current
    DESCRIPTION
            ""
    ::= { lcsStatusWlanLogTableEntry 1 }

-- {COLUMN} 1.3.6.1.4.1.2356.11.1.3.46.1.2
lcsStatusWlanLogTableEntryTime OBJECT-TYPE
    SYNTAX     DisplayString (SIZE(0..255))
    MAX-ACCESS read-only
    STATUS     current
    DESCRIPTION
            ""
    ::= { lcsStatusWlanLogTableEntry 2 }

-- {COLUMN} 1.3.6.1.4.1.2356.11.1.3.46.1.3
lcsStatusWlanLogTableEntryInterface OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46),
                  eP2p11 (1025),
                  eP2p12 (1026),
                  eP2p13 (1027),
                  eP2p14 (1028),
                  eP2p15 (1029),
                  eP2p16 (1030),
                  eP2p21 (1031),
                  eP2p22 (1032),
                  eP2p23 (1033),
                  eP2p24 (1034),
                  eP2p25 (1035),
                  eP2p26 (1036),
                  eP2p17 (1056),
                  eP2p18 (1057),
                  eP2p19 (1058),
                  eP2p110 (1059),
                  eP2p111 (1060),
                  eP2p112 (1061),
                  eP2p113 (1062),
                  eP2p114 (1063),
                  eP2p115 (1064),
                  eP2p116 (1065),
                  eP2p27 (1088),
                  eP2p28 (1089),
                  eP2p29 (1090),
                  eP2p210 (1091),
                  eP2p211 (1092),
                  eP2p212 (1093),
                  eP2p213 (1094),
                  eP2p214 (1095),
                  eP2p215 (1096),
                  eP2p216 (1097)
            }
    MAX-ACCESS read-only
    STATUS     current
    DESCRIPTION
            ""
    ::= { lcsStatusWlanLogTableEntry 3 }

-- {COLUMN} 1.3.6.1.4.1.2356.11.1.3.46.1.4
lcsStatusWlanLogTableEntryEvent OBJECT-TYPE
    SYNTAX     DisplayString (SIZE(0..255))
    MAX-ACCESS read-only
    STATUS     current
    DESCRIPTION
            ""
    ::= { lcsStatusWlanLogTableEntry 4 }

-- {COLUMN} 1.3.6.1.4.1.2356.11.1.3.46.1.5
lcsStatusWlanLogTableEntryAddress OBJECT-TYPE
    SYNTAX     MacAddress
    MAX-ACCESS read-only
    STATUS     current
    DESCRIPTION
            ""
    ::= { lcsStatusWlanLogTableEntry 5 }

-- {COLUMN} 1.3.6.1.4.1.2356.11.1.3.46.1.6
lcsStatusWlanLogTableEntryReason OBJECT-TYPE
    SYNTAX     DisplayString (SIZE(0..255))
    MAX-ACCESS read-only
    STATUS     current
    DESCRIPTION
            ""
    ::= { lcsStatusWlanLogTableEntry 6 }

-- {TABLE} 1.3.6.1.4.1.2356.11.1.3.47
lcsStatusWlanPairwiseKeysTable OBJECT-TYPE
    SYNTAX     SEQUENCE OF LcsStatusWlanPairwiseKeysEntry
    MAX-ACCESS not-accessible
    STATUS     current
    DESCRIPTION
            ""
    ::= { lcsStatusWlan 47 }

-- {ROW} 1.3.6.1.4.1.2356.11.1.3.47.1
lcsStatusWlanPairwiseKeysEntry OBJECT-TYPE
    SYNTAX     LcsStatusWlanPairwiseKeysEntry
    MAX-ACCESS not-accessible
    STATUS     current
    DESCRIPTION
            ""
    INDEX {
            lcsStatusWlanPairwiseKeysEntryIndex
          }
    ::= { lcsStatusWlanPairwiseKeysTable 1 }

LcsStatusWlanPairwiseKeysEntry ::= SEQUENCE {
            lcsStatusWlanPairwiseKeysEntryIndex Integer32,
            lcsStatusWlanPairwiseKeysEntryKeyType INTEGER,
            lcsStatusWlanPairwiseKeysEntryKeyValue DisplayString,
            lcsStatusWlanPairwiseKeysEntryTsc DisplayString,
            lcsStatusWlanPairwiseKeysEntryAge Integer32,
            lcsStatusWlanPairwiseKeysEntryIvSequenceErrors Integer32,
            lcsStatusWlanPairwiseKeysEntryRscBe DisplayString,
            lcsStatusWlanPairwiseKeysEntryRscBk DisplayString,
            lcsStatusWlanPairwiseKeysEntryRscEe DisplayString,
            lcsStatusWlanPairwiseKeysEntryRscCl DisplayString,
            lcsStatusWlanPairwiseKeysEntryRscVi DisplayString,
            lcsStatusWlanPairwiseKeysEntryRscVo DisplayString,
            lcsStatusWlanPairwiseKeysEntryRscNc DisplayString,
            lcsStatusWlanPairwiseKeysEntryRscMgmt DisplayString
    }

-- {COLUMN} 1.3.6.1.4.1.2356.11.1.3.47.1.1
lcsStatusWlanPairwiseKeysEntryIndex OBJECT-TYPE
    SYNTAX     Integer32 (0..65535)
    MAX-ACCESS read-only
    STATUS     current
    DESCRIPTION
            ""
    ::= { lcsStatusWlanPairwiseKeysEntry 1 }

-- {COLUMN} 1.3.6.1.4.1.2356.11.1.3.47.1.3
lcsStatusWlanPairwiseKeysEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eAesCcmp256 (67),
                  eBip (68),
                  eBipCmac256 (69),
                  eAesGcmp128 (70),
                  eAesGcmp256 (71),
                  eBipGmac128 (72),
                  eBipGmac256 (73)
            }
    MAX-ACCESS read-only
    STATUS     current
    DESCRIPTION
            ""
    ::= { lcsStatusWlanPairwiseKeysEntry 3 }

-- {COLUMN} 1.3.6.1.4.1.2356.11.1.3.47.1.4
lcsStatusWlanPairwiseKeysEntryKeyValue OBJECT-TYPE
    SYNTAX     DisplayString (SIZE(0..255))
    MAX-ACCESS read-only
    STATUS     current
    DESCRIPTION
            ""
    ::= { lcsStatusWlanPairwiseKeysEntry 4 }

-- {COLUMN} 1.3.6.1.4.1.2356.11.1.3.47.1.5
lcsStatusWlanPairwiseKeysEntryTsc OBJECT-TYPE
    SYNTAX     DisplayString (SIZE(0..255))
    MAX-ACCESS read-only
    STATUS     current
    DESCRIPTION
            ""
    ::= { lcsStatusWlanPairwiseKeysEntry 5 }

-- {COLUMN} 1.3.6.1.4.1.2356.11.1.3.47.1.7
lcsStatusWlanPairwiseKeysEntryAge OBJECT-TYPE
    SYNTAX     Integer32 (0..2147483647)
    MAX-ACCESS read-only
    STATUS     current
    DESCRIPTION
            ""
    ::= { lcsStatusWlanPairwiseKeysEntry 7 }

-- {COLUMN} 1.3.6.1.4.1.2356.11.1.3.47.1.8
lcsStatusWlanPairwiseKeysEntryIvSequenceErrors OBJECT-TYPE
    SYNTAX     Integer32 (0..2147483647)
    MAX-ACCESS read-only
    STATUS     current
    DESCRIPTION
            ""
    ::= { lcsStatusWlanPairwiseKeysEntry 8 }

-- {COLUMN} 1.3.6.1.4.1.2356.11.1.3.47.1.16
lcsStatusWlanPairwiseKeysEntryRscBe OBJECT-TYPE
    SYNTAX     DisplayString (SIZE(0..255))
    MAX-ACCESS read-only
    STATUS     current
    DESCRIPTION
            ""
    ::= { lcsStatusWlanPairwiseKeysEntry 16 }

-- {COLUMN} 1.3.6.1.4.1.2356.11.1.3.47.1.17
lcsStatusWlanPairwiseKeysEntryRscBk OBJECT-TYPE
    SYNTAX     DisplayString (SIZE(0..255))
    MAX-ACCESS read-only
    STATUS     current
    DESCRIPTION
            ""
    ::= { lcsStatusWlanPairwiseKeysEntry 17 }

-- {COLUMN} 1.3.6.1.4.1.2356.11.1.3.47.1.19
lcsStatusWlanPairwiseKeysEntryRscEe OBJECT-TYPE
    SYNTAX     DisplayString (SIZE(0..255))
    MAX-ACCESS read-only
    STATUS     current
    DESCRIPTION
            ""
    ::= { lcsStatusWlanPairwiseKeysEntry 19 }

-- {COLUMN} 1.3.6.1.4.1.2356.11.1.3.47.1.20
lcsStatusWlanPairwiseKeysEntryRscCl OBJECT-TYPE
    SYNTAX     DisplayString (SIZE(0..255))
    MAX-ACCESS read-only
    STATUS     current
    DESCRIPTION
            ""
    ::= { lcsStatusWlanPairwiseKeysEntry 20 }

-- {COLUMN} 1.3.6.1.4.1.2356.11.1.3.47.1.21
lcsStatusWlanPairwiseKeysEntryRscVi OBJECT-TYPE
    SYNTAX     DisplayString (SIZE(0..255))
    MAX-ACCESS read-only
    STATUS     current
    DESCRIPTION
            ""
    ::= { lcsStatusWlanPairwiseKeysEntry 21 }

-- {COLUMN} 1.3.6.1.4.1.2356.11.1.3.47.1.22
lcsStatusWlanPairwiseKeysEntryRscVo OBJECT-TYPE
    SYNTAX     DisplayString (SIZE(0..255))
    MAX-ACCESS read-only
    STATUS     current
    DESCRIPTION
            ""
    ::= { lcsStatusWlanPairwiseKeysEntry 22 }

-- {COLUMN} 1.3.6.1.4.1.2356.11.1.3.47.1.23
lcsStatusWlanPairwiseKeysEntryRscNc OBJECT-TYPE
    SYNTAX     DisplayString (SIZE(0..255))
    MAX-ACCESS read-only
    STATUS     current
    DESCRIPTION
            ""
    ::= { lcsStatusWlanPairwiseKeysEntry 23 }

-- {COLUMN} 1.3.6.1.4.1.2356.11.1.3.47.1.24
lcsStatusWlanPairwiseKeysEntryRscMgmt OBJECT-TYPE
    SYNTAX     DisplayString (SIZE(0..255))
    MAX-ACCESS read-only
    STATUS     current
    DESCRIPTION
            "-- empty --"
    ::= { lcsStatusWlanPairwiseKeysEntry 24 }

-- {TABLE} 1.3.6.1.4.1.2356.11.1.3.48
lcsStatusWlanRadiusCacheTable OBJECT-TYPE
    SYNTAX     SEQUENCE OF LcsStatusWlanRadiusCacheEntry
    MAX-ACCESS not-accessible
    STATUS     current
    DESCRIPTION
            ""
    ::= { lcsStatusWlan 48 }

-- {ROW} 1.3.6.1.4.1.2356.11.1.3.48.1
lcsStatusWlanRadiusCacheEntry OBJECT-TYPE
    SYNTAX     LcsStatusWlanRadiusCacheEntry
    MAX-ACCESS not-accessible
    STATUS     current
    DESCRIPTION
            ""
    INDEX {
            lcsStatusWlanRadiusCacheEntryMacAddress
          }
    ::= { lcsStatusWlanRadiusCacheTable 1 }

LcsStatusWlanRadiusCacheEntry ::= SEQUENCE {
            lcsStatusWlanRadiusCacheEntryMacAddress MacAddress,
            lcsStatusWlanRadiusCacheEntryAllowed INTEGER,
            lcsStatusWlanRadiusCacheEntryAge Integer32
    }

-- {COLUMN} 1.3.6.1.4.1.2356.11.1.3.48.1.1
lcsStatusWlanRadiusCacheEntryMacAddress OBJECT-TYPE
    SYNTAX     MacAddress
    MAX-ACCESS read-only
    STATUS     current
    DESCRIPTION
            ""
    ::= { lcsStatusWlanRadiusCacheEntry 1 }

-- {COLUMN} 1.3.6.1.4.1.2356.11.1.3.48.1.2
lcsStatusWlanRadiusCacheEntryAllowed OBJECT-TYPE
    SYNTAX     INTEGER {
                  eNo (0),
                  eYes (1)
            }
    MAX-ACCESS read-only
    STATUS     current
    DESCRIPTION
            ""
    ::= { lcsStatusWlanRadiusCacheEntry 2 }

-- {COLUMN} 1.3.6.1.4.1.2356.11.1.3.48.1.3
lcsStatusWlanRadiusCacheEntryAge OBJECT-TYPE
    SYNTAX     Integer32 (0..2147483647)
    MAX-ACCESS read-only
    STATUS     current
    DESCRIPTION
            ""
    ::= { lcsStatusWlanRadiusCacheEntry 3 }

-- {SCALAR} 1.3.6.1.4.1.2356.11.1.3.49
lcsStatusWlanClearLogTable OBJECT-TYPE
    SYNTAX     DisplayString
    MAX-ACCESS read-write
    STATUS     current
    DESCRIPTION
            "-- empty --"
    ::= { lcsStatusWlan 49 }

-- {SCALAR} 1.3.6.1.4.1.2356.11.1.3.50
lcsStatusWlanClearSeenClientsTable OBJECT-TYPE
    SYNTAX     DisplayString
    MAX-ACCESS read-write
    STATUS     current
    DESCRIPTION
            "-- empty --"
    ::= { lcsStatusWlan 50 }

-- {TABLE} 1.3.6.1.4.1.2356.11.1.3.51
lcsStatusWlanIfcsTable OBJECT-TYPE
    SYNTAX     SEQUENCE OF LcsStatusWlanIfcsEntry
    MAX-ACCESS not-accessible
    STATUS     current
    DESCRIPTION
            ""
    ::= { lcsStatusWlan 51 }

-- {ROW} 1.3.6.1.4.1.2356.11.1.3.51.1
lcsStatusWlanIfcsEntry OBJECT-TYPE
    SYNTAX     LcsStatusWlanIfcsEntry
    MAX-ACCESS not-accessible
    STATUS     current
    DESCRIPTION
            ""
    INDEX {
            lcsStatusWlanIfcsEntryIfc
          }
    ::= { lcsStatusWlanIfcsTable 1 }

LcsStatusWlanIfcsEntry ::= SEQUENCE {
            lcsStatusWlanIfcsEntryIfc DisplayString,
            lcsStatusWlanIfcsEntryMacAddress MacAddress,
            lcsStatusWlanIfcsEntryOperating INTEGER,
            lcsStatusWlanIfcsEntryQueuePackets Integer32,
            lcsStatusWlanIfcsEntryCardId DisplayString,
            lcsStatusWlanIfcsEntryFirmwareVersion DisplayString,
            lcsStatusWlanIfcsEntrySerialNumber DisplayString,
            lcsStatusWlanIfcsEntryNumStations Integer32,
            lcsStatusWlanIfcsEntryOperationMode INTEGER,
            lcsStatusWlanIfcsEntryTemperature DisplayString,
            lcsStatusWlanIfcsEntryNumericTemperature Integer32,
            lcsStatusWlanIfcsEntryNumReorderHeap Integer32
    }

-- {COLUMN} 1.3.6.1.4.1.2356.11.1.3.51.1.1
lcsStatusWlanIfcsEntryIfc OBJECT-TYPE
    SYNTAX     DisplayString (SIZE(0..255))
    MAX-ACCESS read-only
    STATUS     current
    DESCRIPTION
            ""
    ::= { lcsStatusWlanIfcsEntry 1 }

-- {COLUMN} 1.3.6.1.4.1.2356.11.1.3.51.1.2
lcsStatusWlanIfcsEntryMacAddress OBJECT-TYPE
    SYNTAX     MacAddress
    MAX-ACCESS read-only
    STATUS     current
    DESCRIPTION
            ""
    ::= { lcsStatusWlanIfcsEntry 2 }

-- {COLUMN} 1.3.6.1.4.1.2356.11.1.3.51.1.3
lcsStatusWlanIfcsEntryOperating OBJECT-TYPE
    SYNTAX     INTEGER {
                  eNo (0),
                  eYes (1)
            }
    MAX-ACCESS read-only
    STATUS     current
    DESCRIPTION
            ""
    ::= { lcsStatusWlanIfcsEntry 3 }

-- {COLUMN} 1.3.6.1.4.1.2356.11.1.3.51.1.4
lcsStatusWlanIfcsEntryQueuePackets OBJECT-TYPE
    SYNTAX     Integer32 (0..2147483647)
    MAX-ACCESS read-only
    STATUS     current
    DESCRIPTION
            ""
    ::= { lcsStatusWlanIfcsEntry 4 }

-- {COLUMN} 1.3.6.1.4.1.2356.11.1.3.51.1.5
lcsStatusWlanIfcsEntryCardId OBJECT-TYPE
    SYNTAX     DisplayString (SIZE(0..255))
    MAX-ACCESS read-only
    STATUS     current
    DESCRIPTION
            ""
    ::= { lcsStatusWlanIfcsEntry 5 }

-- {COLUMN} 1.3.6.1.4.1.2356.11.1.3.51.1.6
lcsStatusWlanIfcsEntryFirmwareVersion OBJECT-TYPE
    SYNTAX     DisplayString (SIZE(0..255))
    MAX-ACCESS read-only
    STATUS     current
    DESCRIPTION
            ""
    ::= { lcsStatusWlanIfcsEntry 6 }

-- {COLUMN} 1.3.6.1.4.1.2356.11.1.3.51.1.7
lcsStatusWlanIfcsEntrySerialNumber OBJECT-TYPE
    SYNTAX     DisplayString (SIZE(0..255))
    MAX-ACCESS read-only
    STATUS     current
    DESCRIPTION
            ""
    ::= { lcsStatusWlanIfcsEntry 7 }

-- {COLUMN} 1.3.6.1.4.1.2356.11.1.3.51.1.8
lcsStatusWlanIfcsEntryNumStations OBJECT-TYPE
    SYNTAX     Integer32 (0..65535)
    MAX-ACCESS read-only
    STATUS     current
    DESCRIPTION
            ""
    ::= { lcsStatusWlanIfcsEntry 8 }

-- {COLUMN} 1.3.6.1.4.1.2356.11.1.3.51.1.9
lcsStatusWlanIfcsEntryOperationMode OBJECT-TYPE
    SYNTAX     INTEGER {
                  eStation (0),
                  eAccessPoint (1),
                  eMonitor (2),
                  eManagedAp (4),
                  eProbe (5),
                  eManagedProbe (6),
                  eScanner (7)
            }
    MAX-ACCESS read-only
    STATUS     current
    DESCRIPTION
            "lancom's description of operation mode"
    ::= { lcsStatusWlanIfcsEntry 9 }

-- {COLUMN} 1.3.6.1.4.1.2356.11.1.3.51.1.10
lcsStatusWlanIfcsEntryTemperature OBJECT-TYPE
    SYNTAX     DisplayString (SIZE(0..255))
    MAX-ACCESS read-only
    STATUS     current
    DESCRIPTION
            "-- empty --"
    ::= { lcsStatusWlanIfcsEntry 10 }

-- {COLUMN} 1.3.6.1.4.1.2356.11.1.3.51.1.11
lcsStatusWlanIfcsEntryNumericTemperature OBJECT-TYPE
    SYNTAX     Integer32 (-32768..32767)
    MAX-ACCESS read-only
    STATUS     current
    DESCRIPTION
            "-- empty --"
    ::= { lcsStatusWlanIfcsEntry 11 }

-- {COLUMN} 1.3.6.1.4.1.2356.11.1.3.51.1.12
lcsStatusWlanIfcsEntryNumReorderHeap OBJECT-TYPE
    SYNTAX     Integer32 (0..2147483647)
    MAX-ACCESS read-only
    STATUS     current
    DESCRIPTION
            "-- empty --"
    ::= { lcsStatusWlanIfcsEntry 12 }

-- {TABLE} 1.3.6.1.4.1.2356.11.1.3.52
lcsStatusWlanByteTransportTable OBJECT-TYPE
    SYNTAX     SEQUENCE OF LcsStatusWlanByteTransportEntry
    MAX-ACCESS not-accessible
    STATUS     current
    DESCRIPTION
            ""
    ::= { lcsStatusWlan 52 }

-- {ROW} 1.3.6.1.4.1.2356.11.1.3.52.1
lcsStatusWlanByteTransportEntry OBJECT-TYPE
    SYNTAX     LcsStatusWlanByteTransportEntry
    MAX-ACCESS not-accessible
    STATUS     current
    DESCRIPTION
            ""
    INDEX {
            lcsStatusWlanByteTransportEntryIfc
          }
    ::= { lcsStatusWlanByteTransportTable 1 }

LcsStatusWlanByteTransportEntry ::= SEQUENCE {
            lcsStatusWlanByteTransportEntryIfc DisplayString,
            lcsStatusWlanByteTransportEntryTxBytes Counter64,
            lcsStatusWlanByteTransportEntryRxBytes Counter64,
            lcsStatusWlanByteTransportEntryThroughput DisplayString,
            lcsStatusWlanByteTransportEntryMaxThroughput DisplayString,
            lcsStatusWlanByteTransportEntryBytesThroughput Integer32,
            lcsStatusWlanByteTransportEntryBytesMaxThroughput Integer32
    }

-- {COLUMN} 1.3.6.1.4.1.2356.11.1.3.52.1.1
lcsStatusWlanByteTransportEntryIfc OBJECT-TYPE
    SYNTAX     DisplayString (SIZE(0..255))
    MAX-ACCESS read-only
    STATUS     current
    DESCRIPTION
            ""
    ::= { lcsStatusWlanByteTransportEntry 1 }

-- {COLUMN} 1.3.6.1.4.1.2356.11.1.3.52.1.2
lcsStatusWlanByteTransportEntryTxBytes OBJECT-TYPE
    SYNTAX     Counter64
    MAX-ACCESS read-only
    STATUS     current
    DESCRIPTION
            ""
    ::= { lcsStatusWlanByteTransportEntry 2 }

-- {COLUMN} 1.3.6.1.4.1.2356.11.1.3.52.1.3
lcsStatusWlanByteTransportEntryRxBytes OBJECT-TYPE
    SYNTAX     Counter64
    MAX-ACCESS read-only
    STATUS     current
    DESCRIPTION
            ""
    ::= { lcsStatusWlanByteTransportEntry 3 }

-- {COLUMN} 1.3.6.1.4.1.2356.11.1.3.52.1.4
lcsStatusWlanByteTransportEntryThroughput OBJECT-TYPE
    SYNTAX     DisplayString (SIZE(0..255))
    MAX-ACCESS read-only
    STATUS     current
    DESCRIPTION
            ""
    ::= { lcsStatusWlanByteTransportEntry 4 }

-- {COLUMN} 1.3.6.1.4.1.2356.11.1.3.52.1.5
lcsStatusWlanByteTransportEntryMaxThroughput OBJECT-TYPE
    SYNTAX     DisplayString (SIZE(0..255))
    MAX-ACCESS read-only
    STATUS     current
    DESCRIPTION
            ""
    ::= { lcsStatusWlanByteTransportEntry 5 }

-- {COLUMN} 1.3.6.1.4.1.2356.11.1.3.52.1.6
lcsStatusWlanByteTransportEntryBytesThroughput OBJECT-TYPE
    SYNTAX     Integer32 (0..2147483647)
    MAX-ACCESS read-only
    STATUS     current
    DESCRIPTION
            ""
    ::= { lcsStatusWlanByteTransportEntry 6 }

-- {COLUMN} 1.3.6.1.4.1.2356.11.1.3.52.1.7
lcsStatusWlanByteTransportEntryBytesMaxThroughput OBJECT-TYPE
    SYNTAX     Integer32 (0..2147483647)
    MAX-ACCESS read-only
    STATUS     current
    DESCRIPTION
            ""
    ::= { lcsStatusWlanByteTransportEntry 7 }

-- {TABLE} 1.3.6.1.4.1.2356.11.1.3.53
lcsStatusWlanPacketTransportTable OBJECT-TYPE
    SYNTAX     SEQUENCE OF LcsStatusWlanPacketTransportEntry
    MAX-ACCESS not-accessible
    STATUS     current
    DESCRIPTION
            ""
    ::= { lcsStatusWlan 53 }

-- {ROW} 1.3.6.1.4.1.2356.11.1.3.53.1
lcsStatusWlanPacketTransportEntry OBJECT-TYPE
    SYNTAX     LcsStatusWlanPacketTransportEntry
    MAX-ACCESS not-accessible
    STATUS     current
    DESCRIPTION
            ""
    INDEX {
            lcsStatusWlanPacketTransportEntryIfc
          }
    ::= { lcsStatusWlanPacketTransportTable 1 }

LcsStatusWlanPacketTransportEntry ::= SEQUENCE {
            lcsStatusWlanPacketTransportEntryIfc DisplayString,
            lcsStatusWlanPacketTransportEntryRxPackets Counter32,
            lcsStatusWlanPacketTransportEntryTxPackets Counter32,
            lcsStatusWlanPacketTransportEntryRxBroadcasts Counter32,
            lcsStatusWlanPacketTransportEntryRxMulticasts Counter32,
            lcsStatusWlanPacketTransportEntryRxUnicasts Counter32,
            lcsStatusWlanPacketTransportEntryTxBroadcasts Counter32,
            lcsStatusWlanPacketTransportEntryTxMulticasts Counter32,
            lcsStatusWlanPacketTransportEntryTxUnicasts Counter32,
            lcsStatusWlanPacketTransportEntryTxAggregates Counter32,
            lcsStatusWlanPacketTransportEntryTxAggrFrames Counter32,
            lcsStatusWlanPacketTransportEntryRxAggregates Counter32,
            lcsStatusWlanPacketTransportEntryRxAggrFrames Counter32,
            lcsStatusWlanPacketTransportEntryRxAMsdu Counter32,
            lcsStatusWlanPacketTransportEntryRxFft Counter32,
            lcsStatusWlanPacketTransportEntryRxBlink Counter32
    }

-- {COLUMN} 1.3.6.1.4.1.2356.11.1.3.53.1.1
lcsStatusWlanPacketTransportEntryIfc OBJECT-TYPE
    SYNTAX     DisplayString (SIZE(0..255))
    MAX-ACCESS read-only
    STATUS     current
    DESCRIPTION
            ""
    ::= { lcsStatusWlanPacketTransportEntry 1 }

-- {COLUMN} 1.3.6.1.4.1.2356.11.1.3.53.1.2
lcsStatusWlanPacketTransportEntryRxPackets OBJECT-TYPE
    SYNTAX     Counter32
    MAX-ACCESS read-only
    STATUS     current
    DESCRIPTION
            ""
    ::= { lcsStatusWlanPacketTransportEntry 2 }

-- {COLUMN} 1.3.6.1.4.1.2356.11.1.3.53.1.3
lcsStatusWlanPacketTransportEntryTxPackets OBJECT-TYPE
    SYNTAX     Counter32
    MAX-ACCESS read-only
    STATUS     current
    DESCRIPTION
            ""
    ::= { lcsStatusWlanPacketTransportEntry 3 }

-- {COLUMN} 1.3.6.1.4.1.2356.11.1.3.53.1.4
lcsStatusWlanPacketTransportEntryRxBroadcasts OBJECT-TYPE
    SYNTAX     Counter32
    MAX-ACCESS read-only
    STATUS     current
    DESCRIPTION
            ""
    ::= { lcsStatusWlanPacketTransportEntry 4 }

-- {COLUMN} 1.3.6.1.4.1.2356.11.1.3.53.1.5
lcsStatusWlanPacketTransportEntryRxMulticasts OBJECT-TYPE
    SYNTAX     Counter32
    MAX-ACCESS read-only
    STATUS     current
    DESCRIPTION
            ""
    ::= { lcsStatusWlanPacketTransportEntry 5 }

-- {COLUMN} 1.3.6.1.4.1.2356.11.1.3.53.1.6
lcsStatusWlanPacketTransportEntryRxUnicasts OBJECT-TYPE
    SYNTAX     Counter32
    MAX-ACCESS read-only
    STATUS     current
    DESCRIPTION
            ""
    ::= { lcsStatusWlanPacketTransportEntry 6 }

-- {COLUMN} 1.3.6.1.4.1.2356.11.1.3.53.1.7
lcsStatusWlanPacketTransportEntryTxBroadcasts OBJECT-TYPE
    SYNTAX     Counter32
    MAX-ACCESS read-only
    STATUS     current
    DESCRIPTION
            ""
    ::= { lcsStatusWlanPacketTransportEntry 7 }

-- {COLUMN} 1.3.6.1.4.1.2356.11.1.3.53.1.8
lcsStatusWlanPacketTransportEntryTxMulticasts OBJECT-TYPE
    SYNTAX     Counter32
    MAX-ACCESS read-only
    STATUS     current
    DESCRIPTION
            ""
    ::= { lcsStatusWlanPacketTransportEntry 8 }

-- {COLUMN} 1.3.6.1.4.1.2356.11.1.3.53.1.9
lcsStatusWlanPacketTransportEntryTxUnicasts OBJECT-TYPE
    SYNTAX     Counter32
    MAX-ACCESS read-only
    STATUS     current
    DESCRIPTION
            ""
    ::= { lcsStatusWlanPacketTransportEntry 9 }

-- {COLUMN} 1.3.6.1.4.1.2356.11.1.3.53.1.12
lcsStatusWlanPacketTransportEntryTxAggregates OBJECT-TYPE
    SYNTAX     Counter32
    MAX-ACCESS read-only
    STATUS     current
    DESCRIPTION
            ""
    ::= { lcsStatusWlanPacketTransportEntry 12 }

-- {COLUMN} 1.3.6.1.4.1.2356.11.1.3.53.1.13
lcsStatusWlanPacketTransportEntryTxAggrFrames OBJECT-TYPE
    SYNTAX     Counter32
    MAX-ACCESS read-only
    STATUS     current
    DESCRIPTION
            ""
    ::= { lcsStatusWlanPacketTransportEntry 13 }

-- {COLUMN} 1.3.6.1.4.1.2356.11.1.3.53.1.14
lcsStatusWlanPacketTransportEntryRxAggregates OBJECT-TYPE
    SYNTAX     Counter32
    MAX-ACCESS read-only
    STATUS     current
    DESCRIPTION
            ""
    ::= { lcsStatusWlanPacketTransportEntry 14 }

-- {COLUMN} 1.3.6.1.4.1.2356.11.1.3.53.1.15
lcsStatusWlanPacketTransportEntryRxAggrFrames OBJECT-TYPE
    SYNTAX     Counter32
    MAX-ACCESS read-only
    STATUS     current
    DESCRIPTION
            ""
    ::= { lcsStatusWlanPacketTransportEntry 15 }

-- {COLUMN} 1.3.6.1.4.1.2356.11.1.3.53.1.16
lcsStatusWlanPacketTransportEntryRxAMsdu OBJECT-TYPE
    SYNTAX     Counter32
    MAX-ACCESS read-only
    STATUS     current
    DESCRIPTION
            "-- empty --"
    ::= { lcsStatusWlanPacketTransportEntry 16 }

-- {COLUMN} 1.3.6.1.4.1.2356.11.1.3.53.1.17
lcsStatusWlanPacketTransportEntryRxFft OBJECT-TYPE
    SYNTAX     Counter32
    MAX-ACCESS read-only
    STATUS     current
    DESCRIPTION
            "-- empty --"
    ::= { lcsStatusWlanPacketTransportEntry 17 }

-- {COLUMN} 1.3.6.1.4.1.2356.11.1.3.53.1.18
lcsStatusWlanPacketTransportEntryRxBlink OBJECT-TYPE
    SYNTAX     Counter32
    MAX-ACCESS read-only
    STATUS     current
    DESCRIPTION
            "-- empty --"
    ::= { lcsStatusWlanPacketTransportEntry 18 }

-- {TABLE} 1.3.6.1.4.1.2356.11.1.3.54
lcsStatusWlanErrorsTable OBJECT-TYPE
    SYNTAX     SEQUENCE OF LcsStatusWlanErrorsEntry
    MAX-ACCESS not-accessible
    STATUS     current
    DESCRIPTION
            ""
    ::= { lcsStatusWlan 54 }

-- {ROW} 1.3.6.1.4.1.2356.11.1.3.54.1
lcsStatusWlanErrorsEntry OBJECT-TYPE
    SYNTAX     LcsStatusWlanErrorsEntry
    MAX-ACCESS not-accessible
    STATUS     current
    DESCRIPTION
            ""
    INDEX {
            lcsStatusWlanErrorsEntryIfc
          }
    ::= { lcsStatusWlanErrorsTable 1 }

LcsStatusWlanErrorsEntry ::= SEQUENCE {
            lcsStatusWlanErrorsEntryIfc DisplayString,
            lcsStatusWlanErrorsEntryRxErrors Counter32,
            lcsStatusWlanErrorsEntryTxErrors Counter32,
            lcsStatusWlanErrorsEntryStackErrors Counter32,
            lcsStatusWlanErrorsEntryNicErrors Counter32,
            lcsStatusWlanErrorsEntryQueueErrors Counter32,
            lcsStatusWlanErrorsEntryTxDiscarded Counter32,
            lcsStatusWlanErrorsEntryRetries Counter32,
            lcsStatusWlanErrorsEntryMultipleRetries Counter32,
            lcsStatusWlanErrorsEntryUndecryptables Counter32,
            lcsStatusWlanErrorsEntryDupeDiscarded Counter32,
            lcsStatusWlanErrorsEntryAged Counter32,
            lcsStatusWlanErrorsEntryMichaelErrors Counter32,
            lcsStatusWlanErrorsEntryIvSequenceErrors Counter32,
            lcsStatusWlanErrorsEntryRxCrcErrors Counter32,
            lcsStatusWlanErrorsEntrySoftRetries Counter32,
            lcsStatusWlanErrorsEntryRxAggrDiscarded Counter32,
            lcsStatusWlanErrorsEntryRxPhyErrors Counter32,
            lcsStatusWlanErrorsEntryRxFifoOverflow Counter32,
            lcsStatusWlanErrorsEntryTxFifoUnderflow Counter32,
            lcsStatusWlanErrorsEntryBusErrors Counter32,
            lcsStatusWlanErrorsEntryRxRestarts Counter32,
            lcsStatusWlanErrorsEntryRxDscrUnderflow Counter32,
            lcsStatusWlanErrorsEntryAgcCalibrateFailures Counter32,
            lcsStatusWlanErrorsEntryBbTimeouts Counter32,
            lcsStatusWlanErrorsEntryRxErrorRatio Counter32,
            lcsStatusWlanErrorsEntryTxErrorRatio Counter32,
            lcsStatusWlanErrorsEntryPowersaveRetransmits Counter32,
            lcsStatusWlanErrorsEntryTxTimeout Counter32,
            lcsStatusWlanErrorsEntryStopPcu Counter32
    }

-- {COLUMN} 1.3.6.1.4.1.2356.11.1.3.54.1.1
lcsStatusWlanErrorsEntryIfc OBJECT-TYPE
    SYNTAX     DisplayString (SIZE(0..255))
    MAX-ACCESS read-only
    STATUS     current
    DESCRIPTION
            ""
    ::= { lcsStatusWlanErrorsEntry 1 }

-- {COLUMN} 1.3.6.1.4.1.2356.11.1.3.54.1.2
lcsStatusWlanErrorsEntryRxErrors OBJECT-TYPE
    SYNTAX     Counter32
    MAX-ACCESS read-only
    STATUS     current
    DESCRIPTION
            ""
    ::= { lcsStatusWlanErrorsEntry 2 }

-- {COLUMN} 1.3.6.1.4.1.2356.11.1.3.54.1.3
lcsStatusWlanErrorsEntryTxErrors OBJECT-TYPE
    SYNTAX     Counter32
    MAX-ACCESS read-only
    STATUS     current
    DESCRIPTION
            ""
    ::= { lcsStatusWlanErrorsEntry 3 }

-- {COLUMN} 1.3.6.1.4.1.2356.11.1.3.54.1.4
lcsStatusWlanErrorsEntryStackErrors OBJECT-TYPE
    SYNTAX     Counter32
    MAX-ACCESS read-only
    STATUS     current
    DESCRIPTION
            ""
    ::= { lcsStatusWlanErrorsEntry 4 }

-- {COLUMN} 1.3.6.1.4.1.2356.11.1.3.54.1.5
lcsStatusWlanErrorsEntryNicErrors OBJECT-TYPE
    SYNTAX     Counter32
    MAX-ACCESS read-only
    STATUS     current
    DESCRIPTION
            ""
    ::= { lcsStatusWlanErrorsEntry 5 }

-- {COLUMN} 1.3.6.1.4.1.2356.11.1.3.54.1.6
lcsStatusWlanErrorsEntryQueueErrors OBJECT-TYPE
    SYNTAX     Counter32
    MAX-ACCESS read-only
    STATUS     current
    DESCRIPTION
            ""
    ::= { lcsStatusWlanErrorsEntry 6 }

-- {COLUMN} 1.3.6.1.4.1.2356.11.1.3.54.1.7
lcsStatusWlanErrorsEntryTxDiscarded OBJECT-TYPE
    SYNTAX     Counter32
    MAX-ACCESS read-only
    STATUS     current
    DESCRIPTION
            ""
    ::= { lcsStatusWlanErrorsEntry 7 }

-- {COLUMN} 1.3.6.1.4.1.2356.11.1.3.54.1.8
lcsStatusWlanErrorsEntryRetries OBJECT-TYPE
    SYNTAX     Counter32
    MAX-ACCESS read-only
    STATUS     current
    DESCRIPTION
            ""
    ::= { lcsStatusWlanErrorsEntry 8 }

-- {COLUMN} 1.3.6.1.4.1.2356.11.1.3.54.1.9
lcsStatusWlanErrorsEntryMultipleRetries OBJECT-TYPE
    SYNTAX     Counter32
    MAX-ACCESS read-only
    STATUS     current
    DESCRIPTION
            ""
    ::= { lcsStatusWlanErrorsEntry 9 }

-- {COLUMN} 1.3.6.1.4.1.2356.11.1.3.54.1.10
lcsStatusWlanErrorsEntryUndecryptables OBJECT-TYPE
    SYNTAX     Counter32
    MAX-ACCESS read-only
    STATUS     current
    DESCRIPTION
            ""
    ::= { lcsStatusWlanErrorsEntry 10 }

-- {COLUMN} 1.3.6.1.4.1.2356.11.1.3.54.1.11
lcsStatusWlanErrorsEntryDupeDiscarded OBJECT-TYPE
    SYNTAX     Counter32
    MAX-ACCESS read-only
    STATUS     current
    DESCRIPTION
            ""
    ::= { lcsStatusWlanErrorsEntry 11 }

-- {COLUMN} 1.3.6.1.4.1.2356.11.1.3.54.1.13
lcsStatusWlanErrorsEntryAged OBJECT-TYPE
    SYNTAX     Counter32
    MAX-ACCESS read-only
    STATUS     current
    DESCRIPTION
            ""
    ::= { lcsStatusWlanErrorsEntry 13 }

-- {COLUMN} 1.3.6.1.4.1.2356.11.1.3.54.1.14
lcsStatusWlanErrorsEntryMichaelErrors OBJECT-TYPE
    SYNTAX     Counter32
    MAX-ACCESS read-only
    STATUS     current
    DESCRIPTION
            ""
    ::= { lcsStatusWlanErrorsEntry 14 }

-- {COLUMN} 1.3.6.1.4.1.2356.11.1.3.54.1.15
lcsStatusWlanErrorsEntryIvSequenceErrors OBJECT-TYPE
    SYNTAX     Counter32
    MAX-ACCESS read-only
    STATUS     current
    DESCRIPTION
            ""
    ::= { lcsStatusWlanErrorsEntry 15 }

-- {COLUMN} 1.3.6.1.4.1.2356.11.1.3.54.1.16
lcsStatusWlanErrorsEntryRxCrcErrors OBJECT-TYPE
    SYNTAX     Counter32
    MAX-ACCESS read-only
    STATUS     current
    DESCRIPTION
            ""
    ::= { lcsStatusWlanErrorsEntry 16 }

-- {COLUMN} 1.3.6.1.4.1.2356.11.1.3.54.1.17
lcsStatusWlanErrorsEntrySoftRetries OBJECT-TYPE
    SYNTAX     Counter32
    MAX-ACCESS read-only
    STATUS     current
    DESCRIPTION
            ""
    ::= { lcsStatusWlanErrorsEntry 17 }

-- {COLUMN} 1.3.6.1.4.1.2356.11.1.3.54.1.18
lcsStatusWlanErrorsEntryRxAggrDiscarded OBJECT-TYPE
    SYNTAX     Counter32
    MAX-ACCESS read-only
    STATUS     current
    DESCRIPTION
            ""
    ::= { lcsStatusWlanErrorsEntry 18 }

-- {COLUMN} 1.3.6.1.4.1.2356.11.1.3.54.1.19
lcsStatusWlanErrorsEntryRxPhyErrors OBJECT-TYPE
    SYNTAX     Counter32
    MAX-ACCESS read-only
    STATUS     current
    DESCRIPTION
            ""
    ::= { lcsStatusWlanErrorsEntry 19 }

-- {COLUMN} 1.3.6.1.4.1.2356.11.1.3.54.1.20
lcsStatusWlanErrorsEntryRxFifoOverflow OBJECT-TYPE
    SYNTAX     Counter32
    MAX-ACCESS read-only
    STATUS     current
    DESCRIPTION
            ""
    ::= { lcsStatusWlanErrorsEntry 20 }

-- {COLUMN} 1.3.6.1.4.1.2356.11.1.3.54.1.21
lcsStatusWlanErrorsEntryTxFifoUnderflow OBJECT-TYPE
    SYNTAX     Counter32
    MAX-ACCESS read-only
    STATUS     current
    DESCRIPTION
            ""
    ::= { lcsStatusWlanErrorsEntry 21 }

-- {COLUMN} 1.3.6.1.4.1.2356.11.1.3.54.1.22
lcsStatusWlanErrorsEntryBusErrors OBJECT-TYPE
    SYNTAX     Counter32
    MAX-ACCESS read-only
    STATUS     current
    DESCRIPTION
            ""
    ::= { lcsStatusWlanErrorsEntry 22 }

-- {COLUMN} 1.3.6.1.4.1.2356.11.1.3.54.1.23
lcsStatusWlanErrorsEntryRxRestarts OBJECT-TYPE
    SYNTAX     Counter32
    MAX-ACCESS read-only
    STATUS     current
    DESCRIPTION
            "-- empty --"
    ::= { lcsStatusWlanErrorsEntry 23 }

-- {COLUMN} 1.3.6.1.4.1.2356.11.1.3.54.1.24
lcsStatusWlanErrorsEntryRxDscrUnderflow OBJECT-TYPE
    SYNTAX     Counter32
    MAX-ACCESS read-only
    STATUS     current
    DESCRIPTION
            "-- empty --"
    ::= { lcsStatusWlanErrorsEntry 24 }

-- {COLUMN} 1.3.6.1.4.1.2356.11.1.3.54.1.25
lcsStatusWlanErrorsEntryAgcCalibrateFailures OBJECT-TYPE
    SYNTAX     Counter32
    MAX-ACCESS read-only
    STATUS     current
    DESCRIPTION
            "-- empty --"
    ::= { lcsStatusWlanErrorsEntry 25 }

-- {COLUMN} 1.3.6.1.4.1.2356.11.1.3.54.1.26
lcsStatusWlanErrorsEntryBbTimeouts OBJECT-TYPE
    SYNTAX     Counter32
    MAX-ACCESS read-only
    STATUS     current
    DESCRIPTION
            "-- empty --"
    ::= { lcsStatusWlanErrorsEntry 26 }

-- {COLUMN} 1.3.6.1.4.1.2356.11.1.3.54.1.27
lcsStatusWlanErrorsEntryRxErrorRatio OBJECT-TYPE
    SYNTAX     Counter32
    MAX-ACCESS read-only
    STATUS     current
    DESCRIPTION
            "-- empty --"
    ::= { lcsStatusWlanErrorsEntry 27 }

-- {COLUMN} 1.3.6.1.4.1.2356.11.1.3.54.1.28
lcsStatusWlanErrorsEntryTxErrorRatio OBJECT-TYPE
    SYNTAX     Counter32
    MAX-ACCESS read-only
    STATUS     current
    DESCRIPTION
            "-- empty --"
    ::= { lcsStatusWlanErrorsEntry 28 }

-- {COLUMN} 1.3.6.1.4.1.2356.11.1.3.54.1.29
lcsStatusWlanErrorsEntryPowersaveRetransmits OBJECT-TYPE
    SYNTAX     Counter32
    MAX-ACCESS read-only
    STATUS     current
    DESCRIPTION
            "-- empty --"
    ::= { lcsStatusWlanErrorsEntry 29 }

-- {COLUMN} 1.3.6.1.4.1.2356.11.1.3.54.1.30
lcsStatusWlanErrorsEntryTxTimeout OBJECT-TYPE
    SYNTAX     Counter32
    MAX-ACCESS read-only
    STATUS     current
    DESCRIPTION
            "-- empty --"
    ::= { lcsStatusWlanErrorsEntry 30 }

-- {COLUMN} 1.3.6.1.4.1.2356.11.1.3.54.1.31
lcsStatusWlanErrorsEntryStopPcu OBJECT-TYPE
    SYNTAX     Counter32
    MAX-ACCESS read-only
    STATUS     current
    DESCRIPTION
            "-- empty --"
    ::= { lcsStatusWlanErrorsEntry 31 }

-- {TABLE} 1.3.6.1.4.1.2356.11.1.3.55
lcsStatusWlanWlanParameterTable OBJECT-TYPE
    SYNTAX     SEQUENCE OF LcsStatusWlanWlanParameterEntry
    MAX-ACCESS not-accessible
    STATUS     current
    DESCRIPTION
            ""
    ::= { lcsStatusWlan 55 }

-- {ROW} 1.3.6.1.4.1.2356.11.1.3.55.1
lcsStatusWlanWlanParameterEntry OBJECT-TYPE
    SYNTAX     LcsStatusWlanWlanParameterEntry
    MAX-ACCESS not-accessible
    STATUS     current
    DESCRIPTION
            ""
    INDEX {
            lcsStatusWlanWlanParameterEntryIfc
          }
    ::= { lcsStatusWlanWlanParameterTable 1 }

LcsStatusWlanWlanParameterEntry ::= SEQUENCE {
            lcsStatusWlanWlanParameterEntryIfc DisplayString,
            lcsStatusWlanWlanParameterEntryRadioChannel Integer32,
            lcsStatusWlanWlanParameterEntryRegulatoryDomain INTEGER,
            lcsStatusWlanWlanParameterEntryPhyType INTEGER,
            lcsStatusWlanWlanParameterEntryWepSupport INTEGER,
            lcsStatusWlanWlanParameterEntryMaximumRate INTEGER,
            lcsStatusWlanWlanParameterEntryTemperatureRange INTEGER,
            lcsStatusWlanWlanParameterEntryPhyVariant DisplayString,
            lcsStatusWlanWlanParameterEntryRadioBand INTEGER,
            lcsStatusWlanWlanParameterEntrySupportedBands INTEGER,
            lcsStatusWlanWlanParameterEntryNoiseLevel Integer32,
            lcsStatusWlanWlanParameterEntrySupportsShortPreamble INTEGER,
            lcsStatusWlanWlanParameterEntryTransmitPower DisplayString,
            lcsStatusWlanWlanParameterEntry108mbpsMode INTEGER,
            lcsStatusWlanWlanParameterEntrySupportsShortSlotTime INTEGER,
            lcsStatusWlanWlanParameterEntryTkipSupport INTEGER,
            lcsStatusWlanWlanParameterEntryAesSupport INTEGER,
            lcsStatusWlanWlanParameterEntrySupportsCompression INTEGER,
            lcsStatusWlanWlanParameterEntryMinimumRate INTEGER,
            lcsStatusWlanWlanParameterEntryEirp DisplayString,
            lcsStatusWlanWlanParameterEntryExcEirp INTEGER,
            lcsStatusWlanWlanParameterEntryModemLoad Integer32,
            lcsStatusWlanWlanParameterEntryBeaconPeriod Integer32,
            lcsStatusWlanWlanParameterEntrySupportsShortGuardInterval INTEGER,
            lcsStatusWlanWlanParameterEntrySupports40mhz INTEGER,
            lcsStatusWlanWlanParameterEntryTxChains Integer32,
            lcsStatusWlanWlanParameterEntryRxChains Integer32,
            lcsStatusWlanWlanParameterEntrySupportedDfsSchemes BITS,
            lcsStatusWlanWlanParameterEntrySupportedAntennas INTEGER,
            lcsStatusWlanWlanParameterEntryRxStbc INTEGER,
            lcsStatusWlanWlanParameterEntryLdpc INTEGER,
            lcsStatusWlanWlanParameterEntryCountry INTEGER,
            lcsStatusWlanWlanParameterEntrySupportsSpectralScan INTEGER,
            lcsStatusWlanWlanParameterEntrySGIMask BITS,
            lcsStatusWlanWlanParameterEntryChannelBandwidths BITS,
            lcsStatusWlanWlanParameterEntryChannelBandwidth INTEGER,
            lcsStatusWlanWlanParameterEntryProtMgmtFrames INTEGER,
            lcsStatusWlanWlanParameterEntryRxStbcHt INTEGER,
            lcsStatusWlanWlanParameterEntryRxStbcVht INTEGER,
            lcsStatusWlanWlanParameterEntryLDPCMask BITS,
            lcsStatusWlanWlanParameterEntrySupported11acBeamforming BITS,
            lcsStatusWlanWlanParameterEntryAntMaskBlockedCBWs BITS,
            lcsStatusWlanWlanParameterEntryWpaKeyTypes BITS
    }

-- {COLUMN} 1.3.6.1.4.1.2356.11.1.3.55.1.1
lcsStatusWlanWlanParameterEntryIfc OBJECT-TYPE
    SYNTAX     DisplayString (SIZE(0..255))
    MAX-ACCESS read-only
    STATUS     current
    DESCRIPTION
            ""
    ::= { lcsStatusWlanWlanParameterEntry 1 }

-- {COLUMN} 1.3.6.1.4.1.2356.11.1.3.55.1.3
lcsStatusWlanWlanParameterEntryRadioChannel OBJECT-TYPE
    SYNTAX     Integer32 (0..255)
    MAX-ACCESS read-only
    STATUS     current
    DESCRIPTION
            ""
    ::= { lcsStatusWlanWlanParameterEntry 3 }

-- {COLUMN} 1.3.6.1.4.1.2356.11.1.3.55.1.4
lcsStatusWlanWlanParameterEntryRegulatoryDomain OBJECT-TYPE
    SYNTAX     INTEGER {
                  eUndefined (0),
                  eFcc (16),
                  eCanada (32),
                  eEuEtsi (48),
                  eSpain (49),
                  eFrance (50),
                  eMkkJapan (64),
                  eMkk2Japan (65),
                  eIsrael (80),
                  eWorld (96)
            }
    MAX-ACCESS read-only
    STATUS     current
    DESCRIPTION
            ""
    ::= { lcsStatusWlanWlanParameterEntry 4 }

-- {COLUMN} 1.3.6.1.4.1.2356.11.1.3.55.1.5
lcsStatusWlanWlanParameterEntryPhyType OBJECT-TYPE
    SYNTAX     INTEGER {
                  eProprietary (0),
                  eFhss (1),
                  eDsss (2),
                  eInfrared (3),
                  eOfdm (4),
                  eHrDsss (5),
                  eErp (6),
                  eHt (7),
                  eVht (9),
                  eTvht (10),
                  eS1g (11),
                  eCdmg (12),
                  eCmmg (13),
                  eHe (14),
                  ePbcc (254)
            }
    MAX-ACCESS read-only
    STATUS     current
    DESCRIPTION
            ""
    ::= { lcsStatusWlanWlanParameterEntry 5 }

-- {COLUMN} 1.3.6.1.4.1.2356.11.1.3.55.1.7
lcsStatusWlanWlanParameterEntryWepSupport OBJECT-TYPE
    SYNTAX     INTEGER {
                  eNo (0),
                  eYes40Bits (1),
                  eYes104Bits (2),
                  eYes128Bits (3)
            }
    MAX-ACCESS read-only
    STATUS     current
    DESCRIPTION
            ""
    ::= { lcsStatusWlanWlanParameterEntry 7 }

-- {COLUMN} 1.3.6.1.4.1.2356.11.1.3.55.1.8
lcsStatusWlanWlanParameterEntryMaximumRate OBJECT-TYPE
    SYNTAX     INTEGER {
                  eUnknown (0),
                  e1M (1),
                  e2M (2),
                  e5M (3),
                  e5M5 (4),
                  e8M (5),
                  e11M (6),
                  e6M (12),
                  e9M (13),
                  e12M (14),
                  e18M (15),
                  e24M (16),
                  e36M (17),
                  e48M (18),
                  e54M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eHT4S26M (52),
                  eHT4S52M (53),
                  eHT4S78M (54),
                  eHT4S104M (55),
                  eHT4S156M (56),
                  eHT4S208M (57),
                  eHT4S234M (58),
                  eHT4S260M (59),
                  eHTDUP6M (60),
                  eHtMcs33 (61),
                  eHtMcs34 (62),
                  eHtMcs35 (63),
                  eHtMcs36 (64),
                  eHtMcs37 (65),
                  eHtMcs38 (66),
                  eHtMcs39 (67),
                  eHtMcs40 (68),
                  eHtMcs41 (69),
                  eHtMcs42 (70),
                  eHtMcs43 (71),
                  eHtMcs44 (72),
                  eHtMcs45 (73),
                  eHtMcs46 (74),
                  eHtMcs47 (75),
                  eHtMcs48 (76),
                  eHtMcs49 (77),
                  eHtMcs50 (78),
                  eHtMcs51 (79),
                  eHtMcs52 (80),
                  eHtMcs53 (81),
                  eHtMcs54 (82),
                  eHtMcs55 (83),
                  eHtMcs56 (84),
                  eHtMcs57 (85),
                  eHtMcs58 (86),
                  eHtMcs59 (87),
                  eHtMcs60 (88),
                  eHtMcs61 (89),
                  eHtMcs62 (90),
                  eHtMcs63 (91),
                  eHtMcs64 (92),
                  eHtMcs65 (93),
                  eHtMcs66 (94),
                  eHtMcs67 (95),
                  eHtMcs68 (96),
                  eHtMcs69 (97),
                  eHtMcs70 (98),
                  eHtMcs71 (99),
                  eHtMcs72 (100),
                  eHtMcs73 (101),
                  eHtMcs74 (102),
                  eHtMcs75 (103),
                  eHtMcs76 (104),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            ""
    ::= { lcsStatusWlanWlanParameterEntry 8 }

-- {COLUMN} 1.3.6.1.4.1.2356.11.1.3.55.1.9
lcsStatusWlanWlanParameterEntryTemperatureRange OBJECT-TYPE
    SYNTAX     INTEGER {
                  eUnknown (0),
                  eCommercial0Plus40DegreeC (1),
                  eIndustrial30Plus70DegreeC (2)
            }
    MAX-ACCESS read-only
    STATUS     current
    DESCRIPTION
            ""
    ::= { lcsStatusWlanWlanParameterEntry 9 }

-- {COLUMN} 1.3.6.1.4.1.2356.11.1.3.55.1.10
lcsStatusWlanWlanParameterEntryPhyVariant OBJECT-TYPE
    SYNTAX     DisplayString (SIZE(0..15))
    MAX-ACCESS read-only
    STATUS     current
    DESCRIPTION
            ""
    ::= { lcsStatusWlanWlanParameterEntry 10 }

-- {COLUMN} 1.3.6.1.4.1.2356.11.1.3.55.1.11
lcsStatusWlanWlanParameterEntryRadioBand OBJECT-TYPE
    SYNTAX     INTEGER {
                  eUnknown (0),
                  e24ghz (1),
                  e5ghz (2),
                  e24ghz5ghz (3)
            }
    MAX-ACCESS read-only
    STATUS     current
    DESCRIPTION
            ""
    ::= { lcsStatusWlanWlanParameterEntry 11 }

-- {COLUMN} 1.3.6.1.4.1.2356.11.1.3.55.1.12
lcsStatusWlanWlanParameterEntrySupportedBands OBJECT-TYPE
    SYNTAX     INTEGER {
                  eUnknown (0),
                  e24ghz (1),
                  e5ghz (2),
                  e24ghz5ghz (3)
            }
    MAX-ACCESS read-only
    STATUS     current
    DESCRIPTION
            ""
    ::= { lcsStatusWlanWlanParameterEntry 12 }

-- {COLUMN} 1.3.6.1.4.1.2356.11.1.3.55.1.13
lcsStatusWlanWlanParameterEntryNoiseLevel OBJECT-TYPE
    SYNTAX     Integer32 (-32768..32767)
    MAX-ACCESS read-only
    STATUS     current
    DESCRIPTION
            ""
    ::= { lcsStatusWlanWlanParameterEntry 13 }

-- {COLUMN} 1.3.6.1.4.1.2356.11.1.3.55.1.14
lcsStatusWlanWlanParameterEntrySupportsShortPreamble OBJECT-TYPE
    SYNTAX     INTEGER {
                  eNo (0),
                  eYes (1)
            }
    MAX-ACCESS read-only
    STATUS     current
    DESCRIPTION
            ""
    ::= { lcsStatusWlanWlanParameterEntry 14 }

-- {COLUMN} 1.3.6.1.4.1.2356.11.1.3.55.1.15
lcsStatusWlanWlanParameterEntryTransmitPower OBJECT-TYPE
    SYNTAX     DisplayString (SIZE(0..255))
    MAX-ACCESS read-only
    STATUS     current
    DESCRIPTION
            ""
    ::= { lcsStatusWlanWlanParameterEntry 15 }

-- {COLUMN} 1.3.6.1.4.1.2356.11.1.3.55.1.16
lcsStatusWlanWlanParameterEntry108mbpsMode OBJECT-TYPE
    SYNTAX     INTEGER {
                  eNo (0),
                  eYes (1)
            }
    MAX-ACCESS read-only
    STATUS     current
    DESCRIPTION
            ""
    ::= { lcsStatusWlanWlanParameterEntry 16 }

-- {COLUMN} 1.3.6.1.4.1.2356.11.1.3.55.1.17
lcsStatusWlanWlanParameterEntrySupportsShortSlotTime OBJECT-TYPE
    SYNTAX     INTEGER {
                  eNo (0),
                  eYes (1)
            }
    MAX-ACCESS read-only
    STATUS     current
    DESCRIPTION
            ""
    ::= { lcsStatusWlanWlanParameterEntry 17 }

-- {COLUMN} 1.3.6.1.4.1.2356.11.1.3.55.1.18
lcsStatusWlanWlanParameterEntryTkipSupport OBJECT-TYPE
    SYNTAX     INTEGER {
                  eNo (0),
                  eYes (1)
            }
    MAX-ACCESS read-only
    STATUS     current
    DESCRIPTION
            ""
    ::= { lcsStatusWlanWlanParameterEntry 18 }

-- {COLUMN} 1.3.6.1.4.1.2356.11.1.3.55.1.19
lcsStatusWlanWlanParameterEntryAesSupport OBJECT-TYPE
    SYNTAX     INTEGER {
                  eNo (0),
                  eOcb (1),
                  eCcm (2),
                  eOcbPlusCcm (3)
            }
    MAX-ACCESS read-only
    STATUS     current
    DESCRIPTION
            ""
    ::= { lcsStatusWlanWlanParameterEntry 19 }

-- {COLUMN} 1.3.6.1.4.1.2356.11.1.3.55.1.20
lcsStatusWlanWlanParameterEntrySupportsCompression OBJECT-TYPE
    SYNTAX     INTEGER {
                  eNo (0),
                  eYes (1)
            }
    MAX-ACCESS read-only
    STATUS     current
    DESCRIPTION
            ""
    ::= { lcsStatusWlanWlanParameterEntry 20 }

-- {COLUMN} 1.3.6.1.4.1.2356.11.1.3.55.1.21
lcsStatusWlanWlanParameterEntryMinimumRate OBJECT-TYPE
    SYNTAX     INTEGER {
                  eUnknown (0),
                  e1M (1),
                  e2M (2),
                  e5M (3),
                  e5M5 (4),
                  e8M (5),
                  e11M (6),
                  e6M (12),
                  e9M (13),
                  e12M (14),
                  e18M (15),
                  e24M (16),
                  e36M (17),
                  e48M (18),
                  e54M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eHT4S26M (52),
                  eHT4S52M (53),
                  eHT4S78M (54),
                  eHT4S104M (55),
                  eHT4S156M (56),
                  eHT4S208M (57),
                  eHT4S234M (58),
                  eHT4S260M (59),
                  eHTDUP6M (60),
                  eHtMcs33 (61),
                  eHtMcs34 (62),
                  eHtMcs35 (63),
                  eHtMcs36 (64),
                  eHtMcs37 (65),
                  eHtMcs38 (66),
                  eHtMcs39 (67),
                  eHtMcs40 (68),
                  eHtMcs41 (69),
                  eHtMcs42 (70),
                  eHtMcs43 (71),
                  eHtMcs44 (72),
                  eHtMcs45 (73),
                  eHtMcs46 (74),
                  eHtMcs47 (75),
                  eHtMcs48 (76),
                  eHtMcs49 (77),
                  eHtMcs50 (78),
                  eHtMcs51 (79),
                  eHtMcs52 (80),
                  eHtMcs53 (81),
                  eHtMcs54 (82),
                  eHtMcs55 (83),
                  eHtMcs56 (84),
                  eHtMcs57 (85),
                  eHtMcs58 (86),
                  eHtMcs59 (87),
                  eHtMcs60 (88),
                  eHtMcs61 (89),
                  eHtMcs62 (90),
                  eHtMcs63 (91),
                  eHtMcs64 (92),
                  eHtMcs65 (93),
                  eHtMcs66 (94),
                  eHtMcs67 (95),
                  eHtMcs68 (96),
                  eHtMcs69 (97),
                  eHtMcs70 (98),
                  eHtMcs71 (99),
                  eHtMcs72 (100),
                  eHtMcs73 (101),
                  eHtMcs74 (102),
                  eHtMcs75 (103),
                  eHtMcs76 (104),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            ""
    ::= { lcsStatusWlanWlanParameterEntry 21 }

-- {COLUMN} 1.3.6.1.4.1.2356.11.1.3.55.1.22
lcsStatusWlanWlanParameterEntryEirp OBJECT-TYPE
    SYNTAX     DisplayString (SIZE(0..255))
    MAX-ACCESS read-only
    STATUS     current
    DESCRIPTION
            ""
    ::= { lcsStatusWlanWlanParameterEntry 22 }

-- {COLUMN} 1.3.6.1.4.1.2356.11.1.3.55.1.23
lcsStatusWlanWlanParameterEntryExcEirp OBJECT-TYPE
    SYNTAX     INTEGER {
                  eNo (0),
                  eYes (1)
            }
    MAX-ACCESS read-only
    STATUS     current
    DESCRIPTION
            ""
    ::= { lcsStatusWlanWlanParameterEntry 23 }

-- {COLUMN} 1.3.6.1.4.1.2356.11.1.3.55.1.24
lcsStatusWlanWlanParameterEntryModemLoad OBJECT-TYPE
    SYNTAX     Integer32 (0..255)
    MAX-ACCESS read-only
    STATUS     current
    DESCRIPTION
            ""
    ::= { lcsStatusWlanWlanParameterEntry 24 }

-- {COLUMN} 1.3.6.1.4.1.2356.11.1.3.55.1.25
lcsStatusWlanWlanParameterEntryBeaconPeriod OBJECT-TYPE
    SYNTAX     Integer32 (0..65535)
    MAX-ACCESS read-only
    STATUS     current
    DESCRIPTION
            ""
    ::= { lcsStatusWlanWlanParameterEntry 25 }

-- {COLUMN} 1.3.6.1.4.1.2356.11.1.3.55.1.26
lcsStatusWlanWlanParameterEntrySupportsShortGuardInterval OBJECT-TYPE
    SYNTAX     INTEGER {
                  eNo (0),
                  e20mhz (1),
                  e40mhz (2),
                  e2040mhz (3)
            }
    MAX-ACCESS read-only
    STATUS     current
    DESCRIPTION
            ""
    ::= { lcsStatusWlanWlanParameterEntry 26 }

-- {COLUMN} 1.3.6.1.4.1.2356.11.1.3.55.1.28
lcsStatusWlanWlanParameterEntrySupports40mhz OBJECT-TYPE
    SYNTAX     INTEGER {
                  eNo (0),
                  eYes (1)
            }
    MAX-ACCESS read-only
    STATUS     current
    DESCRIPTION
            ""
    ::= { lcsStatusWlanWlanParameterEntry 28 }

-- {COLUMN} 1.3.6.1.4.1.2356.11.1.3.55.1.29
lcsStatusWlanWlanParameterEntryTxChains OBJECT-TYPE
    SYNTAX     Integer32 (0..255)
    MAX-ACCESS read-only
    STATUS     current
    DESCRIPTION
            ""
    ::= { lcsStatusWlanWlanParameterEntry 29 }

-- {COLUMN} 1.3.6.1.4.1.2356.11.1.3.55.1.30
lcsStatusWlanWlanParameterEntryRxChains OBJECT-TYPE
    SYNTAX     Integer32 (0..255)
    MAX-ACCESS read-only
    STATUS     current
    DESCRIPTION
            ""
    ::= { lcsStatusWlanWlanParameterEntry 30 }

-- {COLUMN} 1.3.6.1.4.1.2356.11.1.3.55.1.32
lcsStatusWlanWlanParameterEntrySupportedDfsSchemes OBJECT-TYPE
    SYNTAX     BITS {
                  eNone (0),
                  eEn301893V16 (1),
                  eEn301893V15 (2),
                  eJapan (3),
                  eFcc (4),
                  eEn302502 (5),
                  eEn301893V13 (6),
                  eEn301893V12 (7),
                  eEn301893V21 (14),
                  eEn301893V17 (15)
            }
    MAX-ACCESS read-only
    STATUS     current
    DESCRIPTION
            ""
    ::= { lcsStatusWlanWlanParameterEntry 32 }

-- {COLUMN} 1.3.6.1.4.1.2356.11.1.3.55.1.33
lcsStatusWlanWlanParameterEntrySupportedAntennas OBJECT-TYPE
    SYNTAX     INTEGER {
                  eNA (0),
                  eAntenna1 (1),
                  eAntenna1Plus2 (3),
                  eAntenna1Plus3 (5),
                  eAntenna1Plus2Plus3 (7),
                  eAntenna1Plus4 (9),
                  eAntenna1Plus2Plus4 (11),
                  eAntenna1Plus2Plus3Plus4 (15)
            }
    MAX-ACCESS read-only
    STATUS     current
    DESCRIPTION
            ""
    ::= { lcsStatusWlanWlanParameterEntry 33 }

-- {COLUMN} 1.3.6.1.4.1.2356.11.1.3.55.1.34
lcsStatusWlanWlanParameterEntryRxStbc OBJECT-TYPE
    SYNTAX     INTEGER {
                  eNone (0),
                  eOne (1),
                  eTwo (2),
                  eThree (3)
            }
    MAX-ACCESS read-only
    STATUS     current
    DESCRIPTION
            "-- empty --"
    ::= { lcsStatusWlanWlanParameterEntry 34 }

-- {COLUMN} 1.3.6.1.4.1.2356.11.1.3.55.1.35
lcsStatusWlanWlanParameterEntryLdpc OBJECT-TYPE
    SYNTAX     INTEGER {
                  eNo (0),
                  eYes (1)
            }
    MAX-ACCESS read-only
    STATUS     current
    DESCRIPTION
            "-- empty --"
    ::= { lcsStatusWlanWlanParameterEntry 35 }

-- {COLUMN} 1.3.6.1.4.1.2356.11.1.3.55.1.36
lcsStatusWlanWlanParameterEntryCountry OBJECT-TYPE
    SYNTAX     INTEGER {
                  eUnknown (0),
                  eAlbania (8),
                  eAlgeria (12),
                  eArgentina (32),
                  eAustralia (36),
                  eAustria (40),
                  eBahrain (48),
                  eBangladesh (50),
                  eBelgium (56),
                  eBosniaHerzegovina (70),
                  eBrazil (76),
                  eBruneiDarussalam (96),
                  eBulgaria (100),
                  eBelarus (112),
                  eCanada (124),
                  eChile (152),
                  eChina (156),
                  eTaiwan (158),
                  eColombia (170),
                  eCostaRica (188),
                  eCroatia (191),
                  eCyprus (196),
                  eCzech (203),
                  eDenmark (208),
                  eEcuador (218),
                  eEstonia (233),
                  eFinland (246),
                  eFrance (250),
                  eGermany (276),
                  eGhana (288),
                  eGreece (300),
                  eGuatemala (320),
                  eHonduras (340),
                  eHongKong (344),
                  eHungary (348),
                  eIceland (352),
                  eIndia (356),
                  eIndonesia (360),
                  eIreland (372),
                  eIsrael (376),
                  eItaly (380),
                  eJapan (392),
                  eJordan (400),
                  eSouthKorea (410),
                  eKuwait (414),
                  eLebanon (422),
                  eLatvia (428),
                  eLiechtenstein (438),
                  eLithuania (440),
                  eLuxembourg (442),
                  eMacau (446),
                  eMalaysia (458),
                  eMalta (470),
                  eMexico (484),
                  eMoldavia (498),
                  eMorocco (504),
                  eOman (512),
                  eNetherlands (528),
                  eNewZealand (554),
                  eNicaragua (558),
                  eNorway (578),
                  ePakistan (586),
                  ePanama (591),
                  eParaguay (600),
                  ePeru (604),
                  ePhilippines (608),
                  ePoland (616),
                  ePortugal (620),
                  ePuertoRico (630),
                  eQatar (634),
                  eRomania (642),
                  eRussia (643),
                  eSaudiArabia (682),
                  eSingapore (702),
                  eSlovak (703),
                  eSlovenia (705),
                  eSouthAfrica (710),
                  eSpain (724),
                  eSweden (752),
                  eSwitzerland (756),
                  eThailand (764),
                  eUnitedArabEmirates (784),
                  eTunisia (788),
                  eTurkey (792),
                  eUganda (800),
                  eUkraine (804),
                  eMacedonia (807),
                  eEgypt (818),
                  eUnitedKingdom (826),
                  eTanzania (834),
                  eUnitedStatesFcc (840),
                  eUruguay (858),
                  eVenezuela (862),
                  eEurope (998),
                  eEgalistan (999)
            }
    MAX-ACCESS read-only
    STATUS     current
    DESCRIPTION
            "-- empty --"
    ::= { lcsStatusWlanWlanParameterEntry 36 }

-- {COLUMN} 1.3.6.1.4.1.2356.11.1.3.55.1.37
lcsStatusWlanWlanParameterEntrySupportsSpectralScan OBJECT-TYPE
    SYNTAX     INTEGER {
                  eNo (0),
                  eYes (1)
            }
    MAX-ACCESS read-only
    STATUS     current
    DESCRIPTION
            "-- empty --"
    ::= { lcsStatusWlanWlanParameterEntry 37 }

-- {COLUMN} 1.3.6.1.4.1.2356.11.1.3.55.1.38
lcsStatusWlanWlanParameterEntrySGIMask OBJECT-TYPE
    SYNTAX     BITS {
                  eNo (0),
                  e160mhz (28),
                  e80mhz (29),
                  e40mhz (30),
                  e20mhz (31)
            }
    MAX-ACCESS read-only
    STATUS     current
    DESCRIPTION
            "Bit mask of short guard interval support per-CBW"
    ::= { lcsStatusWlanWlanParameterEntry 38 }

-- {COLUMN} 1.3.6.1.4.1.2356.11.1.3.55.1.39
lcsStatusWlanWlanParameterEntryChannelBandwidths OBJECT-TYPE
    SYNTAX     BITS {
                  eT40mhz (26),
                  e80Plus80mhz (27),
                  e160mhz (28),
                  e80mhz (29),
                  e40mhz (30),
                  e20mhz (31)
            }
    MAX-ACCESS read-only
    STATUS     current
    DESCRIPTION
            "-- empty --"
    ::= { lcsStatusWlanWlanParameterEntry 39 }

-- {COLUMN} 1.3.6.1.4.1.2356.11.1.3.55.1.40
lcsStatusWlanWlanParameterEntryChannelBandwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanWlanParameterEntry 40 }

-- {COLUMN} 1.3.6.1.4.1.2356.11.1.3.55.1.41
lcsStatusWlanWlanParameterEntryProtMgmtFrames OBJECT-TYPE
    SYNTAX     INTEGER {
                  eNo (0),
                  eYes (1)
            }
    MAX-ACCESS read-only
    STATUS     current
    DESCRIPTION
            "-- empty --"
    ::= { lcsStatusWlanWlanParameterEntry 41 }

-- {COLUMN} 1.3.6.1.4.1.2356.11.1.3.55.1.42
lcsStatusWlanWlanParameterEntryRxStbcHt OBJECT-TYPE
    SYNTAX     INTEGER {
                  eNone (0),
                  eOne (1),
                  eTwo (2),
                  eThree (3)
            }
    MAX-ACCESS read-only
    STATUS     current
    DESCRIPTION
            "-- empty --"
    ::= { lcsStatusWlanWlanParameterEntry 42 }

-- {COLUMN} 1.3.6.1.4.1.2356.11.1.3.55.1.43
lcsStatusWlanWlanParameterEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { lcsStatusWlanWlanParameterEntry 43 }

-- {COLUMN} 1.3.6.1.4.1.2356.11.1.3.55.1.44
lcsStatusWlanWlanParameterEntryLDPCMask OBJECT-TYPE
    SYNTAX     BITS {
                  eVht (30),
                  eHt (31)
            }
    MAX-ACCESS read-only
    STATUS     current
    DESCRIPTION
            "Bit mask of LDPC support per-PHY-Type"
    ::= { lcsStatusWlanWlanParameterEntry 44 }

-- {COLUMN} 1.3.6.1.4.1.2356.11.1.3.55.1.45
lcsStatusWlanWlanParameterEntrySupported11acBeamforming OBJECT-TYPE
    SYNTAX     BITS {
                  eMuBfee (28),
                  eMuBfer (29),
                  eSuBfee (30),
                  eSuBfer (31)
            }
    MAX-ACCESS read-only
    STATUS     current
    DESCRIPTION
            "-- empty --"
    ::= { lcsStatusWlanWlanParameterEntry 45 }

-- {COLUMN} 1.3.6.1.4.1.2356.11.1.3.55.1.46
lcsStatusWlanWlanParameterEntryAntMaskBlockedCBWs OBJECT-TYPE
    SYNTAX     BITS {
                  eT40mhz (26),
                  e80Plus80mhz (27),
                  e160mhz (28),
                  e80mhz (29),
                  e40mhz (30),
                  e20mhz (31)
            }
    MAX-ACCESS read-only
    STATUS     current
    DESCRIPTION
            "Channel bandwidths blocked due to configured antenna mask"
    ::= { lcsStatusWlanWlanParameterEntry 46 }

-- {COLUMN} 1.3.6.1.4.1.2356.11.1.3.55.1.47
lcsStatusWlanWlanParameterEntryWpaKeyTypes OBJECT-TYPE
    SYNTAX     BITS {
                  eAesOcb (2),
                  eAesGcmp256 (3),
                  eAesGcmp128 (4),
                  eAesCcmp256 (5),
                  eAesCcm (6),
                  eTkip (7)
            }
    MAX-ACCESS read-only
    STATUS     current
    DESCRIPTION
            "-- empty --"
    ::= { lcsStatusWlanWlanParameterEntry 47 }

-- {TABLE} 1.3.6.1.4.1.2356.11.1.3.56
lcsStatusWlanNetworksTable OBJECT-TYPE
    SYNTAX     SEQUENCE OF LcsStatusWlanNetworksEntry
    MAX-ACCESS not-accessible
    STATUS     current
    DESCRIPTION
            ""
    ::= { lcsStatusWlan 56 }

-- {ROW} 1.3.6.1.4.1.2356.11.1.3.56.1
lcsStatusWlanNetworksEntry OBJECT-TYPE
    SYNTAX     LcsStatusWlanNetworksEntry
    MAX-ACCESS not-accessible
    STATUS     current
    DESCRIPTION
            ""
    INDEX {
            lcsStatusWlanNetworksEntryIfc
          }
    ::= { lcsStatusWlanNetworksTable 1 }

LcsStatusWlanNetworksEntry ::= SEQUENCE {
            lcsStatusWlanNetworksEntryIfc DisplayString,
            lcsStatusWlanNetworksEntryOperating INTEGER,
            lcsStatusWlanNetworksEntryNetworkName DisplayString,
            lcsStatusWlanNetworksEntryNumStations Integer32,
            lcsStatusWlanNetworksEntryMcastPwrSave INTEGER,
            lcsStatusWlanNetworksEntryBssid MacAddress,
            lcsStatusWlanNetworksEntryVlanId Integer32,
            lcsStatusWlanNetworksEntryApsd INTEGER,
            lcsStatusWlanNetworksEntryRadioMode INTEGER,
            lcsStatusWlanNetworksEntryAlarmState INTEGER,
            lcsStatusWlanNetworksEntryBasicRate INTEGER,
            lcsStatusWlanNetworksEntryMacFilter INTEGER,
            lcsStatusWlanNetworksEntryAccessMode INTEGER,
            lcsStatusWlanNetworksEntryClosedNetwork INTEGER
    }

-- {COLUMN} 1.3.6.1.4.1.2356.11.1.3.56.1.1
lcsStatusWlanNetworksEntryIfc OBJECT-TYPE
    SYNTAX     DisplayString (SIZE(0..255))
    MAX-ACCESS read-only
    STATUS     current
    DESCRIPTION
            ""
    ::= { lcsStatusWlanNetworksEntry 1 }

-- {COLUMN} 1.3.6.1.4.1.2356.11.1.3.56.1.2
lcsStatusWlanNetworksEntryOperating OBJECT-TYPE
    SYNTAX     INTEGER {
                  eNo (0),
                  eYes (1)
            }
    MAX-ACCESS read-only
    STATUS     current
    DESCRIPTION
            ""
    ::= { lcsStatusWlanNetworksEntry 2 }

-- {COLUMN} 1.3.6.1.4.1.2356.11.1.3.56.1.3
lcsStatusWlanNetworksEntryNetworkName OBJECT-TYPE
    SYNTAX     DisplayString (SIZE(0..255))
    MAX-ACCESS read-only
    STATUS     current
    DESCRIPTION
            ""
    ::= { lcsStatusWlanNetworksEntry 3 }

-- {COLUMN} 1.3.6.1.4.1.2356.11.1.3.56.1.4
lcsStatusWlanNetworksEntryNumStations OBJECT-TYPE
    SYNTAX     Integer32 (0..65535)
    MAX-ACCESS read-only
    STATUS     current
    DESCRIPTION
            ""
    ::= { lcsStatusWlanNetworksEntry 4 }

-- {COLUMN} 1.3.6.1.4.1.2356.11.1.3.56.1.5
lcsStatusWlanNetworksEntryMcastPwrSave OBJECT-TYPE
    SYNTAX     INTEGER {
                  eNo (0),
                  eYes (1)
            }
    MAX-ACCESS read-only
    STATUS     current
    DESCRIPTION
            ""
    ::= { lcsStatusWlanNetworksEntry 5 }

-- {COLUMN} 1.3.6.1.4.1.2356.11.1.3.56.1.6
lcsStatusWlanNetworksEntryBssid OBJECT-TYPE
    SYNTAX     MacAddress
    MAX-ACCESS read-only
    STATUS     current
    DESCRIPTION
            ""
    ::= { lcsStatusWlanNetworksEntry 6 }

-- {COLUMN} 1.3.6.1.4.1.2356.11.1.3.56.1.7
lcsStatusWlanNetworksEntryVlanId OBJECT-TYPE
    SYNTAX     Integer32 (0..65535)
    MAX-ACCESS read-only
    STATUS     current
    DESCRIPTION
            ""
    ::= { lcsStatusWlanNetworksEntry 7 }

-- {COLUMN} 1.3.6.1.4.1.2356.11.1.3.56.1.8
lcsStatusWlanNetworksEntryApsd OBJECT-TYPE
    SYNTAX     INTEGER {
                  eNo (0),
                  eYes (1)
            }
    MAX-ACCESS read-only
    STATUS     current
    DESCRIPTION
            ""
    ::= { lcsStatusWlanNetworksEntry 8 }

-- {COLUMN} 1.3.6.1.4.1.2356.11.1.3.56.1.9
lcsStatusWlanNetworksEntryRadioMode OBJECT-TYPE
    SYNTAX     INTEGER {
                  e11bgMixed (0),
                  e11gOnly (1),
                  e11bOnly (2),
                  e2mMixed (3),
                  eTurboG (4),
                  e11bgnMixed (5),
                  e2m11bgnMixed (6),
                  e11gnMixed (7),
                  eGreenfieldGn (8),
                  e11a (256),
                  eTurboA (257),
                  e11anMixed (259),
                  eGreenfieldAn (260),
                  eHalf11a (261),
                  eQuarter11a (262),
                  e11anacMixed (263),
                  e11nacMixed (264),
                  e11acOnly (265),
                  eNone (65535)
            }
    MAX-ACCESS read-only
    STATUS     current
    DESCRIPTION
            ""
    ::= { lcsStatusWlanNetworksEntry 9 }

-- {COLUMN} 1.3.6.1.4.1.2356.11.1.3.56.1.10
lcsStatusWlanNetworksEntryAlarmState OBJECT-TYPE
    SYNTAX     INTEGER {
                  eNo (0),
                  ePhySignal (1),
                  eTotalRetries (2),
                  eTxErrors (4)
            }
    MAX-ACCESS read-only
    STATUS     current
    DESCRIPTION
            ""
    ::= { lcsStatusWlanNetworksEntry 10 }

-- {COLUMN} 1.3.6.1.4.1.2356.11.1.3.56.1.11
lcsStatusWlanNetworksEntryBasicRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            "-- empty --"
    ::= { lcsStatusWlanNetworksEntry 11 }

-- {COLUMN} 1.3.6.1.4.1.2356.11.1.3.56.1.12
lcsStatusWlanNetworksEntryMacFilter OBJECT-TYPE
    SYNTAX     INTEGER {
                  eYes (0),
                  eNo (1),
                  eLocalOnly (2),
                  eRadiusOnly (3)
            }
    MAX-ACCESS read-only
    STATUS     current
    DESCRIPTION
            "-- empty --"
    ::= { lcsStatusWlanNetworksEntry 12 }

-- {COLUMN} 1.3.6.1.4.1.2356.11.1.3.56.1.13
lcsStatusWlanNetworksEntryAccessMode OBJECT-TYPE
    SYNTAX     INTEGER {
                  eNegative (0),
                  ePositive (1)
            }
    MAX-ACCESS read-only
    STATUS     current
    DESCRIPTION
            "-- empty --"
    ::= { lcsStatusWlanNetworksEntry 13 }

-- {COLUMN} 1.3.6.1.4.1.2356.11.1.3.56.1.14
lcsStatusWlanNetworksEntryClosedNetwork OBJECT-TYPE
    SYNTAX     INTEGER {
                  eNo (0),
                  eYes (1),
                  eTightened (2)
            }
    MAX-ACCESS read-only
    STATUS     current
    DESCRIPTION
            "-- empty --"
    ::= { lcsStatusWlanNetworksEntry 14 }

-- {TABLE} 1.3.6.1.4.1.2356.11.1.3.57
lcsStatusWlanRadiosTable OBJECT-TYPE
    SYNTAX     SEQUENCE OF LcsStatusWlanRadiosEntry
    MAX-ACCESS not-accessible
    STATUS     current
    DESCRIPTION
            ""
    ::= { lcsStatusWlan 57 }

-- {ROW} 1.3.6.1.4.1.2356.11.1.3.57.1
lcsStatusWlanRadiosEntry OBJECT-TYPE
    SYNTAX     LcsStatusWlanRadiosEntry
    MAX-ACCESS not-accessible
    STATUS     current
    DESCRIPTION
            ""
    INDEX {
            lcsStatusWlanRadiosEntryIfc
          }
    ::= { lcsStatusWlanRadiosTable 1 }

LcsStatusWlanRadiosEntry ::= SEQUENCE {
            lcsStatusWlanRadiosEntryIfc DisplayString,
            lcsStatusWlanRadiosEntryRadioBand INTEGER,
            lcsStatusWlanRadiosEntryRadioChannel Integer32,
            lcsStatusWlanRadiosEntryNoiseLevel Integer32,
            lcsStatusWlanRadiosEntryModemLoad Integer32,
            lcsStatusWlanRadiosEntryTransmitPower DisplayString,
            lcsStatusWlanRadiosEntryEirp DisplayString,
            lcsStatusWlanRadiosEntryExcEirp INTEGER,
            lcsStatusWlanRadiosEntryBackgroundScan Integer32,
            lcsStatusWlanRadiosEntryExtChannel INTEGER,
            lcsStatusWlanRadiosEntryBackgroundScanUnit INTEGER,
            lcsStatusWlanRadiosEntryDfsScheme INTEGER,
            lcsStatusWlanRadiosEntryRadioMode INTEGER,
            lcsStatusWlanRadiosEntry40mhzPermitted INTEGER,
            lcsStatusWlanRadiosEntryRadarLoadThreshold Integer32,
            lcsStatusWlanRadiosEntryShortSlotTime INTEGER,
            lcsStatusWlanRadiosEntryAggregateTimeLimitUs Integer32,
            lcsStatusWlanRadiosEntryChannelBandwidth INTEGER,
            lcsStatusWlanRadiosEntryAllowPhyRestarts INTEGER,
            lcsStatusWlanRadiosEntrySecondaryChannel Integer32,
            lcsStatusWlanRadiosEntrySecondaryNoiseLevel Integer32,
            lcsStatusWlanRadiosEntryChannelUtilization Integer32,
            lcsStatusWlanRadiosEntryOwnUtilization Integer32,
            lcsStatusWlanRadiosEntryTxUtilization Integer32,
            lcsStatusWlanRadiosEntryRxUtilization Integer32,
            lcsStatusWlanRadiosEntryCoChannelUtilization Integer32,
            lcsStatusWlanRadiosEntryPowerSetting INTEGER
    }

-- {COLUMN} 1.3.6.1.4.1.2356.11.1.3.57.1.1
lcsStatusWlanRadiosEntryIfc OBJECT-TYPE
    SYNTAX     DisplayString (SIZE(0..255))
    MAX-ACCESS read-only
    STATUS     current
    DESCRIPTION
            ""
    ::= { lcsStatusWlanRadiosEntry 1 }

-- {COLUMN} 1.3.6.1.4.1.2356.11.1.3.57.1.2
lcsStatusWlanRadiosEntryRadioBand OBJECT-TYPE
    SYNTAX     INTEGER {
                  eUnknown (0),
                  e24ghz (1),
                  e5ghz (2),
                  e24ghz5ghz (3)
            }
    MAX-ACCESS read-only
    STATUS     current
    DESCRIPTION
            ""
    ::= { lcsStatusWlanRadiosEntry 2 }

-- {COLUMN} 1.3.6.1.4.1.2356.11.1.3.57.1.3
lcsStatusWlanRadiosEntryRadioChannel OBJECT-TYPE
    SYNTAX     Integer32 (0..255)
    MAX-ACCESS read-only
    STATUS     current
    DESCRIPTION
            ""
    ::= { lcsStatusWlanRadiosEntry 3 }

-- {COLUMN} 1.3.6.1.4.1.2356.11.1.3.57.1.5
lcsStatusWlanRadiosEntryNoiseLevel OBJECT-TYPE
    SYNTAX     Integer32 (-32768..32767)
    MAX-ACCESS read-only
    STATUS     current
    DESCRIPTION
            ""
    ::= { lcsStatusWlanRadiosEntry 5 }

-- {COLUMN} 1.3.6.1.4.1.2356.11.1.3.57.1.6
lcsStatusWlanRadiosEntryModemLoad OBJECT-TYPE
    SYNTAX     Integer32 (0..255)
    MAX-ACCESS read-only
    STATUS     current
    DESCRIPTION
            ""
    ::= { lcsStatusWlanRadiosEntry 6 }

-- {COLUMN} 1.3.6.1.4.1.2356.11.1.3.57.1.7
lcsStatusWlanRadiosEntryTransmitPower OBJECT-TYPE
    SYNTAX     DisplayString (SIZE(0..255))
    MAX-ACCESS read-only
    STATUS     current
    DESCRIPTION
            ""
    ::= { lcsStatusWlanRadiosEntry 7 }

-- {COLUMN} 1.3.6.1.4.1.2356.11.1.3.57.1.8
lcsStatusWlanRadiosEntryEirp OBJECT-TYPE
    SYNTAX     DisplayString (SIZE(0..255))
    MAX-ACCESS read-only
    STATUS     current
    DESCRIPTION
            ""
    ::= { lcsStatusWlanRadiosEntry 8 }

-- {COLUMN} 1.3.6.1.4.1.2356.11.1.3.57.1.9
lcsStatusWlanRadiosEntryExcEirp OBJECT-TYPE
    SYNTAX     INTEGER {
                  eNo (0),
                  eYes (1)
            }
    MAX-ACCESS read-only
    STATUS     current
    DESCRIPTION
            ""
    ::= { lcsStatusWlanRadiosEntry 9 }

-- {COLUMN} 1.3.6.1.4.1.2356.11.1.3.57.1.10
lcsStatusWlanRadiosEntryBackgroundScan OBJECT-TYPE
    SYNTAX     Integer32 (0..2147483647)
    MAX-ACCESS read-only
    STATUS     current
    DESCRIPTION
            ""
    ::= { lcsStatusWlanRadiosEntry 10 }

-- {COLUMN} 1.3.6.1.4.1.2356.11.1.3.57.1.11
lcsStatusWlanRadiosEntryExtChannel OBJECT-TYPE
    SYNTAX     INTEGER {
                  eNone (0),
                  eAbove (1),
                  eBelow (3)
            }
    MAX-ACCESS read-only
    STATUS     current
    DESCRIPTION
            ""
    ::= { lcsStatusWlanRadiosEntry 11 }

-- {COLUMN} 1.3.6.1.4.1.2356.11.1.3.57.1.12
lcsStatusWlanRadiosEntryBackgroundScanUnit OBJECT-TYPE
    SYNTAX     INTEGER {
                  eSeconds (0),
                  eMilliseconds (1),
                  eMicroseconds (2),
                  eMinutes (3),
                  eHours (4),
                  eDays (5),
                  eWeeks (6),
                  eFortnights (7)
            }
    MAX-ACCESS read-only
    STATUS     current
    DESCRIPTION
            ""
    ::= { lcsStatusWlanRadiosEntry 12 }

-- {COLUMN} 1.3.6.1.4.1.2356.11.1.3.57.1.13
lcsStatusWlanRadiosEntryDfsScheme OBJECT-TYPE
    SYNTAX     INTEGER {
                  eNone (0),
                  eEn301893V12 (1),
                  eEn301893V13 (2),
                  eEn302502 (4),
                  eFcc (8),
                  eJapan (16),
                  eEn301893V15 (32),
                  eEn301893V16 (64),
                  eEn301893V17 (256),
                  eEn301893V21 (512)
            }
    MAX-ACCESS read-only
    STATUS     current
    DESCRIPTION
            ""
    ::= { lcsStatusWlanRadiosEntry 13 }

-- {COLUMN} 1.3.6.1.4.1.2356.11.1.3.57.1.14
lcsStatusWlanRadiosEntryRadioMode OBJECT-TYPE
    SYNTAX     INTEGER {
                  e11bgMixed (0),
                  e11gOnly (1),
                  e11bOnly (2),
                  e2mMixed (3),
                  eTurboG (4),
                  e11bgnMixed (5),
                  e2m11bgnMixed (6),
                  e11gnMixed (7),
                  eGreenfieldGn (8),
                  e11a (256),
                  eTurboA (257),
                  e11anMixed (259),
                  eGreenfieldAn (260),
                  eHalf11a (261),
                  eQuarter11a (262),
                  e11anacMixed (263),
                  e11nacMixed (264),
                  e11acOnly (265),
                  eNone (65535)
            }
    MAX-ACCESS read-only
    STATUS     current
    DESCRIPTION
            ""
    ::= { lcsStatusWlanRadiosEntry 14 }

-- {COLUMN} 1.3.6.1.4.1.2356.11.1.3.57.1.15
lcsStatusWlanRadiosEntry40mhzPermitted OBJECT-TYPE
    SYNTAX     INTEGER {
                  eNo (0),
                  eYes (1)
            }
    MAX-ACCESS read-only
    STATUS     current
    DESCRIPTION
            "-- empty --"
    ::= { lcsStatusWlanRadiosEntry 15 }

-- {COLUMN} 1.3.6.1.4.1.2356.11.1.3.57.1.16
lcsStatusWlanRadiosEntryRadarLoadThreshold OBJECT-TYPE
    SYNTAX     Integer32 (0..255)
    MAX-ACCESS read-only
    STATUS     current
    DESCRIPTION
            "-- empty --"
    ::= { lcsStatusWlanRadiosEntry 16 }

-- {COLUMN} 1.3.6.1.4.1.2356.11.1.3.57.1.17
lcsStatusWlanRadiosEntryShortSlotTime OBJECT-TYPE
    SYNTAX     INTEGER {
                  eNo (0),
                  eYes (1)
            }
    MAX-ACCESS read-only
    STATUS     current
    DESCRIPTION
            "-- empty --"
    ::= { lcsStatusWlanRadiosEntry 17 }

-- {COLUMN} 1.3.6.1.4.1.2356.11.1.3.57.1.18
lcsStatusWlanRadiosEntryAggregateTimeLimitUs OBJECT-TYPE
    SYNTAX     Integer32 (0..2147483647)
    MAX-ACCESS read-only
    STATUS     current
    DESCRIPTION
            "-- empty --"
    ::= { lcsStatusWlanRadiosEntry 18 }

-- {COLUMN} 1.3.6.1.4.1.2356.11.1.3.57.1.19
lcsStatusWlanRadiosEntryChannelBandwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanRadiosEntry 19 }

-- {COLUMN} 1.3.6.1.4.1.2356.11.1.3.57.1.25
lcsStatusWlanRadiosEntryAllowPhyRestarts OBJECT-TYPE
    SYNTAX     INTEGER {
                  eNo (0),
                  eYes (1)
            }
    MAX-ACCESS read-only
    STATUS     current
    DESCRIPTION
            "-- empty --"
    ::= { lcsStatusWlanRadiosEntry 25 }

-- {COLUMN} 1.3.6.1.4.1.2356.11.1.3.57.1.26
lcsStatusWlanRadiosEntrySecondaryChannel OBJECT-TYPE
    SYNTAX     Integer32 (0..255)
    MAX-ACCESS read-only
    STATUS     current
    DESCRIPTION
            "-- empty --"
    ::= { lcsStatusWlanRadiosEntry 26 }

-- {COLUMN} 1.3.6.1.4.1.2356.11.1.3.57.1.27
lcsStatusWlanRadiosEntrySecondaryNoiseLevel OBJECT-TYPE
    SYNTAX     Integer32 (-32768..32767)
    MAX-ACCESS read-only
    STATUS     current
    DESCRIPTION
            "-- empty --"
    ::= { lcsStatusWlanRadiosEntry 27 }

-- {COLUMN} 1.3.6.1.4.1.2356.11.1.3.57.1.28
lcsStatusWlanRadiosEntryChannelUtilization OBJECT-TYPE
    SYNTAX     Integer32 (0..255)
    MAX-ACCESS read-only
    STATUS     current
    DESCRIPTION
            "-- empty --"
    ::= { lcsStatusWlanRadiosEntry 28 }

-- {COLUMN} 1.3.6.1.4.1.2356.11.1.3.57.1.29
lcsStatusWlanRadiosEntryOwnUtilization OBJECT-TYPE
    SYNTAX     Integer32 (0..255)
    MAX-ACCESS read-only
    STATUS     current
    DESCRIPTION
            "-- empty --"
    ::= { lcsStatusWlanRadiosEntry 29 }

-- {COLUMN} 1.3.6.1.4.1.2356.11.1.3.57.1.30
lcsStatusWlanRadiosEntryTxUtilization OBJECT-TYPE
    SYNTAX     Integer32 (0..255)
    MAX-ACCESS read-only
    STATUS     current
    DESCRIPTION
            "-- empty --"
    ::= { lcsStatusWlanRadiosEntry 30 }

-- {COLUMN} 1.3.6.1.4.1.2356.11.1.3.57.1.31
lcsStatusWlanRadiosEntryRxUtilization OBJECT-TYPE
    SYNTAX     Integer32 (0..255)
    MAX-ACCESS read-only
    STATUS     current
    DESCRIPTION
            "-- empty --"
    ::= { lcsStatusWlanRadiosEntry 31 }

-- {COLUMN} 1.3.6.1.4.1.2356.11.1.3.57.1.32
lcsStatusWlanRadiosEntryCoChannelUtilization OBJECT-TYPE
    SYNTAX     Integer32 (0..255)
    MAX-ACCESS read-only
    STATUS     current
    DESCRIPTION
            "-- empty --"
    ::= { lcsStatusWlanRadiosEntry 32 }

-- {COLUMN} 1.3.6.1.4.1.2356.11.1.3.57.1.33
lcsStatusWlanRadiosEntryPowerSetting OBJECT-TYPE
    SYNTAX     INTEGER {
                  eAutomatic (0),
                  eManual (1)
            }
    MAX-ACCESS read-only
    STATUS     current
    DESCRIPTION
            "-- empty --"
    ::= { lcsStatusWlanRadiosEntry 33 }

-- {TABLE} 1.3.6.1.4.1.2356.11.1.3.58
lcsStatusWlanQosParametersTable OBJECT-TYPE
    SYNTAX     SEQUENCE OF LcsStatusWlanQosParametersEntry
    MAX-ACCESS not-accessible
    STATUS     current
    DESCRIPTION
            ""
    ::= { lcsStatusWlan 58 }

-- {ROW} 1.3.6.1.4.1.2356.11.1.3.58.1
lcsStatusWlanQosParametersEntry OBJECT-TYPE
    SYNTAX     LcsStatusWlanQosParametersEntry
    MAX-ACCESS not-accessible
    STATUS     current
    DESCRIPTION
            ""
    INDEX {
            lcsStatusWlanQosParametersEntryIfc,
            lcsStatusWlanQosParametersEntryAccessCategory
          }
    ::= { lcsStatusWlanQosParametersTable 1 }

LcsStatusWlanQosParametersEntry ::= SEQUENCE {
            lcsStatusWlanQosParametersEntryIfc DisplayString,
            lcsStatusWlanQosParametersEntryAccessCategory INTEGER,
            lcsStatusWlanQosParametersEntryTxop Integer32,
            lcsStatusWlanQosParametersEntryCwmin Integer32,
            lcsStatusWlanQosParametersEntryCwmax Integer32,
            lcsStatusWlanQosParametersEntryAifs Integer32,
            lcsStatusWlanQosParametersEntryChannelOccupancyTime Integer32
    }

-- {COLUMN} 1.3.6.1.4.1.2356.11.1.3.58.1.1
lcsStatusWlanQosParametersEntryIfc OBJECT-TYPE
    SYNTAX     DisplayString (SIZE(0..255))
    MAX-ACCESS read-only
    STATUS     current
    DESCRIPTION
            ""
    ::= { lcsStatusWlanQosParametersEntry 1 }

-- {COLUMN} 1.3.6.1.4.1.2356.11.1.3.58.1.2
lcsStatusWlanQosParametersEntryAccessCategory OBJECT-TYPE
    SYNTAX     INTEGER {
                  eBestEffort (0),
                  eBackground (1),
                  eVideo (2),
                  eVoice (3)
            }
    MAX-ACCESS read-only
    STATUS     current
    DESCRIPTION
            ""
    ::= { lcsStatusWlanQosParametersEntry 2 }

-- {COLUMN} 1.3.6.1.4.1.2356.11.1.3.58.1.3
lcsStatusWlanQosParametersEntryTxop OBJECT-TYPE
    SYNTAX     Integer32 (0..2147483647)
    MAX-ACCESS read-only
    STATUS     current
    DESCRIPTION
            ""
    ::= { lcsStatusWlanQosParametersEntry 3 }

-- {COLUMN} 1.3.6.1.4.1.2356.11.1.3.58.1.4
lcsStatusWlanQosParametersEntryCwmin OBJECT-TYPE
    SYNTAX     Integer32 (0..65535)
    MAX-ACCESS read-only
    STATUS     current
    DESCRIPTION
            ""
    ::= { lcsStatusWlanQosParametersEntry 4 }

-- {COLUMN} 1.3.6.1.4.1.2356.11.1.3.58.1.5
lcsStatusWlanQosParametersEntryCwmax OBJECT-TYPE
    SYNTAX     Integer32 (0..65535)
    MAX-ACCESS read-only
    STATUS     current
    DESCRIPTION
            ""
    ::= { lcsStatusWlanQosParametersEntry 5 }

-- {COLUMN} 1.3.6.1.4.1.2356.11.1.3.58.1.6
lcsStatusWlanQosParametersEntryAifs OBJECT-TYPE
    SYNTAX     Integer32 (0..255)
    MAX-ACCESS read-only
    STATUS     current
    DESCRIPTION
            ""
    ::= { lcsStatusWlanQosParametersEntry 6 }

-- {COLUMN} 1.3.6.1.4.1.2356.11.1.3.58.1.7
lcsStatusWlanQosParametersEntryChannelOccupancyTime OBJECT-TYPE
    SYNTAX     Integer32 (0..2147483647)
    MAX-ACCESS read-only
    STATUS     current
    DESCRIPTION
            "-- empty --"
    ::= { lcsStatusWlanQosParametersEntry 7 }

-- {TABLE} 1.3.6.1.4.1.2356.11.1.3.59
lcsStatusWlanQosPacketStatisticsTable OBJECT-TYPE
    SYNTAX     SEQUENCE OF LcsStatusWlanQosPacketStatisticsEntry
    MAX-ACCESS not-accessible
    STATUS     current
    DESCRIPTION
            ""
    ::= { lcsStatusWlan 59 }

-- {ROW} 1.3.6.1.4.1.2356.11.1.3.59.1
lcsStatusWlanQosPacketStatisticsEntry OBJECT-TYPE
    SYNTAX     LcsStatusWlanQosPacketStatisticsEntry
    MAX-ACCESS not-accessible
    STATUS     current
    DESCRIPTION
            ""
    INDEX {
            lcsStatusWlanQosPacketStatisticsEntryIfc,
            lcsStatusWlanQosPacketStatisticsEntryAccessCategory
          }
    ::= { lcsStatusWlanQosPacketStatisticsTable 1 }

LcsStatusWlanQosPacketStatisticsEntry ::= SEQUENCE {
            lcsStatusWlanQosPacketStatisticsEntryIfc DisplayString,
            lcsStatusWlanQosPacketStatisticsEntryAccessCategory INTEGER,
            lcsStatusWlanQosPacketStatisticsEntryTxPackets Integer32,
            lcsStatusWlanQosPacketStatisticsEntryTxDiscarded Integer32
    }

-- {COLUMN} 1.3.6.1.4.1.2356.11.1.3.59.1.1
lcsStatusWlanQosPacketStatisticsEntryIfc OBJECT-TYPE
    SYNTAX     DisplayString (SIZE(0..255))
    MAX-ACCESS read-only
    STATUS     current
    DESCRIPTION
            ""
    ::= { lcsStatusWlanQosPacketStatisticsEntry 1 }

-- {COLUMN} 1.3.6.1.4.1.2356.11.1.3.59.1.2
lcsStatusWlanQosPacketStatisticsEntryAccessCategory OBJECT-TYPE
    SYNTAX     INTEGER {
                  eBestEffort (0),
                  eBackground (1),
                  eVideo (2),
                  eVoice (3)
            }
    MAX-ACCESS read-only
    STATUS     current
    DESCRIPTION
            ""
    ::= { lcsStatusWlanQosPacketStatisticsEntry 2 }

-- {COLUMN} 1.3.6.1.4.1.2356.11.1.3.59.1.3
lcsStatusWlanQosPacketStatisticsEntryTxPackets OBJECT-TYPE
    SYNTAX     Integer32 (0..2147483647)
    MAX-ACCESS read-only
    STATUS     current
    DESCRIPTION
            ""
    ::= { lcsStatusWlanQosPacketStatisticsEntry 3 }

-- {COLUMN} 1.3.6.1.4.1.2356.11.1.3.59.1.4
lcsStatusWlanQosPacketStatisticsEntryTxDiscarded OBJECT-TYPE
    SYNTAX     Integer32 (0..2147483647)
    MAX-ACCESS read-only
    STATUS     current
    DESCRIPTION
            ""
    ::= { lcsStatusWlanQosPacketStatisticsEntry 4 }

-- {NODE} 1.3.6.1.4.1.2356.11.1.3.60
lcsStatusWlanPmkCaching OBJECT IDENTIFIER ::= { lcsStatusWlan 60 }

-- {TABLE} 1.3.6.1.4.1.2356.11.1.3.60.1
lcsStatusWlanPmkCachingContentsTable OBJECT-TYPE
    SYNTAX     SEQUENCE OF LcsStatusWlanPmkCachingContentsEntry
    MAX-ACCESS not-accessible
    STATUS     current
    DESCRIPTION
            "-- empty --"
    ::= { lcsStatusWlanPmkCaching 1 }

-- {ROW} 1.3.6.1.4.1.2356.11.1.3.60.1.1
lcsStatusWlanPmkCachingContentsEntry OBJECT-TYPE
    SYNTAX     LcsStatusWlanPmkCachingContentsEntry
    MAX-ACCESS not-accessible
    STATUS     current
    DESCRIPTION
            ""
    INDEX {
            lcsStatusWlanPmkCachingContentsEntryAuthenticator,
            lcsStatusWlanPmkCachingContentsEntrySupplicant
          }
    ::= { lcsStatusWlanPmkCachingContentsTable 1 }

LcsStatusWlanPmkCachingContentsEntry ::= SEQUENCE {
            lcsStatusWlanPmkCachingContentsEntryAuthenticator MacAddress,
            lcsStatusWlanPmkCachingContentsEntrySupplicant MacAddress,
            lcsStatusWlanPmkCachingContentsEntryUserName DisplayString,
            lcsStatusWlanPmkCachingContentsEntryVlanId Integer32,
            lcsStatusWlanPmkCachingContentsEntryLifetime Integer32,
            lcsStatusWlanPmkCachingContentsEntryExpired INTEGER,
            lcsStatusWlanPmkCachingContentsEntrySource INTEGER
    }

-- {COLUMN} 1.3.6.1.4.1.2356.11.1.3.60.1.1.1
lcsStatusWlanPmkCachingContentsEntryAuthenticator OBJECT-TYPE
    SYNTAX     MacAddress
    MAX-ACCESS read-only
    STATUS     current
    DESCRIPTION
            "-- empty --"
    ::= { lcsStatusWlanPmkCachingContentsEntry 1 }

-- {COLUMN} 1.3.6.1.4.1.2356.11.1.3.60.1.1.2
lcsStatusWlanPmkCachingContentsEntrySupplicant OBJECT-TYPE
    SYNTAX     MacAddress
    MAX-ACCESS read-only
    STATUS     current
    DESCRIPTION
            "-- empty --"
    ::= { lcsStatusWlanPmkCachingContentsEntry 2 }

-- {COLUMN} 1.3.6.1.4.1.2356.11.1.3.60.1.1.3
lcsStatusWlanPmkCachingContentsEntryUserName OBJECT-TYPE
    SYNTAX     DisplayString (SIZE(0..255))
    MAX-ACCESS read-only
    STATUS     current
    DESCRIPTION
            "-- empty --"
    ::= { lcsStatusWlanPmkCachingContentsEntry 3 }

-- {COLUMN} 1.3.6.1.4.1.2356.11.1.3.60.1.1.4
lcsStatusWlanPmkCachingContentsEntryVlanId OBJECT-TYPE
    SYNTAX     Integer32 (0..65535)
    MAX-ACCESS read-only
    STATUS     current
    DESCRIPTION
            "-- empty --"
    ::= { lcsStatusWlanPmkCachingContentsEntry 4 }

-- {COLUMN} 1.3.6.1.4.1.2356.11.1.3.60.1.1.5
lcsStatusWlanPmkCachingContentsEntryLifetime OBJECT-TYPE
    SYNTAX     Integer32 (0..2147483647)
    MAX-ACCESS read-only
    STATUS     current
    DESCRIPTION
            "-- empty --"
    ::= { lcsStatusWlanPmkCachingContentsEntry 5 }

-- {COLUMN} 1.3.6.1.4.1.2356.11.1.3.60.1.1.6
lcsStatusWlanPmkCachingContentsEntryExpired OBJECT-TYPE
    SYNTAX     INTEGER {
                  eNo (0),
                  eYes (1)
            }
    MAX-ACCESS read-only
    STATUS     current
    DESCRIPTION
            "-- empty --"
    ::= { lcsStatusWlanPmkCachingContentsEntry 6 }

-- {COLUMN} 1.3.6.1.4.1.2356.11.1.3.60.1.1.7
lcsStatusWlanPmkCachingContentsEntrySource OBJECT-TYPE
    SYNTAX     INTEGER {
                  eUnknown (0),
                  eAuthentication (1),
                  ePreAuthentication (2),
                  eController (3)
            }
    MAX-ACCESS read-only
    STATUS     current
    DESCRIPTION
            "-- empty --"
    ::= { lcsStatusWlanPmkCachingContentsEntry 7 }

-- {TABLE} 1.3.6.1.4.1.2356.11.1.3.60.2
lcsStatusWlanPmkCachingContentsNewTable OBJECT-TYPE
    SYNTAX     SEQUENCE OF LcsStatusWlanPmkCachingContentsNewEntry
    MAX-ACCESS not-accessible
    STATUS     current
    DESCRIPTION
            ""
    ::= { lcsStatusWlanPmkCaching 2 }

-- {ROW} 1.3.6.1.4.1.2356.11.1.3.60.2.1
lcsStatusWlanPmkCachingContentsNewEntry OBJECT-TYPE
    SYNTAX     LcsStatusWlanPmkCachingContentsNewEntry
    MAX-ACCESS not-accessible
    STATUS     current
    DESCRIPTION
            ""
    INDEX {
            lcsStatusWlanPmkCachingContentsNewEntryAuthenticator,
            lcsStatusWlanPmkCachingContentsNewEntrySupplicant,
            lcsStatusWlanPmkCachingContentsNewEntrySource
          }
    ::= { lcsStatusWlanPmkCachingContentsNewTable 1 }

LcsStatusWlanPmkCachingContentsNewEntry ::= SEQUENCE {
            lcsStatusWlanPmkCachingContentsNewEntryAuthenticator MacAddress,
            lcsStatusWlanPmkCachingContentsNewEntrySupplicant MacAddress,
            lcsStatusWlanPmkCachingContentsNewEntryUserName DisplayString,
            lcsStatusWlanPmkCachingContentsNewEntryVlanId Integer32,
            lcsStatusWlanPmkCachingContentsNewEntryLifetime Integer32,
            lcsStatusWlanPmkCachingContentsNewEntryExpired INTEGER,
            lcsStatusWlanPmkCachingContentsNewEntrySource INTEGER,
            lcsStatusWlanPmkCachingContentsNewEntryPmkid OCTET STRING,
            lcsStatusWlanPmkCachingContentsNewEntryWpa2KeyManagement INTEGER,
            lcsStatusWlanPmkCachingContentsNewEntryMobilityDomain DisplayString,
            lcsStatusWlanPmkCachingContentsNewEntryR0khId DisplayString
    }

-- {COLUMN} 1.3.6.1.4.1.2356.11.1.3.60.2.1.1
lcsStatusWlanPmkCachingContentsNewEntryAuthenticator OBJECT-TYPE
    SYNTAX     MacAddress
    MAX-ACCESS read-only
    STATUS     current
    DESCRIPTION
            "-- empty --"
    ::= { lcsStatusWlanPmkCachingContentsNewEntry 1 }

-- {COLUMN} 1.3.6.1.4.1.2356.11.1.3.60.2.1.2
lcsStatusWlanPmkCachingContentsNewEntrySupplicant OBJECT-TYPE
    SYNTAX     MacAddress
    MAX-ACCESS read-only
    STATUS     current
    DESCRIPTION
            "-- empty --"
    ::= { lcsStatusWlanPmkCachingContentsNewEntry 2 }

-- {COLUMN} 1.3.6.1.4.1.2356.11.1.3.60.2.1.3
lcsStatusWlanPmkCachingContentsNewEntryUserName OBJECT-TYPE
    SYNTAX     DisplayString (SIZE(0..255))
    MAX-ACCESS read-only
    STATUS     current
    DESCRIPTION
            "-- empty --"
    ::= { lcsStatusWlanPmkCachingContentsNewEntry 3 }

-- {COLUMN} 1.3.6.1.4.1.2356.11.1.3.60.2.1.4
lcsStatusWlanPmkCachingContentsNewEntryVlanId OBJECT-TYPE
    SYNTAX     Integer32 (0..65535)
    MAX-ACCESS read-only
    STATUS     current
    DESCRIPTION
            "-- empty --"
    ::= { lcsStatusWlanPmkCachingContentsNewEntry 4 }

-- {COLUMN} 1.3.6.1.4.1.2356.11.1.3.60.2.1.5
lcsStatusWlanPmkCachingContentsNewEntryLifetime OBJECT-TYPE
    SYNTAX     Integer32 (0..2147483647)
    MAX-ACCESS read-only
    STATUS     current
    DESCRIPTION
            "-- empty --"
    ::= { lcsStatusWlanPmkCachingContentsNewEntry 5 }

-- {COLUMN} 1.3.6.1.4.1.2356.11.1.3.60.2.1.6
lcsStatusWlanPmkCachingContentsNewEntryExpired OBJECT-TYPE
    SYNTAX     INTEGER {
                  eNo (0),
                  eYes (1)
            }
    MAX-ACCESS read-only
    STATUS     current
    DESCRIPTION
            "-- empty --"
    ::= { lcsStatusWlanPmkCachingContentsNewEntry 6 }

-- {COLUMN} 1.3.6.1.4.1.2356.11.1.3.60.2.1.7
lcsStatusWlanPmkCachingContentsNewEntrySource OBJECT-TYPE
    SYNTAX     INTEGER {
                  eUnknown (0),
                  eAuthentication (1),
                  ePreAuthentication (2),
                  eController (3),
                  eIapp (4),
                  eOWE (5),
                  eSae (6),
                  ePsk (7)
            }
    MAX-ACCESS read-only
    STATUS     current
    DESCRIPTION
            "-- empty --"
    ::= { lcsStatusWlanPmkCachingContentsNewEntry 7 }

-- {COLUMN} 1.3.6.1.4.1.2356.11.1.3.60.2.1.8
lcsStatusWlanPmkCachingContentsNewEntryPmkid OBJECT-TYPE
    SYNTAX     OCTET STRING
    MAX-ACCESS read-only
    STATUS     current
    DESCRIPTION
            "-- empty --"
    ::= { lcsStatusWlanPmkCachingContentsNewEntry 8 }

-- {COLUMN} 1.3.6.1.4.1.2356.11.1.3.60.2.1.9
lcsStatusWlanPmkCachingContentsNewEntryWpa2KeyManagement OBJECT-TYPE
    SYNTAX     INTEGER {
                  eStandard (0),
                  eFastRoaming (1),
                  eSha256 (2),
                  eSha384 (3),
                  eFastRoamingSha384 (4),
                  eNone (255)
            }
    MAX-ACCESS read-only
    STATUS     current
    DESCRIPTION
            "-- empty --"
    ::= { lcsStatusWlanPmkCachingContentsNewEntry 9 }

-- {COLUMN} 1.3.6.1.4.1.2356.11.1.3.60.2.1.10
lcsStatusWlanPmkCachingContentsNewEntryMobilityDomain OBJECT-TYPE
    SYNTAX     DisplayString (SIZE(0..255))
    MAX-ACCESS read-only
    STATUS     current
    DESCRIPTION
            "-- empty --"
    ::= { lcsStatusWlanPmkCachingContentsNewEntry 10 }

-- {COLUMN} 1.3.6.1.4.1.2356.11.1.3.60.2.1.11
lcsStatusWlanPmkCachingContentsNewEntryR0khId OBJECT-TYPE
    SYNTAX     DisplayString (SIZE(0..255))
    MAX-ACCESS read-only
    STATUS     current
    DESCRIPTION
            "-- empty --"
    ::= { lcsStatusWlanPmkCachingContentsNewEntry 11 }

-- {NODE} 1.3.6.1.4.1.2356.11.1.3.61
lcsStatusWlanSpectralScan OBJECT IDENTIFIER ::= { lcsStatusWlan 61 }

-- {TABLE} 1.3.6.1.4.1.2356.11.1.3.61.1
lcsStatusWlanSpectralScanLogTable OBJECT-TYPE
    SYNTAX     SEQUENCE OF LcsStatusWlanSpectralScanLogEntry
    MAX-ACCESS not-accessible
    STATUS     current
    DESCRIPTION
            "-- empty --"
    ::= { lcsStatusWlanSpectralScan 1 }

-- {ROW} 1.3.6.1.4.1.2356.11.1.3.61.1.1
lcsStatusWlanSpectralScanLogEntry OBJECT-TYPE
    SYNTAX     LcsStatusWlanSpectralScanLogEntry
    MAX-ACCESS not-accessible
    STATUS     current
    DESCRIPTION
            ""
    INDEX {
            lcsStatusWlanSpectralScanLogEntryIndex
          }
    ::= { lcsStatusWlanSpectralScanLogTable 1 }

LcsStatusWlanSpectralScanLogEntry ::= SEQUENCE {
            lcsStatusWlanSpectralScanLogEntryIndex Integer32,
            lcsStatusWlanSpectralScanLogEntryInterface INTEGER,
            lcsStatusWlanSpectralScanLogEntryTime DisplayString,
            lcsStatusWlanSpectralScanLogEntryChannel Integer32,
            lcsStatusWlanSpectralScanLogEntryFrequency Integer32,
            lcsStatusWlanSpectralScanLogEntryRssi Integer32,
            lcsStatusWlanSpectralScanLogEntryInterferenceType BITS
    }

-- {COLUMN} 1.3.6.1.4.1.2356.11.1.3.61.1.1.1
lcsStatusWlanSpectralScanLogEntryIndex OBJECT-TYPE
    SYNTAX     Integer32 (0..2147483647)
    MAX-ACCESS read-only
    STATUS     current
    DESCRIPTION
            "-- empty --"
    ::= { lcsStatusWlanSpectralScanLogEntry 1 }

-- {COLUMN} 1.3.6.1.4.1.2356.11.1.3.61.1.1.2
lcsStatusWlanSpectralScanLogEntryInterface OBJECT-TYPE
    SYNTAX     INTEGER {
                  eWlan1 (1),
                  eWlan2 (2)
            }
    MAX-ACCESS read-only
    STATUS     current
    DESCRIPTION
            "-- empty --"
    ::= { lcsStatusWlanSpectralScanLogEntry 2 }

-- {COLUMN} 1.3.6.1.4.1.2356.11.1.3.61.1.1.3
lcsStatusWlanSpectralScanLogEntryTime OBJECT-TYPE
    SYNTAX     DisplayString (SIZE(0..19))
    MAX-ACCESS read-only
    STATUS     current
    DESCRIPTION
            "-- empty --"
    ::= { lcsStatusWlanSpectralScanLogEntry 3 }

-- {COLUMN} 1.3.6.1.4.1.2356.11.1.3.61.1.1.4
lcsStatusWlanSpectralScanLogEntryChannel OBJECT-TYPE
    SYNTAX     Integer32 (0..65535)
    MAX-ACCESS read-only
    STATUS     current
    DESCRIPTION
            "-- empty --"
    ::= { lcsStatusWlanSpectralScanLogEntry 4 }

-- {COLUMN} 1.3.6.1.4.1.2356.11.1.3.61.1.1.5
lcsStatusWlanSpectralScanLogEntryFrequency OBJECT-TYPE
    SYNTAX     Integer32 (0..2147483647)
    MAX-ACCESS read-only
    STATUS     current
    DESCRIPTION
            "-- empty --"
    ::= { lcsStatusWlanSpectralScanLogEntry 5 }

-- {COLUMN} 1.3.6.1.4.1.2356.11.1.3.61.1.1.6
lcsStatusWlanSpectralScanLogEntryRssi OBJECT-TYPE
    SYNTAX     Integer32 (0..65535)
    MAX-ACCESS read-only
    STATUS     current
    DESCRIPTION
            "-- empty --"
    ::= { lcsStatusWlanSpectralScanLogEntry 6 }

-- {COLUMN} 1.3.6.1.4.1.2356.11.1.3.61.1.1.7
lcsStatusWlanSpectralScanLogEntryInterferenceType OBJECT-TYPE
    SYNTAX     BITS {
                  eWifi (2),
                  eContinuousWave (3),
                  eDect (4),
                  eFhss (5),
                  eMicrowave (6)
            }
    MAX-ACCESS read-only
    STATUS     current
    DESCRIPTION
            "-- empty --"
    ::= { lcsStatusWlanSpectralScanLogEntry 7 }

-- {TABLE} 1.3.6.1.4.1.2356.11.1.3.61.2
lcsStatusWlanSpectralScanAllChannelsTable OBJECT-TYPE
    SYNTAX     SEQUENCE OF LcsStatusWlanSpectralScanAllChannelsEntry
    MAX-ACCESS not-accessible
    STATUS     current
    DESCRIPTION
            "-- empty --"
    ::= { lcsStatusWlanSpectralScan 2 }

-- {ROW} 1.3.6.1.4.1.2356.11.1.3.61.2.1
lcsStatusWlanSpectralScanAllChannelsEntry OBJECT-TYPE
    SYNTAX     LcsStatusWlanSpectralScanAllChannelsEntry
    MAX-ACCESS not-accessible
    STATUS     current
    DESCRIPTION
            ""
    INDEX {
            lcsStatusWlanSpectralScanAllChannelsEntryIndex
          }
    ::= { lcsStatusWlanSpectralScanAllChannelsTable 1 }

LcsStatusWlanSpectralScanAllChannelsEntry ::= SEQUENCE {
            lcsStatusWlanSpectralScanAllChannelsEntryIndex Integer32,
            lcsStatusWlanSpectralScanAllChannelsEntryInterface INTEGER,
            lcsStatusWlanSpectralScanAllChannelsEntryChannel Integer32,
            lcsStatusWlanSpectralScanAllChannelsEntryMicrowave BITS,
            lcsStatusWlanSpectralScanAllChannelsEntryLastSeenMicrowave DisplayString,
            lcsStatusWlanSpectralScanAllChannelsEntryFhss BITS,
            lcsStatusWlanSpectralScanAllChannelsEntryLastSeenFhss DisplayString,
            lcsStatusWlanSpectralScanAllChannelsEntryWifi BITS,
            lcsStatusWlanSpectralScanAllChannelsEntryLastSeenWifi DisplayString,
            lcsStatusWlanSpectralScanAllChannelsEntryContinuousWave BITS,
            lcsStatusWlanSpectralScanAllChannelsEntryLastSeenContinuousWave DisplayString
    }

-- {COLUMN} 1.3.6.1.4.1.2356.11.1.3.61.2.1.1
lcsStatusWlanSpectralScanAllChannelsEntryIndex OBJECT-TYPE
    SYNTAX     Integer32 (0..2147483647)
    MAX-ACCESS read-only
    STATUS     current
    DESCRIPTION
            "-- empty --"
    ::= { lcsStatusWlanSpectralScanAllChannelsEntry 1 }

-- {COLUMN} 1.3.6.1.4.1.2356.11.1.3.61.2.1.2
lcsStatusWlanSpectralScanAllChannelsEntryInterface OBJECT-TYPE
    SYNTAX     INTEGER {
                  eWlan1 (1),
                  eWlan2 (2)
            }
    MAX-ACCESS read-only
    STATUS     current
    DESCRIPTION
            "-- empty --"
    ::= { lcsStatusWlanSpectralScanAllChannelsEntry 2 }

-- {COLUMN} 1.3.6.1.4.1.2356.11.1.3.61.2.1.3
lcsStatusWlanSpectralScanAllChannelsEntryChannel OBJECT-TYPE
    SYNTAX     Integer32 (0..255)
    MAX-ACCESS read-only
    STATUS     current
    DESCRIPTION
            "-- empty --"
    ::= { lcsStatusWlanSpectralScanAllChannelsEntry 3 }

-- {COLUMN} 1.3.6.1.4.1.2356.11.1.3.61.2.1.4
lcsStatusWlanSpectralScanAllChannelsEntryMicrowave OBJECT-TYPE
    SYNTAX     BITS {
                  eNo (5),
                  eYes (6)
            }
    MAX-ACCESS read-only
    STATUS     current
    DESCRIPTION
            "-- empty --"
    ::= { lcsStatusWlanSpectralScanAllChannelsEntry 4 }

-- {COLUMN} 1.3.6.1.4.1.2356.11.1.3.61.2.1.5
lcsStatusWlanSpectralScanAllChannelsEntryLastSeenMicrowave OBJECT-TYPE
    SYNTAX     DisplayString (SIZE(0..19))
    MAX-ACCESS read-only
    STATUS     current
    DESCRIPTION
            "-- empty --"
    ::= { lcsStatusWlanSpectralScanAllChannelsEntry 5 }

-- {COLUMN} 1.3.6.1.4.1.2356.11.1.3.61.2.1.6
lcsStatusWlanSpectralScanAllChannelsEntryFhss OBJECT-TYPE
    SYNTAX     BITS {
                  eNo (5),
                  eYes (6)
            }
    MAX-ACCESS read-only
    STATUS     current
    DESCRIPTION
            "-- empty --"
    ::= { lcsStatusWlanSpectralScanAllChannelsEntry 6 }

-- {COLUMN} 1.3.6.1.4.1.2356.11.1.3.61.2.1.7
lcsStatusWlanSpectralScanAllChannelsEntryLastSeenFhss OBJECT-TYPE
    SYNTAX     DisplayString (SIZE(0..19))
    MAX-ACCESS read-only
    STATUS     current
    DESCRIPTION
            "-- empty --"
    ::= { lcsStatusWlanSpectralScanAllChannelsEntry 7 }

-- {COLUMN} 1.3.6.1.4.1.2356.11.1.3.61.2.1.8
lcsStatusWlanSpectralScanAllChannelsEntryWifi OBJECT-TYPE
    SYNTAX     BITS {
                  eNo (5),
                  eYes (6)
            }
    MAX-ACCESS read-only
    STATUS     current
    DESCRIPTION
            "-- empty --"
    ::= { lcsStatusWlanSpectralScanAllChannelsEntry 8 }

-- {COLUMN} 1.3.6.1.4.1.2356.11.1.3.61.2.1.9
lcsStatusWlanSpectralScanAllChannelsEntryLastSeenWifi OBJECT-TYPE
    SYNTAX     DisplayString (SIZE(0..19))
    MAX-ACCESS read-only
    STATUS     current
    DESCRIPTION
            "-- empty --"
    ::= { lcsStatusWlanSpectralScanAllChannelsEntry 9 }

-- {COLUMN} 1.3.6.1.4.1.2356.11.1.3.61.2.1.10
lcsStatusWlanSpectralScanAllChannelsEntryContinuousWave OBJECT-TYPE
    SYNTAX     BITS {
                  eNo (5),
                  eYes (6)
            }
    MAX-ACCESS read-only
    STATUS     current
    DESCRIPTION
            "-- empty --"
    ::= { lcsStatusWlanSpectralScanAllChannelsEntry 10 }

-- {COLUMN} 1.3.6.1.4.1.2356.11.1.3.61.2.1.11
lcsStatusWlanSpectralScanAllChannelsEntryLastSeenContinuousWave OBJECT-TYPE
    SYNTAX     DisplayString (SIZE(0..19))
    MAX-ACCESS read-only
    STATUS     current
    DESCRIPTION
            "-- empty --"
    ::= { lcsStatusWlanSpectralScanAllChannelsEntry 11 }

-- {NODE} 1.3.6.1.4.1.2356.11.1.3.62
lcsStatusWlanArpHandling OBJECT IDENTIFIER ::= { lcsStatusWlan 62 }

-- {TABLE} 1.3.6.1.4.1.2356.11.1.3.62.1
lcsStatusWlanArpHandlingArpTableTable OBJECT-TYPE
    SYNTAX     SEQUENCE OF LcsStatusWlanArpHandlingArpTableEntry
    MAX-ACCESS not-accessible
    STATUS     current
    DESCRIPTION
            "-- empty --"
    ::= { lcsStatusWlanArpHandling 1 }

-- {ROW} 1.3.6.1.4.1.2356.11.1.3.62.1.1
lcsStatusWlanArpHandlingArpTableEntry OBJECT-TYPE
    SYNTAX     LcsStatusWlanArpHandlingArpTableEntry
    MAX-ACCESS not-accessible
    STATUS     current
    DESCRIPTION
            ""
    INDEX {
            lcsStatusWlanArpHandlingArpTableEntryAddress,
            lcsStatusWlanArpHandlingArpTableEntryMacAddress
          }
    ::= { lcsStatusWlanArpHandlingArpTableTable 1 }

LcsStatusWlanArpHandlingArpTableEntry ::= SEQUENCE {
            lcsStatusWlanArpHandlingArpTableEntryAddress IpAddress,
            lcsStatusWlanArpHandlingArpTableEntryMacAddress MacAddress,
            lcsStatusWlanArpHandlingArpTableEntryInterface INTEGER,
            lcsStatusWlanArpHandlingArpTableEntryVlanId Integer32,
            lcsStatusWlanArpHandlingArpTableEntryAge Integer32
    }

-- {COLUMN} 1.3.6.1.4.1.2356.11.1.3.62.1.1.1
lcsStatusWlanArpHandlingArpTableEntryAddress OBJECT-TYPE
    SYNTAX     IpAddress
    MAX-ACCESS read-only
    STATUS     current
    DESCRIPTION
            "-- empty --"
    ::= { lcsStatusWlanArpHandlingArpTableEntry 1 }

-- {COLUMN} 1.3.6.1.4.1.2356.11.1.3.62.1.1.2
lcsStatusWlanArpHandlingArpTableEntryMacAddress OBJECT-TYPE
    SYNTAX     MacAddress
    MAX-ACCESS read-only
    STATUS     current
    DESCRIPTION
            "-- empty --"
    ::= { lcsStatusWlanArpHandlingArpTableEntry 2 }

-- {COLUMN} 1.3.6.1.4.1.2356.11.1.3.62.1.1.3
lcsStatusWlanArpHandlingArpTableEntryInterface OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-only
    STATUS     current
    DESCRIPTION
            "-- empty --"
    ::= { lcsStatusWlanArpHandlingArpTableEntry 3 }

-- {COLUMN} 1.3.6.1.4.1.2356.11.1.3.62.1.1.4
lcsStatusWlanArpHandlingArpTableEntryVlanId OBJECT-TYPE
    SYNTAX     Integer32 (0..65535)
    MAX-ACCESS read-only
    STATUS     current
    DESCRIPTION
            "-- empty --"
    ::= { lcsStatusWlanArpHandlingArpTableEntry 4 }

-- {COLUMN} 1.3.6.1.4.1.2356.11.1.3.62.1.1.5
lcsStatusWlanArpHandlingArpTableEntryAge OBJECT-TYPE
    SYNTAX     Integer32 (0..2147483647)
    MAX-ACCESS read-only
    STATUS     current
    DESCRIPTION
            "-- empty --"
    ::= { lcsStatusWlanArpHandlingArpTableEntry 5 }

-- {TABLE} 1.3.6.1.4.1.2356.11.1.3.62.2
lcsStatusWlanArpHandlingNdTableTable OBJECT-TYPE
    SYNTAX     SEQUENCE OF LcsStatusWlanArpHandlingNdTableEntry
    MAX-ACCESS not-accessible
    STATUS     current
    DESCRIPTION
            "-- empty --"
    ::= { lcsStatusWlanArpHandling 2 }

-- {ROW} 1.3.6.1.4.1.2356.11.1.3.62.2.1
lcsStatusWlanArpHandlingNdTableEntry OBJECT-TYPE
    SYNTAX     LcsStatusWlanArpHandlingNdTableEntry
    MAX-ACCESS not-accessible
    STATUS     current
    DESCRIPTION
            ""
    INDEX {
            lcsStatusWlanArpHandlingNdTableEntryAddress,
            lcsStatusWlanArpHandlingNdTableEntryMacAddress
          }
    ::= { lcsStatusWlanArpHandlingNdTableTable 1 }

LcsStatusWlanArpHandlingNdTableEntry ::= SEQUENCE {
            lcsStatusWlanArpHandlingNdTableEntryAddress IpAddress,
            lcsStatusWlanArpHandlingNdTableEntryMacAddress MacAddress,
            lcsStatusWlanArpHandlingNdTableEntryInterface INTEGER,
            lcsStatusWlanArpHandlingNdTableEntryVlanId Integer32,
            lcsStatusWlanArpHandlingNdTableEntryAge Integer32
    }

-- {COLUMN} 1.3.6.1.4.1.2356.11.1.3.62.2.1.1
lcsStatusWlanArpHandlingNdTableEntryAddress OBJECT-TYPE
    SYNTAX     IpAddress
    MAX-ACCESS read-only
    STATUS     current
    DESCRIPTION
            "-- empty --"
    ::= { lcsStatusWlanArpHandlingNdTableEntry 1 }

-- {COLUMN} 1.3.6.1.4.1.2356.11.1.3.62.2.1.2
lcsStatusWlanArpHandlingNdTableEntryMacAddress OBJECT-TYPE
    SYNTAX     MacAddress
    MAX-ACCESS read-only
    STATUS     current
    DESCRIPTION
            "-- empty --"
    ::= { lcsStatusWlanArpHandlingNdTableEntry 2 }

-- {COLUMN} 1.3.6.1.4.1.2356.11.1.3.62.2.1.3
lcsStatusWlanArpHandlingNdTableEntryInterface OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-only
    STATUS     current
    DESCRIPTION
            "-- empty --"
    ::= { lcsStatusWlanArpHandlingNdTableEntry 3 }

-- {COLUMN} 1.3.6.1.4.1.2356.11.1.3.62.2.1.4
lcsStatusWlanArpHandlingNdTableEntryVlanId OBJECT-TYPE
    SYNTAX     Integer32 (0..65535)
    MAX-ACCESS read-only
    STATUS     current
    DESCRIPTION
            "-- empty --"
    ::= { lcsStatusWlanArpHandlingNdTableEntry 4 }

-- {COLUMN} 1.3.6.1.4.1.2356.11.1.3.62.2.1.5
lcsStatusWlanArpHandlingNdTableEntryAge OBJECT-TYPE
    SYNTAX     Integer32 (0..2147483647)
    MAX-ACCESS read-only
    STATUS     current
    DESCRIPTION
            "-- empty --"
    ::= { lcsStatusWlanArpHandlingNdTableEntry 5 }

-- {SCALAR} 1.3.6.1.4.1.2356.11.1.3.62.11
lcsStatusWlanArpHandlingArpRequestsAnswered OBJECT-TYPE
    SYNTAX     Integer32 (0..2147483647)
    MAX-ACCESS read-only
    STATUS     current
    DESCRIPTION
            "-- empty --"
    ::= { lcsStatusWlanArpHandling 11 }

-- {SCALAR} 1.3.6.1.4.1.2356.11.1.3.62.12
lcsStatusWlanArpHandlingArpRequestsNotAnswered OBJECT-TYPE
    SYNTAX     Integer32 (0..2147483647)
    MAX-ACCESS read-only
    STATUS     current
    DESCRIPTION
            "-- empty --"
    ::= { lcsStatusWlanArpHandling 12 }

-- {SCALAR} 1.3.6.1.4.1.2356.11.1.3.62.13
lcsStatusWlanArpHandlingArpRequestsDiscarded OBJECT-TYPE
    SYNTAX     Integer32 (0..2147483647)
    MAX-ACCESS read-only
    STATUS     current
    DESCRIPTION
            "-- empty --"
    ::= { lcsStatusWlanArpHandling 13 }

-- {SCALAR} 1.3.6.1.4.1.2356.11.1.3.62.14
lcsStatusWlanArpHandlingNdSolicitationsAnswered OBJECT-TYPE
    SYNTAX     Integer32 (0..2147483647)
    MAX-ACCESS read-only
    STATUS     current
    DESCRIPTION
            "-- empty --"
    ::= { lcsStatusWlanArpHandling 14 }

-- {SCALAR} 1.3.6.1.4.1.2356.11.1.3.62.15
lcsStatusWlanArpHandlingNdSolicitationsNotAnswered OBJECT-TYPE
    SYNTAX     Integer32 (0..2147483647)
    MAX-ACCESS read-only
    STATUS     current
    DESCRIPTION
            "-- empty --"
    ::= { lcsStatusWlanArpHandling 15 }

-- {SCALAR} 1.3.6.1.4.1.2356.11.1.3.62.16
lcsStatusWlanArpHandlingNdSolicitationsDiscarded OBJECT-TYPE
    SYNTAX     Integer32 (0..2147483647)
    MAX-ACCESS read-only
    STATUS     current
    DESCRIPTION
            "-- empty --"
    ::= { lcsStatusWlanArpHandling 16 }

-- {SCALAR} 1.3.6.1.4.1.2356.11.1.3.62.99
lcsStatusWlanArpHandlingDeleteValues OBJECT-TYPE
    SYNTAX     DisplayString
    MAX-ACCESS read-write
    STATUS     current
    DESCRIPTION
            "-- empty --"
    ::= { lcsStatusWlanArpHandling 99 }

-- {NODE} 1.3.6.1.4.1.2356.11.1.3.63
lcsStatusWlanNoiseImmunity OBJECT IDENTIFIER ::= { lcsStatusWlan 63 }

-- {TABLE} 1.3.6.1.4.1.2356.11.1.3.63.1
lcsStatusWlanNoiseImmunityCurrentParametersTable OBJECT-TYPE
    SYNTAX     SEQUENCE OF LcsStatusWlanNoiseImmunityCurrentParametersEntry
    MAX-ACCESS not-accessible
    STATUS     current
    DESCRIPTION
            "-- empty --"
    ::= { lcsStatusWlanNoiseImmunity 1 }

-- {ROW} 1.3.6.1.4.1.2356.11.1.3.63.1.1
lcsStatusWlanNoiseImmunityCurrentParametersEntry OBJECT-TYPE
    SYNTAX     LcsStatusWlanNoiseImmunityCurrentParametersEntry
    MAX-ACCESS not-accessible
    STATUS     current
    DESCRIPTION
            ""
    INDEX {
            lcsStatusWlanNoiseImmunityCurrentParametersEntryRadioBand,
            lcsStatusWlanNoiseImmunityCurrentParametersEntryRadioChannel,
            lcsStatusWlanNoiseImmunityCurrentParametersEntryInterface
          }
    ::= { lcsStatusWlanNoiseImmunityCurrentParametersTable 1 }

LcsStatusWlanNoiseImmunityCurrentParametersEntry ::= SEQUENCE {
            lcsStatusWlanNoiseImmunityCurrentParametersEntryRadioChannel Integer32,
            lcsStatusWlanNoiseImmunityCurrentParametersEntryInterface INTEGER,
            lcsStatusWlanNoiseImmunityCurrentParametersEntryRadioBand INTEGER,
            lcsStatusWlanNoiseImmunityCurrParamEntryNoiseImmunityLevel Integer32,
            lcsStatusWlanNoiseImmunityCurrParamEntrySpuriousImmunityLevel Integer32,
            lcsStatusWlanNoiseImmunityCurrentParametersEntryFirStepLevel Integer32,
            lcsStatusWlanNoiseImmunityCurrParamEntryOfdmWeakSignalDetect INTEGER,
            lcsStatusWlanNoiseImmunityCurrParamEntryCckWeakSignalDetectThres Integer32,
            lcsStatusWlanNoiseImmunityCurrentParametersEntryMrcCck INTEGER,
            lcsStatusWlanNoiseImmunityCurrentParametersEntryAge Integer32,
            lcsStatusWlanNoiseImmunityCurrentParametersEntryChannelBandwidth INTEGER
    }

-- {COLUMN} 1.3.6.1.4.1.2356.11.1.3.63.1.1.1
lcsStatusWlanNoiseImmunityCurrentParametersEntryRadioChannel OBJECT-TYPE
    SYNTAX     Integer32 (0..255)
    MAX-ACCESS read-only
    STATUS     current
    DESCRIPTION
            "-- empty --"
    ::= { lcsStatusWlanNoiseImmunityCurrentParametersEntry 1 }

-- {COLUMN} 1.3.6.1.4.1.2356.11.1.3.63.1.1.2
lcsStatusWlanNoiseImmunityCurrentParametersEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { lcsStatusWlanNoiseImmunityCurrentParametersEntry 2 }

-- {COLUMN} 1.3.6.1.4.1.2356.11.1.3.63.1.1.9
lcsStatusWlanNoiseImmunityCurrentParametersEntryRadioBand OBJECT-TYPE
    SYNTAX     INTEGER {
                  eUnknown (0),
                  e24ghz (1),
                  e5ghz (2)
            }
    MAX-ACCESS read-only
    STATUS     current
    DESCRIPTION
            "-- empty --"
    ::= { lcsStatusWlanNoiseImmunityCurrentParametersEntry 9 }

-- {COLUMN} 1.3.6.1.4.1.2356.11.1.3.63.1.1.11
lcsStatusWlanNoiseImmunityCurrParamEntryNoiseImmunityLevel OBJECT-TYPE
    SYNTAX     Integer32 (0..255)
    MAX-ACCESS read-only
    STATUS     current
    DESCRIPTION
            "-- empty --"
    ::= { lcsStatusWlanNoiseImmunityCurrentParametersEntry 11 }

-- {COLUMN} 1.3.6.1.4.1.2356.11.1.3.63.1.1.12
lcsStatusWlanNoiseImmunityCurrParamEntrySpuriousImmunityLevel OBJECT-TYPE
    SYNTAX     Integer32 (0..255)
    MAX-ACCESS read-only
    STATUS     current
    DESCRIPTION
            "-- empty --"
    ::= { lcsStatusWlanNoiseImmunityCurrentParametersEntry 12 }

-- {COLUMN} 1.3.6.1.4.1.2356.11.1.3.63.1.1.13
lcsStatusWlanNoiseImmunityCurrentParametersEntryFirStepLevel OBJECT-TYPE
    SYNTAX     Integer32 (0..255)
    MAX-ACCESS read-only
    STATUS     current
    DESCRIPTION
            "-- empty --"
    ::= { lcsStatusWlanNoiseImmunityCurrentParametersEntry 13 }

-- {COLUMN} 1.3.6.1.4.1.2356.11.1.3.63.1.1.14
lcsStatusWlanNoiseImmunityCurrParamEntryOfdmWeakSignalDetect OBJECT-TYPE
    SYNTAX     INTEGER {
                  eNo (0),
                  eYes (1)
            }
    MAX-ACCESS read-only
    STATUS     current
    DESCRIPTION
            "-- empty --"
    ::= { lcsStatusWlanNoiseImmunityCurrentParametersEntry 14 }

-- {COLUMN} 1.3.6.1.4.1.2356.11.1.3.63.1.1.15
lcsStatusWlanNoiseImmunityCurrParamEntryCckWeakSignalDetectThres OBJECT-TYPE
    SYNTAX     Integer32 (0..255)
    MAX-ACCESS read-only
    STATUS     current
    DESCRIPTION
            "-- empty --"
    ::= { lcsStatusWlanNoiseImmunityCurrentParametersEntry 15 }

-- {COLUMN} 1.3.6.1.4.1.2356.11.1.3.63.1.1.16
lcsStatusWlanNoiseImmunityCurrentParametersEntryMrcCck OBJECT-TYPE
    SYNTAX     INTEGER {
                  eNo (0),
                  eYes (1)
            }
    MAX-ACCESS read-only
    STATUS     current
    DESCRIPTION
            "-- empty --"
    ::= { lcsStatusWlanNoiseImmunityCurrentParametersEntry 16 }

-- {COLUMN} 1.3.6.1.4.1.2356.11.1.3.63.1.1.17
lcsStatusWlanNoiseImmunityCurrentParametersEntryAge OBJECT-TYPE
    SYNTAX     Integer32 (0..2147483647)
    MAX-ACCESS read-only
    STATUS     current
    DESCRIPTION
            "-- empty --"
    ::= { lcsStatusWlanNoiseImmunityCurrentParametersEntry 17 }

-- {COLUMN} 1.3.6.1.4.1.2356.11.1.3.63.1.1.18
lcsStatusWlanNoiseImmunityCurrentParametersEntryChannelBandwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanNoiseImmunityCurrentParametersEntry 18 }

-- {TABLE} 1.3.6.1.4.1.2356.11.1.3.63.2
lcsStatusWlanNoiseImmunityLogTableTable OBJECT-TYPE
    SYNTAX     SEQUENCE OF LcsStatusWlanNoiseImmunityLogTableEntry
    MAX-ACCESS not-accessible
    STATUS     current
    DESCRIPTION
            "-- empty --"
    ::= { lcsStatusWlanNoiseImmunity 2 }

-- {ROW} 1.3.6.1.4.1.2356.11.1.3.63.2.1
lcsStatusWlanNoiseImmunityLogTableEntry OBJECT-TYPE
    SYNTAX     LcsStatusWlanNoiseImmunityLogTableEntry
    MAX-ACCESS not-accessible
    STATUS     current
    DESCRIPTION
            ""
    INDEX {
            lcsStatusWlanNoiseImmunityLogTableEntryIndex
          }
    ::= { lcsStatusWlanNoiseImmunityLogTableTable 1 }

LcsStatusWlanNoiseImmunityLogTableEntry ::= SEQUENCE {
            lcsStatusWlanNoiseImmunityLogTableEntryIndex Integer32,
            lcsStatusWlanNoiseImmunityLogTableEntryTime DisplayString,
            lcsStatusWlanNoiseImmunityLogTableEntryInterface INTEGER,
            lcsStatusWlanNoiseImmunityLogTableEntryRadioBand INTEGER,
            lcsStatusWlanNoiseImmunityLogTableEntryRadioChannel Integer32,
            lcsStatusWlanNoiseImmunityLogTableEntryEvent INTEGER,
            lcsStatusWlanNoiseImmunityLogTableEntryParameter INTEGER,
            lcsStatusWlanNoiseImmunityLogTableEntryValue Integer32
    }

-- {COLUMN} 1.3.6.1.4.1.2356.11.1.3.63.2.1.1
lcsStatusWlanNoiseImmunityLogTableEntryIndex OBJECT-TYPE
    SYNTAX     Integer32 (0..2147483647)
    MAX-ACCESS read-only
    STATUS     current
    DESCRIPTION
            "-- empty --"
    ::= { lcsStatusWlanNoiseImmunityLogTableEntry 1 }

-- {COLUMN} 1.3.6.1.4.1.2356.11.1.3.63.2.1.2
lcsStatusWlanNoiseImmunityLogTableEntryTime OBJECT-TYPE
    SYNTAX     DisplayString (SIZE(0..255))
    MAX-ACCESS read-only
    STATUS     current
    DESCRIPTION
            "-- empty --"
    ::= { lcsStatusWlanNoiseImmunityLogTableEntry 2 }

-- {COLUMN} 1.3.6.1.4.1.2356.11.1.3.63.2.1.3
lcsStatusWlanNoiseImmunityLogTableEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { lcsStatusWlanNoiseImmunityLogTableEntry 3 }

-- {COLUMN} 1.3.6.1.4.1.2356.11.1.3.63.2.1.4
lcsStatusWlanNoiseImmunityLogTableEntryRadioBand OBJECT-TYPE
    SYNTAX     INTEGER {
                  eUnknown (0),
                  e24ghz (1),
                  e5ghz (2)
            }
    MAX-ACCESS read-only
    STATUS     current
    DESCRIPTION
            "-- empty --"
    ::= { lcsStatusWlanNoiseImmunityLogTableEntry 4 }

-- {COLUMN} 1.3.6.1.4.1.2356.11.1.3.63.2.1.5
lcsStatusWlanNoiseImmunityLogTableEntryRadioChannel OBJECT-TYPE
    SYNTAX     Integer32 (0..255)
    MAX-ACCESS read-only
    STATUS     current
    DESCRIPTION
            "-- empty --"
    ::= { lcsStatusWlanNoiseImmunityLogTableEntry 5 }

-- {COLUMN} 1.3.6.1.4.1.2356.11.1.3.63.2.1.6
lcsStatusWlanNoiseImmunityLogTableEntryEvent OBJECT-TYPE
    SYNTAX     INTEGER {
                  eValueChange (0),
                  eOfdmMaxImmunity (1),
                  eCckMaxImmunity (2),
                  eMinImmunity (3),
                  eNotAvailable (4),
                  eEventRepeated (5)
            }
    MAX-ACCESS read-only
    STATUS     current
    DESCRIPTION
            "-- empty --"
    ::= { lcsStatusWlanNoiseImmunityLogTableEntry 6 }

-- {COLUMN} 1.3.6.1.4.1.2356.11.1.3.63.2.1.7
lcsStatusWlanNoiseImmunityLogTableEntryParameter OBJECT-TYPE
    SYNTAX     INTEGER {
                  eNone (0),
                  eNoiseImmunityLevel (1),
                  eOfdmWeakSignalDetection (2),
                  eCckWeakSignalDetectionThreshold (3),
                  eFirStepLevel (4),
                  eSpuriousImmunityLevel (5),
                  eMrcCck (8)
            }
    MAX-ACCESS read-only
    STATUS     current
    DESCRIPTION
            "-- empty --"
    ::= { lcsStatusWlanNoiseImmunityLogTableEntry 7 }

-- {COLUMN} 1.3.6.1.4.1.2356.11.1.3.63.2.1.8
lcsStatusWlanNoiseImmunityLogTableEntryValue OBJECT-TYPE
    SYNTAX     Integer32 (0..255)
    MAX-ACCESS read-only
    STATUS     current
    DESCRIPTION
            "-- empty --"
    ::= { lcsStatusWlanNoiseImmunityLogTableEntry 8 }

-- {TABLE} 1.3.6.1.4.1.2356.11.1.3.64
lcsStatusWlanEncryptionTable OBJECT-TYPE
    SYNTAX     SEQUENCE OF LcsStatusWlanEncryptionEntry
    MAX-ACCESS not-accessible
    STATUS     current
    DESCRIPTION
            "-- empty --"
    ::= { lcsStatusWlan 64 }

-- {ROW} 1.3.6.1.4.1.2356.11.1.3.64.1
lcsStatusWlanEncryptionEntry OBJECT-TYPE
    SYNTAX     LcsStatusWlanEncryptionEntry
    MAX-ACCESS not-accessible
    STATUS     current
    DESCRIPTION
            ""
    INDEX {
            lcsStatusWlanEncryptionEntryInterface
          }
    ::= { lcsStatusWlanEncryptionTable 1 }

LcsStatusWlanEncryptionEntry ::= SEQUENCE {
            lcsStatusWlanEncryptionEntryInterface INTEGER,
            lcsStatusWlanEncryptionEntryEncryption INTEGER,
            lcsStatusWlanEncryptionEntryMethod INTEGER,
            lcsStatusWlanEncryptionEntryWpaVersion INTEGER,
            lcsStatusWlanEncryptionEntryWpa1SessionKeytypes INTEGER,
            lcsStatusWlanEncryptionEntryWpa2SessionKeytypes INTEGER,
            lcsStatusWlanEncryptionEntryProtMgmtFrames INTEGER,
            lcsStatusWlanEncryptionEntryPmkCaching INTEGER,
            lcsStatusWlanEncryptionEntryPreAuthentication INTEGER,
            lcsStatusWlanEncryptionEntryOkc INTEGER,
            lcsStatusWlanEncryptionEntryWpa2KeyManagement BITS,
            lcsStatusWlanEncryptionEntryWpaPskNumWrongPassphrase Counter32,
            lcsStatusWlanEncryptionEntryWpaPskNumSuccess Counter32,
            lcsStatusWlanEncryptionEntryWpaPskNumFailures Counter32,
            lcsStatusWlanEncryptionEntryOWE-Groups BITS,
            lcsStatusWlanEncryptionEntrySaeGroups BITS,
            lcsStatusWlanEncryptionEntryWpa23SessionKeytypes BITS,
            lcsStatusWlanEncryptionEntryWpa8021xSecurityLevel INTEGER
    }

-- {COLUMN} 1.3.6.1.4.1.2356.11.1.3.64.1.1
lcsStatusWlanEncryptionEntryInterface OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-only
    STATUS     current
    DESCRIPTION
            "-- empty --"
    ::= { lcsStatusWlanEncryptionEntry 1 }

-- {COLUMN} 1.3.6.1.4.1.2356.11.1.3.64.1.2
lcsStatusWlanEncryptionEntryEncryption OBJECT-TYPE
    SYNTAX     INTEGER {
                  eNo (0),
                  eYes (2)
            }
    MAX-ACCESS read-only
    STATUS     current
    DESCRIPTION
            "-- empty --"
    ::= { lcsStatusWlanEncryptionEntry 2 }

-- {COLUMN} 1.3.6.1.4.1.2356.11.1.3.64.1.4
lcsStatusWlanEncryptionEntryMethod OBJECT-TYPE
    SYNTAX     INTEGER {
                  eNone (0),
                  eWep40Bits (5),
                  eWep104Bits (13),
                  eWep128Bits (16),
                  e80211iWpaPsk (32),
                  e80211iWpa8021x (33),
                  eWep40Bits8021x (34),
                  eWep104Bits8021x (35),
                  eWep128Bits8021x (36),
                  eWPA-OWE (37),
                  eEnhancedOpenTransitional (38),
                  eOsen (39)
            }
    MAX-ACCESS read-only
    STATUS     current
    DESCRIPTION
            "-- empty --"
    ::= { lcsStatusWlanEncryptionEntry 4 }

-- {COLUMN} 1.3.6.1.4.1.2356.11.1.3.64.1.9
lcsStatusWlanEncryptionEntryWpaVersion OBJECT-TYPE
    SYNTAX     INTEGER {
                  eNone (0),
                  eWpa1 (2),
                  eWpa2 (4),
                  eWpa12 (6),
                  eWpa3 (8),
                  eWpa23 (12),
                  eWpa123 (14)
            }
    MAX-ACCESS read-only
    STATUS     current
    DESCRIPTION
            "-- empty --"
    ::= { lcsStatusWlanEncryptionEntry 9 }

-- {COLUMN} 1.3.6.1.4.1.2356.11.1.3.64.1.12
lcsStatusWlanEncryptionEntryWpa1SessionKeytypes OBJECT-TYPE
    SYNTAX     INTEGER {
                  eNone (0),
                  eTkip (1),
                  eAes (2),
                  eTkipAes (3)
            }
    MAX-ACCESS read-only
    STATUS     current
    DESCRIPTION
            "-- empty --"
    ::= { lcsStatusWlanEncryptionEntry 12 }

-- {COLUMN} 1.3.6.1.4.1.2356.11.1.3.64.1.13
lcsStatusWlanEncryptionEntryWpa2SessionKeytypes OBJECT-TYPE
    SYNTAX     INTEGER {
                  eNone (0),
                  eTkip (1),
                  eAes (2),
                  eTkipAes (3)
            }
    MAX-ACCESS read-only
    STATUS     current
    DESCRIPTION
            "-- empty --"
    ::= { lcsStatusWlanEncryptionEntry 13 }

-- {COLUMN} 1.3.6.1.4.1.2356.11.1.3.64.1.14
lcsStatusWlanEncryptionEntryProtMgmtFrames OBJECT-TYPE
    SYNTAX     INTEGER {
                  eNo (0),
                  eOptional (1),
                  eMandatory (2)
            }
    MAX-ACCESS read-only
    STATUS     current
    DESCRIPTION
            "-- empty --"
    ::= { lcsStatusWlanEncryptionEntry 14 }

-- {COLUMN} 1.3.6.1.4.1.2356.11.1.3.64.1.15
lcsStatusWlanEncryptionEntryPmkCaching OBJECT-TYPE
    SYNTAX     INTEGER {
                  eNo (0),
                  eYes (1)
            }
    MAX-ACCESS read-only
    STATUS     current
    DESCRIPTION
            "-- empty --"
    ::= { lcsStatusWlanEncryptionEntry 15 }

-- {COLUMN} 1.3.6.1.4.1.2356.11.1.3.64.1.16
lcsStatusWlanEncryptionEntryPreAuthentication OBJECT-TYPE
    SYNTAX     INTEGER {
                  eNo (0),
                  eYes (1)
            }
    MAX-ACCESS read-only
    STATUS     current
    DESCRIPTION
            "-- empty --"
    ::= { lcsStatusWlanEncryptionEntry 16 }

-- {COLUMN} 1.3.6.1.4.1.2356.11.1.3.64.1.17
lcsStatusWlanEncryptionEntryOkc OBJECT-TYPE
    SYNTAX     INTEGER {
                  eNo (0),
                  eYes (1)
            }
    MAX-ACCESS read-only
    STATUS     current
    DESCRIPTION
            "-- empty --"
    ::= { lcsStatusWlanEncryptionEntry 17 }

-- {COLUMN} 1.3.6.1.4.1.2356.11.1.3.64.1.19
lcsStatusWlanEncryptionEntryWpa2KeyManagement OBJECT-TYPE
    SYNTAX     BITS {
                  eFastRoamingSha384 (3),
                  eSha384 (4),
                  eSha256 (5),
                  eFastRoaming (6),
                  eStandard (7)
            }
    MAX-ACCESS read-only
    STATUS     current
    DESCRIPTION
            "-- empty --"
    ::= { lcsStatusWlanEncryptionEntry 19 }

-- {COLUMN} 1.3.6.1.4.1.2356.11.1.3.64.1.20
lcsStatusWlanEncryptionEntryWpaPskNumWrongPassphrase OBJECT-TYPE
    SYNTAX     Counter32
    MAX-ACCESS read-only
    STATUS     current
    DESCRIPTION
            "-- empty --"
    ::= { lcsStatusWlanEncryptionEntry 20 }

-- {COLUMN} 1.3.6.1.4.1.2356.11.1.3.64.1.21
lcsStatusWlanEncryptionEntryWpaPskNumSuccess OBJECT-TYPE
    SYNTAX     Counter32
    MAX-ACCESS read-only
    STATUS     current
    DESCRIPTION
            "-- empty --"
    ::= { lcsStatusWlanEncryptionEntry 21 }

-- {COLUMN} 1.3.6.1.4.1.2356.11.1.3.64.1.22
lcsStatusWlanEncryptionEntryWpaPskNumFailures OBJECT-TYPE
    SYNTAX     Counter32
    MAX-ACCESS read-only
    STATUS     current
    DESCRIPTION
            "-- empty --"
    ::= { lcsStatusWlanEncryptionEntry 22 }

-- {COLUMN} 1.3.6.1.4.1.2356.11.1.3.64.1.24
lcsStatusWlanEncryptionEntryOWE-Groups OBJECT-TYPE
    SYNTAX     BITS {
                  eSecp521r1 (10),
                  eSecp384r1 (11),
                  eSecp256r1 (12)
            }
    MAX-ACCESS read-only
    STATUS     current
    DESCRIPTION
            "OWE Finite Groups"
    ::= { lcsStatusWlanEncryptionEntry 24 }

-- {COLUMN} 1.3.6.1.4.1.2356.11.1.3.64.1.26
lcsStatusWlanEncryptionEntrySaeGroups OBJECT-TYPE
    SYNTAX     BITS {
                  eSecp521r1 (10),
                  eSecp384r1 (11),
                  eSecp256r1 (12)
            }
    MAX-ACCESS read-only
    STATUS     current
    DESCRIPTION
            "-- empty --"
    ::= { lcsStatusWlanEncryptionEntry 26 }

-- {COLUMN} 1.3.6.1.4.1.2356.11.1.3.64.1.27
lcsStatusWlanEncryptionEntryWpa23SessionKeytypes OBJECT-TYPE
    SYNTAX     BITS {
                  eAesGcmp256 (3),
                  eAesGcmp128 (4),
                  eAesCcmp256 (5),
                  eAesCcm (6),
                  eTkip (7)
            }
    MAX-ACCESS read-only
    STATUS     current
    DESCRIPTION
            "-- empty --"
    ::= { lcsStatusWlanEncryptionEntry 27 }

-- {COLUMN} 1.3.6.1.4.1.2356.11.1.3.64.1.28
lcsStatusWlanEncryptionEntryWpa8021xSecurityLevel OBJECT-TYPE
    SYNTAX     INTEGER {
                  eStandard (0),
                  eSuiteB128Bits (1),
                  eSuiteB192Bits (2)
            }
    MAX-ACCESS read-only
    STATUS     current
    DESCRIPTION
            "-- empty --"
    ::= { lcsStatusWlanEncryptionEntry 28 }

-- {TABLE} 1.3.6.1.4.1.2356.11.1.3.65
lcsStatusWlanCoexistenceTable OBJECT-TYPE
    SYNTAX     SEQUENCE OF LcsStatusWlanCoexistenceEntry
    MAX-ACCESS not-accessible
    STATUS     current
    DESCRIPTION
            "-- empty --"
    ::= { lcsStatusWlan 65 }

-- {ROW} 1.3.6.1.4.1.2356.11.1.3.65.1
lcsStatusWlanCoexistenceEntry OBJECT-TYPE
    SYNTAX     LcsStatusWlanCoexistenceEntry
    MAX-ACCESS not-accessible
    STATUS     current
    DESCRIPTION
            ""
    INDEX {
            lcsStatusWlanCoexistenceEntryIfc
          }
    ::= { lcsStatusWlanCoexistenceTable 1 }

LcsStatusWlanCoexistenceEntry ::= SEQUENCE {
            lcsStatusWlanCoexistenceEntryIfc DisplayString,
            lcsStatusWlanCoexistenceEntryActiveTimePortion Integer32,
            lcsStatusWlanCoexistenceEntryTotalRequests Integer32,
            lcsStatusWlanCoexistenceEntryRequestRate Integer32,
            lcsStatusWlanCoexistenceEntryCoexCollisions Integer32
    }

-- {COLUMN} 1.3.6.1.4.1.2356.11.1.3.65.1.1
lcsStatusWlanCoexistenceEntryIfc OBJECT-TYPE
    SYNTAX     DisplayString (SIZE(0..255))
    MAX-ACCESS read-only
    STATUS     current
    DESCRIPTION
            "-- empty --"
    ::= { lcsStatusWlanCoexistenceEntry 1 }

-- {COLUMN} 1.3.6.1.4.1.2356.11.1.3.65.1.2
lcsStatusWlanCoexistenceEntryActiveTimePortion OBJECT-TYPE
    SYNTAX     Integer32 (0..255)
    MAX-ACCESS read-only
    STATUS     current
    DESCRIPTION
            "-- empty --"
    ::= { lcsStatusWlanCoexistenceEntry 2 }

-- {COLUMN} 1.3.6.1.4.1.2356.11.1.3.65.1.3
lcsStatusWlanCoexistenceEntryTotalRequests OBJECT-TYPE
    SYNTAX     Integer32 (0..2147483647)
    MAX-ACCESS read-only
    STATUS     current
    DESCRIPTION
            "-- empty --"
    ::= { lcsStatusWlanCoexistenceEntry 3 }

-- {COLUMN} 1.3.6.1.4.1.2356.11.1.3.65.1.4
lcsStatusWlanCoexistenceEntryRequestRate OBJECT-TYPE
    SYNTAX     Integer32 (0..2147483647)
    MAX-ACCESS read-only
    STATUS     current
    DESCRIPTION
            "-- empty --"
    ::= { lcsStatusWlanCoexistenceEntry 4 }

-- {COLUMN} 1.3.6.1.4.1.2356.11.1.3.65.1.5
lcsStatusWlanCoexistenceEntryCoexCollisions OBJECT-TYPE
    SYNTAX     Integer32 (0..2147483647)
    MAX-ACCESS read-only
    STATUS     current
    DESCRIPTION
            "-- empty --"
    ::= { lcsStatusWlanCoexistenceEntry 5 }

-- {TABLE} 1.3.6.1.4.1.2356.11.1.3.66
lcsStatusWlanTransmissionTable OBJECT-TYPE
    SYNTAX     SEQUENCE OF LcsStatusWlanTransmissionEntry
    MAX-ACCESS not-accessible
    STATUS     current
    DESCRIPTION
            "-- empty --"
    ::= { lcsStatusWlan 66 }

-- {ROW} 1.3.6.1.4.1.2356.11.1.3.66.1
lcsStatusWlanTransmissionEntry OBJECT-TYPE
    SYNTAX     LcsStatusWlanTransmissionEntry
    MAX-ACCESS not-accessible
    STATUS     current
    DESCRIPTION
            ""
    INDEX {
            lcsStatusWlanTransmissionEntryInterface
          }
    ::= { lcsStatusWlanTransmissionTable 1 }

LcsStatusWlanTransmissionEntry ::= SEQUENCE {
            lcsStatusWlanTransmissionEntryInterface INTEGER,
            lcsStatusWlanTransmissionEntryPacketSize Integer32,
            lcsStatusWlanTransmissionEntryMinTxRate INTEGER,
            lcsStatusWlanTransmissionEntryBasicRate INTEGER,
            lcsStatusWlanTransmissionEntryRtsThreshold Integer32,
            lcsStatusWlanTransmissionEntry11bPreamble INTEGER,
            lcsStatusWlanTransmissionEntryMaxTxRate INTEGER,
            lcsStatusWlanTransmissionEntryMinFragLen Integer32,
            lcsStatusWlanTransmissionEntrySoftRetries Integer32,
            lcsStatusWlanTransmissionEntryHardRetries Integer32,
            lcsStatusWlanTransmissionEntryShortGuardInterval INTEGER,
            lcsStatusWlanTransmissionEntryMaxSpatialStreams INTEGER,
            lcsStatusWlanTransmissionEntrySendAggregates INTEGER,
            lcsStatusWlanTransmissionEntryMinHtMcs INTEGER,
            lcsStatusWlanTransmissionEntryMaxHtMcs INTEGER,
            lcsStatusWlanTransmissionEntryMinSpatialStreams INTEGER,
            lcsStatusWlanTransmissionEntryEapolRate INTEGER,
            lcsStatusWlanTransmissionEntryMaxAggrPacketCount Integer32,
            lcsStatusWlanTransmissionEntryProberspRetries Integer32,
            lcsStatusWlanTransmissionEntryReceiveAggregates INTEGER,
            lcsStatusWlanTransmissionEntryUseStbc INTEGER,
            lcsStatusWlanTransmissionEntryUseLdpc INTEGER,
            lcsStatusWlanTransmissionEntryConvertToUnicast BITS,
            lcsStatusWlanTransmissionEntry11acBeamforming INTEGER,
            lcsStatusWlanTransmissionEntryQosMapping INTEGER
    }

-- {COLUMN} 1.3.6.1.4.1.2356.11.1.3.66.1.1
lcsStatusWlanTransmissionEntryInterface OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-only
    STATUS     current
    DESCRIPTION
            "-- empty --"
    ::= { lcsStatusWlanTransmissionEntry 1 }

-- {COLUMN} 1.3.6.1.4.1.2356.11.1.3.66.1.2
lcsStatusWlanTransmissionEntryPacketSize OBJECT-TYPE
    SYNTAX     Integer32 (0..65535)
    MAX-ACCESS read-only
    STATUS     current
    DESCRIPTION
            "-- empty --"
    ::= { lcsStatusWlanTransmissionEntry 2 }

-- {COLUMN} 1.3.6.1.4.1.2356.11.1.3.66.1.3
lcsStatusWlanTransmissionEntryMinTxRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-only
    STATUS     current
    DESCRIPTION
            "-- empty --"
    ::= { lcsStatusWlanTransmissionEntry 3 }

-- {COLUMN} 1.3.6.1.4.1.2356.11.1.3.66.1.4
lcsStatusWlanTransmissionEntryBasicRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-only
    STATUS     current
    DESCRIPTION
            "-- empty --"
    ::= { lcsStatusWlanTransmissionEntry 4 }

-- {COLUMN} 1.3.6.1.4.1.2356.11.1.3.66.1.6
lcsStatusWlanTransmissionEntryRtsThreshold OBJECT-TYPE
    SYNTAX     Integer32 (0..65535)
    MAX-ACCESS read-only
    STATUS     current
    DESCRIPTION
            "-- empty --"
    ::= { lcsStatusWlanTransmissionEntry 6 }

-- {COLUMN} 1.3.6.1.4.1.2356.11.1.3.66.1.7
lcsStatusWlanTransmissionEntry11bPreamble OBJECT-TYPE
    SYNTAX     INTEGER {
                  eAuto (0),
                  eLong (1)
            }
    MAX-ACCESS read-only
    STATUS     current
    DESCRIPTION
            "-- empty --"
    ::= { lcsStatusWlanTransmissionEntry 7 }

-- {COLUMN} 1.3.6.1.4.1.2356.11.1.3.66.1.9
lcsStatusWlanTransmissionEntryMaxTxRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-only
    STATUS     current
    DESCRIPTION
            "-- empty --"
    ::= { lcsStatusWlanTransmissionEntry 9 }

-- {COLUMN} 1.3.6.1.4.1.2356.11.1.3.66.1.10
lcsStatusWlanTransmissionEntryMinFragLen OBJECT-TYPE
    SYNTAX     Integer32 (0..65535)
    MAX-ACCESS read-only
    STATUS     current
    DESCRIPTION
            "-- empty --"
    ::= { lcsStatusWlanTransmissionEntry 10 }

-- {COLUMN} 1.3.6.1.4.1.2356.11.1.3.66.1.11
lcsStatusWlanTransmissionEntrySoftRetries OBJECT-TYPE
    SYNTAX     Integer32 (0..255)
    MAX-ACCESS read-only
    STATUS     current
    DESCRIPTION
            "-- empty --"
    ::= { lcsStatusWlanTransmissionEntry 11 }

-- {COLUMN} 1.3.6.1.4.1.2356.11.1.3.66.1.12
lcsStatusWlanTransmissionEntryHardRetries OBJECT-TYPE
    SYNTAX     Integer32 (0..255)
    MAX-ACCESS read-only
    STATUS     current
    DESCRIPTION
            "-- empty --"
    ::= { lcsStatusWlanTransmissionEntry 12 }

-- {COLUMN} 1.3.6.1.4.1.2356.11.1.3.66.1.13
lcsStatusWlanTransmissionEntryShortGuardInterval OBJECT-TYPE
    SYNTAX     INTEGER {
                  eAuto (0),
                  eNo (1)
            }
    MAX-ACCESS read-only
    STATUS     current
    DESCRIPTION
            "-- empty --"
    ::= { lcsStatusWlanTransmissionEntry 13 }

-- {COLUMN} 1.3.6.1.4.1.2356.11.1.3.66.1.14
lcsStatusWlanTransmissionEntryMaxSpatialStreams OBJECT-TYPE
    SYNTAX     INTEGER {
                  eAuto (0),
                  eOne (1),
                  eTwo (2),
                  eThree (3),
                  eFour (4)
            }
    MAX-ACCESS read-only
    STATUS     current
    DESCRIPTION
            "-- empty --"
    ::= { lcsStatusWlanTransmissionEntry 14 }

-- {COLUMN} 1.3.6.1.4.1.2356.11.1.3.66.1.15
lcsStatusWlanTransmissionEntrySendAggregates OBJECT-TYPE
    SYNTAX     INTEGER {
                  eNo (0),
                  eYes (1)
            }
    MAX-ACCESS read-only
    STATUS     current
    DESCRIPTION
            "-- empty --"
    ::= { lcsStatusWlanTransmissionEntry 15 }

-- {COLUMN} 1.3.6.1.4.1.2356.11.1.3.66.1.16
lcsStatusWlanTransmissionEntryMinHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-only
    STATUS     current
    DESCRIPTION
            "-- empty --"
    ::= { lcsStatusWlanTransmissionEntry 16 }

-- {COLUMN} 1.3.6.1.4.1.2356.11.1.3.66.1.17
lcsStatusWlanTransmissionEntryMaxHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-only
    STATUS     current
    DESCRIPTION
            "-- empty --"
    ::= { lcsStatusWlanTransmissionEntry 17 }

-- {COLUMN} 1.3.6.1.4.1.2356.11.1.3.66.1.18
lcsStatusWlanTransmissionEntryMinSpatialStreams OBJECT-TYPE
    SYNTAX     INTEGER {
                  eAuto (0),
                  eOne (1),
                  eTwo (2),
                  eThree (3),
                  eFour (4)
            }
    MAX-ACCESS read-only
    STATUS     current
    DESCRIPTION
            "-- empty --"
    ::= { lcsStatusWlanTransmissionEntry 18 }

-- {COLUMN} 1.3.6.1.4.1.2356.11.1.3.66.1.19
lcsStatusWlanTransmissionEntryEapolRate OBJECT-TYPE
    SYNTAX     INTEGER {
                  eLikeData (0),
                  e1M (1),
                  e2M (2),
                  e5M5 (4),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-only
    STATUS     current
    DESCRIPTION
            "-- empty --"
    ::= { lcsStatusWlanTransmissionEntry 19 }

-- {COLUMN} 1.3.6.1.4.1.2356.11.1.3.66.1.20
lcsStatusWlanTransmissionEntryMaxAggrPacketCount OBJECT-TYPE
    SYNTAX     Integer32 (0..255)
    MAX-ACCESS read-only
    STATUS     current
    DESCRIPTION
            "-- empty --"
    ::= { lcsStatusWlanTransmissionEntry 20 }

-- {COLUMN} 1.3.6.1.4.1.2356.11.1.3.66.1.21
lcsStatusWlanTransmissionEntryProberspRetries OBJECT-TYPE
    SYNTAX     Integer32 (0..255)
    MAX-ACCESS read-only
    STATUS     current
    DESCRIPTION
            "-- empty --"
    ::= { lcsStatusWlanTransmissionEntry 21 }

-- {COLUMN} 1.3.6.1.4.1.2356.11.1.3.66.1.22
lcsStatusWlanTransmissionEntryReceiveAggregates OBJECT-TYPE
    SYNTAX     INTEGER {
                  eNo (0),
                  eYes (1)
            }
    MAX-ACCESS read-only
    STATUS     current
    DESCRIPTION
            "-- empty --"
    ::= { lcsStatusWlanTransmissionEntry 22 }

-- {COLUMN} 1.3.6.1.4.1.2356.11.1.3.66.1.23
lcsStatusWlanTransmissionEntryUseStbc OBJECT-TYPE
    SYNTAX     INTEGER {
                  eNo (0),
                  eYes (1)
            }
    MAX-ACCESS read-only
    STATUS     current
    DESCRIPTION
            "-- empty --"
    ::= { lcsStatusWlanTransmissionEntry 23 }

-- {COLUMN} 1.3.6.1.4.1.2356.11.1.3.66.1.24
lcsStatusWlanTransmissionEntryUseLdpc OBJECT-TYPE
    SYNTAX     INTEGER {
                  eNo (0),
                  eYes (1)
            }
    MAX-ACCESS read-only
    STATUS     current
    DESCRIPTION
            "-- empty --"
    ::= { lcsStatusWlanTransmissionEntry 24 }

-- {COLUMN} 1.3.6.1.4.1.2356.11.1.3.66.1.25
lcsStatusWlanTransmissionEntryConvertToUnicast OBJECT-TYPE
    SYNTAX     BITS {
                  eMulticast (30),
                  eDhcp (31)
            }
    MAX-ACCESS read-only
    STATUS     current
    DESCRIPTION
            "-- empty --"
    ::= { lcsStatusWlanTransmissionEntry 25 }

-- {COLUMN} 1.3.6.1.4.1.2356.11.1.3.66.1.26
lcsStatusWlanTransmissionEntry11acBeamforming OBJECT-TYPE
    SYNTAX     INTEGER {
                  eAuto (0),
                  eNo (1),
                  eSuMimo (2),
                  eMuMimo (3)
            }
    MAX-ACCESS read-only
    STATUS     current
    DESCRIPTION
            "-- empty --"
    ::= { lcsStatusWlanTransmissionEntry 26 }

-- {COLUMN} 1.3.6.1.4.1.2356.11.1.3.66.1.27
lcsStatusWlanTransmissionEntryQosMapping OBJECT-TYPE
    SYNTAX     INTEGER {
                  eNo (0),
                  eYes (1)
            }
    MAX-ACCESS read-only
    STATUS     current
    DESCRIPTION
            "-- empty --"
    ::= { lcsStatusWlanTransmissionEntry 27 }

-- {SCALAR} 1.3.6.1.4.1.2356.11.1.3.67
lcsStatusWlanAutoChannelSelection OBJECT-TYPE
    SYNTAX     DisplayString
    MAX-ACCESS read-write
    STATUS     current
    DESCRIPTION
            "-- empty --"
    ::= { lcsStatusWlan 67 }

-- {TABLE} 1.3.6.1.4.1.2356.11.1.3.68
lcsStatusWlanNetworkByteTransportTable OBJECT-TYPE
    SYNTAX     SEQUENCE OF LcsStatusWlanNetworkByteTransportEntry
    MAX-ACCESS not-accessible
    STATUS     current
    DESCRIPTION
            "-- empty --"
    ::= { lcsStatusWlan 68 }

-- {ROW} 1.3.6.1.4.1.2356.11.1.3.68.1
lcsStatusWlanNetworkByteTransportEntry OBJECT-TYPE
    SYNTAX     LcsStatusWlanNetworkByteTransportEntry
    MAX-ACCESS not-accessible
    STATUS     current
    DESCRIPTION
            ""
    INDEX {
            lcsStatusWlanNetworkByteTransportEntryIfc
          }
    ::= { lcsStatusWlanNetworkByteTransportTable 1 }

LcsStatusWlanNetworkByteTransportEntry ::= SEQUENCE {
            lcsStatusWlanNetworkByteTransportEntryIfc DisplayString,
            lcsStatusWlanNetworkByteTransportEntryTxBytes Counter64,
            lcsStatusWlanNetworkByteTransportEntryRxBytes Counter64,
            lcsStatusWlanNetworkByteTransportEntryThroughput DisplayString,
            lcsStatusWlanNetworkByteTransportEntryMaxThroughput DisplayString,
            lcsStatusWlanNetworkByteTransportEntryBytesThroughput Integer32,
            lcsStatusWlanNetworkByteTransportEntryBytesMaxThroughput Integer32
    }

-- {COLUMN} 1.3.6.1.4.1.2356.11.1.3.68.1.1
lcsStatusWlanNetworkByteTransportEntryIfc OBJECT-TYPE
    SYNTAX     DisplayString (SIZE(0..255))
    MAX-ACCESS read-only
    STATUS     current
    DESCRIPTION
            "-- empty --"
    ::= { lcsStatusWlanNetworkByteTransportEntry 1 }

-- {COLUMN} 1.3.6.1.4.1.2356.11.1.3.68.1.2
lcsStatusWlanNetworkByteTransportEntryTxBytes OBJECT-TYPE
    SYNTAX     Counter64
    MAX-ACCESS read-only
    STATUS     current
    DESCRIPTION
            "-- empty --"
    ::= { lcsStatusWlanNetworkByteTransportEntry 2 }

-- {COLUMN} 1.3.6.1.4.1.2356.11.1.3.68.1.3
lcsStatusWlanNetworkByteTransportEntryRxBytes OBJECT-TYPE
    SYNTAX     Counter64
    MAX-ACCESS read-only
    STATUS     current
    DESCRIPTION
            "-- empty --"
    ::= { lcsStatusWlanNetworkByteTransportEntry 3 }

-- {COLUMN} 1.3.6.1.4.1.2356.11.1.3.68.1.4
lcsStatusWlanNetworkByteTransportEntryThroughput OBJECT-TYPE
    SYNTAX     DisplayString (SIZE(0..255))
    MAX-ACCESS read-only
    STATUS     current
    DESCRIPTION
            "-- empty --"
    ::= { lcsStatusWlanNetworkByteTransportEntry 4 }

-- {COLUMN} 1.3.6.1.4.1.2356.11.1.3.68.1.5
lcsStatusWlanNetworkByteTransportEntryMaxThroughput OBJECT-TYPE
    SYNTAX     DisplayString (SIZE(0..255))
    MAX-ACCESS read-only
    STATUS     current
    DESCRIPTION
            "-- empty --"
    ::= { lcsStatusWlanNetworkByteTransportEntry 5 }

-- {COLUMN} 1.3.6.1.4.1.2356.11.1.3.68.1.6
lcsStatusWlanNetworkByteTransportEntryBytesThroughput OBJECT-TYPE
    SYNTAX     Integer32 (0..2147483647)
    MAX-ACCESS read-only
    STATUS     current
    DESCRIPTION
            "-- empty --"
    ::= { lcsStatusWlanNetworkByteTransportEntry 6 }

-- {COLUMN} 1.3.6.1.4.1.2356.11.1.3.68.1.7
lcsStatusWlanNetworkByteTransportEntryBytesMaxThroughput OBJECT-TYPE
    SYNTAX     Integer32 (0..2147483647)
    MAX-ACCESS read-only
    STATUS     current
    DESCRIPTION
            "-- empty --"
    ::= { lcsStatusWlanNetworkByteTransportEntry 7 }

-- {TABLE} 1.3.6.1.4.1.2356.11.1.3.69
lcsStatusWlanEnvironmentScanResultsTable OBJECT-TYPE
    SYNTAX     SEQUENCE OF LcsStatusWlanEnvironmentScanResultsEntry
    MAX-ACCESS not-accessible
    STATUS     current
    DESCRIPTION
            "-- empty --"
    ::= { lcsStatusWlan 69 }

-- {ROW} 1.3.6.1.4.1.2356.11.1.3.69.1
lcsStatusWlanEnvironmentScanResultsEntry OBJECT-TYPE
    SYNTAX     LcsStatusWlanEnvironmentScanResultsEntry
    MAX-ACCESS not-accessible
    STATUS     current
    DESCRIPTION
            ""
    INDEX {
            lcsStatusWlanEnvironmentScanResultsEntryBssid,
            lcsStatusWlanEnvironmentScanResultsEntryInterface
          }
    ::= { lcsStatusWlanEnvironmentScanResultsTable 1 }

LcsStatusWlanEnvironmentScanResultsEntry ::= SEQUENCE {
            lcsStatusWlanEnvironmentScanResultsEntryBssid MacAddress,
            lcsStatusWlanEnvironmentScanResultsEntryNetworkName DisplayString,
            lcsStatusWlanEnvironmentScanResultsEntryOperationMode INTEGER,
            lcsStatusWlanEnvironmentScanResultsEntryBeaconPeriod Integer32,
            lcsStatusWlanEnvironmentScanResultsEntryDtimPeriod Integer32,
            lcsStatusWlanEnvironmentScanResultsEntryRadioChannel Integer32,
            lcsStatusWlanEnvironmentScanResultsEntryPhySignal Integer32,
            lcsStatusWlanEnvironmentScanResultsEntryNoiseLevel Integer32,
            lcsStatusWlanEnvironmentScanResultsEntryLoad DisplayString,
            lcsStatusWlanEnvironmentScanResultsEntryEncryption INTEGER,
            lcsStatusWlanEnvironmentScanResultsEntryShortPreamble INTEGER,
            lcsStatusWlanEnvironmentScanResultsEntryInterface INTEGER,
            lcsStatusWlanEnvironmentScanResultsEntryRadioBand INTEGER,
            lcsStatusWlanEnvironmentScanResultsEntryShortSlotTime INTEGER,
            lcsStatusWlanEnvironmentScanResultsEntryRate INTEGER,
            lcsStatusWlanEnvironmentScanResultsEntryNonerpPresent INTEGER,
            lcsStatusWlanEnvironmentScanResultsEntryCompression INTEGER,
            lcsStatusWlanEnvironmentScanResultsEntryPcfFunctionality INTEGER,
            lcsStatusWlanEnvironmentScanResultsEntryIdentification DisplayString,
            lcsStatusWlanEnvironmentScanResultsEntryQos INTEGER,
            lcsStatusWlanEnvironmentScanResultsEntryAge Integer32,
            lcsStatusWlanEnvironmentScanResultsEntrySignalLevel Integer32,
            lcsStatusWlanEnvironmentScanResultsEntryExtChannel INTEGER,
            lcsStatusWlanEnvironmentScanResultsEntry40mhzIntolerant INTEGER,
            lcsStatusWlanEnvironmentScanResultsEntryInterpointPeerName DisplayString,
            lcsStatusWlanEnvironmentScanResultsEntryMaxAMpduLen Integer32,
            lcsStatusWlanEnvironmentScanResultsEntryMaxAMsduLen Integer32,
            lcsStatusWlanEnvironmentScanResultsEntryVendor DisplayString,
            lcsStatusWlanEnvironmentScanResultsEntryEffRate Integer32,
            lcsStatusWlanEnvironmentScanResultsEntry40mhzCoexistence INTEGER,
            lcsStatusWlanEnvironmentScanResultsEntryPreAuthentication INTEGER,
            lcsStatusWlanEnvironmentScanResultsEntryEapolPreauthFailed INTEGER,
            lcsStatusWlanEnvironmentScanResultsEntryAutowds INTEGER,
            lcsStatusWlanEnvironmentScanResultsEntrySGIMask BITS,
            lcsStatusWlanEnvironmentScanResultsEntryChannelBandwidths BITS,
            lcsStatusWlanEnvironmentScanResultsEntryChannelBandwidth INTEGER,
            lcsStatusWlanEnvironmentScanResultsEntryClBrgSupport INTEGER,
            lcsStatusWlanEnvironmentScanResultsEntryProtMgmtFrames INTEGER,
            lcsStatusWlanEnvironmentScanResultsEntryTxPowerLimit DisplayString,
            lcsStatusWlanEnvironmentScanResultsEntryTxSTBCMask BITS,
            lcsStatusWlanEnvironmentScanResultsEntryRxStbcHt INTEGER,
            lcsStatusWlanEnvironmentScanResultsEntryRxStbcVht INTEGER,
            lcsStatusWlanEnvironmentScanResultsEntryLDPCMask BITS,
            lcsStatusWlanEnvironmentScanResultsEntryUuid DisplayString,
            lcsStatusWlanEnvironmentScanResultsEntry11acBeamforming BITS,
            lcsStatusWlanEnvironmentScanResultsEntrySecondaryChannel Integer32,
            lcsStatusWlanEnvironmentScanResultsEntryTransitionalMode INTEGER,
            lcsStatusWlanEnvironmentScanResultsEntryTransitionalSsid DisplayString,
            lcsStatusWlanEnvironmentScanResultsEntryTransitionalBssid MacAddress,
            lcsStatusWlanEnvironmentScanResultsEntryQosMapping INTEGER
    }

-- {COLUMN} 1.3.6.1.4.1.2356.11.1.3.69.1.1
lcsStatusWlanEnvironmentScanResultsEntryBssid OBJECT-TYPE
    SYNTAX     MacAddress
    MAX-ACCESS read-only
    STATUS     current
    DESCRIPTION
            "-- empty --"
    ::= { lcsStatusWlanEnvironmentScanResultsEntry 1 }

-- {COLUMN} 1.3.6.1.4.1.2356.11.1.3.69.1.2
lcsStatusWlanEnvironmentScanResultsEntryNetworkName OBJECT-TYPE
    SYNTAX     DisplayString (SIZE(0..255))
    MAX-ACCESS read-only
    STATUS     current
    DESCRIPTION
            "-- empty --"
    ::= { lcsStatusWlanEnvironmentScanResultsEntry 2 }

-- {COLUMN} 1.3.6.1.4.1.2356.11.1.3.69.1.3
lcsStatusWlanEnvironmentScanResultsEntryOperationMode OBJECT-TYPE
    SYNTAX     INTEGER {
                  eNone (0),
                  eAdhoc (1),
                  eInfrastructure (2)
            }
    MAX-ACCESS read-only
    STATUS     current
    DESCRIPTION
            "lancom's description of operation mode"
    ::= { lcsStatusWlanEnvironmentScanResultsEntry 3 }

-- {COLUMN} 1.3.6.1.4.1.2356.11.1.3.69.1.6
lcsStatusWlanEnvironmentScanResultsEntryBeaconPeriod OBJECT-TYPE
    SYNTAX     Integer32 (0..65535)
    MAX-ACCESS read-only
    STATUS     current
    DESCRIPTION
            "-- empty --"
    ::= { lcsStatusWlanEnvironmentScanResultsEntry 6 }

-- {COLUMN} 1.3.6.1.4.1.2356.11.1.3.69.1.7
lcsStatusWlanEnvironmentScanResultsEntryDtimPeriod OBJECT-TYPE
    SYNTAX     Integer32 (0..65535)
    MAX-ACCESS read-only
    STATUS     current
    DESCRIPTION
            "-- empty --"
    ::= { lcsStatusWlanEnvironmentScanResultsEntry 7 }

-- {COLUMN} 1.3.6.1.4.1.2356.11.1.3.69.1.8
lcsStatusWlanEnvironmentScanResultsEntryRadioChannel OBJECT-TYPE
    SYNTAX     Integer32 (0..255)
    MAX-ACCESS read-only
    STATUS     current
    DESCRIPTION
            "-- empty --"
    ::= { lcsStatusWlanEnvironmentScanResultsEntry 8 }

-- {COLUMN} 1.3.6.1.4.1.2356.11.1.3.69.1.10
lcsStatusWlanEnvironmentScanResultsEntryPhySignal OBJECT-TYPE
    SYNTAX     Integer32 (0..65535)
    MAX-ACCESS read-only
    STATUS     current
    DESCRIPTION
            "-- empty --"
    ::= { lcsStatusWlanEnvironmentScanResultsEntry 10 }

-- {COLUMN} 1.3.6.1.4.1.2356.11.1.3.69.1.11
lcsStatusWlanEnvironmentScanResultsEntryNoiseLevel OBJECT-TYPE
    SYNTAX     Integer32 (-128..127)
    MAX-ACCESS read-only
    STATUS     current
    DESCRIPTION
            "-- empty --"
    ::= { lcsStatusWlanEnvironmentScanResultsEntry 11 }

-- {COLUMN} 1.3.6.1.4.1.2356.11.1.3.69.1.12
lcsStatusWlanEnvironmentScanResultsEntryLoad OBJECT-TYPE
    SYNTAX     DisplayString (SIZE(0..255))
    MAX-ACCESS read-only
    STATUS     current
    DESCRIPTION
            "-- empty --"
    ::= { lcsStatusWlanEnvironmentScanResultsEntry 12 }

-- {COLUMN} 1.3.6.1.4.1.2356.11.1.3.69.1.13
lcsStatusWlanEnvironmentScanResultsEntryEncryption OBJECT-TYPE
    SYNTAX     INTEGER {
                  eNone (0),
                  eWep (1),
                  eTkip (2),
                  eAes (3),
                  eAesPlusTkip (4)
            }
    MAX-ACCESS read-only
    STATUS     current
    DESCRIPTION
            "-- empty --"
    ::= { lcsStatusWlanEnvironmentScanResultsEntry 13 }

-- {COLUMN} 1.3.6.1.4.1.2356.11.1.3.69.1.14
lcsStatusWlanEnvironmentScanResultsEntryShortPreamble OBJECT-TYPE
    SYNTAX     INTEGER {
                  eNo (0),
                  eYes (1)
            }
    MAX-ACCESS read-only
    STATUS     current
    DESCRIPTION
            "-- empty --"
    ::= { lcsStatusWlanEnvironmentScanResultsEntry 14 }

-- {COLUMN} 1.3.6.1.4.1.2356.11.1.3.69.1.15
lcsStatusWlanEnvironmentScanResultsEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { lcsStatusWlanEnvironmentScanResultsEntry 15 }

-- {COLUMN} 1.3.6.1.4.1.2356.11.1.3.69.1.16
lcsStatusWlanEnvironmentScanResultsEntryRadioBand OBJECT-TYPE
    SYNTAX     INTEGER {
                  eUnknown (0),
                  e24ghz (1),
                  e5ghz (2)
            }
    MAX-ACCESS read-only
    STATUS     current
    DESCRIPTION
            "-- empty --"
    ::= { lcsStatusWlanEnvironmentScanResultsEntry 16 }

-- {COLUMN} 1.3.6.1.4.1.2356.11.1.3.69.1.18
lcsStatusWlanEnvironmentScanResultsEntryShortSlotTime OBJECT-TYPE
    SYNTAX     INTEGER {
                  eNo (0),
                  eYes (1)
            }
    MAX-ACCESS read-only
    STATUS     current
    DESCRIPTION
            "-- empty --"
    ::= { lcsStatusWlanEnvironmentScanResultsEntry 18 }

-- {COLUMN} 1.3.6.1.4.1.2356.11.1.3.69.1.19
lcsStatusWlanEnvironmentScanResultsEntryRate OBJECT-TYPE
    SYNTAX     INTEGER {
                  eUnknown (0),
                  e1M (1),
                  e2M (2),
                  e5M (3),
                  e5M5 (4),
                  e8M (5),
                  e11M (6),
                  e6M (12),
                  e9M (13),
                  e12M (14),
                  e18M (15),
                  e24M (16),
                  e36M (17),
                  e48M (18),
                  e54M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eHT4S26M (52),
                  eHT4S52M (53),
                  eHT4S78M (54),
                  eHT4S104M (55),
                  eHT4S156M (56),
                  eHT4S208M (57),
                  eHT4S234M (58),
                  eHT4S260M (59),
                  eHTDUP6M (60),
                  eHtMcs33 (61),
                  eHtMcs34 (62),
                  eHtMcs35 (63),
                  eHtMcs36 (64),
                  eHtMcs37 (65),
                  eHtMcs38 (66),
                  eHtMcs39 (67),
                  eHtMcs40 (68),
                  eHtMcs41 (69),
                  eHtMcs42 (70),
                  eHtMcs43 (71),
                  eHtMcs44 (72),
                  eHtMcs45 (73),
                  eHtMcs46 (74),
                  eHtMcs47 (75),
                  eHtMcs48 (76),
                  eHtMcs49 (77),
                  eHtMcs50 (78),
                  eHtMcs51 (79),
                  eHtMcs52 (80),
                  eHtMcs53 (81),
                  eHtMcs54 (82),
                  eHtMcs55 (83),
                  eHtMcs56 (84),
                  eHtMcs57 (85),
                  eHtMcs58 (86),
                  eHtMcs59 (87),
                  eHtMcs60 (88),
                  eHtMcs61 (89),
                  eHtMcs62 (90),
                  eHtMcs63 (91),
                  eHtMcs64 (92),
                  eHtMcs65 (93),
                  eHtMcs66 (94),
                  eHtMcs67 (95),
                  eHtMcs68 (96),
                  eHtMcs69 (97),
                  eHtMcs70 (98),
                  eHtMcs71 (99),
                  eHtMcs72 (100),
                  eHtMcs73 (101),
                  eHtMcs74 (102),
                  eHtMcs75 (103),
                  eHtMcs76 (104),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            "-- empty --"
    ::= { lcsStatusWlanEnvironmentScanResultsEntry 19 }

-- {COLUMN} 1.3.6.1.4.1.2356.11.1.3.69.1.20
lcsStatusWlanEnvironmentScanResultsEntryNonerpPresent OBJECT-TYPE
    SYNTAX     INTEGER {
                  eNo (0),
                  eYes (1)
            }
    MAX-ACCESS read-only
    STATUS     current
    DESCRIPTION
            "-- empty --"
    ::= { lcsStatusWlanEnvironmentScanResultsEntry 20 }

-- {COLUMN} 1.3.6.1.4.1.2356.11.1.3.69.1.21
lcsStatusWlanEnvironmentScanResultsEntryCompression OBJECT-TYPE
    SYNTAX     INTEGER {
                  eNo (0),
                  eYes (1)
            }
    MAX-ACCESS read-only
    STATUS     current
    DESCRIPTION
            "-- empty --"
    ::= { lcsStatusWlanEnvironmentScanResultsEntry 21 }

-- {COLUMN} 1.3.6.1.4.1.2356.11.1.3.69.1.22
lcsStatusWlanEnvironmentScanResultsEntryPcfFunctionality OBJECT-TYPE
    SYNTAX     INTEGER {
                  eNone (0),
                  eDelivery (1),
                  eDeliveryPlusPolling (2)
            }
    MAX-ACCESS read-only
    STATUS     current
    DESCRIPTION
            "-- empty --"
    ::= { lcsStatusWlanEnvironmentScanResultsEntry 22 }

-- {COLUMN} 1.3.6.1.4.1.2356.11.1.3.69.1.23
lcsStatusWlanEnvironmentScanResultsEntryIdentification OBJECT-TYPE
    SYNTAX     DisplayString (SIZE(0..16))
    MAX-ACCESS read-only
    STATUS     current
    DESCRIPTION
            "-- empty --"
    ::= { lcsStatusWlanEnvironmentScanResultsEntry 23 }

-- {COLUMN} 1.3.6.1.4.1.2356.11.1.3.69.1.24
lcsStatusWlanEnvironmentScanResultsEntryQos OBJECT-TYPE
    SYNTAX     INTEGER {
                  eNo (0),
                  eYes (1)
            }
    MAX-ACCESS read-only
    STATUS     current
    DESCRIPTION
            "-- empty --"
    ::= { lcsStatusWlanEnvironmentScanResultsEntry 24 }

-- {COLUMN} 1.3.6.1.4.1.2356.11.1.3.69.1.25
lcsStatusWlanEnvironmentScanResultsEntryAge OBJECT-TYPE
    SYNTAX     Integer32 (0..2147483647)
    MAX-ACCESS read-only
    STATUS     current
    DESCRIPTION
            "-- empty --"
    ::= { lcsStatusWlanEnvironmentScanResultsEntry 25 }

-- {COLUMN} 1.3.6.1.4.1.2356.11.1.3.69.1.26
lcsStatusWlanEnvironmentScanResultsEntrySignalLevel OBJECT-TYPE
    SYNTAX     Integer32 (-32768..32767)
    MAX-ACCESS read-only
    STATUS     current
    DESCRIPTION
            "-- empty --"
    ::= { lcsStatusWlanEnvironmentScanResultsEntry 26 }

-- {COLUMN} 1.3.6.1.4.1.2356.11.1.3.69.1.28
lcsStatusWlanEnvironmentScanResultsEntryExtChannel OBJECT-TYPE
    SYNTAX     INTEGER {
                  eNone (0),
                  eAbove (1),
                  eBelow (3)
            }
    MAX-ACCESS read-only
    STATUS     current
    DESCRIPTION
            "-- empty --"
    ::= { lcsStatusWlanEnvironmentScanResultsEntry 28 }

-- {COLUMN} 1.3.6.1.4.1.2356.11.1.3.69.1.30
lcsStatusWlanEnvironmentScanResultsEntry40mhzIntolerant OBJECT-TYPE
    SYNTAX     INTEGER {
                  eNo (0),
                  eYes (1)
            }
    MAX-ACCESS read-only
    STATUS     current
    DESCRIPTION
            "-- empty --"
    ::= { lcsStatusWlanEnvironmentScanResultsEntry 30 }

-- {COLUMN} 1.3.6.1.4.1.2356.11.1.3.69.1.31
lcsStatusWlanEnvironmentScanResultsEntryInterpointPeerName OBJECT-TYPE
    SYNTAX     DisplayString (SIZE(0..24))
    MAX-ACCESS read-only
    STATUS     current
    DESCRIPTION
            "-- empty --"
    ::= { lcsStatusWlanEnvironmentScanResultsEntry 31 }

-- {COLUMN} 1.3.6.1.4.1.2356.11.1.3.69.1.32
lcsStatusWlanEnvironmentScanResultsEntryMaxAMpduLen OBJECT-TYPE
    SYNTAX     Integer32 (0..2147483647)
    MAX-ACCESS read-only
    STATUS     current
    DESCRIPTION
            "-- empty --"
    ::= { lcsStatusWlanEnvironmentScanResultsEntry 32 }

-- {COLUMN} 1.3.6.1.4.1.2356.11.1.3.69.1.33
lcsStatusWlanEnvironmentScanResultsEntryMaxAMsduLen OBJECT-TYPE
    SYNTAX     Integer32 (0..2147483647)
    MAX-ACCESS read-only
    STATUS     current
    DESCRIPTION
            "-- empty --"
    ::= { lcsStatusWlanEnvironmentScanResultsEntry 33 }

-- {COLUMN} 1.3.6.1.4.1.2356.11.1.3.69.1.34
lcsStatusWlanEnvironmentScanResultsEntryVendor OBJECT-TYPE
    SYNTAX     DisplayString (SIZE(0..255))
    MAX-ACCESS read-only
    STATUS     current
    DESCRIPTION
            "-- empty --"
    ::= { lcsStatusWlanEnvironmentScanResultsEntry 34 }

-- {COLUMN} 1.3.6.1.4.1.2356.11.1.3.69.1.35
lcsStatusWlanEnvironmentScanResultsEntryEffRate OBJECT-TYPE
    SYNTAX     Integer32 (0..2147483647)
    MAX-ACCESS read-only
    STATUS     current
    DESCRIPTION
            "-- empty --"
    ::= { lcsStatusWlanEnvironmentScanResultsEntry 35 }

-- {COLUMN} 1.3.6.1.4.1.2356.11.1.3.69.1.36
lcsStatusWlanEnvironmentScanResultsEntry40mhzCoexistence OBJECT-TYPE
    SYNTAX     INTEGER {
                  eNo (0),
                  eYes (1)
            }
    MAX-ACCESS read-only
    STATUS     current
    DESCRIPTION
            "-- empty --"
    ::= { lcsStatusWlanEnvironmentScanResultsEntry 36 }

-- {COLUMN} 1.3.6.1.4.1.2356.11.1.3.69.1.37
lcsStatusWlanEnvironmentScanResultsEntryPreAuthentication OBJECT-TYPE
    SYNTAX     INTEGER {
                  eNo (0),
                  eYes (1)
            }
    MAX-ACCESS read-only
    STATUS     current
    DESCRIPTION
            "-- empty --"
    ::= { lcsStatusWlanEnvironmentScanResultsEntry 37 }

-- {COLUMN} 1.3.6.1.4.1.2356.11.1.3.69.1.40
lcsStatusWlanEnvironmentScanResultsEntryEapolPreauthFailed OBJECT-TYPE
    SYNTAX     INTEGER {
                  eNo (0),
                  eYes (1)
            }
    MAX-ACCESS read-only
    STATUS     current
    DESCRIPTION
            "-- empty --"
    ::= { lcsStatusWlanEnvironmentScanResultsEntry 40 }

-- {COLUMN} 1.3.6.1.4.1.2356.11.1.3.69.1.42
lcsStatusWlanEnvironmentScanResultsEntryAutowds OBJECT-TYPE
    SYNTAX     INTEGER {
                  eNo (0),
                  eYes (1)
            }
    MAX-ACCESS read-only
    STATUS     current
    DESCRIPTION
            "-- empty --"
    ::= { lcsStatusWlanEnvironmentScanResultsEntry 42 }

-- {COLUMN} 1.3.6.1.4.1.2356.11.1.3.69.1.43
lcsStatusWlanEnvironmentScanResultsEntrySGIMask OBJECT-TYPE
    SYNTAX     BITS {
                  eNo (0),
                  e160mhz (28),
                  e80mhz (29),
                  e40mhz (30),
                  e20mhz (31)
            }
    MAX-ACCESS read-only
    STATUS     current
    DESCRIPTION
            "Bit mask of short guard interval support per-CBW"
    ::= { lcsStatusWlanEnvironmentScanResultsEntry 43 }

-- {COLUMN} 1.3.6.1.4.1.2356.11.1.3.69.1.44
lcsStatusWlanEnvironmentScanResultsEntryChannelBandwidths OBJECT-TYPE
    SYNTAX     BITS {
                  eT40mhz (26),
                  e80Plus80mhz (27),
                  e160mhz (28),
                  e80mhz (29),
                  e40mhz (30),
                  e20mhz (31)
            }
    MAX-ACCESS read-only
    STATUS     current
    DESCRIPTION
            "-- empty --"
    ::= { lcsStatusWlanEnvironmentScanResultsEntry 44 }

-- {COLUMN} 1.3.6.1.4.1.2356.11.1.3.69.1.45
lcsStatusWlanEnvironmentScanResultsEntryChannelBandwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { lcsStatusWlanEnvironmentScanResultsEntry 45 }

-- {COLUMN} 1.3.6.1.4.1.2356.11.1.3.69.1.46
lcsStatusWlanEnvironmentScanResultsEntryClBrgSupport OBJECT-TYPE
    SYNTAX     INTEGER {
                  eNo (0),
                  eYes (1)
            }
    MAX-ACCESS read-only
    STATUS     current
    DESCRIPTION
            "-- empty --"
    ::= { lcsStatusWlanEnvironmentScanResultsEntry 46 }

-- {COLUMN} 1.3.6.1.4.1.2356.11.1.3.69.1.47
lcsStatusWlanEnvironmentScanResultsEntryProtMgmtFrames OBJECT-TYPE
    SYNTAX     INTEGER {
                  eNo (0),
                  eOptional (1),
                  eMandatory (2)
            }
    MAX-ACCESS read-only
    STATUS     current
    DESCRIPTION
            "-- empty --"
    ::= { lcsStatusWlanEnvironmentScanResultsEntry 47 }

-- {COLUMN} 1.3.6.1.4.1.2356.11.1.3.69.1.48
lcsStatusWlanEnvironmentScanResultsEntryTxPowerLimit OBJECT-TYPE
    SYNTAX     DisplayString (SIZE(0..255))
    MAX-ACCESS read-only
    STATUS     current
    DESCRIPTION
            "-- empty --"
    ::= { lcsStatusWlanEnvironmentScanResultsEntry 48 }

-- {COLUMN} 1.3.6.1.4.1.2356.11.1.3.69.1.49
lcsStatusWlanEnvironmentScanResultsEntryTxSTBCMask OBJECT-TYPE
    SYNTAX     BITS {
                  eVht (30),
                  eHt (31)
            }
    MAX-ACCESS read-only
    STATUS     current
    DESCRIPTION
            "Bit mask of Tx STBC support per-PHY-Type"
    ::= { lcsStatusWlanEnvironmentScanResultsEntry 49 }

-- {COLUMN} 1.3.6.1.4.1.2356.11.1.3.69.1.50
lcsStatusWlanEnvironmentScanResultsEntryRxStbcHt OBJECT-TYPE
    SYNTAX     INTEGER {
                  eNone (0),
                  eOne (1),
                  eTwo (2),
                  eThree (3)
            }
    MAX-ACCESS read-only
    STATUS     current
    DESCRIPTION
            "-- empty --"
    ::= { lcsStatusWlanEnvironmentScanResultsEntry 50 }

-- {COLUMN} 1.3.6.1.4.1.2356.11.1.3.69.1.51
lcsStatusWlanEnvironmentScanResultsEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { lcsStatusWlanEnvironmentScanResultsEntry 51 }

-- {COLUMN} 1.3.6.1.4.1.2356.11.1.3.69.1.52
lcsStatusWlanEnvironmentScanResultsEntryLDPCMask OBJECT-TYPE
    SYNTAX     BITS {
                  eVht (30),
                  eHt (31)
            }
    MAX-ACCESS read-only
    STATUS     current
    DESCRIPTION
            "Bit mask of LDPC support per-PHY-Type"
    ::= { lcsStatusWlanEnvironmentScanResultsEntry 52 }

-- {COLUMN} 1.3.6.1.4.1.2356.11.1.3.69.1.53
lcsStatusWlanEnvironmentScanResultsEntryUuid OBJECT-TYPE
    SYNTAX     DisplayString (SIZE(0..255))
    MAX-ACCESS read-only
    STATUS     current
    DESCRIPTION
            "-- empty --"
    ::= { lcsStatusWlanEnvironmentScanResultsEntry 53 }

-- {COLUMN} 1.3.6.1.4.1.2356.11.1.3.69.1.54
lcsStatusWlanEnvironmentScanResultsEntry11acBeamforming OBJECT-TYPE
    SYNTAX     BITS {
                  eMuBfee (28),
                  eMuBfer (29),
                  eSuBfee (30),
                  eSuBfer (31)
            }
    MAX-ACCESS read-only
    STATUS     current
    DESCRIPTION
            "-- empty --"
    ::= { lcsStatusWlanEnvironmentScanResultsEntry 54 }

-- {COLUMN} 1.3.6.1.4.1.2356.11.1.3.69.1.55
lcsStatusWlanEnvironmentScanResultsEntrySecondaryChannel OBJECT-TYPE
    SYNTAX     Integer32 (0..255)
    MAX-ACCESS read-only
    STATUS     current
    DESCRIPTION
            "-- empty --"
    ::= { lcsStatusWlanEnvironmentScanResultsEntry 55 }

-- {COLUMN} 1.3.6.1.4.1.2356.11.1.3.69.1.56
lcsStatusWlanEnvironmentScanResultsEntryTransitionalMode OBJECT-TYPE
    SYNTAX     INTEGER {
                  eNo (0),
                  eYes (1)
            }
    MAX-ACCESS read-only
    STATUS     current
    DESCRIPTION
            "-- empty --"
    ::= { lcsStatusWlanEnvironmentScanResultsEntry 56 }

-- {COLUMN} 1.3.6.1.4.1.2356.11.1.3.69.1.57
lcsStatusWlanEnvironmentScanResultsEntryTransitionalSsid OBJECT-TYPE
    SYNTAX     DisplayString (SIZE(0..255))
    MAX-ACCESS read-only
    STATUS     current
    DESCRIPTION
            "-- empty --"
    ::= { lcsStatusWlanEnvironmentScanResultsEntry 57 }

-- {COLUMN} 1.3.6.1.4.1.2356.11.1.3.69.1.58
lcsStatusWlanEnvironmentScanResultsEntryTransitionalBssid OBJECT-TYPE
    SYNTAX     MacAddress
    MAX-ACCESS read-only
    STATUS     current
    DESCRIPTION
            "-- empty --"
    ::= { lcsStatusWlanEnvironmentScanResultsEntry 58 }

-- {COLUMN} 1.3.6.1.4.1.2356.11.1.3.69.1.59
lcsStatusWlanEnvironmentScanResultsEntryQosMapping OBJECT-TYPE
    SYNTAX     INTEGER {
                  eNo (0),
                  eYes (1)
            }
    MAX-ACCESS read-only
    STATUS     current
    DESCRIPTION
            "-- empty --"
    ::= { lcsStatusWlanEnvironmentScanResultsEntry 59 }

-- {TABLE} 1.3.6.1.4.1.2356.11.1.3.70
lcsStatusWlanVlanGroupkeyMappingTable OBJECT-TYPE
    SYNTAX     SEQUENCE OF LcsStatusWlanVlanGroupkeyMappingEntry
    MAX-ACCESS not-accessible
    STATUS     current
    DESCRIPTION
            "-- empty --"
    ::= { lcsStatusWlan 70 }

-- {ROW} 1.3.6.1.4.1.2356.11.1.3.70.1
lcsStatusWlanVlanGroupkeyMappingEntry OBJECT-TYPE
    SYNTAX     LcsStatusWlanVlanGroupkeyMappingEntry
    MAX-ACCESS not-accessible
    STATUS     current
    DESCRIPTION
            ""
    INDEX {
            lcsStatusWlanVlanGroupkeyMappingEntryNetwork,
            lcsStatusWlanVlanGroupkeyMappingEntryVlanId
          }
    ::= { lcsStatusWlanVlanGroupkeyMappingTable 1 }

LcsStatusWlanVlanGroupkeyMappingEntry ::= SEQUENCE {
            lcsStatusWlanVlanGroupkeyMappingEntryNetwork INTEGER,
            lcsStatusWlanVlanGroupkeyMappingEntryVlanId Integer32,
            lcsStatusWlanVlanGroupkeyMappingEntryGroupkeyIndex Integer32,
            lcsStatusWlanVlanGroupkeyMappingEntrySource INTEGER
    }

-- {COLUMN} 1.3.6.1.4.1.2356.11.1.3.70.1.1
lcsStatusWlanVlanGroupkeyMappingEntryNetwork OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-only
    STATUS     current
    DESCRIPTION
            "-- empty --"
    ::= { lcsStatusWlanVlanGroupkeyMappingEntry 1 }

-- {COLUMN} 1.3.6.1.4.1.2356.11.1.3.70.1.2
lcsStatusWlanVlanGroupkeyMappingEntryVlanId OBJECT-TYPE
    SYNTAX     Integer32 (0..65535)
    MAX-ACCESS read-only
    STATUS     current
    DESCRIPTION
            "-- empty --"
    ::= { lcsStatusWlanVlanGroupkeyMappingEntry 2 }

-- {COLUMN} 1.3.6.1.4.1.2356.11.1.3.70.1.3
lcsStatusWlanVlanGroupkeyMappingEntryGroupkeyIndex OBJECT-TYPE
    SYNTAX     Integer32 (0..255)
    MAX-ACCESS read-only
    STATUS     current
    DESCRIPTION
            "-- empty --"
    ::= { lcsStatusWlanVlanGroupkeyMappingEntry 3 }

-- {COLUMN} 1.3.6.1.4.1.2356.11.1.3.70.1.4
lcsStatusWlanVlanGroupkeyMappingEntrySource OBJECT-TYPE
    SYNTAX     INTEGER {
                  eManual (1),
                  eAutomatic (2)
            }
    MAX-ACCESS read-only
    STATUS     current
    DESCRIPTION
            "-- empty --"
    ::= { lcsStatusWlanVlanGroupkeyMappingEntry 4 }

-- {SCALAR} 1.3.6.1.4.1.2356.11.1.3.72
lcsStatusWlanSteerStation OBJECT-TYPE
    SYNTAX     DisplayString
    MAX-ACCESS read-write
    STATUS     current
    DESCRIPTION
            "-- empty --"
    ::= { lcsStatusWlan 72 }

-- {SCALAR} 1.3.6.1.4.1.2356.11.1.3.75
lcsStatusWlanIappAnnouncementTrigger OBJECT-TYPE
    SYNTAX     DisplayString
    MAX-ACCESS read-write
    STATUS     current
    DESCRIPTION
            "-- empty --"
    ::= { lcsStatusWlan 75 }

-- {NODE} 1.3.6.1.4.1.2356.11.1.3.89
lcsStatusWlanClientSteering OBJECT IDENTIFIER ::= { lcsStatusWlan 89 }

-- {SCALAR} 1.3.6.1.4.1.2356.11.1.3.89.1
lcsStatusWlanClientSteeringTotalBtmEvents OBJECT-TYPE
    SYNTAX     Integer32 (0..2147483647)
    MAX-ACCESS read-only
    STATUS     current
    DESCRIPTION
            "-- empty --"
    ::= { lcsStatusWlanClientSteering 1 }

-- {SCALAR} 1.3.6.1.4.1.2356.11.1.3.89.2
lcsStatusWlanClientSteeringSuccessfulBtmEvents OBJECT-TYPE
    SYNTAX     Integer32 (0..2147483647)
    MAX-ACCESS read-only
    STATUS     current
    DESCRIPTION
            "-- empty --"
    ::= { lcsStatusWlanClientSteering 2 }

-- {SCALAR} 1.3.6.1.4.1.2356.11.1.3.89.3
lcsStatusWlanClientSteeringRejectedBtmEvents OBJECT-TYPE
    SYNTAX     Integer32 (0..2147483647)
    MAX-ACCESS read-only
    STATUS     current
    DESCRIPTION
            "-- empty --"
    ::= { lcsStatusWlanClientSteering 3 }

-- {SCALAR} 1.3.6.1.4.1.2356.11.1.3.89.4
lcsStatusWlanClientSteeringIgnoredBtmEvents OBJECT-TYPE
    SYNTAX     Integer32 (0..2147483647)
    MAX-ACCESS read-only
    STATUS     current
    DESCRIPTION
            "-- empty --"
    ::= { lcsStatusWlanClientSteering 4 }

-- {SCALAR} 1.3.6.1.4.1.2356.11.1.3.89.5
lcsStatusWlanClientSteeringLegacyEvents OBJECT-TYPE
    SYNTAX     Integer32 (0..2147483647)
    MAX-ACCESS read-only
    STATUS     current
    DESCRIPTION
            "-- empty --"
    ::= { lcsStatusWlanClientSteering 5 }

-- {SCALAR} 1.3.6.1.4.1.2356.11.1.3.89.6
lcsStatusWlanClientSteeringTotalSuccessfulEvents OBJECT-TYPE
    SYNTAX     Integer32 (0..2147483647)
    MAX-ACCESS read-only
    STATUS     current
    DESCRIPTION
            "-- empty --"
    ::= { lcsStatusWlanClientSteering 6 }

-- {SCALAR} 1.3.6.1.4.1.2356.11.1.3.89.7
lcsStatusWlanClientSteeringTotalEvents OBJECT-TYPE
    SYNTAX     Integer32 (0..2147483647)
    MAX-ACCESS read-only
    STATUS     current
    DESCRIPTION
            "-- empty --"
    ::= { lcsStatusWlanClientSteering 7 }

-- {SCALAR} 1.3.6.1.4.1.2356.11.1.3.89.8
lcsStatusWlanClientSteeringDryRun OBJECT-TYPE
    SYNTAX     INTEGER {
                  eNo (0),
                  eYes (1)
            }
    MAX-ACCESS read-only
    STATUS     current
    DESCRIPTION
            "-- empty --"
    ::= { lcsStatusWlanClientSteering 8 }

-- {SCALAR} 1.3.6.1.4.1.2356.11.1.3.89.9
lcsStatusWlanClientSteeringOperating OBJECT-TYPE
    SYNTAX     INTEGER {
                  eNo (0),
                  eYes (1),
                  eController (2),
                  eClientManagement (3)
            }
    MAX-ACCESS read-only
    STATUS     current
    DESCRIPTION
            "-- empty --"
    ::= { lcsStatusWlanClientSteering 9 }

-- {SCALAR} 1.3.6.1.4.1.2356.11.1.3.89.10
lcsStatusWlanClientSteeringTotalApSteeringBtmEvents OBJECT-TYPE
    SYNTAX     Integer32 (0..2147483647)
    MAX-ACCESS read-only
    STATUS     current
    DESCRIPTION
            "-- empty --"
    ::= { lcsStatusWlanClientSteering 10 }

-- {SCALAR} 1.3.6.1.4.1.2356.11.1.3.89.11
lcsStatusWlanClientSteeringTotalBandSteeringBtmEvents OBJECT-TYPE
    SYNTAX     Integer32 (0..2147483647)
    MAX-ACCESS read-only
    STATUS     current
    DESCRIPTION
            "-- empty --"
    ::= { lcsStatusWlanClientSteering 11 }

-- {SCALAR} 1.3.6.1.4.1.2356.11.1.3.100
lcsStatusWlanDfsForceRescan OBJECT-TYPE
    SYNTAX     DisplayString
    MAX-ACCESS read-write
    STATUS     current
    DESCRIPTION
            ""
    ::= { lcsStatusWlan 100 }

-- {TABLE} 1.3.6.1.4.1.2356.11.1.3.101
lcsStatusWlanDfsStatisticsTable OBJECT-TYPE
    SYNTAX     SEQUENCE OF LcsStatusWlanDfsStatisticsEntry
    MAX-ACCESS not-accessible
    STATUS     current
    DESCRIPTION
            "-- empty --"
    ::= { lcsStatusWlan 101 }

-- {ROW} 1.3.6.1.4.1.2356.11.1.3.101.1
lcsStatusWlanDfsStatisticsEntry OBJECT-TYPE
    SYNTAX     LcsStatusWlanDfsStatisticsEntry
    MAX-ACCESS not-accessible
    STATUS     current
    DESCRIPTION
            ""
    INDEX {
            lcsStatusWlanDfsStatisticsEntryIfc
          }
    ::= { lcsStatusWlanDfsStatisticsTable 1 }

LcsStatusWlanDfsStatisticsEntry ::= SEQUENCE {
            lcsStatusWlanDfsStatisticsEntryIfc INTEGER,
            lcsStatusWlanDfsStatisticsEntryNumDetections Integer32,
            lcsStatusWlanDfsStatisticsEntryLastDetection DisplayString,
            lcsStatusWlanDfsStatisticsEntryAllChannelsBlocked INTEGER,
            lcsStatusWlanDfsStatisticsEntryBlockedRemainingTime Integer32,
            lcsStatusWlanDfsStatisticsEntryNoServiceTime Integer32,
            lcsStatusWlanDfsStatisticsEntryNumRadarChannelChanges Integer32,
            lcsStatusWlanDfsStatisticsEntryExcNoiseChannelChanges Integer32
    }

-- {COLUMN} 1.3.6.1.4.1.2356.11.1.3.101.1.1
lcsStatusWlanDfsStatisticsEntryIfc OBJECT-TYPE
    SYNTAX     INTEGER {
                  eWlan1 (1),
                  eWlan2 (2)
            }
    MAX-ACCESS read-only
    STATUS     current
    DESCRIPTION
            "-- empty --"
    ::= { lcsStatusWlanDfsStatisticsEntry 1 }

-- {COLUMN} 1.3.6.1.4.1.2356.11.1.3.101.1.2
lcsStatusWlanDfsStatisticsEntryNumDetections OBJECT-TYPE
    SYNTAX     Integer32 (0..2147483647)
    MAX-ACCESS read-only
    STATUS     current
    DESCRIPTION
            "-- empty --"
    ::= { lcsStatusWlanDfsStatisticsEntry 2 }

-- {COLUMN} 1.3.6.1.4.1.2356.11.1.3.101.1.3
lcsStatusWlanDfsStatisticsEntryLastDetection OBJECT-TYPE
    SYNTAX     DisplayString (SIZE(0..21))
    MAX-ACCESS read-only
    STATUS     current
    DESCRIPTION
            "-- empty --"
    ::= { lcsStatusWlanDfsStatisticsEntry 3 }

-- {COLUMN} 1.3.6.1.4.1.2356.11.1.3.101.1.4
lcsStatusWlanDfsStatisticsEntryAllChannelsBlocked OBJECT-TYPE
    SYNTAX     INTEGER {
                  eNo (0),
                  eYes (1)
            }
    MAX-ACCESS read-only
    STATUS     current
    DESCRIPTION
            "-- empty --"
    ::= { lcsStatusWlanDfsStatisticsEntry 4 }

-- {COLUMN} 1.3.6.1.4.1.2356.11.1.3.101.1.5
lcsStatusWlanDfsStatisticsEntryBlockedRemainingTime OBJECT-TYPE
    SYNTAX     Integer32 (0..2147483647)
    MAX-ACCESS read-only
    STATUS     current
    DESCRIPTION
            "-- empty --"
    ::= { lcsStatusWlanDfsStatisticsEntry 5 }

-- {COLUMN} 1.3.6.1.4.1.2356.11.1.3.101.1.6
lcsStatusWlanDfsStatisticsEntryNoServiceTime OBJECT-TYPE
    SYNTAX     Integer32 (0..2147483647)
    MAX-ACCESS read-only
    STATUS     current
    DESCRIPTION
            "-- empty --"
    ::= { lcsStatusWlanDfsStatisticsEntry 6 }

-- {COLUMN} 1.3.6.1.4.1.2356.11.1.3.101.1.7
lcsStatusWlanDfsStatisticsEntryNumRadarChannelChanges OBJECT-TYPE
    SYNTAX     Integer32 (0..2147483647)
    MAX-ACCESS read-only
    STATUS     current
    DESCRIPTION
            "-- empty --"
    ::= { lcsStatusWlanDfsStatisticsEntry 7 }

-- {COLUMN} 1.3.6.1.4.1.2356.11.1.3.101.1.8
lcsStatusWlanDfsStatisticsEntryExcNoiseChannelChanges OBJECT-TYPE
    SYNTAX     Integer32 (0..2147483647)
    MAX-ACCESS read-only
    STATUS     current
    DESCRIPTION
            "-- empty --"
    ::= { lcsStatusWlanDfsStatisticsEntry 8 }

-- {TABLE} 1.3.6.1.4.1.2356.11.1.3.126
lcsStatusWlanBadAmbDetTable OBJECT-TYPE
    SYNTAX     SEQUENCE OF LcsStatusWlanBadAmbDetEntry
    MAX-ACCESS not-accessible
    STATUS     current
    DESCRIPTION
            ""
    ::= { lcsStatusWlan 126 }

-- {ROW} 1.3.6.1.4.1.2356.11.1.3.126.1
lcsStatusWlanBadAmbDetEntry OBJECT-TYPE
    SYNTAX     LcsStatusWlanBadAmbDetEntry
    MAX-ACCESS not-accessible
    STATUS     current
    DESCRIPTION
            ""
    INDEX {
            lcsStatusWlanBadAmbDetEntryIfc
          }
    ::= { lcsStatusWlanBadAmbDetTable 1 }

LcsStatusWlanBadAmbDetEntry ::= SEQUENCE {
            lcsStatusWlanBadAmbDetEntryIfc DisplayString,
            lcsStatusWlanBadAmbDetEntryOperating INTEGER,
            lcsStatusWlanBadAmbDetEntryMinClientPhySignal Integer32,
            lcsStatusWlanBadAmbDetEntryMinClientTxPackets Integer32,
            lcsStatusWlanBadAmbDetEntryTxClientRetryRatioLimit Integer32,
            lcsStatusWlanBadAmbDetEntryTxClientRetryRatio Integer32,
            lcsStatusWlanBadAmbDetEntryNoiseLimit Integer32,
            lcsStatusWlanBadAmbDetEntryMeanNoise Integer32,
            lcsStatusWlanBadAmbDetEntryMarkedChannelTimeout Integer32,
            lcsStatusWlanBadAmbDetEntryMarkedChannel Integer32,
            lcsStatusWlanBadAmbDetEntryTriggerTimespan Integer32,
            lcsStatusWlanBadAmbDetEntryChannelChangesLastHour Integer32,
            lcsStatusWlanBadAmbDetEntryChannelChangesLast5Hours Integer32,
            lcsStatusWlanBadAmbDetEntryChannelChangesLast24Hours Integer32,
            lcsStatusWlanBadAmbDetEntryInterferenceLimit Integer32,
            lcsStatusWlanBadAmbDetEntryMeanInterference Integer32
    }

-- {COLUMN} 1.3.6.1.4.1.2356.11.1.3.126.1.1
lcsStatusWlanBadAmbDetEntryIfc OBJECT-TYPE
    SYNTAX     DisplayString (SIZE(0..255))
    MAX-ACCESS read-only
    STATUS     current
    DESCRIPTION
            "-- empty --"
    ::= { lcsStatusWlanBadAmbDetEntry 1 }

-- {COLUMN} 1.3.6.1.4.1.2356.11.1.3.126.1.2
lcsStatusWlanBadAmbDetEntryOperating OBJECT-TYPE
    SYNTAX     INTEGER {
                  eNo (0),
                  eYes (1)
            }
    MAX-ACCESS read-only
    STATUS     current
    DESCRIPTION
            "-- empty --"
    ::= { lcsStatusWlanBadAmbDetEntry 2 }

-- {COLUMN} 1.3.6.1.4.1.2356.11.1.3.126.1.3
lcsStatusWlanBadAmbDetEntryMinClientPhySignal OBJECT-TYPE
    SYNTAX     Integer32 (0..2147483647)
    MAX-ACCESS read-only
    STATUS     current
    DESCRIPTION
            "-- empty --"
    ::= { lcsStatusWlanBadAmbDetEntry 3 }

-- {COLUMN} 1.3.6.1.4.1.2356.11.1.3.126.1.4
lcsStatusWlanBadAmbDetEntryMinClientTxPackets OBJECT-TYPE
    SYNTAX     Integer32 (0..2147483647)
    MAX-ACCESS read-only
    STATUS     current
    DESCRIPTION
            "-- empty --"
    ::= { lcsStatusWlanBadAmbDetEntry 4 }

-- {COLUMN} 1.3.6.1.4.1.2356.11.1.3.126.1.5
lcsStatusWlanBadAmbDetEntryTxClientRetryRatioLimit OBJECT-TYPE
    SYNTAX     Integer32 (0..2147483647)
    MAX-ACCESS read-only
    STATUS     current
    DESCRIPTION
            "-- empty --"
    ::= { lcsStatusWlanBadAmbDetEntry 5 }

-- {COLUMN} 1.3.6.1.4.1.2356.11.1.3.126.1.6
lcsStatusWlanBadAmbDetEntryTxClientRetryRatio OBJECT-TYPE
    SYNTAX     Integer32 (0..2147483647)
    MAX-ACCESS read-only
    STATUS     current
    DESCRIPTION
            "-- empty --"
    ::= { lcsStatusWlanBadAmbDetEntry 6 }

-- {COLUMN} 1.3.6.1.4.1.2356.11.1.3.126.1.7
lcsStatusWlanBadAmbDetEntryNoiseLimit OBJECT-TYPE
    SYNTAX     Integer32 (-2147483648..2147483647)
    MAX-ACCESS read-only
    STATUS     current
    DESCRIPTION
            "-- empty --"
    ::= { lcsStatusWlanBadAmbDetEntry 7 }

-- {COLUMN} 1.3.6.1.4.1.2356.11.1.3.126.1.8
lcsStatusWlanBadAmbDetEntryMeanNoise OBJECT-TYPE
    SYNTAX     Integer32 (-2147483648..2147483647)
    MAX-ACCESS read-only
    STATUS     current
    DESCRIPTION
            "-- empty --"
    ::= { lcsStatusWlanBadAmbDetEntry 8 }

-- {COLUMN} 1.3.6.1.4.1.2356.11.1.3.126.1.9
lcsStatusWlanBadAmbDetEntryMarkedChannelTimeout OBJECT-TYPE
    SYNTAX     Integer32 (0..2147483647)
    MAX-ACCESS read-only
    STATUS     current
    DESCRIPTION
            "-- empty --"
    ::= { lcsStatusWlanBadAmbDetEntry 9 }

-- {COLUMN} 1.3.6.1.4.1.2356.11.1.3.126.1.10
lcsStatusWlanBadAmbDetEntryMarkedChannel OBJECT-TYPE
    SYNTAX     Integer32 (0..2147483647)
    MAX-ACCESS read-only
    STATUS     current
    DESCRIPTION
            "-- empty --"
    ::= { lcsStatusWlanBadAmbDetEntry 10 }

-- {COLUMN} 1.3.6.1.4.1.2356.11.1.3.126.1.11
lcsStatusWlanBadAmbDetEntryTriggerTimespan OBJECT-TYPE
    SYNTAX     Integer32 (0..2147483647)
    MAX-ACCESS read-only
    STATUS     current
    DESCRIPTION
            "-- empty --"
    ::= { lcsStatusWlanBadAmbDetEntry 11 }

-- {COLUMN} 1.3.6.1.4.1.2356.11.1.3.126.1.12
lcsStatusWlanBadAmbDetEntryChannelChangesLastHour OBJECT-TYPE
    SYNTAX     Integer32 (0..2147483647)
    MAX-ACCESS read-only
    STATUS     current
    DESCRIPTION
            "-- empty --"
    ::= { lcsStatusWlanBadAmbDetEntry 12 }

-- {COLUMN} 1.3.6.1.4.1.2356.11.1.3.126.1.13
lcsStatusWlanBadAmbDetEntryChannelChangesLast5Hours OBJECT-TYPE
    SYNTAX     Integer32 (0..2147483647)
    MAX-ACCESS read-only
    STATUS     current
    DESCRIPTION
            "-- empty --"
    ::= { lcsStatusWlanBadAmbDetEntry 13 }

-- {COLUMN} 1.3.6.1.4.1.2356.11.1.3.126.1.14
lcsStatusWlanBadAmbDetEntryChannelChangesLast24Hours OBJECT-TYPE
    SYNTAX     Integer32 (0..2147483647)
    MAX-ACCESS read-only
    STATUS     current
    DESCRIPTION
            "-- empty --"
    ::= { lcsStatusWlanBadAmbDetEntry 14 }

-- {COLUMN} 1.3.6.1.4.1.2356.11.1.3.126.1.15
lcsStatusWlanBadAmbDetEntryInterferenceLimit OBJECT-TYPE
    SYNTAX     Integer32 (0..2147483647)
    MAX-ACCESS read-only
    STATUS     current
    DESCRIPTION
            "-- empty --"
    ::= { lcsStatusWlanBadAmbDetEntry 15 }

-- {COLUMN} 1.3.6.1.4.1.2356.11.1.3.126.1.16
lcsStatusWlanBadAmbDetEntryMeanInterference OBJECT-TYPE
    SYNTAX     Integer32 (0..2147483647)
    MAX-ACCESS read-only
    STATUS     current
    DESCRIPTION
            "-- empty --"
    ::= { lcsStatusWlanBadAmbDetEntry 16 }

-- {TABLE} 1.3.6.1.4.1.2356.11.1.3.127
lcsStatusWlanThermalMitigationTable OBJECT-TYPE
    SYNTAX     SEQUENCE OF LcsStatusWlanThermalMitigationEntry
    MAX-ACCESS not-accessible
    STATUS     current
    DESCRIPTION
            "-- empty --"
    ::= { lcsStatusWlan 127 }

-- {ROW} 1.3.6.1.4.1.2356.11.1.3.127.1
lcsStatusWlanThermalMitigationEntry OBJECT-TYPE
    SYNTAX     LcsStatusWlanThermalMitigationEntry
    MAX-ACCESS not-accessible
    STATUS     current
    DESCRIPTION
            ""
    INDEX {
            lcsStatusWlanThermalMitigationEntryIfc
          }
    ::= { lcsStatusWlanThermalMitigationTable 1 }

LcsStatusWlanThermalMitigationEntry ::= SEQUENCE {
            lcsStatusWlanThermalMitigationEntryIfc DisplayString,
            lcsStatusWlanThermalMitigationEntryTemperature DisplayString,
            lcsStatusWlanThermalMitigationEntryNumericTemperature Integer32,
            lcsStatusWlanThermalMitigationEntryMitigationLevel Integer32,
            lcsStatusWlanThermalMitigationEntryTxDutyCycle Integer32,
            lcsStatusWlanThermalMitigationEntryMaxTemperature DisplayString,
            lcsStatusWlanThermalMitigationEntryNumericMaxTemperature Integer32,
            lcsStatusWlanThermalMitigationEntryLevel1Cycles Integer32,
            lcsStatusWlanThermalMitigationEntryLevel2Cycles Integer32,
            lcsStatusWlanThermalMitigationEntryLevel3Cycles Integer32,
            lcsStatusWlanThermalMitigationEntryLevel4Cycles Integer32
    }

-- {COLUMN} 1.3.6.1.4.1.2356.11.1.3.127.1.1
lcsStatusWlanThermalMitigationEntryIfc OBJECT-TYPE
    SYNTAX     DisplayString (SIZE(0..255))
    MAX-ACCESS read-only
    STATUS     current
    DESCRIPTION
            "-- empty --"
    ::= { lcsStatusWlanThermalMitigationEntry 1 }

-- {COLUMN} 1.3.6.1.4.1.2356.11.1.3.127.1.2
lcsStatusWlanThermalMitigationEntryTemperature OBJECT-TYPE
    SYNTAX     DisplayString (SIZE(0..255))
    MAX-ACCESS read-only
    STATUS     current
    DESCRIPTION
            "-- empty --"
    ::= { lcsStatusWlanThermalMitigationEntry 2 }

-- {COLUMN} 1.3.6.1.4.1.2356.11.1.3.127.1.3
lcsStatusWlanThermalMitigationEntryNumericTemperature OBJECT-TYPE
    SYNTAX     Integer32 (-32768..32767)
    MAX-ACCESS read-only
    STATUS     current
    DESCRIPTION
            "-- empty --"
    ::= { lcsStatusWlanThermalMitigationEntry 3 }

-- {COLUMN} 1.3.6.1.4.1.2356.11.1.3.127.1.4
lcsStatusWlanThermalMitigationEntryMitigationLevel OBJECT-TYPE
    SYNTAX     Integer32 (0..2147483647)
    MAX-ACCESS read-only
    STATUS     current
    DESCRIPTION
            "-- empty --"
    ::= { lcsStatusWlanThermalMitigationEntry 4 }

-- {COLUMN} 1.3.6.1.4.1.2356.11.1.3.127.1.5
lcsStatusWlanThermalMitigationEntryTxDutyCycle OBJECT-TYPE
    SYNTAX     Integer32 (0..2147483647)
    MAX-ACCESS read-only
    STATUS     current
    DESCRIPTION
            "-- empty --"
    ::= { lcsStatusWlanThermalMitigationEntry 5 }

-- {COLUMN} 1.3.6.1.4.1.2356.11.1.3.127.1.6
lcsStatusWlanThermalMitigationEntryMaxTemperature OBJECT-TYPE
    SYNTAX     DisplayString (SIZE(0..255))
    MAX-ACCESS read-only
    STATUS     current
    DESCRIPTION
            "-- empty --"
    ::= { lcsStatusWlanThermalMitigationEntry 6 }

-- {COLUMN} 1.3.6.1.4.1.2356.11.1.3.127.1.7
lcsStatusWlanThermalMitigationEntryNumericMaxTemperature OBJECT-TYPE
    SYNTAX     Integer32 (-32768..32767)
    MAX-ACCESS read-only
    STATUS     current
    DESCRIPTION
            "-- empty --"
    ::= { lcsStatusWlanThermalMitigationEntry 7 }

-- {COLUMN} 1.3.6.1.4.1.2356.11.1.3.127.1.8
lcsStatusWlanThermalMitigationEntryLevel1Cycles OBJECT-TYPE
    SYNTAX     Integer32 (0..2147483647)
    MAX-ACCESS read-only
    STATUS     current
    DESCRIPTION
            "-- empty --"
    ::= { lcsStatusWlanThermalMitigationEntry 8 }

-- {COLUMN} 1.3.6.1.4.1.2356.11.1.3.127.1.9
lcsStatusWlanThermalMitigationEntryLevel2Cycles OBJECT-TYPE
    SYNTAX     Integer32 (0..2147483647)
    MAX-ACCESS read-only
    STATUS     current
    DESCRIPTION
            "-- empty --"
    ::= { lcsStatusWlanThermalMitigationEntry 9 }

-- {COLUMN} 1.3.6.1.4.1.2356.11.1.3.127.1.10
lcsStatusWlanThermalMitigationEntryLevel3Cycles OBJECT-TYPE
    SYNTAX     Integer32 (0..2147483647)
    MAX-ACCESS read-only
    STATUS     current
    DESCRIPTION
            "-- empty --"
    ::= { lcsStatusWlanThermalMitigationEntry 10 }

-- {COLUMN} 1.3.6.1.4.1.2356.11.1.3.127.1.11
lcsStatusWlanThermalMitigationEntryLevel4Cycles OBJECT-TYPE
    SYNTAX     Integer32 (0..2147483647)
    MAX-ACCESS read-only
    STATUS     current
    DESCRIPTION
            "-- empty --"
    ::= { lcsStatusWlanThermalMitigationEntry 11 }

-- {TABLE} 1.3.6.1.4.1.2356.11.1.3.128
lcsStatusWlanRoamingTargetsTable OBJECT-TYPE
    SYNTAX     SEQUENCE OF LcsStatusWlanRoamingTargetsEntry
    MAX-ACCESS not-accessible
    STATUS     current
    DESCRIPTION
            "-- empty --"
    ::= { lcsStatusWlan 128 }

-- {ROW} 1.3.6.1.4.1.2356.11.1.3.128.1
lcsStatusWlanRoamingTargetsEntry OBJECT-TYPE
    SYNTAX     LcsStatusWlanRoamingTargetsEntry
    MAX-ACCESS not-accessible
    STATUS     current
    DESCRIPTION
            ""
    INDEX {
            lcsStatusWlanRoamingTargetsEntryBssid
          }
    ::= { lcsStatusWlanRoamingTargetsTable 1 }

LcsStatusWlanRoamingTargetsEntry ::= SEQUENCE {
            lcsStatusWlanRoamingTargetsEntryBssid MacAddress,
            lcsStatusWlanRoamingTargetsEntryNetworkName OCTET STRING,
            lcsStatusWlanRoamingTargetsEntryName OCTET STRING
    }

-- {COLUMN} 1.3.6.1.4.1.2356.11.1.3.128.1.1
lcsStatusWlanRoamingTargetsEntryBssid OBJECT-TYPE
    SYNTAX     MacAddress
    MAX-ACCESS read-only
    STATUS     current
    DESCRIPTION
            "-- empty --"
    ::= { lcsStatusWlanRoamingTargetsEntry 1 }

-- {COLUMN} 1.3.6.1.4.1.2356.11.1.3.128.1.2
lcsStatusWlanRoamingTargetsEntryNetworkName OBJECT-TYPE
    SYNTAX     OCTET STRING (SIZE(0..32))
    MAX-ACCESS read-only
    STATUS     current
    DESCRIPTION
            "-- empty --"
    ::= { lcsStatusWlanRoamingTargetsEntry 2 }

-- {COLUMN} 1.3.6.1.4.1.2356.11.1.3.128.1.3
lcsStatusWlanRoamingTargetsEntryName OBJECT-TYPE
    SYNTAX     OCTET STRING (SIZE(0..64))
    MAX-ACCESS read-only
    STATUS     current
    DESCRIPTION
            "-- empty --"
    ::= { lcsStatusWlanRoamingTargetsEntry 3 }

-- {NODE} 1.3.6.1.4.1.2356.11.1.3.129
lcsStatusWlanLepsU OBJECT IDENTIFIER ::= { lcsStatusWlan 129 }

-- {NODE} 1.3.6.1.4.1.2356.11.1.3.129.1
lcsStatusWlanLepsUStatistics OBJECT IDENTIFIER ::= { lcsStatusWlanLepsU 1 }

-- {SCALAR} 1.3.6.1.4.1.2356.11.1.3.129.1.1
lcsStatusWlanLepsUStatisticsNumAuthentications OBJECT-TYPE
    SYNTAX     Integer32 (0..2147483647)
    MAX-ACCESS read-only
    STATUS     current
    DESCRIPTION
            "-- empty --"
    ::= { lcsStatusWlanLepsUStatistics 1 }

-- {SCALAR} 1.3.6.1.4.1.2356.11.1.3.129.1.2
lcsStatusWlanLepsUStatisticsNumAuthSuccess OBJECT-TYPE
    SYNTAX     Integer32 (0..2147483647)
    MAX-ACCESS read-only
    STATUS     current
    DESCRIPTION
            "-- empty --"
    ::= { lcsStatusWlanLepsUStatistics 2 }

-- {SCALAR} 1.3.6.1.4.1.2356.11.1.3.129.1.3
lcsStatusWlanLepsUStatisticsNumAuthFailure OBJECT-TYPE
    SYNTAX     Integer32 (0..2147483647)
    MAX-ACCESS read-only
    STATUS     current
    DESCRIPTION
            "-- empty --"
    ::= { lcsStatusWlanLepsUStatistics 3 }

-- {SCALAR} 1.3.6.1.4.1.2356.11.1.3.129.1.4
lcsStatusWlanLepsUStatisticsNumAuthFailureCongestion OBJECT-TYPE
    SYNTAX     Integer32 (0..2147483647)
    MAX-ACCESS read-only
    STATUS     current
    DESCRIPTION
            "-- empty --"
    ::= { lcsStatusWlanLepsUStatistics 4 }

-- {SCALAR} 1.3.6.1.4.1.2356.11.1.3.129.1.5
lcsStatusWlanLepsUStatisticsNumAuthFailureKeyGeneration OBJECT-TYPE
    SYNTAX     Integer32 (0..2147483647)
    MAX-ACCESS read-only
    STATUS     current
    DESCRIPTION
            "-- empty --"
    ::= { lcsStatusWlanLepsUStatistics 5 }

-- {SCALAR} 1.3.6.1.4.1.2356.11.1.3.129.1.6
lcsStatusWlanLepsUStatisticsMaxAuthTime OBJECT-TYPE
    SYNTAX     Integer32 (0..2147483647)
    MAX-ACCESS read-only
    STATUS     current
    DESCRIPTION
            "-- empty --"
    ::= { lcsStatusWlanLepsUStatistics 6 }

-- {SCALAR} 1.3.6.1.4.1.2356.11.1.3.129.1.7
lcsStatusWlanLepsUStatisticsMaxAuthWaitingTime OBJECT-TYPE
    SYNTAX     Integer32 (0..2147483647)
    MAX-ACCESS read-only
    STATUS     current
    DESCRIPTION
            "-- empty --"
    ::= { lcsStatusWlanLepsUStatistics 7 }

-- {SCALAR} 1.3.6.1.4.1.2356.11.1.3.129.1.99
lcsStatusWlanLepsUStatisticsDeleteValues OBJECT-TYPE
    SYNTAX     DisplayString
    MAX-ACCESS read-write
    STATUS     current
    DESCRIPTION
            "-- empty --"
    ::= { lcsStatusWlanLepsUStatistics 99 }

-- {SCALAR} 1.3.6.1.4.1.2356.11.1.3.129.2
lcsStatusWlanLepsUState OBJECT-TYPE
    SYNTAX     INTEGER {
                  eOff (0),
                  eKeyGeneration (1),
                  eOperating (2)
            }
    MAX-ACCESS read-only
    STATUS     current
    DESCRIPTION
            "-- empty --"
    ::= { lcsStatusWlanLepsU 2 }

-- {SCALAR} 1.3.6.1.4.1.2356.11.1.3.129.3
lcsStatusWlanLepsUNumValidUser OBJECT-TYPE
    SYNTAX     Integer32 (0..2147483647)
    MAX-ACCESS read-only
    STATUS     current
    DESCRIPTION
            "-- empty --"
    ::= { lcsStatusWlanLepsU 3 }

-- {SCALAR} 1.3.6.1.4.1.2356.11.1.3.129.4
lcsStatusWlanLepsUNumValidKeys OBJECT-TYPE
    SYNTAX     Integer32 (0..2147483647)
    MAX-ACCESS read-only
    STATUS     current
    DESCRIPTION
            "-- empty --"
    ::= { lcsStatusWlanLepsU 4 }

-- {SCALAR} 1.3.6.1.4.1.2356.11.1.3.129.5
lcsStatusWlanLepsUKeyGenerationProgressPercent OBJECT-TYPE
    SYNTAX     Integer32 (0..255)
    MAX-ACCESS read-only
    STATUS     current
    DESCRIPTION
            "-- empty --"
    ::= { lcsStatusWlanLepsU 5 }

-- {SCALAR} 1.3.6.1.4.1.2356.11.1.3.129.6
lcsStatusWlanLepsUMaxNumUserPerSsidState OBJECT-TYPE
    SYNTAX     INTEGER {
                  eOk (0),
                  eError (1)
            }
    MAX-ACCESS read-only
    STATUS     current
    DESCRIPTION
            "-- empty --"
    ::= { lcsStatusWlanLepsU 6 }

-- {TABLE} 1.3.6.1.4.1.2356.11.1.3.129.7
lcsStatusWlanLepsUDeviceUserCacheTable OBJECT-TYPE
    SYNTAX     SEQUENCE OF LcsStatusWlanLepsUDeviceUserCacheEntry
    MAX-ACCESS not-accessible
    STATUS     current
    DESCRIPTION
            "-- empty --"
    ::= { lcsStatusWlanLepsU 7 }

-- {ROW} 1.3.6.1.4.1.2356.11.1.3.129.7.1
lcsStatusWlanLepsUDeviceUserCacheEntry OBJECT-TYPE
    SYNTAX     LcsStatusWlanLepsUDeviceUserCacheEntry
    MAX-ACCESS not-accessible
    STATUS     current
    DESCRIPTION
            ""
    INDEX {
            lcsStatusWlanLepsUDeviceUserCacheEntryMacAddress
          }
    ::= { lcsStatusWlanLepsUDeviceUserCacheTable 1 }

LcsStatusWlanLepsUDeviceUserCacheEntry ::= SEQUENCE {
            lcsStatusWlanLepsUDeviceUserCacheEntryMacAddress MacAddress,
            lcsStatusWlanLepsUDeviceUserCacheEntryName OCTET STRING,
            lcsStatusWlanLepsUDeviceUserCacheEntryLifetime Unsigned32
    }

-- {COLUMN} 1.3.6.1.4.1.2356.11.1.3.129.7.1.1
lcsStatusWlanLepsUDeviceUserCacheEntryMacAddress OBJECT-TYPE
    SYNTAX     MacAddress
    MAX-ACCESS read-only
    STATUS     current
    DESCRIPTION
            "-- empty --"
    ::= { lcsStatusWlanLepsUDeviceUserCacheEntry 1 }

-- {COLUMN} 1.3.6.1.4.1.2356.11.1.3.129.7.1.2
lcsStatusWlanLepsUDeviceUserCacheEntryName OBJECT-TYPE
    SYNTAX     OCTET STRING (SIZE(0..32))
    MAX-ACCESS read-only
    STATUS     current
    DESCRIPTION
            "-- empty --"
    ::= { lcsStatusWlanLepsUDeviceUserCacheEntry 2 }

-- {COLUMN} 1.3.6.1.4.1.2356.11.1.3.129.7.1.3
lcsStatusWlanLepsUDeviceUserCacheEntryLifetime OBJECT-TYPE
    SYNTAX     Unsigned32 (0..4294967295)
    MAX-ACCESS read-only
    STATUS     current
    DESCRIPTION
            "-- empty --"
    ::= { lcsStatusWlanLepsUDeviceUserCacheEntry 3 }

-- {NODE} 1.3.6.1.4.1.2356.11.1.3.248
lcsStatusWlanWIds OBJECT IDENTIFIER ::= { lcsStatusWlan 248 }

-- {TABLE} 1.3.6.1.4.1.2356.11.1.3.248.1
lcsStatusWlanWIdsEventTableTable OBJECT-TYPE
    SYNTAX     SEQUENCE OF LcsStatusWlanWIdsEventTableEntry
    MAX-ACCESS not-accessible
    STATUS     current
    DESCRIPTION
            "-- empty --"
    ::= { lcsStatusWlanWIds 1 }

-- {ROW} 1.3.6.1.4.1.2356.11.1.3.248.1.1
lcsStatusWlanWIdsEventTableEntry OBJECT-TYPE
    SYNTAX     LcsStatusWlanWIdsEventTableEntry
    MAX-ACCESS not-accessible
    STATUS     current
    DESCRIPTION
            ""
    INDEX {
            lcsStatusWlanWIdsEventTableEntryEventType,
            lcsStatusWlanWIdsEventTableEntryId
          }
    ::= { lcsStatusWlanWIdsEventTableTable 1 }

LcsStatusWlanWIdsEventTableEntry ::= SEQUENCE {
            lcsStatusWlanWIdsEventTableEntryEventType INTEGER,
            lcsStatusWlanWIdsEventTableEntryId Integer32,
            lcsStatusWlanWIdsEventTableEntryEventTime DisplayString,
            lcsStatusWlanWIdsEventTableEntryEventRate Integer32,
            lcsStatusWlanWIdsEventTableEntryInterface INTEGER,
            lcsStatusWlanWIdsEventTableEntryLocaltime Integer32,
            lcsStatusWlanWIdsEventTableEntryAttackerMac MacAddress
    }

-- {COLUMN} 1.3.6.1.4.1.2356.11.1.3.248.1.1.1
lcsStatusWlanWIdsEventTableEntryEventType OBJECT-TYPE
    SYNTAX     INTEGER {
                  eEapolstart (1),
                  eProbebroad (2),
                  eDeauthenticatebroad (3),
                  eDeauthenticate (4),
                  eAssociatereq (5),
                  eReassociatereq (6),
                  eAuthenticate (7),
                  eDisassociate (8),
                  eBlockackAttack (9),
                  eDelba (10),
                  eNullDataDosAttack (11),
                  eNullDataPSAttack (12),
                  ePSPollAttack (13),
                  eSMPSAttack (14),
                  eDisassociatebroad (15),
                  ePrematureeapolsuccess (16),
                  ePrematureeapolfailure (17),
                  eGenericerror (18)
            }
    MAX-ACCESS read-only
    STATUS     current
    DESCRIPTION
            "-- empty --"
    ::= { lcsStatusWlanWIdsEventTableEntry 1 }

-- {COLUMN} 1.3.6.1.4.1.2356.11.1.3.248.1.1.2
lcsStatusWlanWIdsEventTableEntryId OBJECT-TYPE
    SYNTAX     Integer32 (0..2147483647)
    MAX-ACCESS read-only
    STATUS     current
    DESCRIPTION
            "-- empty --"
    ::= { lcsStatusWlanWIdsEventTableEntry 2 }

-- {COLUMN} 1.3.6.1.4.1.2356.11.1.3.248.1.1.3
lcsStatusWlanWIdsEventTableEntryEventTime OBJECT-TYPE
    SYNTAX     DisplayString (SIZE(0..255))
    MAX-ACCESS read-only
    STATUS     current
    DESCRIPTION
            "-- empty --"
    ::= { lcsStatusWlanWIdsEventTableEntry 3 }

-- {COLUMN} 1.3.6.1.4.1.2356.11.1.3.248.1.1.4
lcsStatusWlanWIdsEventTableEntryEventRate OBJECT-TYPE
    SYNTAX     Integer32 (0..2147483647)
    MAX-ACCESS read-only
    STATUS     current
    DESCRIPTION
            "-- empty --"
    ::= { lcsStatusWlanWIdsEventTableEntry 4 }

-- {COLUMN} 1.3.6.1.4.1.2356.11.1.3.248.1.1.5
lcsStatusWlanWIdsEventTableEntryInterface OBJECT-TYPE
    SYNTAX     INTEGER {
                  eWlan1 (0),
                  eWlan2 (1),
                  eAny (255)
            }
    MAX-ACCESS read-only
    STATUS     current
    DESCRIPTION
            "-- empty --"
    ::= { lcsStatusWlanWIdsEventTableEntry 5 }

-- {COLUMN} 1.3.6.1.4.1.2356.11.1.3.248.1.1.6
lcsStatusWlanWIdsEventTableEntryLocaltime OBJECT-TYPE
    SYNTAX     Integer32 (0..2147483647)
    MAX-ACCESS read-only
    STATUS     current
    DESCRIPTION
            "-- empty --"
    ::= { lcsStatusWlanWIdsEventTableEntry 6 }

-- {COLUMN} 1.3.6.1.4.1.2356.11.1.3.248.1.1.7
lcsStatusWlanWIdsEventTableEntryAttackerMac OBJECT-TYPE
    SYNTAX     MacAddress
    MAX-ACCESS read-only
    STATUS     current
    DESCRIPTION
            "-- empty --"
    ::= { lcsStatusWlanWIdsEventTableEntry 7 }

-- {NODE} 1.3.6.1.4.1.2356.11.1.3.248.2
lcsStatusWlanWIdsSig OBJECT IDENTIFIER ::= { lcsStatusWlanWIds 2 }

-- {NODE} 1.3.6.1.4.1.2356.11.1.3.248.2.1
lcsStatusWlanWIdsSigAssociatereqflood OBJECT IDENTIFIER ::= { lcsStatusWlanWIdsSig 1 }

-- {SCALAR} 1.3.6.1.4.1.2356.11.1.3.248.2.1.1
lcsStatusWlanWIdsSigAssociatereqfloodCounterIfc1 OBJECT-TYPE
    SYNTAX     Integer32 (0..2147483647)
    MAX-ACCESS read-only
    STATUS     current
    DESCRIPTION
            "-- empty --"
    ::= { lcsStatusWlanWIdsSigAssociatereqflood 1 }

-- {SCALAR} 1.3.6.1.4.1.2356.11.1.3.248.2.1.2
lcsStatusWlanWIdsSigAssociatereqfloodAlarmStateIfc1 OBJECT-TYPE
    SYNTAX     INTEGER {
                  eNone (0),
                  eLimitReached (1)
            }
    MAX-ACCESS read-only
    STATUS     current
    DESCRIPTION
            "-- empty --"
    ::= { lcsStatusWlanWIdsSigAssociatereqflood 2 }

-- {SCALAR} 1.3.6.1.4.1.2356.11.1.3.248.2.1.3
lcsStatusWlanWIdsSigAssociatereqfloodAlarmStateIfc2 OBJECT-TYPE
    SYNTAX     INTEGER {
                  eNone (0),
                  eLimitReached (1)
            }
    MAX-ACCESS read-only
    STATUS     current
    DESCRIPTION
            "-- empty --"
    ::= { lcsStatusWlanWIdsSigAssociatereqflood 3 }

-- {SCALAR} 1.3.6.1.4.1.2356.11.1.3.248.2.1.4
lcsStatusWlanWIdsSigAssociatereqfloodCounterIfc2 OBJECT-TYPE
    SYNTAX     Integer32 (0..2147483647)
    MAX-ACCESS read-only
    STATUS     current
    DESCRIPTION
            "-- empty --"
    ::= { lcsStatusWlanWIdsSigAssociatereqflood 4 }

-- {NODE} 1.3.6.1.4.1.2356.11.1.3.248.2.2
lcsStatusWlanWIdsSigReassociatereqflood OBJECT IDENTIFIER ::= { lcsStatusWlanWIdsSig 2 }

-- {SCALAR} 1.3.6.1.4.1.2356.11.1.3.248.2.2.1
lcsStatusWlanWIdsSigReassociatereqfloodCounterIfc1 OBJECT-TYPE
    SYNTAX     Integer32 (0..2147483647)
    MAX-ACCESS read-only
    STATUS     current
    DESCRIPTION
            "-- empty --"
    ::= { lcsStatusWlanWIdsSigReassociatereqflood 1 }

-- {SCALAR} 1.3.6.1.4.1.2356.11.1.3.248.2.2.2
lcsStatusWlanWIdsSigReassociatereqfloodAlarmStateIfc1 OBJECT-TYPE
    SYNTAX     INTEGER {
                  eNone (0),
                  eLimitReached (1)
            }
    MAX-ACCESS read-only
    STATUS     current
    DESCRIPTION
            "-- empty --"
    ::= { lcsStatusWlanWIdsSigReassociatereqflood 2 }

-- {SCALAR} 1.3.6.1.4.1.2356.11.1.3.248.2.2.3
lcsStatusWlanWIdsSigReassociatereqfloodAlarmStateIfc2 OBJECT-TYPE
    SYNTAX     INTEGER {
                  eNone (0),
                  eLimitReached (1)
            }
    MAX-ACCESS read-only
    STATUS     current
    DESCRIPTION
            "-- empty --"
    ::= { lcsStatusWlanWIdsSigReassociatereqflood 3 }

-- {SCALAR} 1.3.6.1.4.1.2356.11.1.3.248.2.2.4
lcsStatusWlanWIdsSigReassociatereqfloodCounterIfc2 OBJECT-TYPE
    SYNTAX     Integer32 (0..2147483647)
    MAX-ACCESS read-only
    STATUS     current
    DESCRIPTION
            "-- empty --"
    ::= { lcsStatusWlanWIdsSigReassociatereqflood 4 }

-- {NODE} 1.3.6.1.4.1.2356.11.1.3.248.2.3
lcsStatusWlanWIdsSigAuthenticatereqflood OBJECT IDENTIFIER ::= { lcsStatusWlanWIdsSig 3 }

-- {SCALAR} 1.3.6.1.4.1.2356.11.1.3.248.2.3.1
lcsStatusWlanWIdsSigAuthenticatereqfloodCounterIfc1 OBJECT-TYPE
    SYNTAX     Integer32 (0..2147483647)
    MAX-ACCESS read-only
    STATUS     current
    DESCRIPTION
            "-- empty --"
    ::= { lcsStatusWlanWIdsSigAuthenticatereqflood 1 }

-- {SCALAR} 1.3.6.1.4.1.2356.11.1.3.248.2.3.2
lcsStatusWlanWIdsSigAuthenticatereqfloodAlarmStateIfc1 OBJECT-TYPE
    SYNTAX     INTEGER {
                  eNone (0),
                  eLimitReached (1)
            }
    MAX-ACCESS read-only
    STATUS     current
    DESCRIPTION
            "-- empty --"
    ::= { lcsStatusWlanWIdsSigAuthenticatereqflood 2 }

-- {SCALAR} 1.3.6.1.4.1.2356.11.1.3.248.2.3.3
lcsStatusWlanWIdsSigAuthenticatereqfloodAlarmStateIfc2 OBJECT-TYPE
    SYNTAX     INTEGER {
                  eNone (0),
                  eLimitReached (1)
            }
    MAX-ACCESS read-only
    STATUS     current
    DESCRIPTION
            "-- empty --"
    ::= { lcsStatusWlanWIdsSigAuthenticatereqflood 3 }

-- {SCALAR} 1.3.6.1.4.1.2356.11.1.3.248.2.3.4
lcsStatusWlanWIdsSigAuthenticatereqfloodCounterIfc2 OBJECT-TYPE
    SYNTAX     Integer32 (0..2147483647)
    MAX-ACCESS read-only
    STATUS     current
    DESCRIPTION
            "-- empty --"
    ::= { lcsStatusWlanWIdsSigAuthenticatereqflood 4 }

-- {NODE} 1.3.6.1.4.1.2356.11.1.3.248.2.4
lcsStatusWlanWIdsSigEapolstart OBJECT IDENTIFIER ::= { lcsStatusWlanWIdsSig 4 }

-- {SCALAR} 1.3.6.1.4.1.2356.11.1.3.248.2.4.1
lcsStatusWlanWIdsSigEapolstartCounterIfc1 OBJECT-TYPE
    SYNTAX     Integer32 (0..2147483647)
    MAX-ACCESS read-only
    STATUS     current
    DESCRIPTION
            "-- empty --"
    ::= { lcsStatusWlanWIdsSigEapolstart 1 }

-- {SCALAR} 1.3.6.1.4.1.2356.11.1.3.248.2.4.2
lcsStatusWlanWIdsSigEapolstartAlarmStateIfc1 OBJECT-TYPE
    SYNTAX     INTEGER {
                  eNone (0),
                  eLimitReached (1)
            }
    MAX-ACCESS read-only
    STATUS     current
    DESCRIPTION
            "-- empty --"
    ::= { lcsStatusWlanWIdsSigEapolstart 2 }

-- {SCALAR} 1.3.6.1.4.1.2356.11.1.3.248.2.4.3
lcsStatusWlanWIdsSigEapolstartAlarmStateIfc2 OBJECT-TYPE
    SYNTAX     INTEGER {
                  eNone (0),
                  eLimitReached (1)
            }
    MAX-ACCESS read-only
    STATUS     current
    DESCRIPTION
            "-- empty --"
    ::= { lcsStatusWlanWIdsSigEapolstart 3 }

-- {SCALAR} 1.3.6.1.4.1.2356.11.1.3.248.2.4.4
lcsStatusWlanWIdsSigEapolstartCounterIfc2 OBJECT-TYPE
    SYNTAX     Integer32 (0..2147483647)
    MAX-ACCESS read-only
    STATUS     current
    DESCRIPTION
            "-- empty --"
    ::= { lcsStatusWlanWIdsSigEapolstart 4 }

-- {NODE} 1.3.6.1.4.1.2356.11.1.3.248.2.5
lcsStatusWlanWIdsSigProbebroadcast OBJECT IDENTIFIER ::= { lcsStatusWlanWIdsSig 5 }

-- {SCALAR} 1.3.6.1.4.1.2356.11.1.3.248.2.5.1
lcsStatusWlanWIdsSigProbebroadcastCounterIfc1 OBJECT-TYPE
    SYNTAX     Integer32 (0..2147483647)
    MAX-ACCESS read-only
    STATUS     current
    DESCRIPTION
            "-- empty --"
    ::= { lcsStatusWlanWIdsSigProbebroadcast 1 }

-- {SCALAR} 1.3.6.1.4.1.2356.11.1.3.248.2.5.2
lcsStatusWlanWIdsSigProbebroadcastAlarmStateIfc1 OBJECT-TYPE
    SYNTAX     INTEGER {
                  eNone (0),
                  eLimitReached (1)
            }
    MAX-ACCESS read-only
    STATUS     current
    DESCRIPTION
            "-- empty --"
    ::= { lcsStatusWlanWIdsSigProbebroadcast 2 }

-- {SCALAR} 1.3.6.1.4.1.2356.11.1.3.248.2.5.3
lcsStatusWlanWIdsSigProbebroadcastAlarmStateIfc2 OBJECT-TYPE
    SYNTAX     INTEGER {
                  eNone (0),
                  eLimitReached (1)
            }
    MAX-ACCESS read-only
    STATUS     current
    DESCRIPTION
            "-- empty --"
    ::= { lcsStatusWlanWIdsSigProbebroadcast 3 }

-- {SCALAR} 1.3.6.1.4.1.2356.11.1.3.248.2.5.4
lcsStatusWlanWIdsSigProbebroadcastCounterIfc2 OBJECT-TYPE
    SYNTAX     Integer32 (0..2147483647)
    MAX-ACCESS read-only
    STATUS     current
    DESCRIPTION
            "-- empty --"
    ::= { lcsStatusWlanWIdsSigProbebroadcast 4 }

-- {NODE} 1.3.6.1.4.1.2356.11.1.3.248.2.6
lcsStatusWlanWIdsSigDisassociatebroadcast OBJECT IDENTIFIER ::= { lcsStatusWlanWIdsSig 6 }

-- {SCALAR} 1.3.6.1.4.1.2356.11.1.3.248.2.6.1
lcsStatusWlanWIdsSigDisassociatebroadcastCounterIfc1 OBJECT-TYPE
    SYNTAX     Integer32 (0..2147483647)
    MAX-ACCESS read-only
    STATUS     current
    DESCRIPTION
            "-- empty --"
    ::= { lcsStatusWlanWIdsSigDisassociatebroadcast 1 }

-- {SCALAR} 1.3.6.1.4.1.2356.11.1.3.248.2.6.2
lcsStatusWlanWIdsSigDisassociatebroadcastAlarmStateIfc1 OBJECT-TYPE
    SYNTAX     INTEGER {
                  eNone (0),
                  eLimitReached (1)
            }
    MAX-ACCESS read-only
    STATUS     current
    DESCRIPTION
            "-- empty --"
    ::= { lcsStatusWlanWIdsSigDisassociatebroadcast 2 }

-- {SCALAR} 1.3.6.1.4.1.2356.11.1.3.248.2.6.3
lcsStatusWlanWIdsSigDisassociatebroadcastAlarmStateIfc2 OBJECT-TYPE
    SYNTAX     INTEGER {
                  eNone (0),
                  eLimitReached (1)
            }
    MAX-ACCESS read-only
    STATUS     current
    DESCRIPTION
            "-- empty --"
    ::= { lcsStatusWlanWIdsSigDisassociatebroadcast 3 }

-- {SCALAR} 1.3.6.1.4.1.2356.11.1.3.248.2.6.4
lcsStatusWlanWIdsSigDisassociatebroadcastCounterIfc2 OBJECT-TYPE
    SYNTAX     Integer32 (0..2147483647)
    MAX-ACCESS read-only
    STATUS     current
    DESCRIPTION
            "-- empty --"
    ::= { lcsStatusWlanWIdsSigDisassociatebroadcast 4 }

-- {NODE} 1.3.6.1.4.1.2356.11.1.3.248.2.7
lcsStatusWlanWIdsSigDeauthenticatebroadcast OBJECT IDENTIFIER ::= { lcsStatusWlanWIdsSig 7 }

-- {SCALAR} 1.3.6.1.4.1.2356.11.1.3.248.2.7.1
lcsStatusWlanWIdsSigDeauthenticatebroadcastCounterIfc1 OBJECT-TYPE
    SYNTAX     Integer32 (0..2147483647)
    MAX-ACCESS read-only
    STATUS     current
    DESCRIPTION
            "-- empty --"
    ::= { lcsStatusWlanWIdsSigDeauthenticatebroadcast 1 }

-- {SCALAR} 1.3.6.1.4.1.2356.11.1.3.248.2.7.2
lcsStatusWlanWIdsSigDeauthenticatebroadcastAlarmStateIfc1 OBJECT-TYPE
    SYNTAX     INTEGER {
                  eNone (0),
                  eLimitReached (1)
            }
    MAX-ACCESS read-only
    STATUS     current
    DESCRIPTION
            "-- empty --"
    ::= { lcsStatusWlanWIdsSigDeauthenticatebroadcast 2 }

-- {SCALAR} 1.3.6.1.4.1.2356.11.1.3.248.2.7.3
lcsStatusWlanWIdsSigDeauthenticatebroadcastAlarmStateIfc2 OBJECT-TYPE
    SYNTAX     INTEGER {
                  eNone (0),
                  eLimitReached (1)
            }
    MAX-ACCESS read-only
    STATUS     current
    DESCRIPTION
            "-- empty --"
    ::= { lcsStatusWlanWIdsSigDeauthenticatebroadcast 3 }

-- {SCALAR} 1.3.6.1.4.1.2356.11.1.3.248.2.7.4
lcsStatusWlanWIdsSigDeauthenticatebroadcastCounterIfc2 OBJECT-TYPE
    SYNTAX     Integer32 (0..2147483647)
    MAX-ACCESS read-only
    STATUS     current
    DESCRIPTION
            "-- empty --"
    ::= { lcsStatusWlanWIdsSigDeauthenticatebroadcast 4 }

-- {NODE} 1.3.6.1.4.1.2356.11.1.3.248.2.8
lcsStatusWlanWIdsSigDisassociatereqflood OBJECT IDENTIFIER ::= { lcsStatusWlanWIdsSig 8 }

-- {SCALAR} 1.3.6.1.4.1.2356.11.1.3.248.2.8.1
lcsStatusWlanWIdsSigDisassociatereqfloodCounterIfc1 OBJECT-TYPE
    SYNTAX     Integer32 (0..2147483647)
    MAX-ACCESS read-only
    STATUS     current
    DESCRIPTION
            "-- empty --"
    ::= { lcsStatusWlanWIdsSigDisassociatereqflood 1 }

-- {SCALAR} 1.3.6.1.4.1.2356.11.1.3.248.2.8.2
lcsStatusWlanWIdsSigDisassociatereqfloodAlarmStateIfc1 OBJECT-TYPE
    SYNTAX     INTEGER {
                  eNone (0),
                  eLimitReached (1)
            }
    MAX-ACCESS read-only
    STATUS     current
    DESCRIPTION
            "-- empty --"
    ::= { lcsStatusWlanWIdsSigDisassociatereqflood 2 }

-- {SCALAR} 1.3.6.1.4.1.2356.11.1.3.248.2.8.3
lcsStatusWlanWIdsSigDisassociatereqfloodAlarmStateIfc2 OBJECT-TYPE
    SYNTAX     INTEGER {
                  eNone (0),
                  eLimitReached (1)
            }
    MAX-ACCESS read-only
    STATUS     current
    DESCRIPTION
            "-- empty --"
    ::= { lcsStatusWlanWIdsSigDisassociatereqflood 3 }

-- {SCALAR} 1.3.6.1.4.1.2356.11.1.3.248.2.8.4
lcsStatusWlanWIdsSigDisassociatereqfloodCounterIfc2 OBJECT-TYPE
    SYNTAX     Integer32 (0..2147483647)
    MAX-ACCESS read-only
    STATUS     current
    DESCRIPTION
            "-- empty --"
    ::= { lcsStatusWlanWIdsSigDisassociatereqflood 4 }

-- {NODE} 1.3.6.1.4.1.2356.11.1.3.248.2.9
lcsStatusWlanWIdsSigBlockackoutofwindow OBJECT IDENTIFIER ::= { lcsStatusWlanWIdsSig 9 }

-- {SCALAR} 1.3.6.1.4.1.2356.11.1.3.248.2.9.1
lcsStatusWlanWIdsSigBlockackoutofwindowCounterIfc1 OBJECT-TYPE
    SYNTAX     Integer32 (0..2147483647)
    MAX-ACCESS read-only
    STATUS     current
    DESCRIPTION
            "-- empty --"
    ::= { lcsStatusWlanWIdsSigBlockackoutofwindow 1 }

-- {SCALAR} 1.3.6.1.4.1.2356.11.1.3.248.2.9.2
lcsStatusWlanWIdsSigBlockackoutofwindowAlarmStateIfc1 OBJECT-TYPE
    SYNTAX     INTEGER {
                  eNone (0),
                  eLimitReached (1)
            }
    MAX-ACCESS read-only
    STATUS     current
    DESCRIPTION
            "-- empty --"
    ::= { lcsStatusWlanWIdsSigBlockackoutofwindow 2 }

-- {SCALAR} 1.3.6.1.4.1.2356.11.1.3.248.2.9.3
lcsStatusWlanWIdsSigBlockackoutofwindowAlarmStateIfc2 OBJECT-TYPE
    SYNTAX     INTEGER {
                  eNone (0),
                  eLimitReached (1)
            }
    MAX-ACCESS read-only
    STATUS     current
    DESCRIPTION
            "-- empty --"
    ::= { lcsStatusWlanWIdsSigBlockackoutofwindow 3 }

-- {SCALAR} 1.3.6.1.4.1.2356.11.1.3.248.2.9.4
lcsStatusWlanWIdsSigBlockackoutofwindowCounterIfc2 OBJECT-TYPE
    SYNTAX     Integer32 (0..2147483647)
    MAX-ACCESS read-only
    STATUS     current
    DESCRIPTION
            "-- empty --"
    ::= { lcsStatusWlanWIdsSigBlockackoutofwindow 4 }

-- {NODE} 1.3.6.1.4.1.2356.11.1.3.248.2.10
lcsStatusWlanWIdsSigBlockackafterdelba OBJECT IDENTIFIER ::= { lcsStatusWlanWIdsSig 10 }

-- {SCALAR} 1.3.6.1.4.1.2356.11.1.3.248.2.10.1
lcsStatusWlanWIdsSigBlockackafterdelbaCounterIfc1 OBJECT-TYPE
    SYNTAX     Integer32 (0..2147483647)
    MAX-ACCESS read-only
    STATUS     current
    DESCRIPTION
            "-- empty --"
    ::= { lcsStatusWlanWIdsSigBlockackafterdelba 1 }

-- {SCALAR} 1.3.6.1.4.1.2356.11.1.3.248.2.10.2
lcsStatusWlanWIdsSigBlockackafterdelbaAlarmStateIfc1 OBJECT-TYPE
    SYNTAX     INTEGER {
                  eNone (0),
                  eLimitReached (1)
            }
    MAX-ACCESS read-only
    STATUS     current
    DESCRIPTION
            "-- empty --"
    ::= { lcsStatusWlanWIdsSigBlockackafterdelba 2 }

-- {SCALAR} 1.3.6.1.4.1.2356.11.1.3.248.2.10.3
lcsStatusWlanWIdsSigBlockackafterdelbaAlarmStateIfc2 OBJECT-TYPE
    SYNTAX     INTEGER {
                  eNone (0),
                  eLimitReached (1)
            }
    MAX-ACCESS read-only
    STATUS     current
    DESCRIPTION
            "-- empty --"
    ::= { lcsStatusWlanWIdsSigBlockackafterdelba 3 }

-- {SCALAR} 1.3.6.1.4.1.2356.11.1.3.248.2.10.4
lcsStatusWlanWIdsSigBlockackafterdelbaCounterIfc2 OBJECT-TYPE
    SYNTAX     Integer32 (0..2147483647)
    MAX-ACCESS read-only
    STATUS     current
    DESCRIPTION
            "-- empty --"
    ::= { lcsStatusWlanWIdsSigBlockackafterdelba 4 }

-- {NODE} 1.3.6.1.4.1.2356.11.1.3.248.2.11
lcsStatusWlanWIdsSigNulldataflood OBJECT IDENTIFIER ::= { lcsStatusWlanWIdsSig 11 }

-- {SCALAR} 1.3.6.1.4.1.2356.11.1.3.248.2.11.1
lcsStatusWlanWIdsSigNulldatafloodCounterIfc1 OBJECT-TYPE
    SYNTAX     Integer32 (0..2147483647)
    MAX-ACCESS read-only
    STATUS     current
    DESCRIPTION
            "-- empty --"
    ::= { lcsStatusWlanWIdsSigNulldataflood 1 }

-- {SCALAR} 1.3.6.1.4.1.2356.11.1.3.248.2.11.2
lcsStatusWlanWIdsSigNulldatafloodAlarmStateIfc1 OBJECT-TYPE
    SYNTAX     INTEGER {
                  eNone (0),
                  eLimitReached (1)
            }
    MAX-ACCESS read-only
    STATUS     current
    DESCRIPTION
            "-- empty --"
    ::= { lcsStatusWlanWIdsSigNulldataflood 2 }

-- {SCALAR} 1.3.6.1.4.1.2356.11.1.3.248.2.11.3
lcsStatusWlanWIdsSigNulldatafloodAlarmStateIfc2 OBJECT-TYPE
    SYNTAX     INTEGER {
                  eNone (0),
                  eLimitReached (1)
            }
    MAX-ACCESS read-only
    STATUS     current
    DESCRIPTION
            "-- empty --"
    ::= { lcsStatusWlanWIdsSigNulldataflood 3 }

-- {SCALAR} 1.3.6.1.4.1.2356.11.1.3.248.2.11.4
lcsStatusWlanWIdsSigNulldatafloodCounterIfc2 OBJECT-TYPE
    SYNTAX     Integer32 (0..2147483647)
    MAX-ACCESS read-only
    STATUS     current
    DESCRIPTION
            "-- empty --"
    ::= { lcsStatusWlanWIdsSigNulldataflood 4 }

-- {NODE} 1.3.6.1.4.1.2356.11.1.3.248.2.12
lcsStatusWlanWIdsSigNullDataPSOv OBJECT IDENTIFIER ::= { lcsStatusWlanWIdsSig 12 }

-- {SCALAR} 1.3.6.1.4.1.2356.11.1.3.248.2.12.1
lcsStatusWlanWIdsSigNullDataPSOvCounterIfc1 OBJECT-TYPE
    SYNTAX     Integer32 (0..2147483647)
    MAX-ACCESS read-only
    STATUS     current
    DESCRIPTION
            "-- empty --"
    ::= { lcsStatusWlanWIdsSigNullDataPSOv 1 }

-- {SCALAR} 1.3.6.1.4.1.2356.11.1.3.248.2.12.2
lcsStatusWlanWIdsSigNullDataPSOvAlarmStateIfc1 OBJECT-TYPE
    SYNTAX     INTEGER {
                  eNone (0),
                  eLimitReached (1)
            }
    MAX-ACCESS read-only
    STATUS     current
    DESCRIPTION
            "-- empty --"
    ::= { lcsStatusWlanWIdsSigNullDataPSOv 2 }

-- {SCALAR} 1.3.6.1.4.1.2356.11.1.3.248.2.12.3
lcsStatusWlanWIdsSigNullDataPSOvAlarmStateIfc2 OBJECT-TYPE
    SYNTAX     INTEGER {
                  eNone (0),
                  eLimitReached (1)
            }
    MAX-ACCESS read-only
    STATUS     current
    DESCRIPTION
            "-- empty --"
    ::= { lcsStatusWlanWIdsSigNullDataPSOv 3 }

-- {SCALAR} 1.3.6.1.4.1.2356.11.1.3.248.2.12.4
lcsStatusWlanWIdsSigNullDataPSOvCounterIfc2 OBJECT-TYPE
    SYNTAX     Integer32 (0..2147483647)
    MAX-ACCESS read-only
    STATUS     current
    DESCRIPTION
            "-- empty --"
    ::= { lcsStatusWlanWIdsSigNullDataPSOv 4 }

-- {NODE} 1.3.6.1.4.1.2356.11.1.3.248.2.13
lcsStatusWlanWIdsSigPspolltiminterval OBJECT IDENTIFIER ::= { lcsStatusWlanWIdsSig 13 }

-- {SCALAR} 1.3.6.1.4.1.2356.11.1.3.248.2.13.1
lcsStatusWlanWIdsSigPspolltimintervalCounterIfc1 OBJECT-TYPE
    SYNTAX     Integer32 (0..2147483647)
    MAX-ACCESS read-only
    STATUS     current
    DESCRIPTION
            "-- empty --"
    ::= { lcsStatusWlanWIdsSigPspolltiminterval 1 }

-- {SCALAR} 1.3.6.1.4.1.2356.11.1.3.248.2.13.2
lcsStatusWlanWIdsSigPspolltimintervalAlarmStateIfc1 OBJECT-TYPE
    SYNTAX     INTEGER {
                  eNone (0),
                  eLimitReached (1)
            }
    MAX-ACCESS read-only
    STATUS     current
    DESCRIPTION
            "-- empty --"
    ::= { lcsStatusWlanWIdsSigPspolltiminterval 2 }

-- {SCALAR} 1.3.6.1.4.1.2356.11.1.3.248.2.13.3
lcsStatusWlanWIdsSigPspolltimintervalAlarmStateIfc2 OBJECT-TYPE
    SYNTAX     INTEGER {
                  eNone (0),
                  eLimitReached (1)
            }
    MAX-ACCESS read-only
    STATUS     current
    DESCRIPTION
            "-- empty --"
    ::= { lcsStatusWlanWIdsSigPspolltiminterval 3 }

-- {SCALAR} 1.3.6.1.4.1.2356.11.1.3.248.2.13.4
lcsStatusWlanWIdsSigPspolltimintervalCounterIfc2 OBJECT-TYPE
    SYNTAX     Integer32 (0..2147483647)
    MAX-ACCESS read-only
    STATUS     current
    DESCRIPTION
            "-- empty --"
    ::= { lcsStatusWlanWIdsSigPspolltiminterval 4 }

-- {NODE} 1.3.6.1.4.1.2356.11.1.3.248.2.14
lcsStatusWlanWIdsSigSmpsmultistream OBJECT IDENTIFIER ::= { lcsStatusWlanWIdsSig 14 }

-- {SCALAR} 1.3.6.1.4.1.2356.11.1.3.248.2.14.1
lcsStatusWlanWIdsSigSmpsmultistreamCounterIfc1 OBJECT-TYPE
    SYNTAX     Integer32 (0..2147483647)
    MAX-ACCESS read-only
    STATUS     current
    DESCRIPTION
            "-- empty --"
    ::= { lcsStatusWlanWIdsSigSmpsmultistream 1 }

-- {SCALAR} 1.3.6.1.4.1.2356.11.1.3.248.2.14.2
lcsStatusWlanWIdsSigSmpsmultistreamAlarmStateIfc1 OBJECT-TYPE
    SYNTAX     INTEGER {
                  eNone (0),
                  eLimitReached (1)
            }
    MAX-ACCESS read-only
    STATUS     current
    DESCRIPTION
            "-- empty --"
    ::= { lcsStatusWlanWIdsSigSmpsmultistream 2 }

-- {SCALAR} 1.3.6.1.4.1.2356.11.1.3.248.2.14.3
lcsStatusWlanWIdsSigSmpsmultistreamAlarmStateIfc2 OBJECT-TYPE
    SYNTAX     INTEGER {
                  eNone (0),
                  eLimitReached (1)
            }
    MAX-ACCESS read-only
    STATUS     current
    DESCRIPTION
            "-- empty --"
    ::= { lcsStatusWlanWIdsSigSmpsmultistream 3 }

-- {SCALAR} 1.3.6.1.4.1.2356.11.1.3.248.2.14.4
lcsStatusWlanWIdsSigSmpsmultistreamCounterIfc2 OBJECT-TYPE
    SYNTAX     Integer32 (0..2147483647)
    MAX-ACCESS read-only
    STATUS     current
    DESCRIPTION
            "-- empty --"
    ::= { lcsStatusWlanWIdsSigSmpsmultistream 4 }

-- {NODE} 1.3.6.1.4.1.2356.11.1.3.248.2.15
lcsStatusWlanWIdsSigDeauthenticatereqflood OBJECT IDENTIFIER ::= { lcsStatusWlanWIdsSig 15 }

-- {SCALAR} 1.3.6.1.4.1.2356.11.1.3.248.2.15.1
lcsStatusWlanWIdsSigDeauthenticatereqfloodCounterIfc1 OBJECT-TYPE
    SYNTAX     Integer32 (0..2147483647)
    MAX-ACCESS read-only
    STATUS     current
    DESCRIPTION
            "-- empty --"
    ::= { lcsStatusWlanWIdsSigDeauthenticatereqflood 1 }

-- {SCALAR} 1.3.6.1.4.1.2356.11.1.3.248.2.15.2
lcsStatusWlanWIdsSigDeauthenticatereqfloodAlarmStateIfc1 OBJECT-TYPE
    SYNTAX     INTEGER {
                  eNone (0),
                  eLimitReached (1)
            }
    MAX-ACCESS read-only
    STATUS     current
    DESCRIPTION
            "-- empty --"
    ::= { lcsStatusWlanWIdsSigDeauthenticatereqflood 2 }

-- {SCALAR} 1.3.6.1.4.1.2356.11.1.3.248.2.15.3
lcsStatusWlanWIdsSigDeauthenticatereqfloodAlarmStateIfc2 OBJECT-TYPE
    SYNTAX     INTEGER {
                  eNone (0),
                  eLimitReached (1)
            }
    MAX-ACCESS read-only
    STATUS     current
    DESCRIPTION
            "-- empty --"
    ::= { lcsStatusWlanWIdsSigDeauthenticatereqflood 3 }

-- {SCALAR} 1.3.6.1.4.1.2356.11.1.3.248.2.15.4
lcsStatusWlanWIdsSigDeauthenticatereqfloodCounterIfc2 OBJECT-TYPE
    SYNTAX     Integer32 (0..2147483647)
    MAX-ACCESS read-only
    STATUS     current
    DESCRIPTION
            "-- empty --"
    ::= { lcsStatusWlanWIdsSigDeauthenticatereqflood 4 }

-- {NODE} 1.3.6.1.4.1.2356.11.1.3.248.2.16
lcsStatusWlanWIdsSigPrematureeapolsuccess OBJECT IDENTIFIER ::= { lcsStatusWlanWIdsSig 16 }

-- {SCALAR} 1.3.6.1.4.1.2356.11.1.3.248.2.16.1
lcsStatusWlanWIdsSigPrematureeapolsuccessCounterIfc1 OBJECT-TYPE
    SYNTAX     Integer32 (0..2147483647)
    MAX-ACCESS read-only
    STATUS     current
    DESCRIPTION
            "-- empty --"
    ::= { lcsStatusWlanWIdsSigPrematureeapolsuccess 1 }

-- {SCALAR} 1.3.6.1.4.1.2356.11.1.3.248.2.16.2
lcsStatusWlanWIdsSigPrematureeapolsuccessAlarmStateIfc1 OBJECT-TYPE
    SYNTAX     INTEGER {
                  eNone (0),
                  eLimitReached (1)
            }
    MAX-ACCESS read-only
    STATUS     current
    DESCRIPTION
            "-- empty --"
    ::= { lcsStatusWlanWIdsSigPrematureeapolsuccess 2 }

-- {SCALAR} 1.3.6.1.4.1.2356.11.1.3.248.2.16.3
lcsStatusWlanWIdsSigPrematureeapolsuccessAlarmStateIfc2 OBJECT-TYPE
    SYNTAX     INTEGER {
                  eNone (0),
                  eLimitReached (1)
            }
    MAX-ACCESS read-only
    STATUS     current
    DESCRIPTION
            "-- empty --"
    ::= { lcsStatusWlanWIdsSigPrematureeapolsuccess 3 }

-- {SCALAR} 1.3.6.1.4.1.2356.11.1.3.248.2.16.4
lcsStatusWlanWIdsSigPrematureeapolsuccessCounterIfc2 OBJECT-TYPE
    SYNTAX     Integer32 (0..2147483647)
    MAX-ACCESS read-only
    STATUS     current
    DESCRIPTION
            "-- empty --"
    ::= { lcsStatusWlanWIdsSigPrematureeapolsuccess 4 }

-- {NODE} 1.3.6.1.4.1.2356.11.1.3.248.2.17
lcsStatusWlanWIdsSigPrematureeapolfailure OBJECT IDENTIFIER ::= { lcsStatusWlanWIdsSig 17 }

-- {SCALAR} 1.3.6.1.4.1.2356.11.1.3.248.2.17.1
lcsStatusWlanWIdsSigPrematureeapolfailureCounterIfc1 OBJECT-TYPE
    SYNTAX     Integer32 (0..2147483647)
    MAX-ACCESS read-only
    STATUS     current
    DESCRIPTION
            "-- empty --"
    ::= { lcsStatusWlanWIdsSigPrematureeapolfailure 1 }

-- {SCALAR} 1.3.6.1.4.1.2356.11.1.3.248.2.17.2
lcsStatusWlanWIdsSigPrematureeapolfailureAlarmStateIfc1 OBJECT-TYPE
    SYNTAX     INTEGER {
                  eNone (0),
                  eLimitReached (1)
            }
    MAX-ACCESS read-only
    STATUS     current
    DESCRIPTION
            "-- empty --"
    ::= { lcsStatusWlanWIdsSigPrematureeapolfailure 2 }

-- {SCALAR} 1.3.6.1.4.1.2356.11.1.3.248.2.17.3
lcsStatusWlanWIdsSigPrematureeapolfailureAlarmStateIfc2 OBJECT-TYPE
    SYNTAX     INTEGER {
                  eNone (0),
                  eLimitReached (1)
            }
    MAX-ACCESS read-only
    STATUS     current
    DESCRIPTION
            "-- empty --"
    ::= { lcsStatusWlanWIdsSigPrematureeapolfailure 3 }

-- {SCALAR} 1.3.6.1.4.1.2356.11.1.3.248.2.17.4
lcsStatusWlanWIdsSigPrematureeapolfailureCounterIfc2 OBJECT-TYPE
    SYNTAX     Integer32 (0..2147483647)
    MAX-ACCESS read-only
    STATUS     current
    DESCRIPTION
            "-- empty --"
    ::= { lcsStatusWlanWIdsSigPrematureeapolfailure 4 }

-- {NODE} 1.3.6.1.4.1.2356.11.1.4
lcsStatusWan OBJECT IDENTIFIER ::= { lcsStatus 4 }

-- {TABLE} 1.3.6.1.4.1.2356.11.1.4.1
lcsStatusWanByteTransportTable OBJECT-TYPE
    SYNTAX     SEQUENCE OF LcsStatusWanByteTransportEntry
    MAX-ACCESS not-accessible
    STATUS     current
    DESCRIPTION
            ""
    ::= { lcsStatusWan 1 }

-- {ROW} 1.3.6.1.4.1.2356.11.1.4.1.1
lcsStatusWanByteTransportEntry OBJECT-TYPE
    SYNTAX     LcsStatusWanByteTransportEntry
    MAX-ACCESS not-accessible
    STATUS     current
    DESCRIPTION
            ""
    INDEX {
            lcsStatusWanByteTransportEntryIfc
          }
    ::= { lcsStatusWanByteTransportTable 1 }

LcsStatusWanByteTransportEntry ::= SEQUENCE {
            lcsStatusWanByteTransportEntryIfc INTEGER,
            lcsStatusWanByteTransportEntryCrxBytes Counter32,
            lcsStatusWanByteTransportEntryRxBytes Counter32,
            lcsStatusWanByteTransportEntryTxBytes Counter32,
            lcsStatusWanByteTransportEntryCtxBytes Counter32,
            lcsStatusWanByteTransportEntryHRxBytes Counter64,
            lcsStatusWanByteTransportEntryHTxBytes Counter64
    }

-- {COLUMN} 1.3.6.1.4.1.2356.11.1.4.1.1.1
lcsStatusWanByteTransportEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusWanByteTransportEntry 1 }

-- {COLUMN} 1.3.6.1.4.1.2356.11.1.4.1.1.2
lcsStatusWanByteTransportEntryCrxBytes OBJECT-TYPE
    SYNTAX     Counter32
    MAX-ACCESS read-only
    STATUS     current
    DESCRIPTION
            ""
    ::= { lcsStatusWanByteTransportEntry 2 }

-- {COLUMN} 1.3.6.1.4.1.2356.11.1.4.1.1.3
lcsStatusWanByteTransportEntryRxBytes OBJECT-TYPE
    SYNTAX     Counter32
    MAX-ACCESS read-only
    STATUS     current
    DESCRIPTION
            ""
    ::= { lcsStatusWanByteTransportEntry 3 }

-- {COLUMN} 1.3.6.1.4.1.2356.11.1.4.1.1.4
lcsStatusWanByteTransportEntryTxBytes OBJECT-TYPE
    SYNTAX     Counter32
    MAX-ACCESS read-only
    STATUS     current
    DESCRIPTION
            ""
    ::= { lcsStatusWanByteTransportEntry 4 }

-- {COLUMN} 1.3.6.1.4.1.2356.11.1.4.1.1.5
lcsStatusWanByteTransportEntryCtxBytes OBJECT-TYPE
    SYNTAX     Counter32
    MAX-ACCESS read-only
    STATUS     current
    DESCRIPTION
            ""
    ::= { lcsStatusWanByteTransportEntry 5 }

-- {COLUMN} 1.3.6.1.4.1.2356.11.1.4.1.1.6
lcsStatusWanByteTransportEntryHRxBytes OBJECT-TYPE
    SYNTAX     Counter64
    MAX-ACCESS read-only
    STATUS     current
    DESCRIPTION
            ""
    ::= { lcsStatusWanByteTransportEntry 6 }

-- {COLUMN} 1.3.6.1.4.1.2356.11.1.4.1.1.7
lcsStatusWanByteTransportEntryHTxBytes OBJECT-TYPE
    SYNTAX     Counter64
    MAX-ACCESS read-only
    STATUS     current
    DESCRIPTION
            ""
    ::= { lcsStatusWanByteTransportEntry 7 }

-- {TABLE} 1.3.6.1.4.1.2356.11.1.4.2
lcsStatusWanPacketTransportTable OBJECT-TYPE
    SYNTAX     SEQUENCE OF LcsStatusWanPacketTransportEntry
    MAX-ACCESS not-accessible
    STATUS     current
    DESCRIPTION
            ""
    ::= { lcsStatusWan 2 }

-- {ROW} 1.3.6.1.4.1.2356.11.1.4.2.1
lcsStatusWanPacketTransportEntry OBJECT-TYPE
    SYNTAX     LcsStatusWanPacketTransportEntry
    MAX-ACCESS not-accessible
    STATUS     current
    DESCRIPTION
            ""
    INDEX {
            lcsStatusWanPacketTransportEntryIfc
          }
    ::= { lcsStatusWanPacketTransportTable 1 }

LcsStatusWanPacketTransportEntry ::= SEQUENCE {
            lcsStatusWanPacketTransportEntryIfc INTEGER,
            lcsStatusWanPacketTransportEntryRx Counter32,
            lcsStatusWanPacketTransportEntryTxTotal Counter32,
            lcsStatusWanPacketTransportEntryTxNormal Counter32,
            lcsStatusWanPacketTransportEntryTxReliable Counter32,
            lcsStatusWanPacketTransportEntryTxUrgent Counter32
    }

-- {COLUMN} 1.3.6.1.4.1.2356.11.1.4.2.1.1
lcsStatusWanPacketTransportEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusWanPacketTransportEntry 1 }

-- {COLUMN} 1.3.6.1.4.1.2356.11.1.4.2.1.2
lcsStatusWanPacketTransportEntryRx OBJECT-TYPE
    SYNTAX     Counter32
    MAX-ACCESS read-only
    STATUS     current
    DESCRIPTION
            ""
    ::= { lcsStatusWanPacketTransportEntry 2 }

-- {COLUMN} 1.3.6.1.4.1.2356.11.1.4.2.1.3
lcsStatusWanPacketTransportEntryTxTotal OBJECT-TYPE
    SYNTAX     Counter32
    MAX-ACCESS read-only
    STATUS     current
    DESCRIPTION
            ""
    ::= { lcsStatusWanPacketTransportEntry 3 }

-- {COLUMN} 1.3.6.1.4.1.2356.11.1.4.2.1.4
lcsStatusWanPacketTransportEntryTxNormal OBJECT-TYPE
    SYNTAX     Counter32
    MAX-ACCESS read-only
    STATUS     current
    DESCRIPTION
            ""
    ::= { lcsStatusWanPacketTransportEntry 4 }

-- {COLUMN} 1.3.6.1.4.1.2356.11.1.4.2.1.5
lcsStatusWanPacketTransportEntryTxReliable OBJECT-TYPE
    SYNTAX     Counter32
    MAX-ACCESS read-only
    STATUS     current
    DESCRIPTION
            ""
    ::= { lcsStatusWanPacketTransportEntry 5 }

-- {COLUMN} 1.3.6.1.4.1.2356.11.1.4.2.1.6
lcsStatusWanPacketTransportEntryTxUrgent OBJECT-TYPE
    SYNTAX     Counter32
    MAX-ACCESS read-only
    STATUS     current
    DESCRIPTION
            ""
    ::= { lcsStatusWanPacketTransportEntry 6 }

-- {TABLE} 1.3.6.1.4.1.2356.11.1.4.3
lcsStatusWanErrorsTable OBJECT-TYPE
    SYNTAX     SEQUENCE OF LcsStatusWanErrorsEntry
    MAX-ACCESS not-accessible
    STATUS     current
    DESCRIPTION
            ""
    ::= { lcsStatusWan 3 }

-- {ROW} 1.3.6.1.4.1.2356.11.1.4.3.1
lcsStatusWanErrorsEntry OBJECT-TYPE
    SYNTAX     LcsStatusWanErrorsEntry
    MAX-ACCESS not-accessible
    STATUS     current
    DESCRIPTION
            ""
    INDEX {
            lcsStatusWanErrorsEntryIfc
          }
    ::= { lcsStatusWanErrorsTable 1 }

LcsStatusWanErrorsEntry ::= SEQUENCE {
            lcsStatusWanErrorsEntryIfc INTEGER,
            lcsStatusWanErrorsEntryRxL1Error Counter32,
            lcsStatusWanErrorsEntryRxL2Error Counter32,
            lcsStatusWanErrorsEntryRxL3Error Counter32,
            lcsStatusWanErrorsEntryStackError Counter32,
            lcsStatusWanErrorsEntryTxError Counter32,
            lcsStatusWanErrorsEntryQueueErrors Counter32
    }

-- {COLUMN} 1.3.6.1.4.1.2356.11.1.4.3.1.1
lcsStatusWanErrorsEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusWanErrorsEntry 1 }

-- {COLUMN} 1.3.6.1.4.1.2356.11.1.4.3.1.2
lcsStatusWanErrorsEntryRxL1Error OBJECT-TYPE
    SYNTAX     Counter32
    MAX-ACCESS read-only
    STATUS     current
    DESCRIPTION
            ""
    ::= { lcsStatusWanErrorsEntry 2 }

-- {COLUMN} 1.3.6.1.4.1.2356.11.1.4.3.1.3
lcsStatusWanErrorsEntryRxL2Error OBJECT-TYPE
    SYNTAX     Counter32
    MAX-ACCESS read-only
    STATUS     current
    DESCRIPTION
            ""
    ::= { lcsStatusWanErrorsEntry 3 }

-- {COLUMN} 1.3.6.1.4.1.2356.11.1.4.3.1.4
lcsStatusWanErrorsEntryRxL3Error OBJECT-TYPE
    SYNTAX     Counter32
    MAX-ACCESS read-only
    STATUS     current
    DESCRIPTION
            ""
    ::= { lcsStatusWanErrorsEntry 4 }

-- {COLUMN} 1.3.6.1.4.1.2356.11.1.4.3.1.5
lcsStatusWanErrorsEntryStackError OBJECT-TYPE
    SYNTAX     Counter32
    MAX-ACCESS read-only
    STATUS     current
    DESCRIPTION
            ""
    ::= { lcsStatusWanErrorsEntry 5 }

-- {COLUMN} 1.3.6.1.4.1.2356.11.1.4.3.1.6
lcsStatusWanErrorsEntryTxError OBJECT-TYPE
    SYNTAX     Counter32
    MAX-ACCESS read-only
    STATUS     current
    DESCRIPTION
            ""
    ::= { lcsStatusWanErrorsEntry 6 }

-- {COLUMN} 1.3.6.1.4.1.2356.11.1.4.3.1.7
lcsStatusWanErrorsEntryQueueErrors OBJECT-TYPE
    SYNTAX     Counter32
    MAX-ACCESS read-only
    STATUS     current
    DESCRIPTION
            ""
    ::= { lcsStatusWanErrorsEntry 7 }

-- {SCALAR} 1.3.6.1.4.1.2356.11.1.4.4
lcsStatusWanWanTxDiscarded OBJECT-TYPE
    SYNTAX     Counter32
    MAX-ACCESS read-only
    STATUS     current
    DESCRIPTION
            ""
    ::= { lcsStatusWan 4 }

-- {SCALAR} 1.3.6.1.4.1.2356.11.1.4.5
lcsStatusWanWanHeapPackets OBJECT-TYPE
    SYNTAX     Integer32 (0..2147483647)
    MAX-ACCESS read-only
    STATUS     current
    DESCRIPTION
            ""
    ::= { lcsStatusWan 5 }

-- {SCALAR} 1.3.6.1.4.1.2356.11.1.4.6
lcsStatusWanWanQueuePackets OBJECT-TYPE
    SYNTAX     Integer32 (0..2147483647)
    MAX-ACCESS read-only
    STATUS     current
    DESCRIPTION
            ""
    ::= { lcsStatusWan 6 }

-- {SCALAR} 1.3.6.1.4.1.2356.11.1.4.7
lcsStatusWanWanQueueErrors OBJECT-TYPE
    SYNTAX     Counter32
    MAX-ACCESS read-only
    STATUS     current
    DESCRIPTION
            ""
    ::= { lcsStatusWan 7 }

-- {TABLE} 1.3.6.1.4.1.2356.11.1.4.8
lcsStatusWanThroughputTable OBJECT-TYPE
    SYNTAX     SEQUENCE OF LcsStatusWanThroughputEntry
    MAX-ACCESS not-accessible
    STATUS     current
    DESCRIPTION
            ""
    ::= { lcsStatusWan 8 }

-- {ROW} 1.3.6.1.4.1.2356.11.1.4.8.1
lcsStatusWanThroughputEntry OBJECT-TYPE
    SYNTAX     LcsStatusWanThroughputEntry
    MAX-ACCESS not-accessible
    STATUS     current
    DESCRIPTION
            ""
    INDEX {
            lcsStatusWanThroughputEntryIfc
          }
    ::= { lcsStatusWanThroughputTable 1 }

LcsStatusWanThroughputEntry ::= SEQUENCE {
            lcsStatusWanThroughputEntryIfc INTEGER,
            lcsStatusWanThroughputEntryRxSCurrent Integer32,
            lcsStatusWanThroughputEntryTxSCurrent Integer32,
            lcsStatusWanThroughputEntryRxSAverage Integer32,
            lcsStatusWanThroughputEntryTxSAverage Integer32
    }

-- {COLUMN} 1.3.6.1.4.1.2356.11.1.4.8.1.1
lcsStatusWanThroughputEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusWanThroughputEntry 1 }

-- {COLUMN} 1.3.6.1.4.1.2356.11.1.4.8.1.2
lcsStatusWanThroughputEntryRxSCurrent OBJECT-TYPE
    SYNTAX     Integer32 (0..2147483647)
    MAX-ACCESS read-only
    STATUS     current
    DESCRIPTION
            ""
    ::= { lcsStatusWanThroughputEntry 2 }

-- {COLUMN} 1.3.6.1.4.1.2356.11.1.4.8.1.3
lcsStatusWanThroughputEntryTxSCurrent OBJECT-TYPE
    SYNTAX     Integer32 (0..2147483647)
    MAX-ACCESS read-only
    STATUS     current
    DESCRIPTION
            ""
    ::= { lcsStatusWanThroughputEntry 3 }

-- {COLUMN} 1.3.6.1.4.1.2356.11.1.4.8.1.4
lcsStatusWanThroughputEntryRxSAverage OBJECT-TYPE
    SYNTAX     Integer32 (0..2147483647)
    MAX-ACCESS read-only
    STATUS     current
    DESCRIPTION
            ""
    ::= { lcsStatusWanThroughputEntry 4 }

-- {COLUMN} 1.3.6.1.4.1.2356.11.1.4.8.1.5
lcsStatusWanThroughputEntryTxSAverage OBJECT-TYPE
    SYNTAX     Integer32 (0..2147483647)
    MAX-ACCESS read-only
    STATUS     current
    DESCRIPTION
            ""
    ::= { lcsStatusWanThroughputEntry 5 }

-- {SCALAR} 1.3.6.1.4.1.2356.11.1.4.9
lcsStatusWanDeleteValues OBJECT-TYPE
    SYNTAX     DisplayString
    MAX-ACCESS read-write
    STATUS     current
    DESCRIPTION
            ""
    ::= { lcsStatusWan 9 }

-- {SCALAR} 1.3.6.1.4.1.2356.11.1.4.10
lcsStatusWanConnections OBJECT-TYPE
    SYNTAX     Integer32 (0..2147483647)
    MAX-ACCESS read-only
    STATUS     current
    DESCRIPTION
            ""
    ::= { lcsStatusWan 10 }

-- {TABLE} 1.3.6.1.4.1.2356.11.1.4.11
lcsStatusWanMtuTable OBJECT-TYPE
    SYNTAX     SEQUENCE OF LcsStatusWanMtuEntry
    MAX-ACCESS not-accessible
    STATUS     current
    DESCRIPTION
            ""
    ::= { lcsStatusWan 11 }

-- {ROW} 1.3.6.1.4.1.2356.11.1.4.11.1
lcsStatusWanMtuEntry OBJECT-TYPE
    SYNTAX     LcsStatusWanMtuEntry
    MAX-ACCESS not-accessible
    STATUS     current
    DESCRIPTION
            ""
    INDEX {
            lcsStatusWanMtuEntryPeer
          }
    ::= { lcsStatusWanMtuTable 1 }

LcsStatusWanMtuEntry ::= SEQUENCE {
            lcsStatusWanMtuEntryPeer DisplayString,
            lcsStatusWanMtuEntryMtu Integer32
    }

-- {COLUMN} 1.3.6.1.4.1.2356.11.1.4.11.1.1
lcsStatusWanMtuEntryPeer OBJECT-TYPE
    SYNTAX     DisplayString (SIZE(0..16))
    MAX-ACCESS read-only
    STATUS     current
    DESCRIPTION
            ""
    ::= { lcsStatusWanMtuEntry 1 }

-- {COLUMN} 1.3.6.1.4.1.2356.11.1.4.11.1.2
lcsStatusWanMtuEntryMtu OBJECT-TYPE
    SYNTAX     Integer32 (0..65535)
    MAX-ACCESS read-only
    STATUS     current
    DESCRIPTION
            ""
    ::= { lcsStatusWanMtuEntry 2 }

-- {SCALAR} 1.3.6.1.4.1.2356.11.1.4.12
lcsStatusWanEncryptedConnections OBJECT-TYPE
    SYNTAX     Integer32 (0..2147483647)
    MAX-ACCESS read-only
    STATUS     current
    DESCRIPTION
            "-- empty --"
    ::= { lcsStatusWan 12 }

-- {NODE} 1.3.6.1.4.1.2356.11.1.4.13
lcsStatusWanIpAddresses OBJECT IDENTIFIER ::= { lcsStatusWan 13 }

-- {TABLE} 1.3.6.1.4.1.2356.11.1.4.13.1
lcsStatusWanIpAddressesIpv4Table OBJECT-TYPE
    SYNTAX     SEQUENCE OF LcsStatusWanIpAddressesIpv4Entry
    MAX-ACCESS not-accessible
    STATUS     current
    DESCRIPTION
            "-- empty --"
    ::= { lcsStatusWanIpAddresses 1 }

-- {ROW} 1.3.6.1.4.1.2356.11.1.4.13.1.1
lcsStatusWanIpAddressesIpv4Entry OBJECT-TYPE
    SYNTAX     LcsStatusWanIpAddressesIpv4Entry
    MAX-ACCESS not-accessible
    STATUS     current
    DESCRIPTION
            ""
    INDEX {
            lcsStatusWanIpAddressesIpv4EntryPeer
          }
    ::= { lcsStatusWanIpAddressesIpv4Table 1 }

LcsStatusWanIpAddressesIpv4Entry ::= SEQUENCE {
            lcsStatusWanIpAddressesIpv4EntryPeer DisplayString,
            lcsStatusWanIpAddressesIpv4EntryType INTEGER,
            lcsStatusWanIpAddressesIpv4EntryIpAddress IpAddress,
            lcsStatusWanIpAddressesIpv4EntryIpNetmask IpAddress,
            lcsStatusWanIpAddressesIpv4EntryGateway IpAddress,
            lcsStatusWanIpAddressesIpv4EntryDnsDefault IpAddress,
            lcsStatusWanIpAddressesIpv4EntryDnsBackup IpAddress,
            lcsStatusWanIpAddressesIpv4EntryNbnsDefault IpAddress,
            lcsStatusWanIpAddressesIpv4EntryNbnsBackup IpAddress,
            lcsStatusWanIpAddressesIpv4EntryDomain DisplayString
    }

-- {COLUMN} 1.3.6.1.4.1.2356.11.1.4.13.1.1.1
lcsStatusWanIpAddressesIpv4EntryPeer OBJECT-TYPE
    SYNTAX     DisplayString (SIZE(0..16))
    MAX-ACCESS read-only
    STATUS     current
    DESCRIPTION
            "-- empty --"
    ::= { lcsStatusWanIpAddressesIpv4Entry 1 }

-- {COLUMN} 1.3.6.1.4.1.2356.11.1.4.13.1.1.2
lcsStatusWanIpAddressesIpv4EntryType OBJECT-TYPE
    SYNTAX     INTEGER {
                  eStatic (1),
                  eDhcp (2),
                  ePpp (3),
                  eAutoconfig (4)
            }
    MAX-ACCESS read-only
    STATUS     current
    DESCRIPTION
            "-- empty --"
    ::= { lcsStatusWanIpAddressesIpv4Entry 2 }

-- {COLUMN} 1.3.6.1.4.1.2356.11.1.4.13.1.1.3
lcsStatusWanIpAddressesIpv4EntryIpAddress OBJECT-TYPE
    SYNTAX     IpAddress
    MAX-ACCESS read-only
    STATUS     current
    DESCRIPTION
            "-- empty --"
    ::= { lcsStatusWanIpAddressesIpv4Entry 3 }

-- {COLUMN} 1.3.6.1.4.1.2356.11.1.4.13.1.1.4
lcsStatusWanIpAddressesIpv4EntryIpNetmask OBJECT-TYPE
    SYNTAX     IpAddress
    MAX-ACCESS read-only
    STATUS     current
    DESCRIPTION
            "-- empty --"
    ::= { lcsStatusWanIpAddressesIpv4Entry 4 }

-- {COLUMN} 1.3.6.1.4.1.2356.11.1.4.13.1.1.5
lcsStatusWanIpAddressesIpv4EntryGateway OBJECT-TYPE
    SYNTAX     IpAddress
    MAX-ACCESS read-only
    STATUS     current
    DESCRIPTION
            "-- empty --"
    ::= { lcsStatusWanIpAddressesIpv4Entry 5 }

-- {COLUMN} 1.3.6.1.4.1.2356.11.1.4.13.1.1.6
lcsStatusWanIpAddressesIpv4EntryDnsDefault OBJECT-TYPE
    SYNTAX     IpAddress
    MAX-ACCESS read-only
    STATUS     current
    DESCRIPTION
            "-- empty --"
    ::= { lcsStatusWanIpAddressesIpv4Entry 6 }

-- {COLUMN} 1.3.6.1.4.1.2356.11.1.4.13.1.1.7
lcsStatusWanIpAddressesIpv4EntryDnsBackup OBJECT-TYPE
    SYNTAX     IpAddress
    MAX-ACCESS read-only
    STATUS     current
    DESCRIPTION
            "-- empty --"
    ::= { lcsStatusWanIpAddressesIpv4Entry 7 }

-- {COLUMN} 1.3.6.1.4.1.2356.11.1.4.13.1.1.8
lcsStatusWanIpAddressesIpv4EntryNbnsDefault OBJECT-TYPE
    SYNTAX     IpAddress
    MAX-ACCESS read-only
    STATUS     current
    DESCRIPTION
            "-- empty --"
    ::= { lcsStatusWanIpAddressesIpv4Entry 8 }

-- {COLUMN} 1.3.6.1.4.1.2356.11.1.4.13.1.1.9
lcsStatusWanIpAddressesIpv4EntryNbnsBackup OBJECT-TYPE
    SYNTAX     IpAddress
    MAX-ACCESS read-only
    STATUS     current
    DESCRIPTION
            "-- empty --"
    ::= { lcsStatusWanIpAddressesIpv4Entry 9 }

-- {COLUMN} 1.3.6.1.4.1.2356.11.1.4.13.1.1.10
lcsStatusWanIpAddressesIpv4EntryDomain OBJECT-TYPE
    SYNTAX     DisplayString (SIZE(0..35))
    MAX-ACCESS read-only
    STATUS     current
    DESCRIPTION
            "-- empty --"
    ::= { lcsStatusWanIpAddressesIpv4Entry 10 }

-- {TABLE} 1.3.6.1.4.1.2356.11.1.4.13.2
lcsStatusWanIpAddressesIpv6Table OBJECT-TYPE
    SYNTAX     SEQUENCE OF LcsStatusWanIpAddressesIpv6Entry
    MAX-ACCESS not-accessible
    STATUS     current
    DESCRIPTION
            "-- empty --"
    ::= { lcsStatusWanIpAddresses 2 }

-- {ROW} 1.3.6.1.4.1.2356.11.1.4.13.2.1
lcsStatusWanIpAddressesIpv6Entry OBJECT-TYPE
    SYNTAX     LcsStatusWanIpAddressesIpv6Entry
    MAX-ACCESS not-accessible
    STATUS     current
    DESCRIPTION
            ""
    INDEX {
            lcsStatusWanIpAddressesIpv6EntryPeer
          }
    ::= { lcsStatusWanIpAddressesIpv6Table 1 }

LcsStatusWanIpAddressesIpv6Entry ::= SEQUENCE {
            lcsStatusWanIpAddressesIpv6EntryPeer DisplayString,
            lcsStatusWanIpAddressesIpv6EntryType INTEGER,
            lcsStatusWanIpAddressesIpv6EntryIpAddress DisplayString,
            lcsStatusWanIpAddressesIpv6EntryPrefixLength Integer32,
            lcsStatusWanIpAddressesIpv6EntryGateway DisplayString,
            lcsStatusWanIpAddressesIpv6EntryDnsDefault DisplayString,
            lcsStatusWanIpAddressesIpv6EntryDnsBackup DisplayString,
            lcsStatusWanIpAddressesIpv6EntryPrefix DisplayString,
            lcsStatusWanIpAddressesIpv6EntryDomain DisplayString
    }

-- {COLUMN} 1.3.6.1.4.1.2356.11.1.4.13.2.1.1
lcsStatusWanIpAddressesIpv6EntryPeer OBJECT-TYPE
    SYNTAX     DisplayString (SIZE(0..25))
    MAX-ACCESS read-only
    STATUS     current
    DESCRIPTION
            "-- empty --"
    ::= { lcsStatusWanIpAddressesIpv6Entry 1 }

-- {COLUMN} 1.3.6.1.4.1.2356.11.1.4.13.2.1.2
lcsStatusWanIpAddressesIpv6EntryType OBJECT-TYPE
    SYNTAX     INTEGER {
                  eUnknown (0),
                  eStatic (1),
                  eDhcp (2),
                  eAutoconfig (4),
                  eTunnel (5)
            }
    MAX-ACCESS read-only
    STATUS     current
    DESCRIPTION
            "-- empty --"
    ::= { lcsStatusWanIpAddressesIpv6Entry 2 }

-- {COLUMN} 1.3.6.1.4.1.2356.11.1.4.13.2.1.3
lcsStatusWanIpAddressesIpv6EntryIpAddress OBJECT-TYPE
    SYNTAX     DisplayString (SIZE(0..255))
    MAX-ACCESS read-only
    STATUS     current
    DESCRIPTION
            "-- empty --"
    ::= { lcsStatusWanIpAddressesIpv6Entry 3 }

-- {COLUMN} 1.3.6.1.4.1.2356.11.1.4.13.2.1.4
lcsStatusWanIpAddressesIpv6EntryPrefixLength OBJECT-TYPE
    SYNTAX     Integer32 (0..2147483647)
    MAX-ACCESS read-only
    STATUS     current
    DESCRIPTION
            "-- empty --"
    ::= { lcsStatusWanIpAddressesIpv6Entry 4 }

-- {COLUMN} 1.3.6.1.4.1.2356.11.1.4.13.2.1.5
lcsStatusWanIpAddressesIpv6EntryGateway OBJECT-TYPE
    SYNTAX     DisplayString (SIZE(0..255))
    MAX-ACCESS read-only
    STATUS     current
    DESCRIPTION
            "-- empty --"
    ::= { lcsStatusWanIpAddressesIpv6Entry 5 }

-- {COLUMN} 1.3.6.1.4.1.2356.11.1.4.13.2.1.6
lcsStatusWanIpAddressesIpv6EntryDnsDefault OBJECT-TYPE
    SYNTAX     DisplayString (SIZE(0..255))
    MAX-ACCESS read-only
    STATUS     current
    DESCRIPTION
            "-- empty --"
    ::= { lcsStatusWanIpAddressesIpv6Entry 6 }

-- {COLUMN} 1.3.6.1.4.1.2356.11.1.4.13.2.1.7
lcsStatusWanIpAddressesIpv6EntryDnsBackup OBJECT-TYPE
    SYNTAX     DisplayString (SIZE(0..255))
    MAX-ACCESS read-only
    STATUS     current
    DESCRIPTION
            "-- empty --"
    ::= { lcsStatusWanIpAddressesIpv6Entry 7 }

-- {COLUMN} 1.3.6.1.4.1.2356.11.1.4.13.2.1.8
lcsStatusWanIpAddressesIpv6EntryPrefix OBJECT-TYPE
    SYNTAX     DisplayString (SIZE(0..255))
    MAX-ACCESS read-only
    STATUS     current
    DESCRIPTION
            "-- empty --"
    ::= { lcsStatusWanIpAddressesIpv6Entry 8 }

-- {COLUMN} 1.3.6.1.4.1.2356.11.1.4.13.2.1.10
lcsStatusWanIpAddressesIpv6EntryDomain OBJECT-TYPE
    SYNTAX     DisplayString (SIZE(0..35))
    MAX-ACCESS read-only
    STATUS     current
    DESCRIPTION
            "-- empty --"
    ::= { lcsStatusWanIpAddressesIpv6Entry 10 }

-- {NODE} 1.3.6.1.4.1.2356.11.1.4.15
lcsStatusWanBackup OBJECT IDENTIFIER ::= { lcsStatusWan 15 }

-- {SCALAR} 1.3.6.1.4.1.2356.11.1.4.15.1
lcsStatusWanBackupActive OBJECT-TYPE
    SYNTAX     INTEGER {
                  eNo (0),
                  eYes (1)
            }
    MAX-ACCESS read-only
    STATUS     current
    DESCRIPTION
            "-- empty --"
    ::= { lcsStatusWanBackup 1 }

-- {SCALAR} 1.3.6.1.4.1.2356.11.1.4.15.2
lcsStatusWanBackupCount OBJECT-TYPE
    SYNTAX     Integer32 (0..2147483647)
    MAX-ACCESS read-only
    STATUS     current
    DESCRIPTION
            "-- empty --"
    ::= { lcsStatusWanBackup 2 }

-- {SCALAR} 1.3.6.1.4.1.2356.11.1.4.15.3
lcsStatusWanBackupDeleteValues OBJECT-TYPE
    SYNTAX     DisplayString
    MAX-ACCESS read-write
    STATUS     current
    DESCRIPTION
            "-- empty --"
    ::= { lcsStatusWanBackup 3 }

-- {NODE} 1.3.6.1.4.1.2356.11.1.4.20
lcsStatusWanActions OBJECT IDENTIFIER ::= { lcsStatusWan 20 }

-- {TABLE} 1.3.6.1.4.1.2356.11.1.4.20.1
lcsStatusWanActionsActionTableTable OBJECT-TYPE
    SYNTAX     SEQUENCE OF LcsStatusWanActionsActionTableEntry
    MAX-ACCESS not-accessible
    STATUS     current
    DESCRIPTION
            ""
    ::= { lcsStatusWanActions 1 }

-- {ROW} 1.3.6.1.4.1.2356.11.1.4.20.1.1
lcsStatusWanActionsActionTableEntry OBJECT-TYPE
    SYNTAX     LcsStatusWanActionsActionTableEntry
    MAX-ACCESS not-accessible
    STATUS     current
    DESCRIPTION
            ""
    INDEX {
            lcsStatusWanActionsActionTableEntryTime
          }
    ::= { lcsStatusWanActionsActionTableTable 1 }

LcsStatusWanActionsActionTableEntry ::= SEQUENCE {
            lcsStatusWanActionsActionTableEntryTime DisplayString,
            lcsStatusWanActionsActionTableEntryAction DisplayString,
            lcsStatusWanActionsActionTableEntryResult DisplayString
    }

-- {COLUMN} 1.3.6.1.4.1.2356.11.1.4.20.1.1.1
lcsStatusWanActionsActionTableEntryTime OBJECT-TYPE
    SYNTAX     DisplayString (SIZE(0..19))
    MAX-ACCESS read-only
    STATUS     current
    DESCRIPTION
            ""
    ::= { lcsStatusWanActionsActionTableEntry 1 }

-- {COLUMN} 1.3.6.1.4.1.2356.11.1.4.20.1.1.2
lcsStatusWanActionsActionTableEntryAction OBJECT-TYPE
    SYNTAX     DisplayString (SIZE(0..255))
    MAX-ACCESS read-only
    STATUS     current
    DESCRIPTION
            ""
    ::= { lcsStatusWanActionsActionTableEntry 2 }

-- {COLUMN} 1.3.6.1.4.1.2356.11.1.4.20.1.1.3
lcsStatusWanActionsActionTableEntryResult OBJECT-TYPE
    SYNTAX     DisplayString (SIZE(0..100))
    MAX-ACCESS read-only
    STATUS     current
    DESCRIPTION
            ""
    ::= { lcsStatusWanActionsActionTableEntry 3 }

-- {TABLE} 1.3.6.1.4.1.2356.11.1.4.20.2
lcsStatusWanActionsLockTableTable OBJECT-TYPE
    SYNTAX     SEQUENCE OF LcsStatusWanActionsLockTableEntry
    MAX-ACCESS not-accessible
    STATUS     current
    DESCRIPTION
            ""
    ::= { lcsStatusWanActions 2 }

-- {ROW} 1.3.6.1.4.1.2356.11.1.4.20.2.1
lcsStatusWanActionsLockTableEntry OBJECT-TYPE
    SYNTAX     LcsStatusWanActionsLockTableEntry
    MAX-ACCESS not-accessible
    STATUS     current
    DESCRIPTION
            ""
    INDEX {
            lcsStatusWanActionsLockTableEntryIndex
          }
    ::= { lcsStatusWanActionsLockTableTable 1 }

LcsStatusWanActionsLockTableEntry ::= SEQUENCE {
            lcsStatusWanActionsLockTableEntryIndex Integer32,
            lcsStatusWanActionsLockTableEntryRemainingLocktime Integer32
    }

-- {COLUMN} 1.3.6.1.4.1.2356.11.1.4.20.2.1.1
lcsStatusWanActionsLockTableEntryIndex OBJECT-TYPE
    SYNTAX     Integer32 (0..65535)
    MAX-ACCESS read-only
    STATUS     current
    DESCRIPTION
            ""
    ::= { lcsStatusWanActionsLockTableEntry 1 }

-- {COLUMN} 1.3.6.1.4.1.2356.11.1.4.20.2.1.2
lcsStatusWanActionsLockTableEntryRemainingLocktime OBJECT-TYPE
    SYNTAX     Integer32 (0..2147483647)
    MAX-ACCESS read-only
    STATUS     current
    DESCRIPTION
            ""
    ::= { lcsStatusWanActionsLockTableEntry 2 }

-- {SCALAR} 1.3.6.1.4.1.2356.11.1.4.21
lcsStatusWanWanQueueMgtDrop OBJECT-TYPE
    SYNTAX     Counter32
    MAX-ACCESS read-only
    STATUS     current
    DESCRIPTION
            ""
    ::= { lcsStatusWan 21 }

-- {NODE} 1.3.6.1.4.1.2356.11.1.4.30
lcsStatusWanVlans OBJECT IDENTIFIER ::= { lcsStatusWan 30 }

-- {TABLE} 1.3.6.1.4.1.2356.11.1.4.30.1
lcsStatusWanVlansProviderListTable OBJECT-TYPE
    SYNTAX     SEQUENCE OF LcsStatusWanVlansProviderListEntry
    MAX-ACCESS not-accessible
    STATUS     current
    DESCRIPTION
            "-- empty --"
    ::= { lcsStatusWanVlans 1 }

-- {ROW} 1.3.6.1.4.1.2356.11.1.4.30.1.1
lcsStatusWanVlansProviderListEntry OBJECT-TYPE
    SYNTAX     LcsStatusWanVlansProviderListEntry
    MAX-ACCESS not-accessible
    STATUS     current
    DESCRIPTION
            ""
    INDEX {
            lcsStatusWanVlansProviderListEntryProvider
          }
    ::= { lcsStatusWanVlansProviderListTable 1 }

LcsStatusWanVlansProviderListEntry ::= SEQUENCE {
            lcsStatusWanVlansProviderListEntryProvider OCTET STRING,
            lcsStatusWanVlansProviderListEntryVlanIds OCTET STRING
    }

-- {COLUMN} 1.3.6.1.4.1.2356.11.1.4.30.1.1.1
lcsStatusWanVlansProviderListEntryProvider OBJECT-TYPE
    SYNTAX     OCTET STRING (SIZE(0..64))
    MAX-ACCESS read-only
    STATUS     current
    DESCRIPTION
            "-- empty --"
    ::= { lcsStatusWanVlansProviderListEntry 1 }

-- {COLUMN} 1.3.6.1.4.1.2356.11.1.4.30.1.1.2
lcsStatusWanVlansProviderListEntryVlanIds OBJECT-TYPE
    SYNTAX     OCTET STRING (SIZE(0..32))
    MAX-ACCESS read-only
    STATUS     current
    DESCRIPTION
            "-- empty --"
    ::= { lcsStatusWanVlansProviderListEntry 2 }

-- {TABLE} 1.3.6.1.4.1.2356.11.1.4.30.2
lcsStatusWanVlansVlansTable OBJECT-TYPE
    SYNTAX     SEQUENCE OF LcsStatusWanVlansVlansEntry
    MAX-ACCESS not-accessible
    STATUS     current
    DESCRIPTION
            "-- empty --"
    ::= { lcsStatusWanVlans 2 }

-- {ROW} 1.3.6.1.4.1.2356.11.1.4.30.2.1
lcsStatusWanVlansVlansEntry OBJECT-TYPE
    SYNTAX     LcsStatusWanVlansVlansEntry
    MAX-ACCESS not-accessible
    STATUS     current
    DESCRIPTION
            ""
    INDEX {
            lcsStatusWanVlansVlansEntryPeer
          }
    ::= { lcsStatusWanVlansVlansTable 1 }

LcsStatusWanVlansVlansEntry ::= SEQUENCE {
            lcsStatusWanVlansVlansEntryPeer DisplayString,
            lcsStatusWanVlansVlansEntryVlanId Integer32
    }

-- {COLUMN} 1.3.6.1.4.1.2356.11.1.4.30.2.1.1
lcsStatusWanVlansVlansEntryPeer OBJECT-TYPE
    SYNTAX     DisplayString (SIZE(0..16))
    MAX-ACCESS read-only
    STATUS     current
    DESCRIPTION
            "-- empty --"
    ::= { lcsStatusWanVlansVlansEntry 1 }

-- {COLUMN} 1.3.6.1.4.1.2356.11.1.4.30.2.1.2
lcsStatusWanVlansVlansEntryVlanId OBJECT-TYPE
    SYNTAX     Integer32 (0..2147483647)
    MAX-ACCESS read-only
    STATUS     current
    DESCRIPTION
            "-- empty --"
    ::= { lcsStatusWanVlansVlansEntry 2 }

-- {NODE} 1.3.6.1.4.1.2356.11.1.4.45
lcsStatusWanX25Bridge OBJECT IDENTIFIER ::= { lcsStatusWan 45 }

-- {TABLE} 1.3.6.1.4.1.2356.11.1.4.45.2
lcsStatusWanX25BridgeConnectionsTable OBJECT-TYPE
    SYNTAX     SEQUENCE OF LcsStatusWanX25BridgeConnectionsEntry
    MAX-ACCESS not-accessible
    STATUS     current
    DESCRIPTION
            "-- empty --"
    ::= { lcsStatusWanX25Bridge 2 }

-- {ROW} 1.3.6.1.4.1.2356.11.1.4.45.2.1
lcsStatusWanX25BridgeConnectionsEntry OBJECT-TYPE
    SYNTAX     LcsStatusWanX25BridgeConnectionsEntry
    MAX-ACCESS not-accessible
    STATUS     current
    DESCRIPTION
            ""
    INDEX {
            lcsStatusWanX25BridgeConnectionsEntryIndex
          }
    ::= { lcsStatusWanX25BridgeConnectionsTable 1 }

LcsStatusWanX25BridgeConnectionsEntry ::= SEQUENCE {
            lcsStatusWanX25BridgeConnectionsEntryIndex Integer32,
            lcsStatusWanX25BridgeConnectionsEntryDirection INTEGER,
            lcsStatusWanX25BridgeConnectionsEntryTcpState INTEGER,
            lcsStatusWanX25BridgeConnectionsEntryIsdnState INTEGER,
            lcsStatusWanX25BridgeConnectionsEntryX25State INTEGER,
            lcsStatusWanX25BridgeConnectionsEntryTerminalIp IpAddress,
            lcsStatusWanX25BridgeConnectionsEntryTerminalPort Integer32,
            lcsStatusWanX25BridgeConnectionsEntryLocalIp IpAddress,
            lcsStatusWanX25BridgeConnectionsEntryLocalPort Integer32,
            lcsStatusWanX25BridgeConnectionsEntryRoutingTag Integer32,
            lcsStatusWanX25BridgeConnectionsEntryIsdnRemote DisplayString,
            lcsStatusWanX25BridgeConnectionsEntryIsdnLocal DisplayString,
            lcsStatusWanX25BridgeConnectionsEntryX25Remote DisplayString,
            lcsStatusWanX25BridgeConnectionsEntryX25Local DisplayString,
            lcsStatusWanX25BridgeConnectionsEntryProtocolId Integer32,
            lcsStatusWanX25BridgeConnectionsEntryUserdata DisplayString,
            lcsStatusWanX25BridgeConnectionsEntryPayloadSize Integer32
    }

-- {COLUMN} 1.3.6.1.4.1.2356.11.1.4.45.2.1.1
lcsStatusWanX25BridgeConnectionsEntryIndex OBJECT-TYPE
    SYNTAX     Integer32 (0..2147483647)
    MAX-ACCESS read-only
    STATUS     current
    DESCRIPTION
            "-- empty --"
    ::= { lcsStatusWanX25BridgeConnectionsEntry 1 }

-- {COLUMN} 1.3.6.1.4.1.2356.11.1.4.45.2.1.2
lcsStatusWanX25BridgeConnectionsEntryDirection OBJECT-TYPE
    SYNTAX     INTEGER {
                  eOutgoing (0),
                  eIncoming (1)
            }
    MAX-ACCESS read-only
    STATUS     current
    DESCRIPTION
            "-- empty --"
    ::= { lcsStatusWanX25BridgeConnectionsEntry 2 }

-- {COLUMN} 1.3.6.1.4.1.2356.11.1.4.45.2.1.3
lcsStatusWanX25BridgeConnectionsEntryTcpState OBJECT-TYPE
    SYNTAX     INTEGER {
                  eListening (0),
                  eConnecting (1),
                  eConnected (2),
                  eDisconnecting (3),
                  eDisconnected (4)
            }
    MAX-ACCESS read-only
    STATUS     current
    DESCRIPTION
            "-- empty --"
    ::= { lcsStatusWanX25BridgeConnectionsEntry 3 }

-- {COLUMN} 1.3.6.1.4.1.2356.11.1.4.45.2.1.4
lcsStatusWanX25BridgeConnectionsEntryIsdnState OBJECT-TYPE
    SYNTAX     INTEGER {
                  eListening (0),
                  eConnecting (1),
                  eConnected (2),
                  eDisconnecting (3),
                  eDisconnected (4)
            }
    MAX-ACCESS read-only
    STATUS     current
    DESCRIPTION
            "-- empty --"
    ::= { lcsStatusWanX25BridgeConnectionsEntry 4 }

-- {COLUMN} 1.3.6.1.4.1.2356.11.1.4.45.2.1.5
lcsStatusWanX25BridgeConnectionsEntryX25State OBJECT-TYPE
    SYNTAX     INTEGER {
                  eListening (0),
                  eConnecting (1),
                  eConnected (2),
                  eDisconnecting (3),
                  eDisconnected (4)
            }
    MAX-ACCESS read-only
    STATUS     current
    DESCRIPTION
            "-- empty --"
    ::= { lcsStatusWanX25BridgeConnectionsEntry 5 }

-- {COLUMN} 1.3.6.1.4.1.2356.11.1.4.45.2.1.6
lcsStatusWanX25BridgeConnectionsEntryTerminalIp OBJECT-TYPE
    SYNTAX     IpAddress
    MAX-ACCESS read-only
    STATUS     current
    DESCRIPTION
            "-- empty --"
    ::= { lcsStatusWanX25BridgeConnectionsEntry 6 }

-- {COLUMN} 1.3.6.1.4.1.2356.11.1.4.45.2.1.7
lcsStatusWanX25BridgeConnectionsEntryTerminalPort OBJECT-TYPE
    SYNTAX     Integer32 (0..65535)
    MAX-ACCESS read-only
    STATUS     current
    DESCRIPTION
            "-- empty --"
    ::= { lcsStatusWanX25BridgeConnectionsEntry 7 }

-- {COLUMN} 1.3.6.1.4.1.2356.11.1.4.45.2.1.8
lcsStatusWanX25BridgeConnectionsEntryLocalIp OBJECT-TYPE
    SYNTAX     IpAddress
    MAX-ACCESS read-only
    STATUS     current
    DESCRIPTION
            "-- empty --"
    ::= { lcsStatusWanX25BridgeConnectionsEntry 8 }

-- {COLUMN} 1.3.6.1.4.1.2356.11.1.4.45.2.1.9
lcsStatusWanX25BridgeConnectionsEntryLocalPort OBJECT-TYPE
    SYNTAX     Integer32 (0..65535)
    MAX-ACCESS read-only
    STATUS     current
    DESCRIPTION
            "-- empty --"
    ::= { lcsStatusWanX25BridgeConnectionsEntry 9 }

-- {COLUMN} 1.3.6.1.4.1.2356.11.1.4.45.2.1.10
lcsStatusWanX25BridgeConnectionsEntryRoutingTag OBJECT-TYPE
    SYNTAX     Integer32 (0..2147483647)
    MAX-ACCESS read-only
    STATUS     current
    DESCRIPTION
            "-- empty --"
    ::= { lcsStatusWanX25BridgeConnectionsEntry 10 }

-- {COLUMN} 1.3.6.1.4.1.2356.11.1.4.45.2.1.11
lcsStatusWanX25BridgeConnectionsEntryIsdnRemote OBJECT-TYPE
    SYNTAX     DisplayString
    MAX-ACCESS read-only
    STATUS     current
    DESCRIPTION
            "-- empty --"
    ::= { lcsStatusWanX25BridgeConnectionsEntry 11 }

-- {COLUMN} 1.3.6.1.4.1.2356.11.1.4.45.2.1.12
lcsStatusWanX25BridgeConnectionsEntryIsdnLocal OBJECT-TYPE
    SYNTAX     DisplayString
    MAX-ACCESS read-only
    STATUS     current
    DESCRIPTION
            "-- empty --"
    ::= { lcsStatusWanX25BridgeConnectionsEntry 12 }

-- {COLUMN} 1.3.6.1.4.1.2356.11.1.4.45.2.1.13
lcsStatusWanX25BridgeConnectionsEntryX25Remote OBJECT-TYPE
    SYNTAX     DisplayString
    MAX-ACCESS read-only
    STATUS     current
    DESCRIPTION
            "-- empty --"
    ::= { lcsStatusWanX25BridgeConnectionsEntry 13 }

-- {COLUMN} 1.3.6.1.4.1.2356.11.1.4.45.2.1.14
lcsStatusWanX25BridgeConnectionsEntryX25Local OBJECT-TYPE
    SYNTAX     DisplayString
    MAX-ACCESS read-only
    STATUS     current
    DESCRIPTION
            "-- empty --"
    ::= { lcsStatusWanX25BridgeConnectionsEntry 14 }

-- {COLUMN} 1.3.6.1.4.1.2356.11.1.4.45.2.1.15
lcsStatusWanX25BridgeConnectionsEntryProtocolId OBJECT-TYPE
    SYNTAX     Integer32 (0..2147483647)
    MAX-ACCESS read-only
    STATUS     current
    DESCRIPTION
            "-- empty --"
    ::= { lcsStatusWanX25BridgeConnectionsEntry 15 }

-- {COLUMN} 1.3.6.1.4.1.2356.11.1.4.45.2.1.16
lcsStatusWanX25BridgeConnectionsEntryUserdata OBJECT-TYPE
    SYNTAX     DisplayString
    MAX-ACCESS read-only
    STATUS     current
    DESCRIPTION
            "-- empty --"
    ::= { lcsStatusWanX25BridgeConnectionsEntry 16 }

-- {COLUMN} 1.3.6.1.4.1.2356.11.1.4.45.2.1.17
lcsStatusWanX25BridgeConnectionsEntryPayloadSize OBJECT-TYPE
    SYNTAX     Integer32 (0..2147483647)
    MAX-ACCESS read-only
    STATUS     current
    DESCRIPTION
            "-- empty --"
    ::= { lcsStatusWanX25BridgeConnectionsEntry 17 }

-- {TABLE} 1.3.6.1.4.1.2356.11.1.4.45.3
lcsStatusWanX25BridgeTcpListenerPortsTable OBJECT-TYPE
    SYNTAX     SEQUENCE OF LcsStatusWanX25BridgeTcpListenerPortsEntry
    MAX-ACCESS not-accessible
    STATUS     current
    DESCRIPTION
            "-- empty --"
    ::= { lcsStatusWanX25Bridge 3 }

-- {ROW} 1.3.6.1.4.1.2356.11.1.4.45.3.1
lcsStatusWanX25BridgeTcpListenerPortsEntry OBJECT-TYPE
    SYNTAX     LcsStatusWanX25BridgeTcpListenerPortsEntry
    MAX-ACCESS not-accessible
    STATUS     current
    DESCRIPTION
            ""
    INDEX {
            lcsStatusWanX25BridgeTcpListenerPortsEntryLocalPort
          }
    ::= { lcsStatusWanX25BridgeTcpListenerPortsTable 1 }

LcsStatusWanX25BridgeTcpListenerPortsEntry ::= SEQUENCE {
            lcsStatusWanX25BridgeTcpListenerPortsEntryLocalPort Integer32
    }

-- {COLUMN} 1.3.6.1.4.1.2356.11.1.4.45.3.1.1
lcsStatusWanX25BridgeTcpListenerPortsEntryLocalPort OBJECT-TYPE
    SYNTAX     Integer32 (0..65535)
    MAX-ACCESS read-only
    STATUS     current
    DESCRIPTION
            "-- empty --"
    ::= { lcsStatusWanX25BridgeTcpListenerPortsEntry 1 }

-- {SCALAR} 1.3.6.1.4.1.2356.11.1.4.45.4
lcsStatusWanX25BridgeDisconnectAll OBJECT-TYPE
    SYNTAX     DisplayString
    MAX-ACCESS read-write
    STATUS     current
    DESCRIPTION
            "-- empty --"
    ::= { lcsStatusWanX25Bridge 4 }

-- {TABLE} 1.3.6.1.4.1.2356.11.1.4.46
lcsStatusWanConnectionBandwidthTable OBJECT-TYPE
    SYNTAX     SEQUENCE OF LcsStatusWanConnectionBandwidthEntry
    MAX-ACCESS not-accessible
    STATUS     current
    DESCRIPTION
            "-- empty --"
    ::= { lcsStatusWan 46 }

-- {ROW} 1.3.6.1.4.1.2356.11.1.4.46.1
lcsStatusWanConnectionBandwidthEntry OBJECT-TYPE
    SYNTAX     LcsStatusWanConnectionBandwidthEntry
    MAX-ACCESS not-accessible
    STATUS     current
    DESCRIPTION
            ""
    INDEX {
            lcsStatusWanConnectionBandwidthEntryIfc
          }
    ::= { lcsStatusWanConnectionBandwidthTable 1 }

LcsStatusWanConnectionBandwidthEntry ::= SEQUENCE {
            lcsStatusWanConnectionBandwidthEntryIfc DisplayString,
            lcsStatusWanConnectionBandwidthEntryLineTxrate Integer32,
            lcsStatusWanConnectionBandwidthEntryLineRxrate Integer32,
            lcsStatusWanConnectionBandwidthEntryAnnTxrate Integer32,
            lcsStatusWanConnectionBandwidthEntryAnnRxrate Integer32,
            lcsStatusWanConnectionBandwidthEntryActTxrate Integer32,
            lcsStatusWanConnectionBandwidthEntryActRxrate Integer32
    }

-- {COLUMN} 1.3.6.1.4.1.2356.11.1.4.46.1.1
lcsStatusWanConnectionBandwidthEntryIfc OBJECT-TYPE
    SYNTAX     DisplayString (SIZE(0..16))
    MAX-ACCESS read-only
    STATUS     current
    DESCRIPTION
            "-- empty --"
    ::= { lcsStatusWanConnectionBandwidthEntry 1 }

-- {COLUMN} 1.3.6.1.4.1.2356.11.1.4.46.1.2
lcsStatusWanConnectionBandwidthEntryLineTxrate OBJECT-TYPE
    SYNTAX     Integer32 (0..2147483647)
    MAX-ACCESS read-only
    STATUS     current
    DESCRIPTION
            "-- empty --"
    ::= { lcsStatusWanConnectionBandwidthEntry 2 }

-- {COLUMN} 1.3.6.1.4.1.2356.11.1.4.46.1.3
lcsStatusWanConnectionBandwidthEntryLineRxrate OBJECT-TYPE
    SYNTAX     Integer32 (0..2147483647)
    MAX-ACCESS read-only
    STATUS     current
    DESCRIPTION
            "-- empty --"
    ::= { lcsStatusWanConnectionBandwidthEntry 3 }

-- {COLUMN} 1.3.6.1.4.1.2356.11.1.4.46.1.6
lcsStatusWanConnectionBandwidthEntryAnnTxrate OBJECT-TYPE
    SYNTAX     Integer32 (0..2147483647)
    MAX-ACCESS read-only
    STATUS     current
    DESCRIPTION
            "-- empty --"
    ::= { lcsStatusWanConnectionBandwidthEntry 6 }

-- {COLUMN} 1.3.6.1.4.1.2356.11.1.4.46.1.7
lcsStatusWanConnectionBandwidthEntryAnnRxrate OBJECT-TYPE
    SYNTAX     Integer32 (0..2147483647)
    MAX-ACCESS read-only
    STATUS     current
    DESCRIPTION
            "-- empty --"
    ::= { lcsStatusWanConnectionBandwidthEntry 7 }

-- {COLUMN} 1.3.6.1.4.1.2356.11.1.4.46.1.8
lcsStatusWanConnectionBandwidthEntryActTxrate OBJECT-TYPE
    SYNTAX     Integer32 (0..2147483647)
    MAX-ACCESS read-only
    STATUS     current
    DESCRIPTION
            "-- empty --"
    ::= { lcsStatusWanConnectionBandwidthEntry 8 }

-- {COLUMN} 1.3.6.1.4.1.2356.11.1.4.46.1.9
lcsStatusWanConnectionBandwidthEntryActRxrate OBJECT-TYPE
    SYNTAX     Integer32 (0..2147483647)
    MAX-ACCESS read-only
    STATUS     current
    DESCRIPTION
            "-- empty --"
    ::= { lcsStatusWanConnectionBandwidthEntry 9 }

-- {NODE} 1.3.6.1.4.1.2356.11.1.5
lcsStatusLan OBJECT IDENTIFIER ::= { lcsStatus 5 }

-- {SCALAR} 1.3.6.1.4.1.2356.11.1.5.7
lcsStatusLanLanHeapPackets OBJECT-TYPE
    SYNTAX     Integer32 (0..2147483647)
    MAX-ACCESS read-only
    STATUS     current
    DESCRIPTION
            ""
    ::= { lcsStatusLan 7 }

-- {SCALAR} 1.3.6.1.4.1.2356.11.1.5.11
lcsStatusLanDeleteValues OBJECT-TYPE
    SYNTAX     DisplayString
    MAX-ACCESS read-write
    STATUS     current
    DESCRIPTION
            ""
    ::= { lcsStatusLan 11 }

-- {TABLE} 1.3.6.1.4.1.2356.11.1.5.51
lcsStatusLanInterfacesTable OBJECT-TYPE
    SYNTAX     SEQUENCE OF LcsStatusLanInterfacesEntry
    MAX-ACCESS not-accessible
    STATUS     current
    DESCRIPTION
            ""
    ::= { lcsStatusLan 51 }

-- {ROW} 1.3.6.1.4.1.2356.11.1.5.51.1
lcsStatusLanInterfacesEntry OBJECT-TYPE
    SYNTAX     LcsStatusLanInterfacesEntry
    MAX-ACCESS not-accessible
    STATUS     current
    DESCRIPTION
            ""
    INDEX {
            lcsStatusLanInterfacesEntryIfc
          }
    ::= { lcsStatusLanInterfacesTable 1 }

LcsStatusLanInterfacesEntry ::= SEQUENCE {
            lcsStatusLanInterfacesEntryIfc DisplayString,
            lcsStatusLanInterfacesEntryQueuePackets Integer32,
            lcsStatusLanInterfacesEntryLinkActive INTEGER,
            lcsStatusLanInterfacesEntryConnector INTEGER,
            lcsStatusLanInterfacesEntryFlowControl INTEGER,
            lcsStatusLanInterfacesEntryMdiMode INTEGER,
            lcsStatusLanInterfacesEntryAutoNegotiation INTEGER,
            lcsStatusLanInterfacesEntryDownshift INTEGER,
            lcsStatusLanInterfacesEntryClockRole INTEGER,
            lcsStatusLanInterfacesEntryRemoteFault INTEGER,
            lcsStatusLanInterfacesEntryPowerSaving INTEGER,
            lcsStatusLanInterfacesEntryMacAddress MacAddress
    }

-- {COLUMN} 1.3.6.1.4.1.2356.11.1.5.51.1.1
lcsStatusLanInterfacesEntryIfc OBJECT-TYPE
    SYNTAX     DisplayString (SIZE(0..255))
    MAX-ACCESS read-only
    STATUS     current
    DESCRIPTION
            ""
    ::= { lcsStatusLanInterfacesEntry 1 }

-- {COLUMN} 1.3.6.1.4.1.2356.11.1.5.51.1.2
lcsStatusLanInterfacesEntryQueuePackets OBJECT-TYPE
    SYNTAX     Integer32 (0..2147483647)
    MAX-ACCESS read-only
    STATUS     current
    DESCRIPTION
            ""
    ::= { lcsStatusLanInterfacesEntry 2 }

-- {COLUMN} 1.3.6.1.4.1.2356.11.1.5.51.1.3
lcsStatusLanInterfacesEntryLinkActive OBJECT-TYPE
    SYNTAX     INTEGER {
                  eNo (0),
                  eYes (1)
            }
    MAX-ACCESS read-only
    STATUS     current
    DESCRIPTION
            ""
    ::= { lcsStatusLanInterfacesEntry 3 }

-- {COLUMN} 1.3.6.1.4.1.2356.11.1.5.51.1.4
lcsStatusLanInterfacesEntryConnector OBJECT-TYPE
    SYNTAX     INTEGER {
                  eNone (0),
                  e10bT (1),
                  eFd10bTx (2),
                  e100bTx (3),
                  eFd100bTx (4),
                  eFd1000bTx (6),
                  eFd2500bTx (9),
                  eFd5000bTx (10),
                  eFd10gbTx (11),
                  e10b2 (33),
                  e10b5 (34),
                  eFd1000bF (70),
                  eFd10gbF (75),
                  ePowerDown (255)
            }
    MAX-ACCESS read-only
    STATUS     current
    DESCRIPTION
            ""
    ::= { lcsStatusLanInterfacesEntry 4 }

-- {COLUMN} 1.3.6.1.4.1.2356.11.1.5.51.1.6
lcsStatusLanInterfacesEntryFlowControl OBJECT-TYPE
    SYNTAX     INTEGER {
                  eNo (0),
                  eYes (1),
                  eTxOnly (3),
                  eRxOnly (4)
            }
    MAX-ACCESS read-only
    STATUS     current
    DESCRIPTION
            ""
    ::= { lcsStatusLanInterfacesEntry 6 }

-- {COLUMN} 1.3.6.1.4.1.2356.11.1.5.51.1.7
lcsStatusLanInterfacesEntryMdiMode OBJECT-TYPE
    SYNTAX     INTEGER {
                  eUnknown (0),
                  eMdi (1),
                  eMdix (2),
                  eNotApplicable (3)
            }
    MAX-ACCESS read-only
    STATUS     current
    DESCRIPTION
            ""
    ::= { lcsStatusLanInterfacesEntry 7 }

-- {COLUMN} 1.3.6.1.4.1.2356.11.1.5.51.1.8
lcsStatusLanInterfacesEntryAutoNegotiation OBJECT-TYPE
    SYNTAX     INTEGER {
                  ePending (0),
                  eCompleted (1),
                  eDisabled (2),
                  eNotAvailable (3)
            }
    MAX-ACCESS read-only
    STATUS     current
    DESCRIPTION
            ""
    ::= { lcsStatusLanInterfacesEntry 8 }

-- {COLUMN} 1.3.6.1.4.1.2356.11.1.5.51.1.9
lcsStatusLanInterfacesEntryDownshift OBJECT-TYPE
    SYNTAX     INTEGER {
                  eNo (0),
                  eYes (1)
            }
    MAX-ACCESS read-only
    STATUS     current
    DESCRIPTION
            ""
    ::= { lcsStatusLanInterfacesEntry 9 }

-- {COLUMN} 1.3.6.1.4.1.2356.11.1.5.51.1.10
lcsStatusLanInterfacesEntryClockRole OBJECT-TYPE
    SYNTAX     INTEGER {
                  eNone (0),
                  eMaster (1),
                  eSlave (2),
                  eFault (3)
            }
    MAX-ACCESS read-only
    STATUS     current
    DESCRIPTION
            ""
    ::= { lcsStatusLanInterfacesEntry 10 }

-- {COLUMN} 1.3.6.1.4.1.2356.11.1.5.51.1.11
lcsStatusLanInterfacesEntryRemoteFault OBJECT-TYPE
    SYNTAX     INTEGER {
                  eNo (0),
                  eYes (1)
            }
    MAX-ACCESS read-only
    STATUS     current
    DESCRIPTION
            "-- empty --"
    ::= { lcsStatusLanInterfacesEntry 11 }

-- {COLUMN} 1.3.6.1.4.1.2356.11.1.5.51.1.12
lcsStatusLanInterfacesEntryPowerSaving OBJECT-TYPE
    SYNTAX     INTEGER {
                  eNo (0),
                  eYes (1)
            }
    MAX-ACCESS read-only
    STATUS     current
    DESCRIPTION
            "-- empty --"
    ::= { lcsStatusLanInterfacesEntry 12 }

-- {COLUMN} 1.3.6.1.4.1.2356.11.1.5.51.1.13
lcsStatusLanInterfacesEntryMacAddress OBJECT-TYPE
    SYNTAX     MacAddress
    MAX-ACCESS read-only
    STATUS     current
    DESCRIPTION
            "-- empty --"
    ::= { lcsStatusLanInterfacesEntry 13 }

-- {TABLE} 1.3.6.1.4.1.2356.11.1.5.52
lcsStatusLanByteTransportTable OBJECT-TYPE
    SYNTAX     SEQUENCE OF LcsStatusLanByteTransportEntry
    MAX-ACCESS not-accessible
    STATUS     current
    DESCRIPTION
            ""
    ::= { lcsStatusLan 52 }

-- {ROW} 1.3.6.1.4.1.2356.11.1.5.52.1
lcsStatusLanByteTransportEntry OBJECT-TYPE
    SYNTAX     LcsStatusLanByteTransportEntry
    MAX-ACCESS not-accessible
    STATUS     current
    DESCRIPTION
            ""
    INDEX {
            lcsStatusLanByteTransportEntryIfc
          }
    ::= { lcsStatusLanByteTransportTable 1 }

LcsStatusLanByteTransportEntry ::= SEQUENCE {
            lcsStatusLanByteTransportEntryIfc DisplayString,
            lcsStatusLanByteTransportEntryTxBytes Counter64,
            lcsStatusLanByteTransportEntryRxBytes Counter64,
            lcsStatusLanByteTransportEntryThroughput DisplayString,
            lcsStatusLanByteTransportEntryMaxThroughput DisplayString,
            lcsStatusLanByteTransportEntryBytesThroughput Integer32,
            lcsStatusLanByteTransportEntryBytesMaxThroughput Integer32
    }

-- {COLUMN} 1.3.6.1.4.1.2356.11.1.5.52.1.1
lcsStatusLanByteTransportEntryIfc OBJECT-TYPE
    SYNTAX     DisplayString (SIZE(0..255))
    MAX-ACCESS read-only
    STATUS     current
    DESCRIPTION
            ""
    ::= { lcsStatusLanByteTransportEntry 1 }

-- {COLUMN} 1.3.6.1.4.1.2356.11.1.5.52.1.2
lcsStatusLanByteTransportEntryTxBytes OBJECT-TYPE
    SYNTAX     Counter64
    MAX-ACCESS read-only
    STATUS     current
    DESCRIPTION
            ""
    ::= { lcsStatusLanByteTransportEntry 2 }

-- {COLUMN} 1.3.6.1.4.1.2356.11.1.5.52.1.3
lcsStatusLanByteTransportEntryRxBytes OBJECT-TYPE
    SYNTAX     Counter64
    MAX-ACCESS read-only
    STATUS     current
    DESCRIPTION
            ""
    ::= { lcsStatusLanByteTransportEntry 3 }

-- {COLUMN} 1.3.6.1.4.1.2356.11.1.5.52.1.4
lcsStatusLanByteTransportEntryThroughput OBJECT-TYPE
    SYNTAX     DisplayString (SIZE(0..255))
    MAX-ACCESS read-only
    STATUS     current
    DESCRIPTION
            ""
    ::= { lcsStatusLanByteTransportEntry 4 }

-- {COLUMN} 1.3.6.1.4.1.2356.11.1.5.52.1.5
lcsStatusLanByteTransportEntryMaxThroughput OBJECT-TYPE
    SYNTAX     DisplayString (SIZE(0..255))
    MAX-ACCESS read-only
    STATUS     current
    DESCRIPTION
            ""
    ::= { lcsStatusLanByteTransportEntry 5 }

-- {COLUMN} 1.3.6.1.4.1.2356.11.1.5.52.1.6
lcsStatusLanByteTransportEntryBytesThroughput OBJECT-TYPE
    SYNTAX     Integer32 (0..2147483647)
    MAX-ACCESS read-only
    STATUS     current
    DESCRIPTION
            ""
    ::= { lcsStatusLanByteTransportEntry 6 }

-- {COLUMN} 1.3.6.1.4.1.2356.11.1.5.52.1.7
lcsStatusLanByteTransportEntryBytesMaxThroughput OBJECT-TYPE
    SYNTAX     Integer32 (0..2147483647)
    MAX-ACCESS read-only
    STATUS     current
    DESCRIPTION
            ""
    ::= { lcsStatusLanByteTransportEntry 7 }

-- {TABLE} 1.3.6.1.4.1.2356.11.1.5.53
lcsStatusLanPacketTransportTable OBJECT-TYPE
    SYNTAX     SEQUENCE OF LcsStatusLanPacketTransportEntry
    MAX-ACCESS not-accessible
    STATUS     current
    DESCRIPTION
            ""
    ::= { lcsStatusLan 53 }

-- {ROW} 1.3.6.1.4.1.2356.11.1.5.53.1
lcsStatusLanPacketTransportEntry OBJECT-TYPE
    SYNTAX     LcsStatusLanPacketTransportEntry
    MAX-ACCESS not-accessible
    STATUS     current
    DESCRIPTION
            ""
    INDEX {
            lcsStatusLanPacketTransportEntryIfc
          }
    ::= { lcsStatusLanPacketTransportTable 1 }

LcsStatusLanPacketTransportEntry ::= SEQUENCE {
            lcsStatusLanPacketTransportEntryIfc DisplayString,
            lcsStatusLanPacketTransportEntryRxPackets Counter32,
            lcsStatusLanPacketTransportEntryTxPackets Counter32,
            lcsStatusLanPacketTransportEntryRxBroadcasts Counter32,
            lcsStatusLanPacketTransportEntryRxMulticasts Counter32,
            lcsStatusLanPacketTransportEntryRxUnicasts Counter32,
            lcsStatusLanPacketTransportEntryTxBroadcasts Counter32,
            lcsStatusLanPacketTransportEntryTxMulticasts Counter32,
            lcsStatusLanPacketTransportEntryTxUnicasts Counter32
    }

-- {COLUMN} 1.3.6.1.4.1.2356.11.1.5.53.1.1
lcsStatusLanPacketTransportEntryIfc OBJECT-TYPE
    SYNTAX     DisplayString (SIZE(0..255))
    MAX-ACCESS read-only
    STATUS     current
    DESCRIPTION
            ""
    ::= { lcsStatusLanPacketTransportEntry 1 }

-- {COLUMN} 1.3.6.1.4.1.2356.11.1.5.53.1.2
lcsStatusLanPacketTransportEntryRxPackets OBJECT-TYPE
    SYNTAX     Counter32
    MAX-ACCESS read-only
    STATUS     current
    DESCRIPTION
            ""
    ::= { lcsStatusLanPacketTransportEntry 2 }

-- {COLUMN} 1.3.6.1.4.1.2356.11.1.5.53.1.3
lcsStatusLanPacketTransportEntryTxPackets OBJECT-TYPE
    SYNTAX     Counter32
    MAX-ACCESS read-only
    STATUS     current
    DESCRIPTION
            ""
    ::= { lcsStatusLanPacketTransportEntry 3 }

-- {COLUMN} 1.3.6.1.4.1.2356.11.1.5.53.1.4
lcsStatusLanPacketTransportEntryRxBroadcasts OBJECT-TYPE
    SYNTAX     Counter32
    MAX-ACCESS read-only
    STATUS     current
    DESCRIPTION
            ""
    ::= { lcsStatusLanPacketTransportEntry 4 }

-- {COLUMN} 1.3.6.1.4.1.2356.11.1.5.53.1.5
lcsStatusLanPacketTransportEntryRxMulticasts OBJECT-TYPE
    SYNTAX     Counter32
    MAX-ACCESS read-only
    STATUS     current
    DESCRIPTION
            ""
    ::= { lcsStatusLanPacketTransportEntry 5 }

-- {COLUMN} 1.3.6.1.4.1.2356.11.1.5.53.1.6
lcsStatusLanPacketTransportEntryRxUnicasts OBJECT-TYPE
    SYNTAX     Counter32
    MAX-ACCESS read-only
    STATUS     current
    DESCRIPTION
            ""
    ::= { lcsStatusLanPacketTransportEntry 6 }

-- {COLUMN} 1.3.6.1.4.1.2356.11.1.5.53.1.7
lcsStatusLanPacketTransportEntryTxBroadcasts OBJECT-TYPE
    SYNTAX     Counter32
    MAX-ACCESS read-only
    STATUS     current
    DESCRIPTION
            ""
    ::= { lcsStatusLanPacketTransportEntry 7 }

-- {COLUMN} 1.3.6.1.4.1.2356.11.1.5.53.1.8
lcsStatusLanPacketTransportEntryTxMulticasts OBJECT-TYPE
    SYNTAX     Counter32
    MAX-ACCESS read-only
    STATUS     current
    DESCRIPTION
            ""
    ::= { lcsStatusLanPacketTransportEntry 8 }

-- {COLUMN} 1.3.6.1.4.1.2356.11.1.5.53.1.9
lcsStatusLanPacketTransportEntryTxUnicasts OBJECT-TYPE
    SYNTAX     Counter32
    MAX-ACCESS read-only
    STATUS     current
    DESCRIPTION
            ""
    ::= { lcsStatusLanPacketTransportEntry 9 }

-- {TABLE} 1.3.6.1.4.1.2356.11.1.5.54
lcsStatusLanErrorsTable OBJECT-TYPE
    SYNTAX     SEQUENCE OF LcsStatusLanErrorsEntry
    MAX-ACCESS not-accessible
    STATUS     current
    DESCRIPTION
            ""
    ::= { lcsStatusLan 54 }

-- {ROW} 1.3.6.1.4.1.2356.11.1.5.54.1
lcsStatusLanErrorsEntry OBJECT-TYPE
    SYNTAX     LcsStatusLanErrorsEntry
    MAX-ACCESS not-accessible
    STATUS     current
    DESCRIPTION
            ""
    INDEX {
            lcsStatusLanErrorsEntryIfc
          }
    ::= { lcsStatusLanErrorsTable 1 }

LcsStatusLanErrorsEntry ::= SEQUENCE {
            lcsStatusLanErrorsEntryIfc DisplayString,
            lcsStatusLanErrorsEntryRxErrors Counter32,
            lcsStatusLanErrorsEntryTxErrors Counter32,
            lcsStatusLanErrorsEntryStackErrors Counter32,
            lcsStatusLanErrorsEntryNicErrors Counter32,
            lcsStatusLanErrorsEntryQueueErrors Counter32,
            lcsStatusLanErrorsEntryRxCrcErrors Counter32,
            lcsStatusLanErrorsEntryCollisions Counter32,
            lcsStatusLanErrorsEntrySingleCollisions Counter32,
            lcsStatusLanErrorsEntryMultipleCollisions Counter32,
            lcsStatusLanErrorsEntryLateCollisions Counter32,
            lcsStatusLanErrorsEntryExcessiveCollisions Counter32,
            lcsStatusLanErrorsEntryRxAlignErrors Counter32,
            lcsStatusLanErrorsEntryRxTooShort Counter32,
            lcsStatusLanErrorsEntryRxTooLong Counter32,
            lcsStatusLanErrorsEntryTxCarrier Counter32,
            lcsStatusLanErrorsEntryTxDeferred Counter32,
            lcsStatusLanErrorsEntryRxPhyErrors Counter32,
            lcsStatusLanErrorsEntryRxFifoOverflow Counter32,
            lcsStatusLanErrorsEntryTxDiscarded Counter32,
            lcsStatusLanErrorsEntryRxDscrUnderflow Counter32
    }

-- {COLUMN} 1.3.6.1.4.1.2356.11.1.5.54.1.1
lcsStatusLanErrorsEntryIfc OBJECT-TYPE
    SYNTAX     DisplayString (SIZE(0..255))
    MAX-ACCESS read-only
    STATUS     current
    DESCRIPTION
            ""
    ::= { lcsStatusLanErrorsEntry 1 }

-- {COLUMN} 1.3.6.1.4.1.2356.11.1.5.54.1.2
lcsStatusLanErrorsEntryRxErrors OBJECT-TYPE
    SYNTAX     Counter32
    MAX-ACCESS read-only
    STATUS     current
    DESCRIPTION
            ""
    ::= { lcsStatusLanErrorsEntry 2 }

-- {COLUMN} 1.3.6.1.4.1.2356.11.1.5.54.1.3
lcsStatusLanErrorsEntryTxErrors OBJECT-TYPE
    SYNTAX     Counter32
    MAX-ACCESS read-only
    STATUS     current
    DESCRIPTION
            ""
    ::= { lcsStatusLanErrorsEntry 3 }

-- {COLUMN} 1.3.6.1.4.1.2356.11.1.5.54.1.4
lcsStatusLanErrorsEntryStackErrors OBJECT-TYPE
    SYNTAX     Counter32
    MAX-ACCESS read-only
    STATUS     current
    DESCRIPTION
            ""
    ::= { lcsStatusLanErrorsEntry 4 }

-- {COLUMN} 1.3.6.1.4.1.2356.11.1.5.54.1.5
lcsStatusLanErrorsEntryNicErrors OBJECT-TYPE
    SYNTAX     Counter32
    MAX-ACCESS read-only
    STATUS     current
    DESCRIPTION
            ""
    ::= { lcsStatusLanErrorsEntry 5 }

-- {COLUMN} 1.3.6.1.4.1.2356.11.1.5.54.1.6
lcsStatusLanErrorsEntryQueueErrors OBJECT-TYPE
    SYNTAX     Counter32
    MAX-ACCESS read-only
    STATUS     current
    DESCRIPTION
            ""
    ::= { lcsStatusLanErrorsEntry 6 }

-- {COLUMN} 1.3.6.1.4.1.2356.11.1.5.54.1.7
lcsStatusLanErrorsEntryRxCrcErrors OBJECT-TYPE
    SYNTAX     Counter32
    MAX-ACCESS read-only
    STATUS     current
    DESCRIPTION
            ""
    ::= { lcsStatusLanErrorsEntry 7 }

-- {COLUMN} 1.3.6.1.4.1.2356.11.1.5.54.1.8
lcsStatusLanErrorsEntryCollisions OBJECT-TYPE
    SYNTAX     Counter32
    MAX-ACCESS read-only
    STATUS     current
    DESCRIPTION
            ""
    ::= { lcsStatusLanErrorsEntry 8 }

-- {COLUMN} 1.3.6.1.4.1.2356.11.1.5.54.1.9
lcsStatusLanErrorsEntrySingleCollisions OBJECT-TYPE
    SYNTAX     Counter32
    MAX-ACCESS read-only
    STATUS     current
    DESCRIPTION
            ""
    ::= { lcsStatusLanErrorsEntry 9 }

-- {COLUMN} 1.3.6.1.4.1.2356.11.1.5.54.1.10
lcsStatusLanErrorsEntryMultipleCollisions OBJECT-TYPE
    SYNTAX     Counter32
    MAX-ACCESS read-only
    STATUS     current
    DESCRIPTION
            ""
    ::= { lcsStatusLanErrorsEntry 10 }

-- {COLUMN} 1.3.6.1.4.1.2356.11.1.5.54.1.11
lcsStatusLanErrorsEntryLateCollisions OBJECT-TYPE
    SYNTAX     Counter32
    MAX-ACCESS read-only
    STATUS     current
    DESCRIPTION
            ""
    ::= { lcsStatusLanErrorsEntry 11 }

-- {COLUMN} 1.3.6.1.4.1.2356.11.1.5.54.1.12
lcsStatusLanErrorsEntryExcessiveCollisions OBJECT-TYPE
    SYNTAX     Counter32
    MAX-ACCESS read-only
    STATUS     current
    DESCRIPTION
            ""
    ::= { lcsStatusLanErrorsEntry 12 }

-- {COLUMN} 1.3.6.1.4.1.2356.11.1.5.54.1.13
lcsStatusLanErrorsEntryRxAlignErrors OBJECT-TYPE
    SYNTAX     Counter32
    MAX-ACCESS read-only
    STATUS     current
    DESCRIPTION
            ""
    ::= { lcsStatusLanErrorsEntry 13 }

-- {COLUMN} 1.3.6.1.4.1.2356.11.1.5.54.1.14
lcsStatusLanErrorsEntryRxTooShort OBJECT-TYPE
    SYNTAX     Counter32
    MAX-ACCESS read-only
    STATUS     current
    DESCRIPTION
            ""
    ::= { lcsStatusLanErrorsEntry 14 }

-- {COLUMN} 1.3.6.1.4.1.2356.11.1.5.54.1.15
lcsStatusLanErrorsEntryRxTooLong OBJECT-TYPE
    SYNTAX     Counter32
    MAX-ACCESS read-only
    STATUS     current
    DESCRIPTION
            ""
    ::= { lcsStatusLanErrorsEntry 15 }

-- {COLUMN} 1.3.6.1.4.1.2356.11.1.5.54.1.16
lcsStatusLanErrorsEntryTxCarrier OBJECT-TYPE
    SYNTAX     Counter32
    MAX-ACCESS read-only
    STATUS     current
    DESCRIPTION
            ""
    ::= { lcsStatusLanErrorsEntry 16 }

-- {COLUMN} 1.3.6.1.4.1.2356.11.1.5.54.1.17
lcsStatusLanErrorsEntryTxDeferred OBJECT-TYPE
    SYNTAX     Counter32
    MAX-ACCESS read-only
    STATUS     current
    DESCRIPTION
            ""
    ::= { lcsStatusLanErrorsEntry 17 }

-- {COLUMN} 1.3.6.1.4.1.2356.11.1.5.54.1.18
lcsStatusLanErrorsEntryRxPhyErrors OBJECT-TYPE
    SYNTAX     Counter32
    MAX-ACCESS read-only
    STATUS     current
    DESCRIPTION
            ""
    ::= { lcsStatusLanErrorsEntry 18 }

-- {COLUMN} 1.3.6.1.4.1.2356.11.1.5.54.1.19
lcsStatusLanErrorsEntryRxFifoOverflow OBJECT-TYPE
    SYNTAX     Counter32
    MAX-ACCESS read-only
    STATUS     current
    DESCRIPTION
            "-- empty --"
    ::= { lcsStatusLanErrorsEntry 19 }

-- {COLUMN} 1.3.6.1.4.1.2356.11.1.5.54.1.20
lcsStatusLanErrorsEntryTxDiscarded OBJECT-TYPE
    SYNTAX     Counter32
    MAX-ACCESS read-only
    STATUS     current
    DESCRIPTION
            "-- empty --"
    ::= { lcsStatusLanErrorsEntry 20 }

-- {COLUMN} 1.3.6.1.4.1.2356.11.1.5.54.1.21
lcsStatusLanErrorsEntryRxDscrUnderflow OBJECT-TYPE
    SYNTAX     Counter32
    MAX-ACCESS read-only
    STATUS     current
    DESCRIPTION
            "-- empty --"
    ::= { lcsStatusLanErrorsEntry 21 }

-- {SCALAR} 1.3.6.1.4.1.2356.11.1.5.60
lcsStatusLanLanQueueMgtDrop OBJECT-TYPE
    SYNTAX     Counter32
    MAX-ACCESS read-only
    STATUS     current
    DESCRIPTION
            ""
    ::= { lcsStatusLan 60 }

-- {SCALAR} 1.3.6.1.4.1.2356.11.1.5.70
lcsStatusLanCableTest OBJECT-TYPE
    SYNTAX     DisplayString
    MAX-ACCESS read-write
    STATUS     current
    DESCRIPTION
            ""
    ::= { lcsStatusLan 70 }

-- {TABLE} 1.3.6.1.4.1.2356.11.1.5.71
lcsStatusLanCableTestResultsTable OBJECT-TYPE
    SYNTAX     SEQUENCE OF LcsStatusLanCableTestResultsEntry
    MAX-ACCESS not-accessible
    STATUS     current
    DESCRIPTION
            ""
    ::= { lcsStatusLan 71 }

-- {ROW} 1.3.6.1.4.1.2356.11.1.5.71.1
lcsStatusLanCableTestResultsEntry OBJECT-TYPE
    SYNTAX     LcsStatusLanCableTestResultsEntry
    MAX-ACCESS not-accessible
    STATUS     current
    DESCRIPTION
            ""
    INDEX {
            lcsStatusLanCableTestResultsEntryIfc
          }
    ::= { lcsStatusLanCableTestResultsTable 1 }

LcsStatusLanCableTestResultsEntry ::= SEQUENCE {
            lcsStatusLanCableTestResultsEntryIfc INTEGER,
            lcsStatusLanCableTestResultsEntryMdi0Status INTEGER,
            lcsStatusLanCableTestResultsEntryMdi0Distance DisplayString,
            lcsStatusLanCableTestResultsEntryMdi1Status INTEGER,
            lcsStatusLanCableTestResultsEntryMdi1Distance DisplayString,
            lcsStatusLanCableTestResultsEntryMdi2Status INTEGER,
            lcsStatusLanCableTestResultsEntryMdi2Distance DisplayString,
            lcsStatusLanCableTestResultsEntryMdi3Status INTEGER,
            lcsStatusLanCableTestResultsEntryMdi3Distance DisplayString
    }

-- {COLUMN} 1.3.6.1.4.1.2356.11.1.5.71.1.1
lcsStatusLanCableTestResultsEntryIfc OBJECT-TYPE
    SYNTAX     INTEGER {
                  eLan1 (1),
                  eLan2 (2)
            }
    MAX-ACCESS read-only
    STATUS     current
    DESCRIPTION
            ""
    ::= { lcsStatusLanCableTestResultsEntry 1 }

-- {COLUMN} 1.3.6.1.4.1.2356.11.1.5.71.1.6
lcsStatusLanCableTestResultsEntryMdi0Status OBJECT-TYPE
    SYNTAX     INTEGER {
                  eUnknown (0),
                  eOk (1),
                  eOpen (2),
                  eShort (3),
                  eImpedanceFault (4),
                  eFail (5),
                  eBusy (6),
                  eLinkUp (7),
                  eInterPairShort (8),
                  eNotSupported (9)
            }
    MAX-ACCESS read-only
    STATUS     current
    DESCRIPTION
            ""
    ::= { lcsStatusLanCableTestResultsEntry 6 }

-- {COLUMN} 1.3.6.1.4.1.2356.11.1.5.71.1.7
lcsStatusLanCableTestResultsEntryMdi0Distance OBJECT-TYPE
    SYNTAX     DisplayString (SIZE(0..10))
    MAX-ACCESS read-only
    STATUS     current
    DESCRIPTION
            ""
    ::= { lcsStatusLanCableTestResultsEntry 7 }

-- {COLUMN} 1.3.6.1.4.1.2356.11.1.5.71.1.8
lcsStatusLanCableTestResultsEntryMdi1Status OBJECT-TYPE
    SYNTAX     INTEGER {
                  eUnknown (0),
                  eOk (1),
                  eOpen (2),
                  eShort (3),
                  eImpedanceFault (4),
                  eFail (5),
                  eBusy (6),
                  eLinkUp (7),
                  eInterPairShort (8),
                  eNotSupported (9)
            }
    MAX-ACCESS read-only
    STATUS     current
    DESCRIPTION
            ""
    ::= { lcsStatusLanCableTestResultsEntry 8 }

-- {COLUMN} 1.3.6.1.4.1.2356.11.1.5.71.1.9
lcsStatusLanCableTestResultsEntryMdi1Distance OBJECT-TYPE
    SYNTAX     DisplayString (SIZE(0..10))
    MAX-ACCESS read-only
    STATUS     current
    DESCRIPTION
            ""
    ::= { lcsStatusLanCableTestResultsEntry 9 }

-- {COLUMN} 1.3.6.1.4.1.2356.11.1.5.71.1.10
lcsStatusLanCableTestResultsEntryMdi2Status OBJECT-TYPE
    SYNTAX     INTEGER {
                  eUnknown (0),
                  eOk (1),
                  eOpen (2),
                  eShort (3),
                  eImpedanceFault (4),
                  eFail (5),
                  eBusy (6),
                  eLinkUp (7),
                  eInterPairShort (8),
                  eNotSupported (9)
            }
    MAX-ACCESS read-only
    STATUS     current
    DESCRIPTION
            ""
    ::= { lcsStatusLanCableTestResultsEntry 10 }

-- {COLUMN} 1.3.6.1.4.1.2356.11.1.5.71.1.11
lcsStatusLanCableTestResultsEntryMdi2Distance OBJECT-TYPE
    SYNTAX     DisplayString (SIZE(0..10))
    MAX-ACCESS read-only
    STATUS     current
    DESCRIPTION
            ""
    ::= { lcsStatusLanCableTestResultsEntry 11 }

-- {COLUMN} 1.3.6.1.4.1.2356.11.1.5.71.1.12
lcsStatusLanCableTestResultsEntryMdi3Status OBJECT-TYPE
    SYNTAX     INTEGER {
                  eUnknown (0),
                  eOk (1),
                  eOpen (2),
                  eShort (3),
                  eImpedanceFault (4),
                  eFail (5),
                  eBusy (6),
                  eLinkUp (7),
                  eInterPairShort (8),
                  eNotSupported (9)
            }
    MAX-ACCESS read-only
    STATUS     current
    DESCRIPTION
            ""
    ::= { lcsStatusLanCableTestResultsEntry 12 }

-- {COLUMN} 1.3.6.1.4.1.2356.11.1.5.71.1.13
lcsStatusLanCableTestResultsEntryMdi3Distance OBJECT-TYPE
    SYNTAX     DisplayString (SIZE(0..10))
    MAX-ACCESS read-only
    STATUS     current
    DESCRIPTION
            ""
    ::= { lcsStatusLanCableTestResultsEntry 13 }

-- {NODE} 1.3.6.1.4.1.2356.11.1.5.80
lcsStatusLanIeee8021x OBJECT IDENTIFIER ::= { lcsStatusLan 80 }

-- {TABLE} 1.3.6.1.4.1.2356.11.1.5.80.1
lcsStatusLanIeee8021xSupplicantIfcStateTable OBJECT-TYPE
    SYNTAX     SEQUENCE OF LcsStatusLanIeee8021xSupplicantIfcStateEntry
    MAX-ACCESS not-accessible
    STATUS     current
    DESCRIPTION
            ""
    ::= { lcsStatusLanIeee8021x 1 }

-- {ROW} 1.3.6.1.4.1.2356.11.1.5.80.1.1
lcsStatusLanIeee8021xSupplicantIfcStateEntry OBJECT-TYPE
    SYNTAX     LcsStatusLanIeee8021xSupplicantIfcStateEntry
    MAX-ACCESS not-accessible
    STATUS     current
    DESCRIPTION
            ""
    INDEX {
            lcsStatusLanIeee8021xSupplicantIfcStateEntryIfc
          }
    ::= { lcsStatusLanIeee8021xSupplicantIfcStateTable 1 }

LcsStatusLanIeee8021xSupplicantIfcStateEntry ::= SEQUENCE {
            lcsStatusLanIeee8021xSupplicantIfcStateEntryIfc INTEGER,
            lcsStatusLanIeee8021xSupplicantIfcStateEntryMethod INTEGER,
            lcsStatusLanIeee8021xSupplicantIfcStateEntryState INTEGER,
            lcsStatusLanIeee8021xSupplicantIfcStateEntryAuthenticatorAddress MacAddress
    }

-- {COLUMN} 1.3.6.1.4.1.2356.11.1.5.80.1.1.1
lcsStatusLanIeee8021xSupplicantIfcStateEntryIfc OBJECT-TYPE
    SYNTAX     INTEGER {
                  eLan1 (1),
                  eLan2 (2),
                  eLan3 (3),
                  eLan4 (4)
            }
    MAX-ACCESS read-only
    STATUS     current
    DESCRIPTION
            ""
    ::= { lcsStatusLanIeee8021xSupplicantIfcStateEntry 1 }

-- {COLUMN} 1.3.6.1.4.1.2356.11.1.5.80.1.1.2
lcsStatusLanIeee8021xSupplicantIfcStateEntryMethod OBJECT-TYPE
    SYNTAX     INTEGER {
                  eNone (0),
                  eMd5 (1024),
                  eTls (3328),
                  eTtlsMd5 (5380),
                  eTtlsPap (5383),
                  eTtlsChap (5384),
                  eTtlsMschapv2 (5402),
                  eTtlsMschap (5567),
                  ePeapGtc (6406),
                  ePeapMschapv2 (6426)
            }
    MAX-ACCESS read-only
    STATUS     current
    DESCRIPTION
            ""
    ::= { lcsStatusLanIeee8021xSupplicantIfcStateEntry 2 }

-- {COLUMN} 1.3.6.1.4.1.2356.11.1.5.80.1.1.3
lcsStatusLanIeee8021xSupplicantIfcStateEntryState OBJECT-TYPE
    SYNTAX     INTEGER {
                  eIdle (0),
                  eUnauthorized (1),
                  eAuthorized (2)
            }
    MAX-ACCESS read-only
    STATUS     current
    DESCRIPTION
            ""
    ::= { lcsStatusLanIeee8021xSupplicantIfcStateEntry 3 }

-- {COLUMN} 1.3.6.1.4.1.2356.11.1.5.80.1.1.4
lcsStatusLanIeee8021xSupplicantIfcStateEntryAuthenticatorAddress OBJECT-TYPE
    SYNTAX     MacAddress
    MAX-ACCESS read-only
    STATUS     current
    DESCRIPTION
            ""
    ::= { lcsStatusLanIeee8021xSupplicantIfcStateEntry 4 }

-- {TABLE} 1.3.6.1.4.1.2356.11.1.5.80.2
lcsStatusLanIeee8021xAuthenticatorIfcStatusTable OBJECT-TYPE
    SYNTAX     SEQUENCE OF LcsStatusLanIeee8021xAuthenticatorIfcStatusEntry
    MAX-ACCESS not-accessible
    STATUS     current
    DESCRIPTION
            "-- empty --"
    ::= { lcsStatusLanIeee8021x 2 }

-- {ROW} 1.3.6.1.4.1.2356.11.1.5.80.2.1
lcsStatusLanIeee8021xAuthenticatorIfcStatusEntry OBJECT-TYPE
    SYNTAX     LcsStatusLanIeee8021xAuthenticatorIfcStatusEntry
    MAX-ACCESS not-accessible
    STATUS     current
    DESCRIPTION
            ""
    INDEX {
            lcsStatusLanIeee8021xAuthenticatorIfcStatusEntryIfc
          }
    ::= { lcsStatusLanIeee8021xAuthenticatorIfcStatusTable 1 }

LcsStatusLanIeee8021xAuthenticatorIfcStatusEntry ::= SEQUENCE {
            lcsStatusLanIeee8021xAuthenticatorIfcStatusEntryIfc INTEGER,
            lcsStatusLanIeee8021xAuthenticatorIfcStatusEntryOperating INTEGER,
            lcsStatusLanIeee8021xAuthenticatorIfcStatusEntryMode INTEGER,
            lcsStatusLanIeee8021xAuthenticatorIfcStatusEntryState INTEGER,
            lcsStatusLanIeee8021xAuthenticatorIfcStatusEntryMacAddress MacAddress,
            lcsStatusLanIeee8021xAuthenticatorIfcStatusEntryAuthCount Integer32
    }

-- {COLUMN} 1.3.6.1.4.1.2356.11.1.5.80.2.1.1
lcsStatusLanIeee8021xAuthenticatorIfcStatusEntryIfc OBJECT-TYPE
    SYNTAX     INTEGER {
                  eLan1 (1),
                  eLan2 (2),
                  eLan3 (3),
                  eLan4 (4)
            }
    MAX-ACCESS read-only
    STATUS     current
    DESCRIPTION
            "-- empty --"
    ::= { lcsStatusLanIeee8021xAuthenticatorIfcStatusEntry 1 }

-- {COLUMN} 1.3.6.1.4.1.2356.11.1.5.80.2.1.2
lcsStatusLanIeee8021xAuthenticatorIfcStatusEntryOperating OBJECT-TYPE
    SYNTAX     INTEGER {
                  eNo (0),
                  eYes (1)
            }
    MAX-ACCESS read-only
    STATUS     current
    DESCRIPTION
            "-- empty --"
    ::= { lcsStatusLanIeee8021xAuthenticatorIfcStatusEntry 2 }

-- {COLUMN} 1.3.6.1.4.1.2356.11.1.5.80.2.1.3
lcsStatusLanIeee8021xAuthenticatorIfcStatusEntryMode OBJECT-TYPE
    SYNTAX     INTEGER {
                  eSingleHost (0),
                  eMultipleHost (1),
                  eMultipleAuth (2)
            }
    MAX-ACCESS read-only
    STATUS     current
    DESCRIPTION
            "-- empty --"
    ::= { lcsStatusLanIeee8021xAuthenticatorIfcStatusEntry 3 }

-- {COLUMN} 1.3.6.1.4.1.2356.11.1.5.80.2.1.4
lcsStatusLanIeee8021xAuthenticatorIfcStatusEntryState OBJECT-TYPE
    SYNTAX     INTEGER {
                  eOff (0),
                  eLinkLayerDown (1),
                  eOperating (2),
                  eUnauthenticated (3),
                  eAuthenticated (4),
                  eBlocked (5)
            }
    MAX-ACCESS read-only
    STATUS     current
    DESCRIPTION
            "-- empty --"
    ::= { lcsStatusLanIeee8021xAuthenticatorIfcStatusEntry 4 }

-- {COLUMN} 1.3.6.1.4.1.2356.11.1.5.80.2.1.5
lcsStatusLanIeee8021xAuthenticatorIfcStatusEntryMacAddress OBJECT-TYPE
    SYNTAX     MacAddress
    MAX-ACCESS read-only
    STATUS     current
    DESCRIPTION
            "-- empty --"
    ::= { lcsStatusLanIeee8021xAuthenticatorIfcStatusEntry 5 }

-- {COLUMN} 1.3.6.1.4.1.2356.11.1.5.80.2.1.6
lcsStatusLanIeee8021xAuthenticatorIfcStatusEntryAuthCount OBJECT-TYPE
    SYNTAX     Integer32 (0..2147483647)
    MAX-ACCESS read-only
    STATUS     current
    DESCRIPTION
            "-- empty --"
    ::= { lcsStatusLanIeee8021xAuthenticatorIfcStatusEntry 6 }

-- {NODE} 1.3.6.1.4.1.2356.11.1.5.81
lcsStatusLanInterfaceBundling OBJECT IDENTIFIER ::= { lcsStatusLan 81 }

-- {TABLE} 1.3.6.1.4.1.2356.11.1.5.81.1
lcsStatusLanInterfaceBundlingInterfacesTable OBJECT-TYPE
    SYNTAX     SEQUENCE OF LcsStatusLanInterfaceBundlingInterfacesEntry
    MAX-ACCESS not-accessible
    STATUS     current
    DESCRIPTION
            "-- empty --"
    ::= { lcsStatusLanInterfaceBundling 1 }

-- {ROW} 1.3.6.1.4.1.2356.11.1.5.81.1.1
lcsStatusLanInterfaceBundlingInterfacesEntry OBJECT-TYPE
    SYNTAX     LcsStatusLanInterfaceBundlingInterfacesEntry
    MAX-ACCESS not-accessible
    STATUS     current
    DESCRIPTION
            ""
    INDEX {
            lcsStatusLanInterfaceBundlingInterfacesEntryInterface
          }
    ::= { lcsStatusLanInterfaceBundlingInterfacesTable 1 }

LcsStatusLanInterfaceBundlingInterfacesEntry ::= SEQUENCE {
            lcsStatusLanInterfaceBundlingInterfacesEntryInterface DisplayString,
            lcsStatusLanInterfaceBundlingInterfacesEntryStatus INTEGER,
            lcsStatusLanInterfaceBundlingInterfacesEntryInterfaceA INTEGER,
            lcsStatusLanInterfaceBundlingInterfacesEntryInterfaceB INTEGER
    }

-- {COLUMN} 1.3.6.1.4.1.2356.11.1.5.81.1.1.1
lcsStatusLanInterfaceBundlingInterfacesEntryInterface OBJECT-TYPE
    SYNTAX     DisplayString (SIZE(0..255))
    MAX-ACCESS read-only
    STATUS     current
    DESCRIPTION
            "-- empty --"
    ::= { lcsStatusLanInterfaceBundlingInterfacesEntry 1 }

-- {COLUMN} 1.3.6.1.4.1.2356.11.1.5.81.1.1.2
lcsStatusLanInterfaceBundlingInterfacesEntryStatus OBJECT-TYPE
    SYNTAX     INTEGER {
                  eIdle (0),
                  eConfigError (1),
                  eStatupError (2),
                  eRunning (3)
            }
    MAX-ACCESS read-only
    STATUS     current
    DESCRIPTION
            "-- empty --"
    ::= { lcsStatusLanInterfaceBundlingInterfacesEntry 2 }

-- {COLUMN} 1.3.6.1.4.1.2356.11.1.5.81.1.1.5
lcsStatusLanInterfaceBundlingInterfacesEntryInterfaceA OBJECT-TYPE
    SYNTAX     INTEGER {
                  eNone (0),
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eXdsl1 (2816),
                  eXdsl2 (2817)
            }
    MAX-ACCESS read-only
    STATUS     current
    DESCRIPTION
            "-- empty --"
    ::= { lcsStatusLanInterfaceBundlingInterfacesEntry 5 }

-- {COLUMN} 1.3.6.1.4.1.2356.11.1.5.81.1.1.6
lcsStatusLanInterfaceBundlingInterfacesEntryInterfaceB OBJECT-TYPE
    SYNTAX     INTEGER {
                  eNone (0),
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eXdsl1 (2816),
                  eXdsl2 (2817)
            }
    MAX-ACCESS read-only
    STATUS     current
    DESCRIPTION
            "-- empty --"
    ::= { lcsStatusLanInterfaceBundlingInterfacesEntry 6 }

-- {TABLE} 1.3.6.1.4.1.2356.11.1.5.81.2
lcsStatusLanInterfaceBundlingByteTransportTable OBJECT-TYPE
    SYNTAX     SEQUENCE OF LcsStatusLanInterfaceBundlingByteTransportEntry
    MAX-ACCESS not-accessible
    STATUS     current
    DESCRIPTION
            "-- empty --"
    ::= { lcsStatusLanInterfaceBundling 2 }

-- {ROW} 1.3.6.1.4.1.2356.11.1.5.81.2.1
lcsStatusLanInterfaceBundlingByteTransportEntry OBJECT-TYPE
    SYNTAX     LcsStatusLanInterfaceBundlingByteTransportEntry
    MAX-ACCESS not-accessible
    STATUS     current
    DESCRIPTION
            ""
    INDEX {
            lcsStatusLanInterfaceBundlingByteTransportEntryIfc
          }
    ::= { lcsStatusLanInterfaceBundlingByteTransportTable 1 }

LcsStatusLanInterfaceBundlingByteTransportEntry ::= SEQUENCE {
            lcsStatusLanInterfaceBundlingByteTransportEntryIfc DisplayString,
            lcsStatusLanInterfaceBundlingByteTransportEntryTxBytes Counter64,
            lcsStatusLanInterfaceBundlingByteTransportEntryRxBytes Counter64,
            lcsStatusLanInterfaceBundlingByteTransportEntryThroughput DisplayString,
            lcsStatusLanInterfaceBundlingByteTransportEntryMaxThroughput DisplayString,
            lcsStatusLanInterfaceBundlingByteTransportEntryBytesThroughput Integer32,
            lcsStatusLanInterfaceBundlingByteTransportEntryBytesMaxThrpt Integer32
    }

-- {COLUMN} 1.3.6.1.4.1.2356.11.1.5.81.2.1.1
lcsStatusLanInterfaceBundlingByteTransportEntryIfc OBJECT-TYPE
    SYNTAX     DisplayString (SIZE(0..255))
    MAX-ACCESS read-only
    STATUS     current
    DESCRIPTION
            "-- empty --"
    ::= { lcsStatusLanInterfaceBundlingByteTransportEntry 1 }

-- {COLUMN} 1.3.6.1.4.1.2356.11.1.5.81.2.1.2
lcsStatusLanInterfaceBundlingByteTransportEntryTxBytes OBJECT-TYPE
    SYNTAX     Counter64
    MAX-ACCESS read-only
    STATUS     current
    DESCRIPTION
            "-- empty --"
    ::= { lcsStatusLanInterfaceBundlingByteTransportEntry 2 }

-- {COLUMN} 1.3.6.1.4.1.2356.11.1.5.81.2.1.3
lcsStatusLanInterfaceBundlingByteTransportEntryRxBytes OBJECT-TYPE
    SYNTAX     Counter64
    MAX-ACCESS read-only
    STATUS     current
    DESCRIPTION
            "-- empty --"
    ::= { lcsStatusLanInterfaceBundlingByteTransportEntry 3 }

-- {COLUMN} 1.3.6.1.4.1.2356.11.1.5.81.2.1.4
lcsStatusLanInterfaceBundlingByteTransportEntryThroughput OBJECT-TYPE
    SYNTAX     DisplayString (SIZE(0..255))
    MAX-ACCESS read-only
    STATUS     current
    DESCRIPTION
            "-- empty --"
    ::= { lcsStatusLanInterfaceBundlingByteTransportEntry 4 }

-- {COLUMN} 1.3.6.1.4.1.2356.11.1.5.81.2.1.5
lcsStatusLanInterfaceBundlingByteTransportEntryMaxThroughput OBJECT-TYPE
    SYNTAX     DisplayString (SIZE(0..255))
    MAX-ACCESS read-only
    STATUS     current
    DESCRIPTION
            "-- empty --"
    ::= { lcsStatusLanInterfaceBundlingByteTransportEntry 5 }

-- {COLUMN} 1.3.6.1.4.1.2356.11.1.5.81.2.1.6
lcsStatusLanInterfaceBundlingByteTransportEntryBytesThroughput OBJECT-TYPE
    SYNTAX     Integer32 (0..2147483647)
    MAX-ACCESS read-only
    STATUS     current
    DESCRIPTION
            "-- empty --"
    ::= { lcsStatusLanInterfaceBundlingByteTransportEntry 6 }

-- {COLUMN} 1.3.6.1.4.1.2356.11.1.5.81.2.1.7
lcsStatusLanInterfaceBundlingByteTransportEntryBytesMaxThrpt OBJECT-TYPE
    SYNTAX     Integer32 (0..2147483647)
    MAX-ACCESS read-only
    STATUS     current
    DESCRIPTION
            ""
    ::= { lcsStatusLanInterfaceBundlingByteTransportEntry 7 }

-- {TABLE} 1.3.6.1.4.1.2356.11.1.5.81.3
lcsStatusLanInterfaceBundlingPacketTransportTable OBJECT-TYPE
    SYNTAX     SEQUENCE OF LcsStatusLanInterfaceBundlingPacketTransportEntry
    MAX-ACCESS not-accessible
    STATUS     current
    DESCRIPTION
            "-- empty --"
    ::= { lcsStatusLanInterfaceBundling 3 }

-- {ROW} 1.3.6.1.4.1.2356.11.1.5.81.3.1
lcsStatusLanInterfaceBundlingPacketTransportEntry OBJECT-TYPE
    SYNTAX     LcsStatusLanInterfaceBundlingPacketTransportEntry
    MAX-ACCESS not-accessible
    STATUS     current
    DESCRIPTION
            ""
    INDEX {
            lcsStatusLanInterfaceBundlingPacketTransportEntryIfc
          }
    ::= { lcsStatusLanInterfaceBundlingPacketTransportTable 1 }

LcsStatusLanInterfaceBundlingPacketTransportEntry ::= SEQUENCE {
            lcsStatusLanInterfaceBundlingPacketTransportEntryIfc DisplayString,
            lcsStatusLanInterfaceBundlingPacketTransportEntryRxPackets Counter32,
            lcsStatusLanInterfaceBundlingPacketTransportEntryTxPackets Counter32,
            lcsStatusLanInterfaceBundlingPacketTransportEntryRxBroadcasts Counter32,
            lcsStatusLanInterfaceBundlingPacketTransportEntryRxMulticasts Counter32,
            lcsStatusLanInterfaceBundlingPacketTransportEntryRxUnicasts Counter32,
            lcsStatusLanInterfaceBundlingPacketTransportEntryTxBroadcasts Counter32,
            lcsStatusLanInterfaceBundlingPacketTransportEntryTxMulticasts Counter32,
            lcsStatusLanInterfaceBundlingPacketTransportEntryTxUnicasts Counter32
    }

-- {COLUMN} 1.3.6.1.4.1.2356.11.1.5.81.3.1.1
lcsStatusLanInterfaceBundlingPacketTransportEntryIfc OBJECT-TYPE
    SYNTAX     DisplayString (SIZE(0..255))
    MAX-ACCESS read-only
    STATUS     current
    DESCRIPTION
            "-- empty --"
    ::= { lcsStatusLanInterfaceBundlingPacketTransportEntry 1 }

-- {COLUMN} 1.3.6.1.4.1.2356.11.1.5.81.3.1.2
lcsStatusLanInterfaceBundlingPacketTransportEntryRxPackets OBJECT-TYPE
    SYNTAX     Counter32
    MAX-ACCESS read-only
    STATUS     current
    DESCRIPTION
            "-- empty --"
    ::= { lcsStatusLanInterfaceBundlingPacketTransportEntry 2 }

-- {COLUMN} 1.3.6.1.4.1.2356.11.1.5.81.3.1.3
lcsStatusLanInterfaceBundlingPacketTransportEntryTxPackets OBJECT-TYPE
    SYNTAX     Counter32
    MAX-ACCESS read-only
    STATUS     current
    DESCRIPTION
            "-- empty --"
    ::= { lcsStatusLanInterfaceBundlingPacketTransportEntry 3 }

-- {COLUMN} 1.3.6.1.4.1.2356.11.1.5.81.3.1.4
lcsStatusLanInterfaceBundlingPacketTransportEntryRxBroadcasts OBJECT-TYPE
    SYNTAX     Counter32
    MAX-ACCESS read-only
    STATUS     current
    DESCRIPTION
            "-- empty --"
    ::= { lcsStatusLanInterfaceBundlingPacketTransportEntry 4 }

-- {COLUMN} 1.3.6.1.4.1.2356.11.1.5.81.3.1.5
lcsStatusLanInterfaceBundlingPacketTransportEntryRxMulticasts OBJECT-TYPE
    SYNTAX     Counter32
    MAX-ACCESS read-only
    STATUS     current
    DESCRIPTION
            "-- empty --"
    ::= { lcsStatusLanInterfaceBundlingPacketTransportEntry 5 }

-- {COLUMN} 1.3.6.1.4.1.2356.11.1.5.81.3.1.6
lcsStatusLanInterfaceBundlingPacketTransportEntryRxUnicasts OBJECT-TYPE
    SYNTAX     Counter32
    MAX-ACCESS read-only
    STATUS     current
    DESCRIPTION
            "-- empty --"
    ::= { lcsStatusLanInterfaceBundlingPacketTransportEntry 6 }

-- {COLUMN} 1.3.6.1.4.1.2356.11.1.5.81.3.1.7
lcsStatusLanInterfaceBundlingPacketTransportEntryTxBroadcasts OBJECT-TYPE
    SYNTAX     Counter32
    MAX-ACCESS read-only
    STATUS     current
    DESCRIPTION
            "-- empty --"
    ::= { lcsStatusLanInterfaceBundlingPacketTransportEntry 7 }

-- {COLUMN} 1.3.6.1.4.1.2356.11.1.5.81.3.1.8
lcsStatusLanInterfaceBundlingPacketTransportEntryTxMulticasts OBJECT-TYPE
    SYNTAX     Counter32
    MAX-ACCESS read-only
    STATUS     current
    DESCRIPTION
            "-- empty --"
    ::= { lcsStatusLanInterfaceBundlingPacketTransportEntry 8 }

-- {COLUMN} 1.3.6.1.4.1.2356.11.1.5.81.3.1.9
lcsStatusLanInterfaceBundlingPacketTransportEntryTxUnicasts OBJECT-TYPE
    SYNTAX     Counter32
    MAX-ACCESS read-only
    STATUS     current
    DESCRIPTION
            "-- empty --"
    ::= { lcsStatusLanInterfaceBundlingPacketTransportEntry 9 }

-- {TABLE} 1.3.6.1.4.1.2356.11.1.5.81.4
lcsStatusLanInterfaceBundlingErrorsTable OBJECT-TYPE
    SYNTAX     SEQUENCE OF LcsStatusLanInterfaceBundlingErrorsEntry
    MAX-ACCESS not-accessible
    STATUS     current
    DESCRIPTION
            "-- empty --"
    ::= { lcsStatusLanInterfaceBundling 4 }

-- {ROW} 1.3.6.1.4.1.2356.11.1.5.81.4.1
lcsStatusLanInterfaceBundlingErrorsEntry OBJECT-TYPE
    SYNTAX     LcsStatusLanInterfaceBundlingErrorsEntry
    MAX-ACCESS not-accessible
    STATUS     current
    DESCRIPTION
            ""
    INDEX {
            lcsStatusLanInterfaceBundlingErrorsEntryIfc
          }
    ::= { lcsStatusLanInterfaceBundlingErrorsTable 1 }

LcsStatusLanInterfaceBundlingErrorsEntry ::= SEQUENCE {
            lcsStatusLanInterfaceBundlingErrorsEntryIfc DisplayString,
            lcsStatusLanInterfaceBundlingErrorsEntryTxDiscarded Counter32
    }

-- {COLUMN} 1.3.6.1.4.1.2356.11.1.5.81.4.1.1
lcsStatusLanInterfaceBundlingErrorsEntryIfc OBJECT-TYPE
    SYNTAX     DisplayString (SIZE(0..255))
    MAX-ACCESS read-only
    STATUS     current
    DESCRIPTION
            "-- empty --"
    ::= { lcsStatusLanInterfaceBundlingErrorsEntry 1 }

-- {COLUMN} 1.3.6.1.4.1.2356.11.1.5.81.4.1.2
lcsStatusLanInterfaceBundlingErrorsEntryTxDiscarded OBJECT-TYPE
    SYNTAX     Counter32
    MAX-ACCESS read-only
    STATUS     current
    DESCRIPTION
            "-- empty --"
    ::= { lcsStatusLanInterfaceBundlingErrorsEntry 2 }

-- {NODE} 1.3.6.1.4.1.2356.11.1.5.81.11
lcsStatusLanInterfaceBundlingPrp OBJECT IDENTIFIER ::= { lcsStatusLanInterfaceBundling 11 }

-- {TABLE} 1.3.6.1.4.1.2356.11.1.5.81.11.1
lcsStatusLanInterfaceBundlingPrpInterfacesTable OBJECT-TYPE
    SYNTAX     SEQUENCE OF LcsStatusLanInterfaceBundlingPrpInterfacesEntry
    MAX-ACCESS not-accessible
    STATUS     current
    DESCRIPTION
            "-- empty --"
    ::= { lcsStatusLanInterfaceBundlingPrp 1 }

-- {ROW} 1.3.6.1.4.1.2356.11.1.5.81.11.1.1
lcsStatusLanInterfaceBundlingPrpInterfacesEntry OBJECT-TYPE
    SYNTAX     LcsStatusLanInterfaceBundlingPrpInterfacesEntry
    MAX-ACCESS not-accessible
    STATUS     current
    DESCRIPTION
            ""
    INDEX {
            lcsStatusLanInterfaceBundlingPrpInterfacesEntryInterface
          }
    ::= { lcsStatusLanInterfaceBundlingPrpInterfacesTable 1 }

LcsStatusLanInterfaceBundlingPrpInterfacesEntry ::= SEQUENCE {
            lcsStatusLanInterfaceBundlingPrpInterfacesEntryInterface DisplayString,
            lcsStatusLanInterfaceBundlingPrpInterfacesEntryCnterrora Integer32,
            lcsStatusLanInterfaceBundlingPrpInterfacesEntryCnterrorb Integer32,
            lcsStatusLanInterfaceBundlingPrpInterfacesEntryCntreceiveda Integer32,
            lcsStatusLanInterfaceBundlingPrpInterfacesEntryCntreceivedb Integer32,
            lcsStatusLanInterfaceBundlingPrpInterfacesEntryCnterrwronglana Integer32,
            lcsStatusLanInterfaceBundlingPrpInterfacesEntryCnterrwronglanb Integer32,
            lcsStatusLanInterfaceBundlingPrpInterfacesEntryActivea INTEGER,
            lcsStatusLanInterfaceBundlingPrpInterfacesEntryActiveb INTEGER,
            lcsStatusLanInterfaceBundlingPrpInterfacesEntryCntuniquea Integer32,
            lcsStatusLanInterfaceBundlingPrpInterfacesEntryCntuniqueb Integer32,
            lcsStatusLanInterfaceBundlingPrpInterfacesEntryCntduplicatea Integer32,
            lcsStatusLanInterfaceBundlingPrpInterfacesEntryCntduplicateb Integer32,
            lcsStatusLanInterfaceBundlingPrpInterfacesEntryCntmultia Integer32,
            lcsStatusLanInterfaceBundlingPrpInterfacesEntryCntmultib Integer32
    }

-- {COLUMN} 1.3.6.1.4.1.2356.11.1.5.81.11.1.1.1
lcsStatusLanInterfaceBundlingPrpInterfacesEntryInterface OBJECT-TYPE
    SYNTAX     DisplayString (SIZE(0..255))
    MAX-ACCESS read-only
    STATUS     current
    DESCRIPTION
            "-- empty --"
    ::= { lcsStatusLanInterfaceBundlingPrpInterfacesEntry 1 }

-- {COLUMN} 1.3.6.1.4.1.2356.11.1.5.81.11.1.1.2
lcsStatusLanInterfaceBundlingPrpInterfacesEntryCnterrora OBJECT-TYPE
    SYNTAX     Integer32 (0..2147483647)
    MAX-ACCESS read-only
    STATUS     current
    DESCRIPTION
            "-- empty --"
    ::= { lcsStatusLanInterfaceBundlingPrpInterfacesEntry 2 }

-- {COLUMN} 1.3.6.1.4.1.2356.11.1.5.81.11.1.1.3
lcsStatusLanInterfaceBundlingPrpInterfacesEntryCnterrorb OBJECT-TYPE
    SYNTAX     Integer32 (0..2147483647)
    MAX-ACCESS read-only
    STATUS     current
    DESCRIPTION
            "-- empty --"
    ::= { lcsStatusLanInterfaceBundlingPrpInterfacesEntry 3 }

-- {COLUMN} 1.3.6.1.4.1.2356.11.1.5.81.11.1.1.4
lcsStatusLanInterfaceBundlingPrpInterfacesEntryCntreceiveda OBJECT-TYPE
    SYNTAX     Integer32 (0..2147483647)
    MAX-ACCESS read-only
    STATUS     current
    DESCRIPTION
            "-- empty --"
    ::= { lcsStatusLanInterfaceBundlingPrpInterfacesEntry 4 }

-- {COLUMN} 1.3.6.1.4.1.2356.11.1.5.81.11.1.1.5
lcsStatusLanInterfaceBundlingPrpInterfacesEntryCntreceivedb OBJECT-TYPE
    SYNTAX     Integer32 (0..2147483647)
    MAX-ACCESS read-only
    STATUS     current
    DESCRIPTION
            "-- empty --"
    ::= { lcsStatusLanInterfaceBundlingPrpInterfacesEntry 5 }

-- {COLUMN} 1.3.6.1.4.1.2356.11.1.5.81.11.1.1.6
lcsStatusLanInterfaceBundlingPrpInterfacesEntryCnterrwronglana OBJECT-TYPE
    SYNTAX     Integer32 (0..2147483647)
    MAX-ACCESS read-only
    STATUS     current
    DESCRIPTION
            "-- empty --"
    ::= { lcsStatusLanInterfaceBundlingPrpInterfacesEntry 6 }

-- {COLUMN} 1.3.6.1.4.1.2356.11.1.5.81.11.1.1.7
lcsStatusLanInterfaceBundlingPrpInterfacesEntryCnterrwronglanb OBJECT-TYPE
    SYNTAX     Integer32 (0..2147483647)
    MAX-ACCESS read-only
    STATUS     current
    DESCRIPTION
            "-- empty --"
    ::= { lcsStatusLanInterfaceBundlingPrpInterfacesEntry 7 }

-- {COLUMN} 1.3.6.1.4.1.2356.11.1.5.81.11.1.1.8
lcsStatusLanInterfaceBundlingPrpInterfacesEntryActivea OBJECT-TYPE
    SYNTAX     INTEGER {
                  eNo (0),
                  eYes (1)
            }
    MAX-ACCESS read-only
    STATUS     current
    DESCRIPTION
            "-- empty --"
    ::= { lcsStatusLanInterfaceBundlingPrpInterfacesEntry 8 }

-- {COLUMN} 1.3.6.1.4.1.2356.11.1.5.81.11.1.1.9
lcsStatusLanInterfaceBundlingPrpInterfacesEntryActiveb OBJECT-TYPE
    SYNTAX     INTEGER {
                  eNo (0),
                  eYes (1)
            }
    MAX-ACCESS read-only
    STATUS     current
    DESCRIPTION
            "-- empty --"
    ::= { lcsStatusLanInterfaceBundlingPrpInterfacesEntry 9 }

-- {COLUMN} 1.3.6.1.4.1.2356.11.1.5.81.11.1.1.10
lcsStatusLanInterfaceBundlingPrpInterfacesEntryCntuniquea OBJECT-TYPE
    SYNTAX     Integer32 (0..2147483647)
    MAX-ACCESS read-only
    STATUS     current
    DESCRIPTION
            "-- empty --"
    ::= { lcsStatusLanInterfaceBundlingPrpInterfacesEntry 10 }

-- {COLUMN} 1.3.6.1.4.1.2356.11.1.5.81.11.1.1.11
lcsStatusLanInterfaceBundlingPrpInterfacesEntryCntuniqueb OBJECT-TYPE
    SYNTAX     Integer32 (0..2147483647)
    MAX-ACCESS read-only
    STATUS     current
    DESCRIPTION
            "-- empty --"
    ::= { lcsStatusLanInterfaceBundlingPrpInterfacesEntry 11 }

-- {COLUMN} 1.3.6.1.4.1.2356.11.1.5.81.11.1.1.12
lcsStatusLanInterfaceBundlingPrpInterfacesEntryCntduplicatea OBJECT-TYPE
    SYNTAX     Integer32 (0..2147483647)
    MAX-ACCESS read-only
    STATUS     current
    DESCRIPTION
            "-- empty --"
    ::= { lcsStatusLanInterfaceBundlingPrpInterfacesEntry 12 }

-- {COLUMN} 1.3.6.1.4.1.2356.11.1.5.81.11.1.1.13
lcsStatusLanInterfaceBundlingPrpInterfacesEntryCntduplicateb OBJECT-TYPE
    SYNTAX     Integer32 (0..2147483647)
    MAX-ACCESS read-only
    STATUS     current
    DESCRIPTION
            "-- empty --"
    ::= { lcsStatusLanInterfaceBundlingPrpInterfacesEntry 13 }

-- {COLUMN} 1.3.6.1.4.1.2356.11.1.5.81.11.1.1.14
lcsStatusLanInterfaceBundlingPrpInterfacesEntryCntmultia OBJECT-TYPE
    SYNTAX     Integer32 (0..2147483647)
    MAX-ACCESS read-only
    STATUS     current
    DESCRIPTION
            "-- empty --"
    ::= { lcsStatusLanInterfaceBundlingPrpInterfacesEntry 14 }

-- {COLUMN} 1.3.6.1.4.1.2356.11.1.5.81.11.1.1.15
lcsStatusLanInterfaceBundlingPrpInterfacesEntryCntmultib OBJECT-TYPE
    SYNTAX     Integer32 (0..2147483647)
    MAX-ACCESS read-only
    STATUS     current
    DESCRIPTION
            "-- empty --"
    ::= { lcsStatusLanInterfaceBundlingPrpInterfacesEntry 15 }

-- {TABLE} 1.3.6.1.4.1.2356.11.1.5.81.11.2
lcsStatusLanInterfaceBundlingPrpNodeTableTable OBJECT-TYPE
    SYNTAX     SEQUENCE OF LcsStatusLanInterfaceBundlingPrpNodeTableEntry
    MAX-ACCESS not-accessible
    STATUS     current
    DESCRIPTION
            "-- empty --"
    ::= { lcsStatusLanInterfaceBundlingPrp 2 }

-- {ROW} 1.3.6.1.4.1.2356.11.1.5.81.11.2.1
lcsStatusLanInterfaceBundlingPrpNodeTableEntry OBJECT-TYPE
    SYNTAX     LcsStatusLanInterfaceBundlingPrpNodeTableEntry
    MAX-ACCESS not-accessible
    STATUS     current
    DESCRIPTION
            ""
    INDEX {
            lcsStatusLanInterfaceBundlingPrpNodeTableEntryInterface,
            lcsStatusLanInterfaceBundlingPrpNodeTableEntryMacAddress
          }
    ::= { lcsStatusLanInterfaceBundlingPrpNodeTableTable 1 }

LcsStatusLanInterfaceBundlingPrpNodeTableEntry ::= SEQUENCE {
            lcsStatusLanInterfaceBundlingPrpNodeTableEntryInterface DisplayString,
            lcsStatusLanInterfaceBundlingPrpNodeTableEntryMacAddress MacAddress,
            lcsStatusLanInterfaceBundlingPrpNodeTableEntryType INTEGER,
            lcsStatusLanInterfaceBundlingPrpNodeTableEntryDuplicateMode INTEGER,
            lcsStatusLanInterfaceBundlingPrpNodeTableEntryTimelastseena Integer32,
            lcsStatusLanInterfaceBundlingPrpNodeTableEntryTimelastseenb Integer32,
            lcsStatusLanInterfaceBundlingPrpNodeTableEntryCntreceiveda Integer32,
            lcsStatusLanInterfaceBundlingPrpNodeTableEntryCntreceivedb Integer32,
            lcsStatusLanInterfaceBundlingPrpNodeTableEntryCnterrwronglana Integer32,
            lcsStatusLanInterfaceBundlingPrpNodeTableEntryCnterrwronglanb Integer32,
            lcsStatusLanInterfaceBundlingPrpNodeTableEntryNumEntries Integer32
    }

-- {COLUMN} 1.3.6.1.4.1.2356.11.1.5.81.11.2.1.1
lcsStatusLanInterfaceBundlingPrpNodeTableEntryInterface OBJECT-TYPE
    SYNTAX     DisplayString (SIZE(0..255))
    MAX-ACCESS read-only
    STATUS     current
    DESCRIPTION
            "-- empty --"
    ::= { lcsStatusLanInterfaceBundlingPrpNodeTableEntry 1 }

-- {COLUMN} 1.3.6.1.4.1.2356.11.1.5.81.11.2.1.2
lcsStatusLanInterfaceBundlingPrpNodeTableEntryMacAddress OBJECT-TYPE
    SYNTAX     MacAddress
    MAX-ACCESS read-only
    STATUS     current
    DESCRIPTION
            "-- empty --"
    ::= { lcsStatusLanInterfaceBundlingPrpNodeTableEntry 2 }

-- {COLUMN} 1.3.6.1.4.1.2356.11.1.5.81.11.2.1.3
lcsStatusLanInterfaceBundlingPrpNodeTableEntryType OBJECT-TYPE
    SYNTAX     INTEGER {
                  eUnknown (0),
                  eSana (1),
                  eSanb (2),
                  eSanab (3),
                  eDanp (4),
                  eVdanp (5),
                  eRedboxp (6)
            }
    MAX-ACCESS read-only
    STATUS     current
    DESCRIPTION
            "-- empty --"
    ::= { lcsStatusLanInterfaceBundlingPrpNodeTableEntry 3 }

-- {COLUMN} 1.3.6.1.4.1.2356.11.1.5.81.11.2.1.4
lcsStatusLanInterfaceBundlingPrpNodeTableEntryDuplicateMode OBJECT-TYPE
    SYNTAX     INTEGER {
                  eNone (0),
                  eAccept (1),
                  eDiscard (2)
            }
    MAX-ACCESS read-only
    STATUS     current
    DESCRIPTION
            "-- empty --"
    ::= { lcsStatusLanInterfaceBundlingPrpNodeTableEntry 4 }

-- {COLUMN} 1.3.6.1.4.1.2356.11.1.5.81.11.2.1.5
lcsStatusLanInterfaceBundlingPrpNodeTableEntryTimelastseena OBJECT-TYPE
    SYNTAX     Integer32 (0..2147483647)
    MAX-ACCESS read-only
    STATUS     current
    DESCRIPTION
            "-- empty --"
    ::= { lcsStatusLanInterfaceBundlingPrpNodeTableEntry 5 }

-- {COLUMN} 1.3.6.1.4.1.2356.11.1.5.81.11.2.1.6
lcsStatusLanInterfaceBundlingPrpNodeTableEntryTimelastseenb OBJECT-TYPE
    SYNTAX     Integer32 (0..2147483647)
    MAX-ACCESS read-only
    STATUS     current
    DESCRIPTION
            "-- empty --"
    ::= { lcsStatusLanInterfaceBundlingPrpNodeTableEntry 6 }

-- {COLUMN} 1.3.6.1.4.1.2356.11.1.5.81.11.2.1.7
lcsStatusLanInterfaceBundlingPrpNodeTableEntryCntreceiveda OBJECT-TYPE
    SYNTAX     Integer32 (0..2147483647)
    MAX-ACCESS read-only
    STATUS     current
    DESCRIPTION
            "-- empty --"
    ::= { lcsStatusLanInterfaceBundlingPrpNodeTableEntry 7 }

-- {COLUMN} 1.3.6.1.4.1.2356.11.1.5.81.11.2.1.8
lcsStatusLanInterfaceBundlingPrpNodeTableEntryCntreceivedb OBJECT-TYPE
    SYNTAX     Integer32 (0..2147483647)
    MAX-ACCESS read-only
    STATUS     current
    DESCRIPTION
            "-- empty --"
    ::= { lcsStatusLanInterfaceBundlingPrpNodeTableEntry 8 }

-- {COLUMN} 1.3.6.1.4.1.2356.11.1.5.81.11.2.1.9
lcsStatusLanInterfaceBundlingPrpNodeTableEntryCnterrwronglana OBJECT-TYPE
    SYNTAX     Integer32 (0..2147483647)
    MAX-ACCESS read-only
    STATUS     current
    DESCRIPTION
            "-- empty --"
    ::= { lcsStatusLanInterfaceBundlingPrpNodeTableEntry 9 }

-- {COLUMN} 1.3.6.1.4.1.2356.11.1.5.81.11.2.1.10
lcsStatusLanInterfaceBundlingPrpNodeTableEntryCnterrwronglanb OBJECT-TYPE
    SYNTAX     Integer32 (0..2147483647)
    MAX-ACCESS read-only
    STATUS     current
    DESCRIPTION
            "-- empty --"
    ::= { lcsStatusLanInterfaceBundlingPrpNodeTableEntry 10 }

-- {COLUMN} 1.3.6.1.4.1.2356.11.1.5.81.11.2.1.11
lcsStatusLanInterfaceBundlingPrpNodeTableEntryNumEntries OBJECT-TYPE
    SYNTAX     Integer32 (0..2147483647)
    MAX-ACCESS read-only
    STATUS     current
    DESCRIPTION
            "-- empty --"
    ::= { lcsStatusLanInterfaceBundlingPrpNodeTableEntry 11 }

-- {TABLE} 1.3.6.1.4.1.2356.11.1.5.81.11.3
lcsStatusLanInterfaceBundlingPrpProxyNodeTableTable OBJECT-TYPE
    SYNTAX     SEQUENCE OF LcsStatusLanInterfaceBundlingPrpProxyNodeTableEntry
    MAX-ACCESS not-accessible
    STATUS     current
    DESCRIPTION
            "-- empty --"
    ::= { lcsStatusLanInterfaceBundlingPrp 3 }

-- {ROW} 1.3.6.1.4.1.2356.11.1.5.81.11.3.1
lcsStatusLanInterfaceBundlingPrpProxyNodeTableEntry OBJECT-TYPE
    SYNTAX     LcsStatusLanInterfaceBundlingPrpProxyNodeTableEntry
    MAX-ACCESS not-accessible
    STATUS     current
    DESCRIPTION
            ""
    INDEX {
            lcsStatusLanInterfaceBundlingPrpProxyNodeTableEntryInterface,
            lcsStatusLanInterfaceBundlingPrpProxyNodeTableEntryMacAddress
          }
    ::= { lcsStatusLanInterfaceBundlingPrpProxyNodeTableTable 1 }

LcsStatusLanInterfaceBundlingPrpProxyNodeTableEntry ::= SEQUENCE {
            lcsStatusLanInterfaceBundlingPrpProxyNodeTableEntryInterface DisplayString,
            lcsStatusLanInterfaceBundlingPrpProxyNodeTableEntryMacAddress MacAddress,
            lcsStatusLanInterfaceBundlingPrpProxyNodeTableEntryTimelastseen Integer32,
            lcsStatusLanInterfaceBundlingPrpProxyNodeTableEntryCntreceived Integer32,
            lcsStatusLanInterfaceBundlingPrpProxyNodeTableEntryTxseqnum Integer32
    }

-- {COLUMN} 1.3.6.1.4.1.2356.11.1.5.81.11.3.1.1
lcsStatusLanInterfaceBundlingPrpProxyNodeTableEntryInterface OBJECT-TYPE
    SYNTAX     DisplayString (SIZE(0..255))
    MAX-ACCESS read-only
    STATUS     current
    DESCRIPTION
            "-- empty --"
    ::= { lcsStatusLanInterfaceBundlingPrpProxyNodeTableEntry 1 }

-- {COLUMN} 1.3.6.1.4.1.2356.11.1.5.81.11.3.1.2
lcsStatusLanInterfaceBundlingPrpProxyNodeTableEntryMacAddress OBJECT-TYPE
    SYNTAX     MacAddress
    MAX-ACCESS read-only
    STATUS     current
    DESCRIPTION
            "-- empty --"
    ::= { lcsStatusLanInterfaceBundlingPrpProxyNodeTableEntry 2 }

-- {COLUMN} 1.3.6.1.4.1.2356.11.1.5.81.11.3.1.3
lcsStatusLanInterfaceBundlingPrpProxyNodeTableEntryTimelastseen OBJECT-TYPE
    SYNTAX     Integer32 (0..2147483647)
    MAX-ACCESS read-only
    STATUS     current
    DESCRIPTION
            "-- empty --"
    ::= { lcsStatusLanInterfaceBundlingPrpProxyNodeTableEntry 3 }

-- {COLUMN} 1.3.6.1.4.1.2356.11.1.5.81.11.3.1.4
lcsStatusLanInterfaceBundlingPrpProxyNodeTableEntryCntreceived OBJECT-TYPE
    SYNTAX     Integer32 (0..2147483647)
    MAX-ACCESS read-only
    STATUS     current
    DESCRIPTION
            "-- empty --"
    ::= { lcsStatusLanInterfaceBundlingPrpProxyNodeTableEntry 4 }

-- {COLUMN} 1.3.6.1.4.1.2356.11.1.5.81.11.3.1.5
lcsStatusLanInterfaceBundlingPrpProxyNodeTableEntryTxseqnum OBJECT-TYPE
    SYNTAX     Integer32 (0..65535)
    MAX-ACCESS read-only
    STATUS     current
    DESCRIPTION
            "-- empty --"
    ::= { lcsStatusLanInterfaceBundlingPrpProxyNodeTableEntry 5 }

-- {SCALAR} 1.3.6.1.4.1.2356.11.1.5.81.11.99
lcsStatusLanInterfaceBundlingPrpDeleteValues OBJECT-TYPE
    SYNTAX     DisplayString
    MAX-ACCESS read-write
    STATUS     current
    DESCRIPTION
            "-- empty --"
    ::= { lcsStatusLanInterfaceBundlingPrp 99 }

-- {NODE} 1.3.6.1.4.1.2356.11.1.5.81.12
lcsStatusLanInterfaceBundlingLacp OBJECT IDENTIFIER ::= { lcsStatusLanInterfaceBundling 12 }

-- {TABLE} 1.3.6.1.4.1.2356.11.1.5.81.12.1
lcsStatusLanInterfaceBundlingLacpIfcsTable OBJECT-TYPE
    SYNTAX     SEQUENCE OF LcsStatusLanInterfaceBundlingLacpIfcsEntry
    MAX-ACCESS not-accessible
    STATUS     current
    DESCRIPTION
            "LACP Interface Status"
    ::= { lcsStatusLanInterfaceBundlingLacp 1 }

-- {ROW} 1.3.6.1.4.1.2356.11.1.5.81.12.1.1
lcsStatusLanInterfaceBundlingLacpIfcsEntry OBJECT-TYPE
    SYNTAX     LcsStatusLanInterfaceBundlingLacpIfcsEntry
    MAX-ACCESS not-accessible
    STATUS     current
    DESCRIPTION
            ""
    INDEX {
            lcsStatusLanInterfaceBundlingLacpIfcsEntryInterface
          }
    ::= { lcsStatusLanInterfaceBundlingLacpIfcsTable 1 }

LcsStatusLanInterfaceBundlingLacpIfcsEntry ::= SEQUENCE {
            lcsStatusLanInterfaceBundlingLacpIfcsEntryInterface DisplayString,
            lcsStatusLanInterfaceBundlingLacpIfcsEntryPortSpeedMismatch INTEGER
    }

-- {COLUMN} 1.3.6.1.4.1.2356.11.1.5.81.12.1.1.1
lcsStatusLanInterfaceBundlingLacpIfcsEntryInterface OBJECT-TYPE
    SYNTAX     DisplayString (SIZE(0..255))
    MAX-ACCESS read-only
    STATUS     current
    DESCRIPTION
            "-- empty --"
    ::= { lcsStatusLanInterfaceBundlingLacpIfcsEntry 1 }

-- {COLUMN} 1.3.6.1.4.1.2356.11.1.5.81.12.1.1.2
lcsStatusLanInterfaceBundlingLacpIfcsEntryPortSpeedMismatch OBJECT-TYPE
    SYNTAX     INTEGER {
                  eNo (0),
                  eYes (1)
            }
    MAX-ACCESS read-only
    STATUS     current
    DESCRIPTION
            "-- empty --"
    ::= { lcsStatusLanInterfaceBundlingLacpIfcsEntry 2 }

-- {TABLE} 1.3.6.1.4.1.2356.11.1.5.81.12.2
lcsStatusLanInterfaceBundlingLacpPortsTable OBJECT-TYPE
    SYNTAX     SEQUENCE OF LcsStatusLanInterfaceBundlingLacpPortsEntry
    MAX-ACCESS not-accessible
    STATUS     current
    DESCRIPTION
            "-- empty --"
    ::= { lcsStatusLanInterfaceBundlingLacp 2 }

-- {ROW} 1.3.6.1.4.1.2356.11.1.5.81.12.2.1
lcsStatusLanInterfaceBundlingLacpPortsEntry OBJECT-TYPE
    SYNTAX     LcsStatusLanInterfaceBundlingLacpPortsEntry
    MAX-ACCESS not-accessible
    STATUS     current
    DESCRIPTION
            ""
    INDEX {
            lcsStatusLanInterfaceBundlingLacpPortsEntryInterface,
            lcsStatusLanInterfaceBundlingLacpPortsEntryPort
          }
    ::= { lcsStatusLanInterfaceBundlingLacpPortsTable 1 }

LcsStatusLanInterfaceBundlingLacpPortsEntry ::= SEQUENCE {
            lcsStatusLanInterfaceBundlingLacpPortsEntryInterface DisplayString,
            lcsStatusLanInterfaceBundlingLacpPortsEntryPort INTEGER,
            lcsStatusLanInterfaceBundlingLacpPortsEntryUp INTEGER,
            lcsStatusLanInterfaceBundlingLacpPortsEntryProtocolActive INTEGER,
            lcsStatusLanInterfaceBundlingLacpPortsEntryActorSystemPriority Integer32,
            lcsStatusLanInterfaceBundlingLacpPortsEntryActorSystem MacAddress,
            lcsStatusLanInterfaceBundlingLacpPortsEntryActorKey Integer32,
            lcsStatusLanInterfaceBundlingLacpPortsEntryActorPortPriority Integer32,
            lcsStatusLanInterfaceBundlingLacpPortsEntryActorPortNumber Integer32,
            lcsStatusLanInterfaceBundlingLacpPortsEntryPartnerSystemPriority Integer32,
            lcsStatusLanInterfaceBundlingLacpPortsEntryPartnerSystem MacAddress,
            lcsStatusLanInterfaceBundlingLacpPortsEntryPartnerKey Integer32,
            lcsStatusLanInterfaceBundlingLacpPortsEntryPartnerPortPriority Integer32,
            lcsStatusLanInterfaceBundlingLacpPortsEntryPartnerPortNumber Integer32,
            lcsStatusLanInterfaceBundlingLacpPortsEntryActorState BITS,
            lcsStatusLanInterfaceBundlingLacpPortsEntryAggregator Integer32,
            lcsStatusLanInterfaceBundlingLacpPortsEntryPartnerState BITS
    }

-- {COLUMN} 1.3.6.1.4.1.2356.11.1.5.81.12.2.1.1
lcsStatusLanInterfaceBundlingLacpPortsEntryInterface OBJECT-TYPE
    SYNTAX     DisplayString (SIZE(0..255))
    MAX-ACCESS read-only
    STATUS     current
    DESCRIPTION
            "-- empty --"
    ::= { lcsStatusLanInterfaceBundlingLacpPortsEntry 1 }

-- {COLUMN} 1.3.6.1.4.1.2356.11.1.5.81.12.2.1.2
lcsStatusLanInterfaceBundlingLacpPortsEntryPort OBJECT-TYPE
    SYNTAX     INTEGER {
                  eA (0),
                  eB (1)
            }
    MAX-ACCESS read-only
    STATUS     current
    DESCRIPTION
            "-- empty --"
    ::= { lcsStatusLanInterfaceBundlingLacpPortsEntry 2 }

-- {COLUMN} 1.3.6.1.4.1.2356.11.1.5.81.12.2.1.3
lcsStatusLanInterfaceBundlingLacpPortsEntryUp OBJECT-TYPE
    SYNTAX     INTEGER {
                  eNo (0),
                  eYes (1)
            }
    MAX-ACCESS read-only
    STATUS     current
    DESCRIPTION
            "-- empty --"
    ::= { lcsStatusLanInterfaceBundlingLacpPortsEntry 3 }

-- {COLUMN} 1.3.6.1.4.1.2356.11.1.5.81.12.2.1.4
lcsStatusLanInterfaceBundlingLacpPortsEntryProtocolActive OBJECT-TYPE
    SYNTAX     INTEGER {
                  eNo (0),
                  eYes (1)
            }
    MAX-ACCESS read-only
    STATUS     current
    DESCRIPTION
            "-- empty --"
    ::= { lcsStatusLanInterfaceBundlingLacpPortsEntry 4 }

-- {COLUMN} 1.3.6.1.4.1.2356.11.1.5.81.12.2.1.5
lcsStatusLanInterfaceBundlingLacpPortsEntryActorSystemPriority OBJECT-TYPE
    SYNTAX     Integer32 (0..65535)
    MAX-ACCESS read-only
    STATUS     current
    DESCRIPTION
            "-- empty --"
    ::= { lcsStatusLanInterfaceBundlingLacpPortsEntry 5 }

-- {COLUMN} 1.3.6.1.4.1.2356.11.1.5.81.12.2.1.6
lcsStatusLanInterfaceBundlingLacpPortsEntryActorSystem OBJECT-TYPE
    SYNTAX     MacAddress
    MAX-ACCESS read-only
    STATUS     current
    DESCRIPTION
            "-- empty --"
    ::= { lcsStatusLanInterfaceBundlingLacpPortsEntry 6 }

-- {COLUMN} 1.3.6.1.4.1.2356.11.1.5.81.12.2.1.7
lcsStatusLanInterfaceBundlingLacpPortsEntryActorKey OBJECT-TYPE
    SYNTAX     Integer32 (0..65535)
    MAX-ACCESS read-only
    STATUS     current
    DESCRIPTION
            "-- empty --"
    ::= { lcsStatusLanInterfaceBundlingLacpPortsEntry 7 }

-- {COLUMN} 1.3.6.1.4.1.2356.11.1.5.81.12.2.1.8
lcsStatusLanInterfaceBundlingLacpPortsEntryActorPortPriority OBJECT-TYPE
    SYNTAX     Integer32 (0..65535)
    MAX-ACCESS read-only
    STATUS     current
    DESCRIPTION
            "-- empty --"
    ::= { lcsStatusLanInterfaceBundlingLacpPortsEntry 8 }

-- {COLUMN} 1.3.6.1.4.1.2356.11.1.5.81.12.2.1.9
lcsStatusLanInterfaceBundlingLacpPortsEntryActorPortNumber OBJECT-TYPE
    SYNTAX     Integer32 (0..65535)
    MAX-ACCESS read-only
    STATUS     current
    DESCRIPTION
            "-- empty --"
    ::= { lcsStatusLanInterfaceBundlingLacpPortsEntry 9 }

-- {COLUMN} 1.3.6.1.4.1.2356.11.1.5.81.12.2.1.10
lcsStatusLanInterfaceBundlingLacpPortsEntryPartnerSystemPriority OBJECT-TYPE
    SYNTAX     Integer32 (0..65535)
    MAX-ACCESS read-only
    STATUS     current
    DESCRIPTION
            "-- empty --"
    ::= { lcsStatusLanInterfaceBundlingLacpPortsEntry 10 }

-- {COLUMN} 1.3.6.1.4.1.2356.11.1.5.81.12.2.1.11
lcsStatusLanInterfaceBundlingLacpPortsEntryPartnerSystem OBJECT-TYPE
    SYNTAX     MacAddress
    MAX-ACCESS read-only
    STATUS     current
    DESCRIPTION
            "-- empty --"
    ::= { lcsStatusLanInterfaceBundlingLacpPortsEntry 11 }

-- {COLUMN} 1.3.6.1.4.1.2356.11.1.5.81.12.2.1.12
lcsStatusLanInterfaceBundlingLacpPortsEntryPartnerKey OBJECT-TYPE
    SYNTAX     Integer32 (0..65535)
    MAX-ACCESS read-only
    STATUS     current
    DESCRIPTION
            "-- empty --"
    ::= { lcsStatusLanInterfaceBundlingLacpPortsEntry 12 }

-- {COLUMN} 1.3.6.1.4.1.2356.11.1.5.81.12.2.1.13
lcsStatusLanInterfaceBundlingLacpPortsEntryPartnerPortPriority OBJECT-TYPE
    SYNTAX     Integer32 (0..65535)
    MAX-ACCESS read-only
    STATUS     current
    DESCRIPTION
            "-- empty --"
    ::= { lcsStatusLanInterfaceBundlingLacpPortsEntry 13 }

-- {COLUMN} 1.3.6.1.4.1.2356.11.1.5.81.12.2.1.14
lcsStatusLanInterfaceBundlingLacpPortsEntryPartnerPortNumber OBJECT-TYPE
    SYNTAX     Integer32 (0..65535)
    MAX-ACCESS read-only
    STATUS     current
    DESCRIPTION
            "-- empty --"
    ::= { lcsStatusLanInterfaceBundlingLacpPortsEntry 14 }

-- {COLUMN} 1.3.6.1.4.1.2356.11.1.5.81.12.2.1.15
lcsStatusLanInterfaceBundlingLacpPortsEntryActorState OBJECT-TYPE
    SYNTAX     BITS {
                  eDistributing (2),
                  eCollecting (3),
                  eSynchronized (4)
            }
    MAX-ACCESS read-only
    STATUS     current
    DESCRIPTION
            "-- empty --"
    ::= { lcsStatusLanInterfaceBundlingLacpPortsEntry 15 }

-- {COLUMN} 1.3.6.1.4.1.2356.11.1.5.81.12.2.1.16
lcsStatusLanInterfaceBundlingLacpPortsEntryAggregator OBJECT-TYPE
    SYNTAX     Integer32 (0..65535)
    MAX-ACCESS read-only
    STATUS     current
    DESCRIPTION
            "-- empty --"
    ::= { lcsStatusLanInterfaceBundlingLacpPortsEntry 16 }

-- {COLUMN} 1.3.6.1.4.1.2356.11.1.5.81.12.2.1.17
lcsStatusLanInterfaceBundlingLacpPortsEntryPartnerState OBJECT-TYPE
    SYNTAX     BITS {
                  eDistributing (2),
                  eCollecting (3),
                  eSynchronized (4)
            }
    MAX-ACCESS read-only
    STATUS     current
    DESCRIPTION
            "-- empty --"
    ::= { lcsStatusLanInterfaceBundlingLacpPortsEntry 17 }

-- {TABLE} 1.3.6.1.4.1.2356.11.1.5.81.12.3
lcsStatusLanInterfaceBundlingLacpAggrsTable OBJECT-TYPE
    SYNTAX     SEQUENCE OF LcsStatusLanInterfaceBundlingLacpAggrsEntry
    MAX-ACCESS not-accessible
    STATUS     current
    DESCRIPTION
            "LACP Aggregator Staus"
    ::= { lcsStatusLanInterfaceBundlingLacp 3 }

-- {ROW} 1.3.6.1.4.1.2356.11.1.5.81.12.3.1
lcsStatusLanInterfaceBundlingLacpAggrsEntry OBJECT-TYPE
    SYNTAX     LcsStatusLanInterfaceBundlingLacpAggrsEntry
    MAX-ACCESS not-accessible
    STATUS     current
    DESCRIPTION
            ""
    INDEX {
            lcsStatusLanInterfaceBundlingLacpAggrsEntryInterface,
            lcsStatusLanInterfaceBundlingLacpAggrsEntryAggregator
          }
    ::= { lcsStatusLanInterfaceBundlingLacpAggrsTable 1 }

LcsStatusLanInterfaceBundlingLacpAggrsEntry ::= SEQUENCE {
            lcsStatusLanInterfaceBundlingLacpAggrsEntryInterface DisplayString,
            lcsStatusLanInterfaceBundlingLacpAggrsEntryAggregator Integer32,
            lcsStatusLanInterfaceBundlingLacpAggrsEntryNumPorts Integer32,
            lcsStatusLanInterfaceBundlingLacpAggrsEntryPartnerSystemPriority Integer32,
            lcsStatusLanInterfaceBundlingLacpAggrsEntryPartnerSystem MacAddress,
            lcsStatusLanInterfaceBundlingLacpAggrsEntryPartnerKey Integer32,
            lcsStatusLanInterfaceBundlingLacpAggrsEntryTransmitting INTEGER,
            lcsStatusLanInterfaceBundlingLacpAggrsEntryReceiving INTEGER
    }

-- {COLUMN} 1.3.6.1.4.1.2356.11.1.5.81.12.3.1.1
lcsStatusLanInterfaceBundlingLacpAggrsEntryInterface OBJECT-TYPE
    SYNTAX     DisplayString (SIZE(0..255))
    MAX-ACCESS read-only
    STATUS     current
    DESCRIPTION
            "-- empty --"
    ::= { lcsStatusLanInterfaceBundlingLacpAggrsEntry 1 }

-- {COLUMN} 1.3.6.1.4.1.2356.11.1.5.81.12.3.1.2
lcsStatusLanInterfaceBundlingLacpAggrsEntryAggregator OBJECT-TYPE
    SYNTAX     Integer32 (0..255)
    MAX-ACCESS read-only
    STATUS     current
    DESCRIPTION
            "-- empty --"
    ::= { lcsStatusLanInterfaceBundlingLacpAggrsEntry 2 }

-- {COLUMN} 1.3.6.1.4.1.2356.11.1.5.81.12.3.1.3
lcsStatusLanInterfaceBundlingLacpAggrsEntryNumPorts OBJECT-TYPE
    SYNTAX     Integer32 (0..255)
    MAX-ACCESS read-only
    STATUS     current
    DESCRIPTION
            "-- empty --"
    ::= { lcsStatusLanInterfaceBundlingLacpAggrsEntry 3 }

-- {COLUMN} 1.3.6.1.4.1.2356.11.1.5.81.12.3.1.4
lcsStatusLanInterfaceBundlingLacpAggrsEntryPartnerSystemPriority OBJECT-TYPE
    SYNTAX     Integer32 (0..65535)
    MAX-ACCESS read-only
    STATUS     current
    DESCRIPTION
            "-- empty --"
    ::= { lcsStatusLanInterfaceBundlingLacpAggrsEntry 4 }

-- {COLUMN} 1.3.6.1.4.1.2356.11.1.5.81.12.3.1.5
lcsStatusLanInterfaceBundlingLacpAggrsEntryPartnerSystem OBJECT-TYPE
    SYNTAX     MacAddress
    MAX-ACCESS read-only
    STATUS     current
    DESCRIPTION
            "-- empty --"
    ::= { lcsStatusLanInterfaceBundlingLacpAggrsEntry 5 }

-- {COLUMN} 1.3.6.1.4.1.2356.11.1.5.81.12.3.1.6
lcsStatusLanInterfaceBundlingLacpAggrsEntryPartnerKey OBJECT-TYPE
    SYNTAX     Integer32 (0..65535)
    MAX-ACCESS read-only
    STATUS     current
    DESCRIPTION
            "-- empty --"
    ::= { lcsStatusLanInterfaceBundlingLacpAggrsEntry 6 }

-- {COLUMN} 1.3.6.1.4.1.2356.11.1.5.81.12.3.1.7
lcsStatusLanInterfaceBundlingLacpAggrsEntryTransmitting OBJECT-TYPE
    SYNTAX     INTEGER {
                  eNo (0),
                  eYes (1)
            }
    MAX-ACCESS read-only
    STATUS     current
    DESCRIPTION
            "-- empty --"
    ::= { lcsStatusLanInterfaceBundlingLacpAggrsEntry 7 }

-- {COLUMN} 1.3.6.1.4.1.2356.11.1.5.81.12.3.1.8
lcsStatusLanInterfaceBundlingLacpAggrsEntryReceiving OBJECT-TYPE
    SYNTAX     INTEGER {
                  eNo (0),
                  eYes (1)
            }
    MAX-ACCESS read-only
    STATUS     current
    DESCRIPTION
            "-- empty --"
    ::= { lcsStatusLanInterfaceBundlingLacpAggrsEntry 8 }

-- {SCALAR} 1.3.6.1.4.1.2356.11.1.5.81.99
lcsStatusLanInterfaceBundlingDeleteValues OBJECT-TYPE
    SYNTAX     DisplayString
    MAX-ACCESS read-write
    STATUS     current
    DESCRIPTION
            "-- empty --"
    ::= { lcsStatusLanInterfaceBundling 99 }

-- {TABLE} 1.3.6.1.4.1.2356.11.1.5.90
lcsStatusLanStationTableTable OBJECT-TYPE
    SYNTAX     SEQUENCE OF LcsStatusLanStationTableEntry
    MAX-ACCESS not-accessible
    STATUS     current
    DESCRIPTION
            "-- empty --"
    ::= { lcsStatusLan 90 }

-- {ROW} 1.3.6.1.4.1.2356.11.1.5.90.1
lcsStatusLanStationTableEntry OBJECT-TYPE
    SYNTAX     LcsStatusLanStationTableEntry
    MAX-ACCESS not-accessible
    STATUS     current
    DESCRIPTION
            ""
    INDEX {
            lcsStatusLanStationTableEntryInterface,
            lcsStatusLanStationTableEntryMacAddress
          }
    ::= { lcsStatusLanStationTableTable 1 }

LcsStatusLanStationTableEntry ::= SEQUENCE {
            lcsStatusLanStationTableEntryMacAddress MacAddress,
            lcsStatusLanStationTableEntryInterface INTEGER,
            lcsStatusLanStationTableEntryTxLimit Integer32,
            lcsStatusLanStationTableEntryRxLimit Integer32,
            lcsStatusLanStationTableEntryVlanId Integer32,
            lcsStatusLanStationTableEntryOrigVlanId Integer32,
            lcsStatusLanStationTableEntryAuthenticated INTEGER
    }

-- {COLUMN} 1.3.6.1.4.1.2356.11.1.5.90.1.1
lcsStatusLanStationTableEntryMacAddress OBJECT-TYPE
    SYNTAX     MacAddress
    MAX-ACCESS read-only
    STATUS     current
    DESCRIPTION
            "-- empty --"
    ::= { lcsStatusLanStationTableEntry 1 }

-- {COLUMN} 1.3.6.1.4.1.2356.11.1.5.90.1.2
lcsStatusLanStationTableEntryInterface OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            "-- empty --"
    ::= { lcsStatusLanStationTableEntry 2 }

-- {COLUMN} 1.3.6.1.4.1.2356.11.1.5.90.1.3
lcsStatusLanStationTableEntryTxLimit OBJECT-TYPE
    SYNTAX     Integer32 (0..2147483647)
    MAX-ACCESS read-only
    STATUS     current
    DESCRIPTION
            "-- empty --"
    ::= { lcsStatusLanStationTableEntry 3 }

-- {COLUMN} 1.3.6.1.4.1.2356.11.1.5.90.1.4
lcsStatusLanStationTableEntryRxLimit OBJECT-TYPE
    SYNTAX     Integer32 (0..2147483647)
    MAX-ACCESS read-only
    STATUS     current
    DESCRIPTION
            "-- empty --"
    ::= { lcsStatusLanStationTableEntry 4 }

-- {COLUMN} 1.3.6.1.4.1.2356.11.1.5.90.1.5
lcsStatusLanStationTableEntryVlanId OBJECT-TYPE
    SYNTAX     Integer32 (0..65535)
    MAX-ACCESS read-only
    STATUS     current
    DESCRIPTION
            "-- empty --"
    ::= { lcsStatusLanStationTableEntry 5 }

-- {COLUMN} 1.3.6.1.4.1.2356.11.1.5.90.1.6
lcsStatusLanStationTableEntryOrigVlanId OBJECT-TYPE
    SYNTAX     Integer32 (0..65535)
    MAX-ACCESS read-only
    STATUS     current
    DESCRIPTION
            "-- empty --"
    ::= { lcsStatusLanStationTableEntry 6 }

-- {COLUMN} 1.3.6.1.4.1.2356.11.1.5.90.1.7
lcsStatusLanStationTableEntryAuthenticated OBJECT-TYPE
    SYNTAX     INTEGER {
                  eNo (0),
                  eYes (1)
            }
    MAX-ACCESS read-only
    STATUS     current
    DESCRIPTION
            "-- empty --"
    ::= { lcsStatusLanStationTableEntry 7 }

-- {NODE} 1.3.6.1.4.1.2356.11.1.6
lcsStatusPpp OBJECT IDENTIFIER ::= { lcsStatus 6 }

-- {TABLE} 1.3.6.1.4.1.2356.11.1.6.1
lcsStatusPppPppPhasesTable OBJECT-TYPE
    SYNTAX     SEQUENCE OF LcsStatusPppPppPhasesEntry
    MAX-ACCESS not-accessible
    STATUS     current
    DESCRIPTION
            ""
    ::= { lcsStatusPpp 1 }

-- {ROW} 1.3.6.1.4.1.2356.11.1.6.1.1
lcsStatusPppPppPhasesEntry OBJECT-TYPE
    SYNTAX     LcsStatusPppPppPhasesEntry
    MAX-ACCESS not-accessible
    STATUS     current
    DESCRIPTION
            ""
    INDEX {
            lcsStatusPppPppPhasesEntryIfc
          }
    ::= { lcsStatusPppPppPhasesTable 1 }

LcsStatusPppPppPhasesEntry ::= SEQUENCE {
            lcsStatusPppPppPhasesEntryIfc INTEGER,
            lcsStatusPppPppPhasesEntryPhase INTEGER,
            lcsStatusPppPppPhasesEntryLcp INTEGER,
            lcsStatusPppPppPhasesEntryIpcp INTEGER,
            lcsStatusPppPppPhasesEntryCcp INTEGER,
            lcsStatusPppPppPhasesEntryBacp INTEGER,
            lcsStatusPppPppPhasesEntryIpv6cp INTEGER
    }

-- {COLUMN} 1.3.6.1.4.1.2356.11.1.6.1.1.1
lcsStatusPppPppPhasesEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusPppPppPhasesEntry 1 }

-- {COLUMN} 1.3.6.1.4.1.2356.11.1.6.1.1.2
lcsStatusPppPppPhasesEntryPhase OBJECT-TYPE
    SYNTAX     INTEGER {
                  eDead (1),
                  eEstablish (2),
                  eTerminate (3),
                  eAuthenticate (4),
                  eCallback (5),
                  eNetwork (6)
            }
    MAX-ACCESS read-only
    STATUS     current
    DESCRIPTION
            ""
    ::= { lcsStatusPppPppPhasesEntry 2 }

-- {COLUMN} 1.3.6.1.4.1.2356.11.1.6.1.1.3
lcsStatusPppPppPhasesEntryLcp OBJECT-TYPE
    SYNTAX     INTEGER {
                  eInitial (1),
                  eStartng (2),
                  eClosed (3),
                  eStopped (4),
                  eClosing (5),
                  eStoppng (6),
                  eReqsent (7),
                  eAckrcvd (8),
                  eAcksent (9),
                  eOpened (10)
            }
    MAX-ACCESS read-only
    STATUS     current
    DESCRIPTION
            ""
    ::= { lcsStatusPppPppPhasesEntry 3 }

-- {COLUMN} 1.3.6.1.4.1.2356.11.1.6.1.1.4
lcsStatusPppPppPhasesEntryIpcp OBJECT-TYPE
    SYNTAX     INTEGER {
                  eInitial (1),
                  eStartng (2),
                  eClosed (3),
                  eStopped (4),
                  eClosing (5),
                  eStoppng (6),
                  eReqsent (7),
                  eAckrcvd (8),
                  eAcksent (9),
                  eOpened (10)
            }
    MAX-ACCESS read-only
    STATUS     current
    DESCRIPTION
            ""
    ::= { lcsStatusPppPppPhasesEntry 4 }

-- {COLUMN} 1.3.6.1.4.1.2356.11.1.6.1.1.6
lcsStatusPppPppPhasesEntryCcp OBJECT-TYPE
    SYNTAX     INTEGER {
                  eInitial (1),
                  eStartng (2),
                  eClosed (3),
                  eStopped (4),
                  eClosing (5),
                  eStoppng (6),
                  eReqsent (7),
                  eAckrcvd (8),
                  eAcksent (9),
                  eOpened (10)
            }
    MAX-ACCESS read-only
    STATUS     current
    DESCRIPTION
            ""
    ::= { lcsStatusPppPppPhasesEntry 6 }

-- {COLUMN} 1.3.6.1.4.1.2356.11.1.6.1.1.7
lcsStatusPppPppPhasesEntryBacp OBJECT-TYPE
    SYNTAX     INTEGER {
                  eInitial (1),
                  eStartng (2),
                  eClosed (3),
                  eStopped (4),
                  eClosing (5),
                  eStoppng (6),
                  eReqsent (7),
                  eAckrcvd (8),
                  eAcksent (9),
                  eOpened (10)
            }
    MAX-ACCESS read-only
    STATUS     current
    DESCRIPTION
            ""
    ::= { lcsStatusPppPppPhasesEntry 7 }

-- {COLUMN} 1.3.6.1.4.1.2356.11.1.6.1.1.8
lcsStatusPppPppPhasesEntryIpv6cp OBJECT-TYPE
    SYNTAX     INTEGER {
                  eInitial (1),
                  eStartng (2),
                  eClosed (3),
                  eStopped (4),
                  eClosing (5),
                  eStoppng (6),
                  eReqsent (7),
                  eAckrcvd (8),
                  eAcksent (9),
                  eOpened (10)
            }
    MAX-ACCESS read-only
    STATUS     current
    DESCRIPTION
            "-- empty --"
    ::= { lcsStatusPppPppPhasesEntry 8 }

-- {NODE} 1.3.6.1.4.1.2356.11.1.6.2
lcsStatusPppLcp OBJECT IDENTIFIER ::= { lcsStatusPpp 2 }

-- {SCALAR} 1.3.6.1.4.1.2356.11.1.6.2.1
lcsStatusPppLcpRxErrors OBJECT-TYPE
    SYNTAX     Counter32
    MAX-ACCESS read-only
    STATUS     current
    DESCRIPTION
            ""
    ::= { lcsStatusPppLcp 1 }

-- {SCALAR} 1.3.6.1.4.1.2356.11.1.6.2.2
lcsStatusPppLcpRxDiscarded OBJECT-TYPE
    SYNTAX     Counter32
    MAX-ACCESS read-only
    STATUS     current
    DESCRIPTION
            ""
    ::= { lcsStatusPppLcp 2 }

-- {SCALAR} 1.3.6.1.4.1.2356.11.1.6.2.3
lcsStatusPppLcpRxConfigRequest OBJECT-TYPE
    SYNTAX     Counter32
    MAX-ACCESS read-only
    STATUS     current
    DESCRIPTION
            ""
    ::= { lcsStatusPppLcp 3 }

-- {SCALAR} 1.3.6.1.4.1.2356.11.1.6.2.4
lcsStatusPppLcpRxConfigAck OBJECT-TYPE
    SYNTAX     Counter32
    MAX-ACCESS read-only
    STATUS     current
    DESCRIPTION
            ""
    ::= { lcsStatusPppLcp 4 }

-- {SCALAR} 1.3.6.1.4.1.2356.11.1.6.2.5
lcsStatusPppLcpRxConfigNak OBJECT-TYPE
    SYNTAX     Counter32
    MAX-ACCESS read-only
    STATUS     current
    DESCRIPTION
            ""
    ::= { lcsStatusPppLcp 5 }

-- {SCALAR} 1.3.6.1.4.1.2356.11.1.6.2.6
lcsStatusPppLcpRxConfigReject OBJECT-TYPE
    SYNTAX     Counter32
    MAX-ACCESS read-only
    STATUS     current
    DESCRIPTION
            ""
    ::= { lcsStatusPppLcp 6 }

-- {SCALAR} 1.3.6.1.4.1.2356.11.1.6.2.7
lcsStatusPppLcpRxTerminateRequest OBJECT-TYPE
    SYNTAX     Counter32
    MAX-ACCESS read-only
    STATUS     current
    DESCRIPTION
            ""
    ::= { lcsStatusPppLcp 7 }

-- {SCALAR} 1.3.6.1.4.1.2356.11.1.6.2.8
lcsStatusPppLcpRxTerminateAck OBJECT-TYPE
    SYNTAX     Counter32
    MAX-ACCESS read-only
    STATUS     current
    DESCRIPTION
            ""
    ::= { lcsStatusPppLcp 8 }

-- {SCALAR} 1.3.6.1.4.1.2356.11.1.6.2.9
lcsStatusPppLcpRxCodeReject OBJECT-TYPE
    SYNTAX     Counter32
    MAX-ACCESS read-only
    STATUS     current
    DESCRIPTION
            ""
    ::= { lcsStatusPppLcp 9 }

-- {SCALAR} 1.3.6.1.4.1.2356.11.1.6.2.10
lcsStatusPppLcpRxProtocolReject OBJECT-TYPE
    SYNTAX     Counter32
    MAX-ACCESS read-only
    STATUS     current
    DESCRIPTION
            ""
    ::= { lcsStatusPppLcp 10 }

-- {SCALAR} 1.3.6.1.4.1.2356.11.1.6.2.11
lcsStatusPppLcpRxEchoRequest OBJECT-TYPE
    SYNTAX     Counter32
    MAX-ACCESS read-only
    STATUS     current
    DESCRIPTION
            ""
    ::= { lcsStatusPppLcp 11 }

-- {SCALAR} 1.3.6.1.4.1.2356.11.1.6.2.12
lcsStatusPppLcpRxEchoReply OBJECT-TYPE
    SYNTAX     Counter32
    MAX-ACCESS read-only
    STATUS     current
    DESCRIPTION
            ""
    ::= { lcsStatusPppLcp 12 }

-- {SCALAR} 1.3.6.1.4.1.2356.11.1.6.2.13
lcsStatusPppLcpRxDiscardRequest OBJECT-TYPE
    SYNTAX     Counter32
    MAX-ACCESS read-only
    STATUS     current
    DESCRIPTION
            ""
    ::= { lcsStatusPppLcp 13 }

-- {SCALAR} 1.3.6.1.4.1.2356.11.1.6.2.14
lcsStatusPppLcpTxConfigRequest OBJECT-TYPE
    SYNTAX     Counter32
    MAX-ACCESS read-only
    STATUS     current
    DESCRIPTION
            ""
    ::= { lcsStatusPppLcp 14 }

-- {SCALAR} 1.3.6.1.4.1.2356.11.1.6.2.15
lcsStatusPppLcpTxConfigAck OBJECT-TYPE
    SYNTAX     Counter32
    MAX-ACCESS read-only
    STATUS     current
    DESCRIPTION
            ""
    ::= { lcsStatusPppLcp 15 }

-- {SCALAR} 1.3.6.1.4.1.2356.11.1.6.2.16
lcsStatusPppLcpTxConfigNak OBJECT-TYPE
    SYNTAX     Counter32
    MAX-ACCESS read-only
    STATUS     current
    DESCRIPTION
            ""
    ::= { lcsStatusPppLcp 16 }

-- {SCALAR} 1.3.6.1.4.1.2356.11.1.6.2.17
lcsStatusPppLcpTxConfigReject OBJECT-TYPE
    SYNTAX     Counter32
    MAX-ACCESS read-only
    STATUS     current
    DESCRIPTION
            ""
    ::= { lcsStatusPppLcp 17 }

-- {SCALAR} 1.3.6.1.4.1.2356.11.1.6.2.18
lcsStatusPppLcpTxTerminateRequest OBJECT-TYPE
    SYNTAX     Counter32
    MAX-ACCESS read-only
    STATUS     current
    DESCRIPTION
            ""
    ::= { lcsStatusPppLcp 18 }

-- {SCALAR} 1.3.6.1.4.1.2356.11.1.6.2.19
lcsStatusPppLcpTxTerminateAck OBJECT-TYPE
    SYNTAX     Counter32
    MAX-ACCESS read-only
    STATUS     current
    DESCRIPTION
            ""
    ::= { lcsStatusPppLcp 19 }

-- {SCALAR} 1.3.6.1.4.1.2356.11.1.6.2.20
lcsStatusPppLcpTxCodeReject OBJECT-TYPE
    SYNTAX     Counter32
    MAX-ACCESS read-only
    STATUS     current
    DESCRIPTION
            ""
    ::= { lcsStatusPppLcp 20 }

-- {SCALAR} 1.3.6.1.4.1.2356.11.1.6.2.21
lcsStatusPppLcpTxProtocolReject OBJECT-TYPE
    SYNTAX     Counter32
    MAX-ACCESS read-only
    STATUS     current
    DESCRIPTION
            ""
    ::= { lcsStatusPppLcp 21 }

-- {SCALAR} 1.3.6.1.4.1.2356.11.1.6.2.22
lcsStatusPppLcpTxEchoRequest OBJECT-TYPE
    SYNTAX     Counter32
    MAX-ACCESS read-only
    STATUS     current
    DESCRIPTION
            ""
    ::= { lcsStatusPppLcp 22 }

-- {SCALAR} 1.3.6.1.4.1.2356.11.1.6.2.23
lcsStatusPppLcpTxEchoReply OBJECT-TYPE
    SYNTAX     Counter32
    MAX-ACCESS read-only
    STATUS     current
    DESCRIPTION
            ""
    ::= { lcsStatusPppLcp 23 }

-- {SCALAR} 1.3.6.1.4.1.2356.11.1.6.2.24
lcsStatusPppLcpTxDiscardRequest OBJECT-TYPE
    SYNTAX     Counter32
    MAX-ACCESS read-only
    STATUS     current
    DESCRIPTION
            ""
    ::= { lcsStatusPppLcp 24 }

-- {SCALAR} 1.3.6.1.4.1.2356.11.1.6.2.25
lcsStatusPppLcpDeleteValues OBJECT-TYPE
    SYNTAX     DisplayString
    MAX-ACCESS read-write
    STATUS     current
    DESCRIPTION
            ""
    ::= { lcsStatusPppLcp 25 }

-- {NODE} 1.3.6.1.4.1.2356.11.1.6.3
lcsStatusPppPap OBJECT IDENTIFIER ::= { lcsStatusPpp 3 }

-- {SCALAR} 1.3.6.1.4.1.2356.11.1.6.3.1
lcsStatusPppPapRxDiscarded OBJECT-TYPE
    SYNTAX     Counter32
    MAX-ACCESS read-only
    STATUS     current
    DESCRIPTION
            ""
    ::= { lcsStatusPppPap 1 }

-- {SCALAR} 1.3.6.1.4.1.2356.11.1.6.3.2
lcsStatusPppPapRxRequest OBJECT-TYPE
    SYNTAX     Counter32
    MAX-ACCESS read-only
    STATUS     current
    DESCRIPTION
            ""
    ::= { lcsStatusPppPap 2 }

-- {SCALAR} 1.3.6.1.4.1.2356.11.1.6.3.3
lcsStatusPppPapRxSuccess OBJECT-TYPE
    SYNTAX     Counter32
    MAX-ACCESS read-only
    STATUS     current
    DESCRIPTION
            ""
    ::= { lcsStatusPppPap 3 }

-- {SCALAR} 1.3.6.1.4.1.2356.11.1.6.3.4
lcsStatusPppPapRxFailure OBJECT-TYPE
    SYNTAX     Counter32
    MAX-ACCESS read-only
    STATUS     current
    DESCRIPTION
            ""
    ::= { lcsStatusPppPap 4 }

-- {SCALAR} 1.3.6.1.4.1.2356.11.1.6.3.5
lcsStatusPppPapTxRetry OBJECT-TYPE
    SYNTAX     Counter32
    MAX-ACCESS read-only
    STATUS     current
    DESCRIPTION
            ""
    ::= { lcsStatusPppPap 5 }

-- {SCALAR} 1.3.6.1.4.1.2356.11.1.6.3.6
lcsStatusPppPapTxRequest OBJECT-TYPE
    SYNTAX     Counter32
    MAX-ACCESS read-only
    STATUS     current
    DESCRIPTION
            ""
    ::= { lcsStatusPppPap 6 }

-- {SCALAR} 1.3.6.1.4.1.2356.11.1.6.3.7
lcsStatusPppPapTxSuccess OBJECT-TYPE
    SYNTAX     Counter32
    MAX-ACCESS read-only
    STATUS     current
    DESCRIPTION
            ""
    ::= { lcsStatusPppPap 7 }

-- {SCALAR} 1.3.6.1.4.1.2356.11.1.6.3.8
lcsStatusPppPapTxFailure OBJECT-TYPE
    SYNTAX     Counter32
    MAX-ACCESS read-only
    STATUS     current
    DESCRIPTION
            ""
    ::= { lcsStatusPppPap 8 }

-- {SCALAR} 1.3.6.1.4.1.2356.11.1.6.3.9
lcsStatusPppPapDeleteValues OBJECT-TYPE
    SYNTAX     DisplayString
    MAX-ACCESS read-write
    STATUS     current
    DESCRIPTION
            ""
    ::= { lcsStatusPppPap 9 }

-- {NODE} 1.3.6.1.4.1.2356.11.1.6.4
lcsStatusPppChap OBJECT IDENTIFIER ::= { lcsStatusPpp 4 }

-- {SCALAR} 1.3.6.1.4.1.2356.11.1.6.4.1
lcsStatusPppChapRxDiscarded OBJECT-TYPE
    SYNTAX     Counter32
    MAX-ACCESS read-only
    STATUS     current
    DESCRIPTION
            ""
    ::= { lcsStatusPppChap 1 }

-- {SCALAR} 1.3.6.1.4.1.2356.11.1.6.4.2
lcsStatusPppChapRxChallenge OBJECT-TYPE
    SYNTAX     Counter32
    MAX-ACCESS read-only
    STATUS     current
    DESCRIPTION
            ""
    ::= { lcsStatusPppChap 2 }

-- {SCALAR} 1.3.6.1.4.1.2356.11.1.6.4.3
lcsStatusPppChapRxResponse OBJECT-TYPE
    SYNTAX     Counter32
    MAX-ACCESS read-only
    STATUS     current
    DESCRIPTION
            ""
    ::= { lcsStatusPppChap 3 }

-- {SCALAR} 1.3.6.1.4.1.2356.11.1.6.4.4
lcsStatusPppChapRxSuccess OBJECT-TYPE
    SYNTAX     Counter32
    MAX-ACCESS read-only
    STATUS     current
    DESCRIPTION
            ""
    ::= { lcsStatusPppChap 4 }

-- {SCALAR} 1.3.6.1.4.1.2356.11.1.6.4.5
lcsStatusPppChapRxFailure OBJECT-TYPE
    SYNTAX     Counter32
    MAX-ACCESS read-only
    STATUS     current
    DESCRIPTION
            ""
    ::= { lcsStatusPppChap 5 }

-- {SCALAR} 1.3.6.1.4.1.2356.11.1.6.4.6
lcsStatusPppChapTxRetry OBJECT-TYPE
    SYNTAX     Counter32
    MAX-ACCESS read-only
    STATUS     current
    DESCRIPTION
            ""
    ::= { lcsStatusPppChap 6 }

-- {SCALAR} 1.3.6.1.4.1.2356.11.1.6.4.7
lcsStatusPppChapTxChallenge OBJECT-TYPE
    SYNTAX     Counter32
    MAX-ACCESS read-only
    STATUS     current
    DESCRIPTION
            ""
    ::= { lcsStatusPppChap 7 }

-- {SCALAR} 1.3.6.1.4.1.2356.11.1.6.4.8
lcsStatusPppChapTxResponse OBJECT-TYPE
    SYNTAX     Counter32
    MAX-ACCESS read-only
    STATUS     current
    DESCRIPTION
            ""
    ::= { lcsStatusPppChap 8 }

-- {SCALAR} 1.3.6.1.4.1.2356.11.1.6.4.9
lcsStatusPppChapTxSuccess OBJECT-TYPE
    SYNTAX     Counter32
    MAX-ACCESS read-only
    STATUS     current
    DESCRIPTION
            ""
    ::= { lcsStatusPppChap 9 }

-- {SCALAR} 1.3.6.1.4.1.2356.11.1.6.4.10
lcsStatusPppChapTxFailure OBJECT-TYPE
    SYNTAX     Counter32
    MAX-ACCESS read-only
    STATUS     current
    DESCRIPTION
            ""
    ::= { lcsStatusPppChap 10 }

-- {SCALAR} 1.3.6.1.4.1.2356.11.1.6.4.11
lcsStatusPppChapDeleteValues OBJECT-TYPE
    SYNTAX     DisplayString
    MAX-ACCESS read-write
    STATUS     current
    DESCRIPTION
            ""
    ::= { lcsStatusPppChap 11 }

-- {NODE} 1.3.6.1.4.1.2356.11.1.6.6
lcsStatusPppIpcp OBJECT IDENTIFIER ::= { lcsStatusPpp 6 }

-- {SCALAR} 1.3.6.1.4.1.2356.11.1.6.6.1
lcsStatusPppIpcpRxDiscarded OBJECT-TYPE
    SYNTAX     Counter32
    MAX-ACCESS read-only
    STATUS     current
    DESCRIPTION
            ""
    ::= { lcsStatusPppIpcp 1 }

-- {SCALAR} 1.3.6.1.4.1.2356.11.1.6.6.2
lcsStatusPppIpcpRxConfigRequest OBJECT-TYPE
    SYNTAX     Counter32
    MAX-ACCESS read-only
    STATUS     current
    DESCRIPTION
            ""
    ::= { lcsStatusPppIpcp 2 }

-- {SCALAR} 1.3.6.1.4.1.2356.11.1.6.6.3
lcsStatusPppIpcpRxConfigAck OBJECT-TYPE
    SYNTAX     Counter32
    MAX-ACCESS read-only
    STATUS     current
    DESCRIPTION
            ""
    ::= { lcsStatusPppIpcp 3 }

-- {SCALAR} 1.3.6.1.4.1.2356.11.1.6.6.4
lcsStatusPppIpcpRxConfigNak OBJECT-TYPE
    SYNTAX     Counter32
    MAX-ACCESS read-only
    STATUS     current
    DESCRIPTION
            ""
    ::= { lcsStatusPppIpcp 4 }

-- {SCALAR} 1.3.6.1.4.1.2356.11.1.6.6.5
lcsStatusPppIpcpRxConfigReject OBJECT-TYPE
    SYNTAX     Counter32
    MAX-ACCESS read-only
    STATUS     current
    DESCRIPTION
            ""
    ::= { lcsStatusPppIpcp 5 }

-- {SCALAR} 1.3.6.1.4.1.2356.11.1.6.6.6
lcsStatusPppIpcpRxTerminateRequest OBJECT-TYPE
    SYNTAX     Counter32
    MAX-ACCESS read-only
    STATUS     current
    DESCRIPTION
            ""
    ::= { lcsStatusPppIpcp 6 }

-- {SCALAR} 1.3.6.1.4.1.2356.11.1.6.6.7
lcsStatusPppIpcpRxTerminateAck OBJECT-TYPE
    SYNTAX     Counter32
    MAX-ACCESS read-only
    STATUS     current
    DESCRIPTION
            ""
    ::= { lcsStatusPppIpcp 7 }

-- {SCALAR} 1.3.6.1.4.1.2356.11.1.6.6.8
lcsStatusPppIpcpRxCodeReject OBJECT-TYPE
    SYNTAX     Counter32
    MAX-ACCESS read-only
    STATUS     current
    DESCRIPTION
            ""
    ::= { lcsStatusPppIpcp 8 }

-- {SCALAR} 1.3.6.1.4.1.2356.11.1.6.6.9
lcsStatusPppIpcpTxConfigRequest OBJECT-TYPE
    SYNTAX     Counter32
    MAX-ACCESS read-only
    STATUS     current
    DESCRIPTION
            ""
    ::= { lcsStatusPppIpcp 9 }

-- {SCALAR} 1.3.6.1.4.1.2356.11.1.6.6.10
lcsStatusPppIpcpTxConfigAck OBJECT-TYPE
    SYNTAX     Counter32
    MAX-ACCESS read-only
    STATUS     current
    DESCRIPTION
            ""
    ::= { lcsStatusPppIpcp 10 }

-- {SCALAR} 1.3.6.1.4.1.2356.11.1.6.6.11
lcsStatusPppIpcpTxConfigNak OBJECT-TYPE
    SYNTAX     Counter32
    MAX-ACCESS read-only
    STATUS     current
    DESCRIPTION
            ""
    ::= { lcsStatusPppIpcp 11 }

-- {SCALAR} 1.3.6.1.4.1.2356.11.1.6.6.12
lcsStatusPppIpcpTxConfigReject OBJECT-TYPE
    SYNTAX     Counter32
    MAX-ACCESS read-only
    STATUS     current
    DESCRIPTION
            ""
    ::= { lcsStatusPppIpcp 12 }

-- {SCALAR} 1.3.6.1.4.1.2356.11.1.6.6.13
lcsStatusPppIpcpTxTerminateRequest OBJECT-TYPE
    SYNTAX     Counter32
    MAX-ACCESS read-only
    STATUS     current
    DESCRIPTION
            ""
    ::= { lcsStatusPppIpcp 13 }

-- {SCALAR} 1.3.6.1.4.1.2356.11.1.6.6.14
lcsStatusPppIpcpTxTerminateAck OBJECT-TYPE
    SYNTAX     Counter32
    MAX-ACCESS read-only
    STATUS     current
    DESCRIPTION
            ""
    ::= { lcsStatusPppIpcp 14 }

-- {SCALAR} 1.3.6.1.4.1.2356.11.1.6.6.15
lcsStatusPppIpcpTxCodeReject OBJECT-TYPE
    SYNTAX     Counter32
    MAX-ACCESS read-only
    STATUS     current
    DESCRIPTION
            ""
    ::= { lcsStatusPppIpcp 15 }

-- {SCALAR} 1.3.6.1.4.1.2356.11.1.6.6.16
lcsStatusPppIpcpDeleteValues OBJECT-TYPE
    SYNTAX     DisplayString
    MAX-ACCESS read-write
    STATUS     current
    DESCRIPTION
            ""
    ::= { lcsStatusPppIpcp 16 }

-- {NODE} 1.3.6.1.4.1.2356.11.1.6.7
lcsStatusPppCbcp OBJECT IDENTIFIER ::= { lcsStatusPpp 7 }

-- {SCALAR} 1.3.6.1.4.1.2356.11.1.6.7.1
lcsStatusPppCbcpRxDiscarded OBJECT-TYPE
    SYNTAX     Counter32
    MAX-ACCESS read-only
    STATUS     current
    DESCRIPTION
            ""
    ::= { lcsStatusPppCbcp 1 }

-- {SCALAR} 1.3.6.1.4.1.2356.11.1.6.7.2
lcsStatusPppCbcpRxRequest OBJECT-TYPE
    SYNTAX     Counter32
    MAX-ACCESS read-only
    STATUS     current
    DESCRIPTION
            ""
    ::= { lcsStatusPppCbcp 2 }

-- {SCALAR} 1.3.6.1.4.1.2356.11.1.6.7.3
lcsStatusPppCbcpRxResponse OBJECT-TYPE
    SYNTAX     Counter32
    MAX-ACCESS read-only
    STATUS     current
    DESCRIPTION
            ""
    ::= { lcsStatusPppCbcp 3 }

-- {SCALAR} 1.3.6.1.4.1.2356.11.1.6.7.4
lcsStatusPppCbcpRxAcknowledge OBJECT-TYPE
    SYNTAX     Counter32
    MAX-ACCESS read-only
    STATUS     current
    DESCRIPTION
            ""
    ::= { lcsStatusPppCbcp 4 }

-- {SCALAR} 1.3.6.1.4.1.2356.11.1.6.7.5
lcsStatusPppCbcpTxRequest OBJECT-TYPE
    SYNTAX     Counter32
    MAX-ACCESS read-only
    STATUS     current
    DESCRIPTION
            ""
    ::= { lcsStatusPppCbcp 5 }

-- {SCALAR} 1.3.6.1.4.1.2356.11.1.6.7.6
lcsStatusPppCbcpTxResponse OBJECT-TYPE
    SYNTAX     Counter32
    MAX-ACCESS read-only
    STATUS     current
    DESCRIPTION
            ""
    ::= { lcsStatusPppCbcp 6 }

-- {SCALAR} 1.3.6.1.4.1.2356.11.1.6.7.7
lcsStatusPppCbcpTxAcknowledge OBJECT-TYPE
    SYNTAX     Counter32
    MAX-ACCESS read-only
    STATUS     current
    DESCRIPTION
            ""
    ::= { lcsStatusPppCbcp 7 }

-- {SCALAR} 1.3.6.1.4.1.2356.11.1.6.7.8
lcsStatusPppCbcpDeleteValues OBJECT-TYPE
    SYNTAX     DisplayString
    MAX-ACCESS read-write
    STATUS     current
    DESCRIPTION
            ""
    ::= { lcsStatusPppCbcp 8 }

-- {NODE} 1.3.6.1.4.1.2356.11.1.6.8
lcsStatusPppRxOptions OBJECT IDENTIFIER ::= { lcsStatusPpp 8 }

-- {TABLE} 1.3.6.1.4.1.2356.11.1.6.8.1
lcsStatusPppRxOptionsLcpTable OBJECT-TYPE
    SYNTAX     SEQUENCE OF LcsStatusPppRxOptionsLcpEntry
    MAX-ACCESS not-accessible
    STATUS     current
    DESCRIPTION
            ""
    ::= { lcsStatusPppRxOptions 1 }

-- {ROW} 1.3.6.1.4.1.2356.11.1.6.8.1.1
lcsStatusPppRxOptionsLcpEntry OBJECT-TYPE
    SYNTAX     LcsStatusPppRxOptionsLcpEntry
    MAX-ACCESS not-accessible
    STATUS     current
    DESCRIPTION
            ""
    INDEX {
            lcsStatusPppRxOptionsLcpEntryIfc
          }
    ::= { lcsStatusPppRxOptionsLcpTable 1 }

LcsStatusPppRxOptionsLcpEntry ::= SEQUENCE {
            lcsStatusPppRxOptionsLcpEntryIfc INTEGER,
            lcsStatusPppRxOptionsLcpEntryMru Integer32,
            lcsStatusPppRxOptionsLcpEntryAccm DisplayString,
            lcsStatusPppRxOptionsLcpEntryAuthentRequest INTEGER,
            lcsStatusPppRxOptionsLcpEntryCallBack INTEGER,
            lcsStatusPppRxOptionsLcpEntryMagicNum DisplayString,
            lcsStatusPppRxOptionsLcpEntryPfc INTEGER,
            lcsStatusPppRxOptionsLcpEntryAcfc INTEGER
    }

-- {COLUMN} 1.3.6.1.4.1.2356.11.1.6.8.1.1.1
lcsStatusPppRxOptionsLcpEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusPppRxOptionsLcpEntry 1 }

-- {COLUMN} 1.3.6.1.4.1.2356.11.1.6.8.1.1.2
lcsStatusPppRxOptionsLcpEntryMru OBJECT-TYPE
    SYNTAX     Integer32 (0..65535)
    MAX-ACCESS read-only
    STATUS     current
    DESCRIPTION
            ""
    ::= { lcsStatusPppRxOptionsLcpEntry 2 }

-- {COLUMN} 1.3.6.1.4.1.2356.11.1.6.8.1.1.3
lcsStatusPppRxOptionsLcpEntryAccm OBJECT-TYPE
    SYNTAX     DisplayString (SIZE(0..8))
    MAX-ACCESS read-only
    STATUS     current
    DESCRIPTION
            ""
    ::= { lcsStatusPppRxOptionsLcpEntry 3 }

-- {COLUMN} 1.3.6.1.4.1.2356.11.1.6.8.1.1.4
lcsStatusPppRxOptionsLcpEntryAuthentRequest OBJECT-TYPE
    SYNTAX     INTEGER {
                  eNone (0),
                  ePap (4),
                  eChap (8),
                  eMsChap (16),
                  eMsChapv2 (32)
            }
    MAX-ACCESS read-only
    STATUS     current
    DESCRIPTION
            ""
    ::= { lcsStatusPppRxOptionsLcpEntry 4 }

-- {COLUMN} 1.3.6.1.4.1.2356.11.1.6.8.1.1.5
lcsStatusPppRxOptionsLcpEntryCallBack OBJECT-TYPE
    SYNTAX     INTEGER {
                  eLcpCbAdm (0),
                  eLcpCbUsr (1),
                  eLcpCbNameAuth (2),
                  eLcpCbE164 (3),
                  eLcpCbHost (4),
                  eLcpCb (5),
                  eLcpMsCBCP (6),
                  eNone (255)
            }
    MAX-ACCESS read-only
    STATUS     current
    DESCRIPTION
            ""
    ::= { lcsStatusPppRxOptionsLcpEntry 5 }

-- {COLUMN} 1.3.6.1.4.1.2356.11.1.6.8.1.1.6
lcsStatusPppRxOptionsLcpEntryMagicNum OBJECT-TYPE
    SYNTAX     DisplayString (SIZE(0..8))
    MAX-ACCESS read-only
    STATUS     current
    DESCRIPTION
            ""
    ::= { lcsStatusPppRxOptionsLcpEntry 6 }

-- {COLUMN} 1.3.6.1.4.1.2356.11.1.6.8.1.1.7
lcsStatusPppRxOptionsLcpEntryPfc OBJECT-TYPE
    SYNTAX     INTEGER {
                  eNo (0),
                  eYes (1)
            }
    MAX-ACCESS read-only
    STATUS     current
    DESCRIPTION
            ""
    ::= { lcsStatusPppRxOptionsLcpEntry 7 }

-- {COLUMN} 1.3.6.1.4.1.2356.11.1.6.8.1.1.8
lcsStatusPppRxOptionsLcpEntryAcfc OBJECT-TYPE
    SYNTAX     INTEGER {
                  eNo (0),
                  eYes (1)
            }
    MAX-ACCESS read-only
    STATUS     current
    DESCRIPTION
            ""
    ::= { lcsStatusPppRxOptionsLcpEntry 8 }

-- {TABLE} 1.3.6.1.4.1.2356.11.1.6.8.3
lcsStatusPppRxOptionsIpcpTable OBJECT-TYPE
    SYNTAX     SEQUENCE OF LcsStatusPppRxOptionsIpcpEntry
    MAX-ACCESS not-accessible
    STATUS     current
    DESCRIPTION
            ""
    ::= { lcsStatusPppRxOptions 3 }

-- {ROW} 1.3.6.1.4.1.2356.11.1.6.8.3.1
lcsStatusPppRxOptionsIpcpEntry OBJECT-TYPE
    SYNTAX     LcsStatusPppRxOptionsIpcpEntry
    MAX-ACCESS not-accessible
    STATUS     current
    DESCRIPTION
            ""
    INDEX {
            lcsStatusPppRxOptionsIpcpEntryIfc
          }
    ::= { lcsStatusPppRxOptionsIpcpTable 1 }

LcsStatusPppRxOptionsIpcpEntry ::= SEQUENCE {
            lcsStatusPppRxOptionsIpcpEntryIfc INTEGER,
            lcsStatusPppRxOptionsIpcpEntryIpAddress IpAddress,
            lcsStatusPppRxOptionsIpcpEntryDnsDefault IpAddress,
            lcsStatusPppRxOptionsIpcpEntryNbnsDefault IpAddress,
            lcsStatusPppRxOptionsIpcpEntryDnsBackup IpAddress,
            lcsStatusPppRxOptionsIpcpEntryNbnsBackup IpAddress
    }

-- {COLUMN} 1.3.6.1.4.1.2356.11.1.6.8.3.1.1
lcsStatusPppRxOptionsIpcpEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusPppRxOptionsIpcpEntry 1 }

-- {COLUMN} 1.3.6.1.4.1.2356.11.1.6.8.3.1.2
lcsStatusPppRxOptionsIpcpEntryIpAddress OBJECT-TYPE
    SYNTAX     IpAddress
    MAX-ACCESS read-only
    STATUS     current
    DESCRIPTION
            ""
    ::= { lcsStatusPppRxOptionsIpcpEntry 2 }

-- {COLUMN} 1.3.6.1.4.1.2356.11.1.6.8.3.1.3
lcsStatusPppRxOptionsIpcpEntryDnsDefault OBJECT-TYPE
    SYNTAX     IpAddress
    MAX-ACCESS read-only
    STATUS     current
    DESCRIPTION
            ""
    ::= { lcsStatusPppRxOptionsIpcpEntry 3 }

-- {COLUMN} 1.3.6.1.4.1.2356.11.1.6.8.3.1.4
lcsStatusPppRxOptionsIpcpEntryNbnsDefault OBJECT-TYPE
    SYNTAX     IpAddress
    MAX-ACCESS read-only
    STATUS     current
    DESCRIPTION
            ""
    ::= { lcsStatusPppRxOptionsIpcpEntry 4 }

-- {COLUMN} 1.3.6.1.4.1.2356.11.1.6.8.3.1.5
lcsStatusPppRxOptionsIpcpEntryDnsBackup OBJECT-TYPE
    SYNTAX     IpAddress
    MAX-ACCESS read-only
    STATUS     current
    DESCRIPTION
            ""
    ::= { lcsStatusPppRxOptionsIpcpEntry 5 }

-- {COLUMN} 1.3.6.1.4.1.2356.11.1.6.8.3.1.6
lcsStatusPppRxOptionsIpcpEntryNbnsBackup OBJECT-TYPE
    SYNTAX     IpAddress
    MAX-ACCESS read-only
    STATUS     current
    DESCRIPTION
            ""
    ::= { lcsStatusPppRxOptionsIpcpEntry 6 }

-- {TABLE} 1.3.6.1.4.1.2356.11.1.6.8.4
lcsStatusPppRxOptionsIpv6cpTable OBJECT-TYPE
    SYNTAX     SEQUENCE OF LcsStatusPppRxOptionsIpv6cpEntry
    MAX-ACCESS not-accessible
    STATUS     current
    DESCRIPTION
            "-- empty --"
    ::= { lcsStatusPppRxOptions 4 }

-- {ROW} 1.3.6.1.4.1.2356.11.1.6.8.4.1
lcsStatusPppRxOptionsIpv6cpEntry OBJECT-TYPE
    SYNTAX     LcsStatusPppRxOptionsIpv6cpEntry
    MAX-ACCESS not-accessible
    STATUS     current
    DESCRIPTION
            ""
    INDEX {
            lcsStatusPppRxOptionsIpv6cpEntryIfc
          }
    ::= { lcsStatusPppRxOptionsIpv6cpTable 1 }

LcsStatusPppRxOptionsIpv6cpEntry ::= SEQUENCE {
            lcsStatusPppRxOptionsIpv6cpEntryIfc INTEGER,
            lcsStatusPppRxOptionsIpv6cpEntryIdentifier Integer32
    }

-- {COLUMN} 1.3.6.1.4.1.2356.11.1.6.8.4.1.1
lcsStatusPppRxOptionsIpv6cpEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            "-- empty --"
    ::= { lcsStatusPppRxOptionsIpv6cpEntry 1 }

-- {COLUMN} 1.3.6.1.4.1.2356.11.1.6.8.4.1.2
lcsStatusPppRxOptionsIpv6cpEntryIdentifier OBJECT-TYPE
    SYNTAX     Integer32 (0..2147483647)
    MAX-ACCESS read-only
    STATUS     current
    DESCRIPTION
            "-- empty --"
    ::= { lcsStatusPppRxOptionsIpv6cpEntry 2 }

-- {NODE} 1.3.6.1.4.1.2356.11.1.6.9
lcsStatusPppTxOptions OBJECT IDENTIFIER ::= { lcsStatusPpp 9 }

-- {TABLE} 1.3.6.1.4.1.2356.11.1.6.9.1
lcsStatusPppTxOptionsLcpTable OBJECT-TYPE
    SYNTAX     SEQUENCE OF LcsStatusPppTxOptionsLcpEntry
    MAX-ACCESS not-accessible
    STATUS     current
    DESCRIPTION
            ""
    ::= { lcsStatusPppTxOptions 1 }

-- {ROW} 1.3.6.1.4.1.2356.11.1.6.9.1.1
lcsStatusPppTxOptionsLcpEntry OBJECT-TYPE
    SYNTAX     LcsStatusPppTxOptionsLcpEntry
    MAX-ACCESS not-accessible
    STATUS     current
    DESCRIPTION
            ""
    INDEX {
            lcsStatusPppTxOptionsLcpEntryIfc
          }
    ::= { lcsStatusPppTxOptionsLcpTable 1 }

LcsStatusPppTxOptionsLcpEntry ::= SEQUENCE {
            lcsStatusPppTxOptionsLcpEntryIfc INTEGER,
            lcsStatusPppTxOptionsLcpEntryMru Integer32,
            lcsStatusPppTxOptionsLcpEntryAccm DisplayString,
            lcsStatusPppTxOptionsLcpEntryAuthentRequest INTEGER,
            lcsStatusPppTxOptionsLcpEntryCallBack INTEGER,
            lcsStatusPppTxOptionsLcpEntryMagicNum DisplayString,
            lcsStatusPppTxOptionsLcpEntryPfc INTEGER,
            lcsStatusPppTxOptionsLcpEntryAcfc INTEGER
    }

-- {COLUMN} 1.3.6.1.4.1.2356.11.1.6.9.1.1.1
lcsStatusPppTxOptionsLcpEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusPppTxOptionsLcpEntry 1 }

-- {COLUMN} 1.3.6.1.4.1.2356.11.1.6.9.1.1.2
lcsStatusPppTxOptionsLcpEntryMru OBJECT-TYPE
    SYNTAX     Integer32 (0..65535)
    MAX-ACCESS read-only
    STATUS     current
    DESCRIPTION
            ""
    ::= { lcsStatusPppTxOptionsLcpEntry 2 }

-- {COLUMN} 1.3.6.1.4.1.2356.11.1.6.9.1.1.3
lcsStatusPppTxOptionsLcpEntryAccm OBJECT-TYPE
    SYNTAX     DisplayString (SIZE(0..8))
    MAX-ACCESS read-only
    STATUS     current
    DESCRIPTION
            ""
    ::= { lcsStatusPppTxOptionsLcpEntry 3 }

-- {COLUMN} 1.3.6.1.4.1.2356.11.1.6.9.1.1.4
lcsStatusPppTxOptionsLcpEntryAuthentRequest OBJECT-TYPE
    SYNTAX     INTEGER {
                  eNone (0),
                  ePap (4),
                  eChap (8),
                  eMsChap (16),
                  eMsChapv2 (32)
            }
    MAX-ACCESS read-only
    STATUS     current
    DESCRIPTION
            ""
    ::= { lcsStatusPppTxOptionsLcpEntry 4 }

-- {COLUMN} 1.3.6.1.4.1.2356.11.1.6.9.1.1.5
lcsStatusPppTxOptionsLcpEntryCallBack OBJECT-TYPE
    SYNTAX     INTEGER {
                  eLcpCbAdm (0),
                  eLcpCbUsr (1),
                  eLcpCbNameAuth (2),
                  eLcpCbE164 (3),
                  eLcpCbHost (4),
                  eLcpCb (5),
                  eLcpMsCBCP (6),
                  eNone (255)
            }
    MAX-ACCESS read-only
    STATUS     current
    DESCRIPTION
            ""
    ::= { lcsStatusPppTxOptionsLcpEntry 5 }

-- {COLUMN} 1.3.6.1.4.1.2356.11.1.6.9.1.1.6
lcsStatusPppTxOptionsLcpEntryMagicNum OBJECT-TYPE
    SYNTAX     DisplayString (SIZE(0..8))
    MAX-ACCESS read-only
    STATUS     current
    DESCRIPTION
            ""
    ::= { lcsStatusPppTxOptionsLcpEntry 6 }

-- {COLUMN} 1.3.6.1.4.1.2356.11.1.6.9.1.1.7
lcsStatusPppTxOptionsLcpEntryPfc OBJECT-TYPE
    SYNTAX     INTEGER {
                  eNo (0),
                  eYes (1)
            }
    MAX-ACCESS read-only
    STATUS     current
    DESCRIPTION
            ""
    ::= { lcsStatusPppTxOptionsLcpEntry 7 }

-- {COLUMN} 1.3.6.1.4.1.2356.11.1.6.9.1.1.8
lcsStatusPppTxOptionsLcpEntryAcfc OBJECT-TYPE
    SYNTAX     INTEGER {
                  eNo (0),
                  eYes (1)
            }
    MAX-ACCESS read-only
    STATUS     current
    DESCRIPTION
            ""
    ::= { lcsStatusPppTxOptionsLcpEntry 8 }

-- {TABLE} 1.3.6.1.4.1.2356.11.1.6.9.3
lcsStatusPppTxOptionsIpcpTable OBJECT-TYPE
    SYNTAX     SEQUENCE OF LcsStatusPppTxOptionsIpcpEntry
    MAX-ACCESS not-accessible
    STATUS     current
    DESCRIPTION
            ""
    ::= { lcsStatusPppTxOptions 3 }

-- {ROW} 1.3.6.1.4.1.2356.11.1.6.9.3.1
lcsStatusPppTxOptionsIpcpEntry OBJECT-TYPE
    SYNTAX     LcsStatusPppTxOptionsIpcpEntry
    MAX-ACCESS not-accessible
    STATUS     current
    DESCRIPTION
            ""
    INDEX {
            lcsStatusPppTxOptionsIpcpEntryIfc
          }
    ::= { lcsStatusPppTxOptionsIpcpTable 1 }

LcsStatusPppTxOptionsIpcpEntry ::= SEQUENCE {
            lcsStatusPppTxOptionsIpcpEntryIfc INTEGER,
            lcsStatusPppTxOptionsIpcpEntryIpAddress IpAddress,
            lcsStatusPppTxOptionsIpcpEntryDnsDefault IpAddress,
            lcsStatusPppTxOptionsIpcpEntryNbnsDefault IpAddress,
            lcsStatusPppTxOptionsIpcpEntryDnsBackup IpAddress,
            lcsStatusPppTxOptionsIpcpEntryNbnsBackup IpAddress
    }

-- {COLUMN} 1.3.6.1.4.1.2356.11.1.6.9.3.1.1
lcsStatusPppTxOptionsIpcpEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusPppTxOptionsIpcpEntry 1 }

-- {COLUMN} 1.3.6.1.4.1.2356.11.1.6.9.3.1.2
lcsStatusPppTxOptionsIpcpEntryIpAddress OBJECT-TYPE
    SYNTAX     IpAddress
    MAX-ACCESS read-only
    STATUS     current
    DESCRIPTION
            ""
    ::= { lcsStatusPppTxOptionsIpcpEntry 2 }

-- {COLUMN} 1.3.6.1.4.1.2356.11.1.6.9.3.1.3
lcsStatusPppTxOptionsIpcpEntryDnsDefault OBJECT-TYPE
    SYNTAX     IpAddress
    MAX-ACCESS read-only
    STATUS     current
    DESCRIPTION
            ""
    ::= { lcsStatusPppTxOptionsIpcpEntry 3 }

-- {COLUMN} 1.3.6.1.4.1.2356.11.1.6.9.3.1.4
lcsStatusPppTxOptionsIpcpEntryNbnsDefault OBJECT-TYPE
    SYNTAX     IpAddress
    MAX-ACCESS read-only
    STATUS     current
    DESCRIPTION
            ""
    ::= { lcsStatusPppTxOptionsIpcpEntry 4 }

-- {COLUMN} 1.3.6.1.4.1.2356.11.1.6.9.3.1.5
lcsStatusPppTxOptionsIpcpEntryDnsBackup OBJECT-TYPE
    SYNTAX     IpAddress
    MAX-ACCESS read-only
    STATUS     current
    DESCRIPTION
            ""
    ::= { lcsStatusPppTxOptionsIpcpEntry 5 }

-- {COLUMN} 1.3.6.1.4.1.2356.11.1.6.9.3.1.6
lcsStatusPppTxOptionsIpcpEntryNbnsBackup OBJECT-TYPE
    SYNTAX     IpAddress
    MAX-ACCESS read-only
    STATUS     current
    DESCRIPTION
            ""
    ::= { lcsStatusPppTxOptionsIpcpEntry 6 }

-- {TABLE} 1.3.6.1.4.1.2356.11.1.6.9.4
lcsStatusPppTxOptionsIpv6cpTable OBJECT-TYPE
    SYNTAX     SEQUENCE OF LcsStatusPppTxOptionsIpv6cpEntry
    MAX-ACCESS not-accessible
    STATUS     current
    DESCRIPTION
            "-- empty --"
    ::= { lcsStatusPppTxOptions 4 }

-- {ROW} 1.3.6.1.4.1.2356.11.1.6.9.4.1
lcsStatusPppTxOptionsIpv6cpEntry OBJECT-TYPE
    SYNTAX     LcsStatusPppTxOptionsIpv6cpEntry
    MAX-ACCESS not-accessible
    STATUS     current
    DESCRIPTION
            ""
    INDEX {
            lcsStatusPppTxOptionsIpv6cpEntryIfc
          }
    ::= { lcsStatusPppTxOptionsIpv6cpTable 1 }

LcsStatusPppTxOptionsIpv6cpEntry ::= SEQUENCE {
            lcsStatusPppTxOptionsIpv6cpEntryIfc INTEGER,
            lcsStatusPppTxOptionsIpv6cpEntryIdentifier Integer32
    }

-- {COLUMN} 1.3.6.1.4.1.2356.11.1.6.9.4.1.1
lcsStatusPppTxOptionsIpv6cpEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            "-- empty --"
    ::= { lcsStatusPppTxOptionsIpv6cpEntry 1 }

-- {COLUMN} 1.3.6.1.4.1.2356.11.1.6.9.4.1.2
lcsStatusPppTxOptionsIpv6cpEntryIdentifier OBJECT-TYPE
    SYNTAX     Integer32 (0..2147483647)
    MAX-ACCESS read-only
    STATUS     current
    DESCRIPTION
            "-- empty --"
    ::= { lcsStatusPppTxOptionsIpv6cpEntry 2 }

-- {NODE} 1.3.6.1.4.1.2356.11.1.6.10
lcsStatusPppCcp OBJECT IDENTIFIER ::= { lcsStatusPpp 10 }

-- {SCALAR} 1.3.6.1.4.1.2356.11.1.6.10.1
lcsStatusPppCcpRxDiscarded OBJECT-TYPE
    SYNTAX     Counter32
    MAX-ACCESS read-only
    STATUS     current
    DESCRIPTION
            ""
    ::= { lcsStatusPppCcp 1 }

-- {SCALAR} 1.3.6.1.4.1.2356.11.1.6.10.2
lcsStatusPppCcpRxConfigRequest OBJECT-TYPE
    SYNTAX     Counter32
    MAX-ACCESS read-only
    STATUS     current
    DESCRIPTION
            ""
    ::= { lcsStatusPppCcp 2 }

-- {SCALAR} 1.3.6.1.4.1.2356.11.1.6.10.3
lcsStatusPppCcpRxConfigAck OBJECT-TYPE
    SYNTAX     Counter32
    MAX-ACCESS read-only
    STATUS     current
    DESCRIPTION
            ""
    ::= { lcsStatusPppCcp 3 }

-- {SCALAR} 1.3.6.1.4.1.2356.11.1.6.10.4
lcsStatusPppCcpRxConfigNak OBJECT-TYPE
    SYNTAX     Counter32
    MAX-ACCESS read-only
    STATUS     current
    DESCRIPTION
            ""
    ::= { lcsStatusPppCcp 4 }

-- {SCALAR} 1.3.6.1.4.1.2356.11.1.6.10.5
lcsStatusPppCcpRxConfigReject OBJECT-TYPE
    SYNTAX     Counter32
    MAX-ACCESS read-only
    STATUS     current
    DESCRIPTION
            ""
    ::= { lcsStatusPppCcp 5 }

-- {SCALAR} 1.3.6.1.4.1.2356.11.1.6.10.6
lcsStatusPppCcpRxTerminateRequest OBJECT-TYPE
    SYNTAX     Counter32
    MAX-ACCESS read-only
    STATUS     current
    DESCRIPTION
            ""
    ::= { lcsStatusPppCcp 6 }

-- {SCALAR} 1.3.6.1.4.1.2356.11.1.6.10.7
lcsStatusPppCcpRxTerminateAck OBJECT-TYPE
    SYNTAX     Counter32
    MAX-ACCESS read-only
    STATUS     current
    DESCRIPTION
            ""
    ::= { lcsStatusPppCcp 7 }

-- {SCALAR} 1.3.6.1.4.1.2356.11.1.6.10.8
lcsStatusPppCcpRxCodeReject OBJECT-TYPE
    SYNTAX     Counter32
    MAX-ACCESS read-only
    STATUS     current
    DESCRIPTION
            ""
    ::= { lcsStatusPppCcp 8 }

-- {SCALAR} 1.3.6.1.4.1.2356.11.1.6.10.9
lcsStatusPppCcpRxResetRequest OBJECT-TYPE
    SYNTAX     Counter32
    MAX-ACCESS read-only
    STATUS     current
    DESCRIPTION
            ""
    ::= { lcsStatusPppCcp 9 }

-- {SCALAR} 1.3.6.1.4.1.2356.11.1.6.10.10
lcsStatusPppCcpRxResetAck OBJECT-TYPE
    SYNTAX     Counter32
    MAX-ACCESS read-only
    STATUS     current
    DESCRIPTION
            ""
    ::= { lcsStatusPppCcp 10 }

-- {SCALAR} 1.3.6.1.4.1.2356.11.1.6.10.11
lcsStatusPppCcpTxConfigRequest OBJECT-TYPE
    SYNTAX     Counter32
    MAX-ACCESS read-only
    STATUS     current
    DESCRIPTION
            ""
    ::= { lcsStatusPppCcp 11 }

-- {SCALAR} 1.3.6.1.4.1.2356.11.1.6.10.12
lcsStatusPppCcpTxConfigAck OBJECT-TYPE
    SYNTAX     Counter32
    MAX-ACCESS read-only
    STATUS     current
    DESCRIPTION
            ""
    ::= { lcsStatusPppCcp 12 }

-- {SCALAR} 1.3.6.1.4.1.2356.11.1.6.10.13
lcsStatusPppCcpTxConfigNak OBJECT-TYPE
    SYNTAX     Counter32
    MAX-ACCESS read-only
    STATUS     current
    DESCRIPTION
            ""
    ::= { lcsStatusPppCcp 13 }

-- {SCALAR} 1.3.6.1.4.1.2356.11.1.6.10.14
lcsStatusPppCcpTxConfigReject OBJECT-TYPE
    SYNTAX     Counter32
    MAX-ACCESS read-only
    STATUS     current
    DESCRIPTION
            ""
    ::= { lcsStatusPppCcp 14 }

-- {SCALAR} 1.3.6.1.4.1.2356.11.1.6.10.15
lcsStatusPppCcpTxTerminateRequest OBJECT-TYPE
    SYNTAX     Counter32
    MAX-ACCESS read-only
    STATUS     current
    DESCRIPTION
            ""
    ::= { lcsStatusPppCcp 15 }

-- {SCALAR} 1.3.6.1.4.1.2356.11.1.6.10.16
lcsStatusPppCcpTxTerminateAck OBJECT-TYPE
    SYNTAX     Counter32
    MAX-ACCESS read-only
    STATUS     current
    DESCRIPTION
            ""
    ::= { lcsStatusPppCcp 16 }

-- {SCALAR} 1.3.6.1.4.1.2356.11.1.6.10.17
lcsStatusPppCcpTxCodeReject OBJECT-TYPE
    SYNTAX     Counter32
    MAX-ACCESS read-only
    STATUS     current
    DESCRIPTION
            ""
    ::= { lcsStatusPppCcp 17 }

-- {SCALAR} 1.3.6.1.4.1.2356.11.1.6.10.19
lcsStatusPppCcpTxResetRequest OBJECT-TYPE
    SYNTAX     Counter32
    MAX-ACCESS read-only
    STATUS     current
    DESCRIPTION
            ""
    ::= { lcsStatusPppCcp 19 }

-- {SCALAR} 1.3.6.1.4.1.2356.11.1.6.10.20
lcsStatusPppCcpTxResetAck OBJECT-TYPE
    SYNTAX     Counter32
    MAX-ACCESS read-only
    STATUS     current
    DESCRIPTION
            ""
    ::= { lcsStatusPppCcp 20 }

-- {SCALAR} 1.3.6.1.4.1.2356.11.1.6.10.21
lcsStatusPppCcpDeleteValues OBJECT-TYPE
    SYNTAX     DisplayString
    MAX-ACCESS read-write
    STATUS     current
    DESCRIPTION
            ""
    ::= { lcsStatusPppCcp 21 }

-- {SCALAR} 1.3.6.1.4.1.2356.11.1.6.10.22
lcsStatusPppCcpCompressionErrors OBJECT-TYPE
    SYNTAX     Counter32
    MAX-ACCESS read-only
    STATUS     current
    DESCRIPTION
            ""
    ::= { lcsStatusPppCcp 22 }

-- {NODE} 1.3.6.1.4.1.2356.11.1.6.11
lcsStatusPppMl OBJECT IDENTIFIER ::= { lcsStatusPpp 11 }

-- {SCALAR} 1.3.6.1.4.1.2356.11.1.6.11.1
lcsStatusPppMlBundleConnections OBJECT-TYPE
    SYNTAX     Integer32 (0..2147483647)
    MAX-ACCESS read-only
    STATUS     current
    DESCRIPTION
            ""
    ::= { lcsStatusPppMl 1 }

-- {SCALAR} 1.3.6.1.4.1.2356.11.1.6.11.2
lcsStatusPppMlRxSeqLost OBJECT-TYPE
    SYNTAX     Counter32
    MAX-ACCESS read-only
    STATUS     current
    DESCRIPTION
            ""
    ::= { lcsStatusPppMl 2 }

-- {SCALAR} 1.3.6.1.4.1.2356.11.1.6.11.3
lcsStatusPppMlRxSeqRepeat OBJECT-TYPE
    SYNTAX     Counter32
    MAX-ACCESS read-only
    STATUS     current
    DESCRIPTION
            ""
    ::= { lcsStatusPppMl 3 }

-- {SCALAR} 1.3.6.1.4.1.2356.11.1.6.11.4
lcsStatusPppMlRxMrruExceeded OBJECT-TYPE
    SYNTAX     Counter32
    MAX-ACCESS read-only
    STATUS     current
    DESCRIPTION
            ""
    ::= { lcsStatusPppMl 4 }

-- {SCALAR} 1.3.6.1.4.1.2356.11.1.6.11.5
lcsStatusPppMlRxHeaderError OBJECT-TYPE
    SYNTAX     Counter32
    MAX-ACCESS read-only
    STATUS     current
    DESCRIPTION
            ""
    ::= { lcsStatusPppMl 5 }

-- {SCALAR} 1.3.6.1.4.1.2356.11.1.6.11.6
lcsStatusPppMlRxDiscarded OBJECT-TYPE
    SYNTAX     Counter32
    MAX-ACCESS read-only
    STATUS     current
    DESCRIPTION
            ""
    ::= { lcsStatusPppMl 6 }

-- {SCALAR} 1.3.6.1.4.1.2356.11.1.6.11.7
lcsStatusPppMlRxFragStart OBJECT-TYPE
    SYNTAX     Counter32
    MAX-ACCESS read-only
    STATUS     current
    DESCRIPTION
            ""
    ::= { lcsStatusPppMl 7 }

-- {SCALAR} 1.3.6.1.4.1.2356.11.1.6.11.8
lcsStatusPppMlRxFragMid OBJECT-TYPE
    SYNTAX     Counter32
    MAX-ACCESS read-only
    STATUS     current
    DESCRIPTION
            ""
    ::= { lcsStatusPppMl 8 }

-- {SCALAR} 1.3.6.1.4.1.2356.11.1.6.11.9
lcsStatusPppMlRxFragEnd OBJECT-TYPE
    SYNTAX     Counter32
    MAX-ACCESS read-only
    STATUS     current
    DESCRIPTION
            ""
    ::= { lcsStatusPppMl 9 }

-- {SCALAR} 1.3.6.1.4.1.2356.11.1.6.11.10
lcsStatusPppMlRxNotFragmented OBJECT-TYPE
    SYNTAX     Counter32
    MAX-ACCESS read-only
    STATUS     current
    DESCRIPTION
            ""
    ::= { lcsStatusPppMl 10 }

-- {SCALAR} 1.3.6.1.4.1.2356.11.1.6.11.11
lcsStatusPppMlDeleteValues OBJECT-TYPE
    SYNTAX     DisplayString
    MAX-ACCESS read-write
    STATUS     current
    DESCRIPTION
            ""
    ::= { lcsStatusPppMl 11 }

-- {NODE} 1.3.6.1.4.1.2356.11.1.6.12
lcsStatusPppBacp OBJECT IDENTIFIER ::= { lcsStatusPpp 12 }

-- {SCALAR} 1.3.6.1.4.1.2356.11.1.6.12.1
lcsStatusPppBacpRxErrors OBJECT-TYPE
    SYNTAX     Counter32
    MAX-ACCESS read-only
    STATUS     current
    DESCRIPTION
            ""
    ::= { lcsStatusPppBacp 1 }

-- {SCALAR} 1.3.6.1.4.1.2356.11.1.6.12.2
lcsStatusPppBacpRxDiscarded OBJECT-TYPE
    SYNTAX     Counter32
    MAX-ACCESS read-only
    STATUS     current
    DESCRIPTION
            ""
    ::= { lcsStatusPppBacp 2 }

-- {SCALAR} 1.3.6.1.4.1.2356.11.1.6.12.3
lcsStatusPppBacpRxCallRequest OBJECT-TYPE
    SYNTAX     Counter32
    MAX-ACCESS read-only
    STATUS     current
    DESCRIPTION
            ""
    ::= { lcsStatusPppBacp 3 }

-- {SCALAR} 1.3.6.1.4.1.2356.11.1.6.12.4
lcsStatusPppBacpRxCallResponse OBJECT-TYPE
    SYNTAX     Counter32
    MAX-ACCESS read-only
    STATUS     current
    DESCRIPTION
            ""
    ::= { lcsStatusPppBacp 4 }

-- {SCALAR} 1.3.6.1.4.1.2356.11.1.6.12.5
lcsStatusPppBacpRxCallbackRequest OBJECT-TYPE
    SYNTAX     Counter32
    MAX-ACCESS read-only
    STATUS     current
    DESCRIPTION
            ""
    ::= { lcsStatusPppBacp 5 }

-- {SCALAR} 1.3.6.1.4.1.2356.11.1.6.12.6
lcsStatusPppBacpRxCallbackResponse OBJECT-TYPE
    SYNTAX     Counter32
    MAX-ACCESS read-only
    STATUS     current
    DESCRIPTION
            ""
    ::= { lcsStatusPppBacp 6 }

-- {SCALAR} 1.3.6.1.4.1.2356.11.1.6.12.7
lcsStatusPppBacpRxLinkDropRequest OBJECT-TYPE
    SYNTAX     Counter32
    MAX-ACCESS read-only
    STATUS     current
    DESCRIPTION
            ""
    ::= { lcsStatusPppBacp 7 }

-- {SCALAR} 1.3.6.1.4.1.2356.11.1.6.12.8
lcsStatusPppBacpRxLinkDropResponse OBJECT-TYPE
    SYNTAX     Counter32
    MAX-ACCESS read-only
    STATUS     current
    DESCRIPTION
            ""
    ::= { lcsStatusPppBacp 8 }

-- {SCALAR} 1.3.6.1.4.1.2356.11.1.6.12.9
lcsStatusPppBacpRxStatusIndication OBJECT-TYPE
    SYNTAX     Counter32
    MAX-ACCESS read-only
    STATUS     current
    DESCRIPTION
            ""
    ::= { lcsStatusPppBacp 9 }

-- {SCALAR} 1.3.6.1.4.1.2356.11.1.6.12.10
lcsStatusPppBacpRxStatusResponse OBJECT-TYPE
    SYNTAX     Counter32
    MAX-ACCESS read-only
    STATUS     current
    DESCRIPTION
            ""
    ::= { lcsStatusPppBacp 10 }

-- {SCALAR} 1.3.6.1.4.1.2356.11.1.6.12.11
lcsStatusPppBacpTxCallRequest OBJECT-TYPE
    SYNTAX     Counter32
    MAX-ACCESS read-only
    STATUS     current
    DESCRIPTION
            ""
    ::= { lcsStatusPppBacp 11 }

-- {SCALAR} 1.3.6.1.4.1.2356.11.1.6.12.12
lcsStatusPppBacpTxCallResponse OBJECT-TYPE
    SYNTAX     Counter32
    MAX-ACCESS read-only
    STATUS     current
    DESCRIPTION
            ""
    ::= { lcsStatusPppBacp 12 }

-- {SCALAR} 1.3.6.1.4.1.2356.11.1.6.12.13
lcsStatusPppBacpTxCallbackRequest OBJECT-TYPE
    SYNTAX     Counter32
    MAX-ACCESS read-only
    STATUS     current
    DESCRIPTION
            ""
    ::= { lcsStatusPppBacp 13 }

-- {SCALAR} 1.3.6.1.4.1.2356.11.1.6.12.14
lcsStatusPppBacpTxCallbackResponse OBJECT-TYPE
    SYNTAX     Counter32
    MAX-ACCESS read-only
    STATUS     current
    DESCRIPTION
            ""
    ::= { lcsStatusPppBacp 14 }

-- {SCALAR} 1.3.6.1.4.1.2356.11.1.6.12.15
lcsStatusPppBacpTxLinkDropRequest OBJECT-TYPE
    SYNTAX     Counter32
    MAX-ACCESS read-only
    STATUS     current
    DESCRIPTION
            ""
    ::= { lcsStatusPppBacp 15 }

-- {SCALAR} 1.3.6.1.4.1.2356.11.1.6.12.16
lcsStatusPppBacpTxLinkDropResponse OBJECT-TYPE
    SYNTAX     Counter32
    MAX-ACCESS read-only
    STATUS     current
    DESCRIPTION
            ""
    ::= { lcsStatusPppBacp 16 }

-- {SCALAR} 1.3.6.1.4.1.2356.11.1.6.12.17
lcsStatusPppBacpTxStatusIndication OBJECT-TYPE
    SYNTAX     Counter32
    MAX-ACCESS read-only
    STATUS     current
    DESCRIPTION
            ""
    ::= { lcsStatusPppBacp 17 }

-- {SCALAR} 1.3.6.1.4.1.2356.11.1.6.12.18
lcsStatusPppBacpTxStatusResponse OBJECT-TYPE
    SYNTAX     Counter32
    MAX-ACCESS read-only
    STATUS     current
    DESCRIPTION
            ""
    ::= { lcsStatusPppBacp 18 }

-- {SCALAR} 1.3.6.1.4.1.2356.11.1.6.12.19
lcsStatusPppBacpDeleteValues OBJECT-TYPE
    SYNTAX     DisplayString
    MAX-ACCESS read-write
    STATUS     current
    DESCRIPTION
            ""
    ::= { lcsStatusPppBacp 19 }

-- {SCALAR} 1.3.6.1.4.1.2356.11.1.6.13
lcsStatusPppDeleteValues OBJECT-TYPE
    SYNTAX     DisplayString
    MAX-ACCESS read-write
    STATUS     current
    DESCRIPTION
            ""
    ::= { lcsStatusPpp 13 }

-- {NODE} 1.3.6.1.4.1.2356.11.1.6.14
lcsStatusPppIpv6cp OBJECT IDENTIFIER ::= { lcsStatusPpp 14 }

-- {SCALAR} 1.3.6.1.4.1.2356.11.1.6.14.1
lcsStatusPppIpv6cpRxDiscarded OBJECT-TYPE
    SYNTAX     Counter32
    MAX-ACCESS read-only
    STATUS     current
    DESCRIPTION
            "-- empty --"
    ::= { lcsStatusPppIpv6cp 1 }

-- {SCALAR} 1.3.6.1.4.1.2356.11.1.6.14.2
lcsStatusPppIpv6cpRxConfigRequest OBJECT-TYPE
    SYNTAX     Counter32
    MAX-ACCESS read-only
    STATUS     current
    DESCRIPTION
            "-- empty --"
    ::= { lcsStatusPppIpv6cp 2 }

-- {SCALAR} 1.3.6.1.4.1.2356.11.1.6.14.3
lcsStatusPppIpv6cpRxConfigAck OBJECT-TYPE
    SYNTAX     Counter32
    MAX-ACCESS read-only
    STATUS     current
    DESCRIPTION
            "-- empty --"
    ::= { lcsStatusPppIpv6cp 3 }

-- {SCALAR} 1.3.6.1.4.1.2356.11.1.6.14.4
lcsStatusPppIpv6cpRxConfigNak OBJECT-TYPE
    SYNTAX     Counter32
    MAX-ACCESS read-only
    STATUS     current
    DESCRIPTION
            "-- empty --"
    ::= { lcsStatusPppIpv6cp 4 }

-- {SCALAR} 1.3.6.1.4.1.2356.11.1.6.14.5
lcsStatusPppIpv6cpRxConfigReject OBJECT-TYPE
    SYNTAX     Counter32
    MAX-ACCESS read-only
    STATUS     current
    DESCRIPTION
            "-- empty --"
    ::= { lcsStatusPppIpv6cp 5 }

-- {SCALAR} 1.3.6.1.4.1.2356.11.1.6.14.6
lcsStatusPppIpv6cpRxTerminateRequest OBJECT-TYPE
    SYNTAX     Counter32
    MAX-ACCESS read-only
    STATUS     current
    DESCRIPTION
            "-- empty --"
    ::= { lcsStatusPppIpv6cp 6 }

-- {SCALAR} 1.3.6.1.4.1.2356.11.1.6.14.7
lcsStatusPppIpv6cpRxTerminateAck OBJECT-TYPE
    SYNTAX     Counter32
    MAX-ACCESS read-only
    STATUS     current
    DESCRIPTION
            "-- empty --"
    ::= { lcsStatusPppIpv6cp 7 }

-- {SCALAR} 1.3.6.1.4.1.2356.11.1.6.14.8
lcsStatusPppIpv6cpRxCodeReject OBJECT-TYPE
    SYNTAX     Counter32
    MAX-ACCESS read-only
    STATUS     current
    DESCRIPTION
            "-- empty --"
    ::= { lcsStatusPppIpv6cp 8 }

-- {SCALAR} 1.3.6.1.4.1.2356.11.1.6.14.9
lcsStatusPppIpv6cpTxConfigRequest OBJECT-TYPE
    SYNTAX     Counter32
    MAX-ACCESS read-only
    STATUS     current
    DESCRIPTION
            "-- empty --"
    ::= { lcsStatusPppIpv6cp 9 }

-- {SCALAR} 1.3.6.1.4.1.2356.11.1.6.14.10
lcsStatusPppIpv6cpTxConfigAck OBJECT-TYPE
    SYNTAX     Counter32
    MAX-ACCESS read-only
    STATUS     current
    DESCRIPTION
            "-- empty --"
    ::= { lcsStatusPppIpv6cp 10 }

-- {SCALAR} 1.3.6.1.4.1.2356.11.1.6.14.11
lcsStatusPppIpv6cpTxConfigNak OBJECT-TYPE
    SYNTAX     Counter32
    MAX-ACCESS read-only
    STATUS     current
    DESCRIPTION
            "-- empty --"
    ::= { lcsStatusPppIpv6cp 11 }

-- {SCALAR} 1.3.6.1.4.1.2356.11.1.6.14.12
lcsStatusPppIpv6cpTxConfigReject OBJECT-TYPE
    SYNTAX     Counter32
    MAX-ACCESS read-only
    STATUS     current
    DESCRIPTION
            "-- empty --"
    ::= { lcsStatusPppIpv6cp 12 }

-- {SCALAR} 1.3.6.1.4.1.2356.11.1.6.14.13
lcsStatusPppIpv6cpTxTerminateRequest OBJECT-TYPE
    SYNTAX     Counter32
    MAX-ACCESS read-only
    STATUS     current
    DESCRIPTION
            "-- empty --"
    ::= { lcsStatusPppIpv6cp 13 }

-- {SCALAR} 1.3.6.1.4.1.2356.11.1.6.14.14
lcsStatusPppIpv6cpTxTerminateAck OBJECT-TYPE
    SYNTAX     Counter32
    MAX-ACCESS read-only
    STATUS     current
    DESCRIPTION
            "-- empty --"
    ::= { lcsStatusPppIpv6cp 14 }

-- {SCALAR} 1.3.6.1.4.1.2356.11.1.6.14.15
lcsStatusPppIpv6cpTxCodeReject OBJECT-TYPE
    SYNTAX     Counter32
    MAX-ACCESS read-only
    STATUS     current
    DESCRIPTION
            "-- empty --"
    ::= { lcsStatusPppIpv6cp 15 }

-- {SCALAR} 1.3.6.1.4.1.2356.11.1.6.14.16
lcsStatusPppIpv6cpDeleteValues OBJECT-TYPE
    SYNTAX     DisplayString
    MAX-ACCESS read-write
    STATUS     current
    DESCRIPTION
            "-- empty --"
    ::= { lcsStatusPppIpv6cp 16 }

-- {NODE} 1.3.6.1.4.1.2356.11.1.9
lcsStatusTcpIp OBJECT IDENTIFIER ::= { lcsStatus 9 }

-- {NODE} 1.3.6.1.4.1.2356.11.1.9.1
lcsStatusTcpIpArp OBJECT IDENTIFIER ::= { lcsStatusTcpIp 1 }

-- {SCALAR} 1.3.6.1.4.1.2356.11.1.9.1.1
lcsStatusTcpIpArpLanRx OBJECT-TYPE
    SYNTAX     Counter32
    MAX-ACCESS read-only
    STATUS     current
    DESCRIPTION
            ""
    ::= { lcsStatusTcpIpArp 1 }

-- {SCALAR} 1.3.6.1.4.1.2356.11.1.9.1.2
lcsStatusTcpIpArpLanTx OBJECT-TYPE
    SYNTAX     Counter32
    MAX-ACCESS read-only
    STATUS     current
    DESCRIPTION
            ""
    ::= { lcsStatusTcpIpArp 2 }

-- {SCALAR} 1.3.6.1.4.1.2356.11.1.9.1.3
lcsStatusTcpIpArpLanErrors OBJECT-TYPE
    SYNTAX     Counter32
    MAX-ACCESS read-only
    STATUS     current
    DESCRIPTION
            ""
    ::= { lcsStatusTcpIpArp 3 }

-- {SCALAR} 1.3.6.1.4.1.2356.11.1.9.1.4
lcsStatusTcpIpArpWanRx OBJECT-TYPE
    SYNTAX     Counter32
    MAX-ACCESS read-only
    STATUS     current
    DESCRIPTION
            ""
    ::= { lcsStatusTcpIpArp 4 }

-- {SCALAR} 1.3.6.1.4.1.2356.11.1.9.1.5
lcsStatusTcpIpArpWanTx OBJECT-TYPE
    SYNTAX     Counter32
    MAX-ACCESS read-only
    STATUS     current
    DESCRIPTION
            ""
    ::= { lcsStatusTcpIpArp 5 }

-- {SCALAR} 1.3.6.1.4.1.2356.11.1.9.1.6
lcsStatusTcpIpArpWanErrors OBJECT-TYPE
    SYNTAX     Counter32
    MAX-ACCESS read-only
    STATUS     current
    DESCRIPTION
            ""
    ::= { lcsStatusTcpIpArp 6 }

-- {TABLE} 1.3.6.1.4.1.2356.11.1.9.1.7
lcsStatusTcpIpArpTableArpTable OBJECT-TYPE
    SYNTAX     SEQUENCE OF LcsStatusTcpIpArpTableArpEntry
    MAX-ACCESS not-accessible
    STATUS     current
    DESCRIPTION
            ""
    ::= { lcsStatusTcpIpArp 7 }

-- {ROW} 1.3.6.1.4.1.2356.11.1.9.1.7.1
lcsStatusTcpIpArpTableArpEntry OBJECT-TYPE
    SYNTAX     LcsStatusTcpIpArpTableArpEntry
    MAX-ACCESS not-accessible
    STATUS     current
    DESCRIPTION
            ""
    INDEX {
            lcsStatusTcpIpArpTableArpEntryIpAddress
          }
    ::= { lcsStatusTcpIpArpTableArpTable 1 }

LcsStatusTcpIpArpTableArpEntry ::= SEQUENCE {
            lcsStatusTcpIpArpTableArpEntryIpAddress IpAddress,
            lcsStatusTcpIpArpTableArpEntryMacAddress MacAddress,
            lcsStatusTcpIpArpTableArpEntryLastAccess Integer32,
            lcsStatusTcpIpArpTableArpEntryEthernetPort INTEGER,
            lcsStatusTcpIpArpTableArpEntryPeer DisplayString,
            lcsStatusTcpIpArpTableArpEntryVlanId Integer32,
            lcsStatusTcpIpArpTableArpEntryConnect INTEGER
    }

-- {COLUMN} 1.3.6.1.4.1.2356.11.1.9.1.7.1.1
lcsStatusTcpIpArpTableArpEntryIpAddress OBJECT-TYPE
    SYNTAX     IpAddress
    MAX-ACCESS read-only
    STATUS     current
    DESCRIPTION
            ""
    ::= { lcsStatusTcpIpArpTableArpEntry 1 }

-- {COLUMN} 1.3.6.1.4.1.2356.11.1.9.1.7.1.2
lcsStatusTcpIpArpTableArpEntryMacAddress OBJECT-TYPE
    SYNTAX     MacAddress
    MAX-ACCESS read-only
    STATUS     current
    DESCRIPTION
            ""
    ::= { lcsStatusTcpIpArpTableArpEntry 2 }

-- {COLUMN} 1.3.6.1.4.1.2356.11.1.9.1.7.1.3
lcsStatusTcpIpArpTableArpEntryLastAccess OBJECT-TYPE
    SYNTAX     Integer32 (0..2147483647)
    MAX-ACCESS read-only
    STATUS     current
    DESCRIPTION
            ""
    ::= { lcsStatusTcpIpArpTableArpEntry 3 }

-- {COLUMN} 1.3.6.1.4.1.2356.11.1.9.1.7.1.5
lcsStatusTcpIpArpTableArpEntryEthernetPort OBJECT-TYPE
    SYNTAX     INTEGER {
                  eUnknown (0),
                  eUplink (1),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            ""
    ::= { lcsStatusTcpIpArpTableArpEntry 5 }

-- {COLUMN} 1.3.6.1.4.1.2356.11.1.9.1.7.1.6
lcsStatusTcpIpArpTableArpEntryPeer OBJECT-TYPE
    SYNTAX     DisplayString (SIZE(0..255))
    MAX-ACCESS read-only
    STATUS     current
    DESCRIPTION
            ""
    ::= { lcsStatusTcpIpArpTableArpEntry 6 }

-- {COLUMN} 1.3.6.1.4.1.2356.11.1.9.1.7.1.7
lcsStatusTcpIpArpTableArpEntryVlanId OBJECT-TYPE
    SYNTAX     Integer32 (0..65535)
    MAX-ACCESS read-only
    STATUS     current
    DESCRIPTION
            ""
    ::= { lcsStatusTcpIpArpTableArpEntry 7 }

-- {COLUMN} 1.3.6.1.4.1.2356.11.1.9.1.7.1.8
lcsStatusTcpIpArpTableArpEntryConnect OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eWan (32768)
            }
    MAX-ACCESS read-only
    STATUS     current
    DESCRIPTION
            ""
    ::= { lcsStatusTcpIpArpTableArpEntry 8 }

-- {SCALAR} 1.3.6.1.4.1.2356.11.1.9.1.8
lcsStatusTcpIpArpDeleteValues OBJECT-TYPE
    SYNTAX     DisplayString
    MAX-ACCESS read-write
    STATUS     current
    DESCRIPTION
            ""
    ::= { lcsStatusTcpIpArp 8 }

-- {TABLE} 1.3.6.1.4.1.2356.11.1.9.1.10
lcsStatusTcpIpArpLanProxyRulesTable OBJECT-TYPE
    SYNTAX     SEQUENCE OF LcsStatusTcpIpArpLanProxyRulesEntry
    MAX-ACCESS not-accessible
    STATUS     current
    DESCRIPTION
            "-- empty --"
    ::= { lcsStatusTcpIpArp 10 }

-- {ROW} 1.3.6.1.4.1.2356.11.1.9.1.10.1
lcsStatusTcpIpArpLanProxyRulesEntry OBJECT-TYPE
    SYNTAX     LcsStatusTcpIpArpLanProxyRulesEntry
    MAX-ACCESS not-accessible
    STATUS     current
    DESCRIPTION
            ""
    INDEX {
            lcsStatusTcpIpArpLanProxyRulesEntrySrcAddress,
            lcsStatusTcpIpArpLanProxyRulesEntryLanInterface,
            lcsStatusTcpIpArpLanProxyRulesEntryVlanId,
            lcsStatusTcpIpArpLanProxyRulesEntryDstAddress
          }
    ::= { lcsStatusTcpIpArpLanProxyRulesTable 1 }

LcsStatusTcpIpArpLanProxyRulesEntry ::= SEQUENCE {
            lcsStatusTcpIpArpLanProxyRulesEntrySrcAddress IpAddress,
            lcsStatusTcpIpArpLanProxyRulesEntryLanInterface INTEGER,
            lcsStatusTcpIpArpLanProxyRulesEntryVlanId Unsigned32,
            lcsStatusTcpIpArpLanProxyRulesEntryDstAddress IpAddress
    }

-- {COLUMN} 1.3.6.1.4.1.2356.11.1.9.1.10.1.1
lcsStatusTcpIpArpLanProxyRulesEntrySrcAddress OBJECT-TYPE
    SYNTAX     IpAddress
    MAX-ACCESS read-only
    STATUS     current
    DESCRIPTION
            "-- empty --"
    ::= { lcsStatusTcpIpArpLanProxyRulesEntry 1 }

-- {COLUMN} 1.3.6.1.4.1.2356.11.1.9.1.10.1.2
lcsStatusTcpIpArpLanProxyRulesEntryLanInterface OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            "-- empty --"
    ::= { lcsStatusTcpIpArpLanProxyRulesEntry 2 }

-- {COLUMN} 1.3.6.1.4.1.2356.11.1.9.1.10.1.3
lcsStatusTcpIpArpLanProxyRulesEntryVlanId OBJECT-TYPE
    SYNTAX     Unsigned32 (0..65535)
    MAX-ACCESS read-only
    STATUS     current
    DESCRIPTION
            "-- empty --"
    ::= { lcsStatusTcpIpArpLanProxyRulesEntry 3 }

-- {COLUMN} 1.3.6.1.4.1.2356.11.1.9.1.10.1.4
lcsStatusTcpIpArpLanProxyRulesEntryDstAddress OBJECT-TYPE
    SYNTAX     IpAddress
    MAX-ACCESS read-only
    STATUS     current
    DESCRIPTION
            "-- empty --"
    ::= { lcsStatusTcpIpArpLanProxyRulesEntry 4 }

-- {NODE} 1.3.6.1.4.1.2356.11.1.9.2
lcsStatusTcpIpIp OBJECT IDENTIFIER ::= { lcsStatusTcpIp 2 }

-- {SCALAR} 1.3.6.1.4.1.2356.11.1.9.2.1
lcsStatusTcpIpIpLanRx OBJECT-TYPE
    SYNTAX     Counter32
    MAX-ACCESS read-only
    STATUS     current
    DESCRIPTION
            ""
    ::= { lcsStatusTcpIpIp 1 }

-- {SCALAR} 1.3.6.1.4.1.2356.11.1.9.2.2
lcsStatusTcpIpIpLanTx OBJECT-TYPE
    SYNTAX     Counter32
    MAX-ACCESS read-only
    STATUS     current
    DESCRIPTION
            ""
    ::= { lcsStatusTcpIpIp 2 }

-- {SCALAR} 1.3.6.1.4.1.2356.11.1.9.2.3
lcsStatusTcpIpIpLanChecksumErrors OBJECT-TYPE
    SYNTAX     Counter32
    MAX-ACCESS read-only
    STATUS     current
    DESCRIPTION
            ""
    ::= { lcsStatusTcpIpIp 3 }

-- {SCALAR} 1.3.6.1.4.1.2356.11.1.9.2.4
lcsStatusTcpIpIpLanServiceErrors OBJECT-TYPE
    SYNTAX     Counter32
    MAX-ACCESS read-only
    STATUS     current
    DESCRIPTION
            ""
    ::= { lcsStatusTcpIpIp 4 }

-- {SCALAR} 1.3.6.1.4.1.2356.11.1.9.2.5
lcsStatusTcpIpIpWanRx OBJECT-TYPE
    SYNTAX     Counter32
    MAX-ACCESS read-only
    STATUS     current
    DESCRIPTION
            ""
    ::= { lcsStatusTcpIpIp 5 }

-- {SCALAR} 1.3.6.1.4.1.2356.11.1.9.2.6
lcsStatusTcpIpIpWanTx OBJECT-TYPE
    SYNTAX     Counter32
    MAX-ACCESS read-only
    STATUS     current
    DESCRIPTION
            ""
    ::= { lcsStatusTcpIpIp 6 }

-- {SCALAR} 1.3.6.1.4.1.2356.11.1.9.2.7
lcsStatusTcpIpIpWanChecksumErrors OBJECT-TYPE
    SYNTAX     Counter32
    MAX-ACCESS read-only
    STATUS     current
    DESCRIPTION
            ""
    ::= { lcsStatusTcpIpIp 7 }

-- {SCALAR} 1.3.6.1.4.1.2356.11.1.9.2.8
lcsStatusTcpIpIpWanServiceErrors OBJECT-TYPE
    SYNTAX     Counter32
    MAX-ACCESS read-only
    STATUS     current
    DESCRIPTION
            ""
    ::= { lcsStatusTcpIpIp 8 }

-- {SCALAR} 1.3.6.1.4.1.2356.11.1.9.2.9
lcsStatusTcpIpIpWanRxDisconnect OBJECT-TYPE
    SYNTAX     Counter32
    MAX-ACCESS read-only
    STATUS     current
    DESCRIPTION
            ""
    ::= { lcsStatusTcpIpIp 9 }

-- {SCALAR} 1.3.6.1.4.1.2356.11.1.9.2.10
lcsStatusTcpIpIpLanFragmentationErrors OBJECT-TYPE
    SYNTAX     Counter32
    MAX-ACCESS read-only
    STATUS     current
    DESCRIPTION
            ""
    ::= { lcsStatusTcpIpIp 10 }

-- {SCALAR} 1.3.6.1.4.1.2356.11.1.9.2.11
lcsStatusTcpIpIpWanFragmentationErrors OBJECT-TYPE
    SYNTAX     Counter32
    MAX-ACCESS read-only
    STATUS     current
    DESCRIPTION
            ""
    ::= { lcsStatusTcpIpIp 11 }

-- {SCALAR} 1.3.6.1.4.1.2356.11.1.9.2.12
lcsStatusTcpIpIpDeleteValues OBJECT-TYPE
    SYNTAX     DisplayString
    MAX-ACCESS read-write
    STATUS     current
    DESCRIPTION
            ""
    ::= { lcsStatusTcpIpIp 12 }

-- {SCALAR} 1.3.6.1.4.1.2356.11.1.9.2.13
lcsStatusTcpIpIpLanFragmentations OBJECT-TYPE
    SYNTAX     Counter32
    MAX-ACCESS read-only
    STATUS     current
    DESCRIPTION
            ""
    ::= { lcsStatusTcpIpIp 13 }

-- {SCALAR} 1.3.6.1.4.1.2356.11.1.9.2.14
lcsStatusTcpIpIpLanFragmentationsForced OBJECT-TYPE
    SYNTAX     Counter32
    MAX-ACCESS read-only
    STATUS     current
    DESCRIPTION
            ""
    ::= { lcsStatusTcpIpIp 14 }

-- {SCALAR} 1.3.6.1.4.1.2356.11.1.9.2.15
lcsStatusTcpIpIpWanFragmentations OBJECT-TYPE
    SYNTAX     Counter32
    MAX-ACCESS read-only
    STATUS     current
    DESCRIPTION
            ""
    ::= { lcsStatusTcpIpIp 15 }

-- {SCALAR} 1.3.6.1.4.1.2356.11.1.9.2.16
lcsStatusTcpIpIpWanFragmentationsForced OBJECT-TYPE
    SYNTAX     Counter32
    MAX-ACCESS read-only
    STATUS     current
    DESCRIPTION
            ""
    ::= { lcsStatusTcpIpIp 16 }

-- {SCALAR} 1.3.6.1.4.1.2356.11.1.9.2.17
lcsStatusTcpIpIpLoopError OBJECT-TYPE
    SYNTAX     Counter32
    MAX-ACCESS read-only
    STATUS     current
    DESCRIPTION
            ""
    ::= { lcsStatusTcpIpIp 17 }

-- {NODE} 1.3.6.1.4.1.2356.11.1.9.3
lcsStatusTcpIpIcmp OBJECT IDENTIFIER ::= { lcsStatusTcpIp 3 }

-- {SCALAR} 1.3.6.1.4.1.2356.11.1.9.3.1
lcsStatusTcpIpIcmpLanRx OBJECT-TYPE
    SYNTAX     Counter32
    MAX-ACCESS read-only
    STATUS     current
    DESCRIPTION
            ""
    ::= { lcsStatusTcpIpIcmp 1 }

-- {SCALAR} 1.3.6.1.4.1.2356.11.1.9.3.2
lcsStatusTcpIpIcmpLanTx OBJECT-TYPE
    SYNTAX     Counter32
    MAX-ACCESS read-only
    STATUS     current
    DESCRIPTION
            ""
    ::= { lcsStatusTcpIpIcmp 2 }

-- {SCALAR} 1.3.6.1.4.1.2356.11.1.9.3.3
lcsStatusTcpIpIcmpLanChecksumErrors OBJECT-TYPE
    SYNTAX     Counter32
    MAX-ACCESS read-only
    STATUS     current
    DESCRIPTION
            ""
    ::= { lcsStatusTcpIpIcmp 3 }

-- {SCALAR} 1.3.6.1.4.1.2356.11.1.9.3.4
lcsStatusTcpIpIcmpLanServiceErrors OBJECT-TYPE
    SYNTAX     Counter32
    MAX-ACCESS read-only
    STATUS     current
    DESCRIPTION
            ""
    ::= { lcsStatusTcpIpIcmp 4 }

-- {SCALAR} 1.3.6.1.4.1.2356.11.1.9.3.5
lcsStatusTcpIpIcmpWanRx OBJECT-TYPE
    SYNTAX     Counter32
    MAX-ACCESS read-only
    STATUS     current
    DESCRIPTION
            ""
    ::= { lcsStatusTcpIpIcmp 5 }

-- {SCALAR} 1.3.6.1.4.1.2356.11.1.9.3.6
lcsStatusTcpIpIcmpWanTx OBJECT-TYPE
    SYNTAX     Counter32
    MAX-ACCESS read-only
    STATUS     current
    DESCRIPTION
            ""
    ::= { lcsStatusTcpIpIcmp 6 }

-- {SCALAR} 1.3.6.1.4.1.2356.11.1.9.3.7
lcsStatusTcpIpIcmpWanChecksumErrors OBJECT-TYPE
    SYNTAX     Counter32
    MAX-ACCESS read-only
    STATUS     current
    DESCRIPTION
            ""
    ::= { lcsStatusTcpIpIcmp 7 }

-- {SCALAR} 1.3.6.1.4.1.2356.11.1.9.3.8
lcsStatusTcpIpIcmpWanServiceErrors OBJECT-TYPE
    SYNTAX     Counter32
    MAX-ACCESS read-only
    STATUS     current
    DESCRIPTION
            ""
    ::= { lcsStatusTcpIpIcmp 8 }

-- {SCALAR} 1.3.6.1.4.1.2356.11.1.9.3.9
lcsStatusTcpIpIcmpDeleteValues OBJECT-TYPE
    SYNTAX     DisplayString
    MAX-ACCESS read-write
    STATUS     current
    DESCRIPTION
            ""
    ::= { lcsStatusTcpIpIcmp 9 }

-- {NODE} 1.3.6.1.4.1.2356.11.1.9.4
lcsStatusTcpIpTftp OBJECT IDENTIFIER ::= { lcsStatusTcpIp 4 }

-- {SCALAR} 1.3.6.1.4.1.2356.11.1.9.4.1
lcsStatusTcpIpTftpLanRx OBJECT-TYPE
    SYNTAX     Counter32
    MAX-ACCESS read-only
    STATUS     current
    DESCRIPTION
            ""
    ::= { lcsStatusTcpIpTftp 1 }

-- {SCALAR} 1.3.6.1.4.1.2356.11.1.9.4.2
lcsStatusTcpIpTftpLanRxReadRequest OBJECT-TYPE
    SYNTAX     Counter32
    MAX-ACCESS read-only
    STATUS     current
    DESCRIPTION
            ""
    ::= { lcsStatusTcpIpTftp 2 }

-- {SCALAR} 1.3.6.1.4.1.2356.11.1.9.4.3
lcsStatusTcpIpTftpLanRxWriteRequest OBJECT-TYPE
    SYNTAX     Counter32
    MAX-ACCESS read-only
    STATUS     current
    DESCRIPTION
            ""
    ::= { lcsStatusTcpIpTftp 3 }

-- {SCALAR} 1.3.6.1.4.1.2356.11.1.9.4.4
lcsStatusTcpIpTftpLanRxData OBJECT-TYPE
    SYNTAX     Counter32
    MAX-ACCESS read-only
    STATUS     current
    DESCRIPTION
            ""
    ::= { lcsStatusTcpIpTftp 4 }

-- {SCALAR} 1.3.6.1.4.1.2356.11.1.9.4.5
lcsStatusTcpIpTftpLanRxAck OBJECT-TYPE
    SYNTAX     Counter32
    MAX-ACCESS read-only
    STATUS     current
    DESCRIPTION
            ""
    ::= { lcsStatusTcpIpTftp 5 }

-- {SCALAR} 1.3.6.1.4.1.2356.11.1.9.4.6
lcsStatusTcpIpTftpLanRxOptionAck OBJECT-TYPE
    SYNTAX     Counter32
    MAX-ACCESS read-only
    STATUS     current
    DESCRIPTION
            ""
    ::= { lcsStatusTcpIpTftp 6 }

-- {SCALAR} 1.3.6.1.4.1.2356.11.1.9.4.7
lcsStatusTcpIpTftpLanRxErrors OBJECT-TYPE
    SYNTAX     Counter32
    MAX-ACCESS read-only
    STATUS     current
    DESCRIPTION
            ""
    ::= { lcsStatusTcpIpTftp 7 }

-- {SCALAR} 1.3.6.1.4.1.2356.11.1.9.4.8
lcsStatusTcpIpTftpLanRxBadPackets OBJECT-TYPE
    SYNTAX     Counter32
    MAX-ACCESS read-only
    STATUS     current
    DESCRIPTION
            ""
    ::= { lcsStatusTcpIpTftp 8 }

-- {SCALAR} 1.3.6.1.4.1.2356.11.1.9.4.9
lcsStatusTcpIpTftpLanTx OBJECT-TYPE
    SYNTAX     Counter32
    MAX-ACCESS read-only
    STATUS     current
    DESCRIPTION
            ""
    ::= { lcsStatusTcpIpTftp 9 }

-- {SCALAR} 1.3.6.1.4.1.2356.11.1.9.4.10
lcsStatusTcpIpTftpLanTxData OBJECT-TYPE
    SYNTAX     Counter32
    MAX-ACCESS read-only
    STATUS     current
    DESCRIPTION
            ""
    ::= { lcsStatusTcpIpTftp 10 }

-- {SCALAR} 1.3.6.1.4.1.2356.11.1.9.4.11
lcsStatusTcpIpTftpLanTxAck OBJECT-TYPE
    SYNTAX     Counter32
    MAX-ACCESS read-only
    STATUS     current
    DESCRIPTION
            ""
    ::= { lcsStatusTcpIpTftp 11 }

-- {SCALAR} 1.3.6.1.4.1.2356.11.1.9.4.12
lcsStatusTcpIpTftpLanTxOptionAck OBJECT-TYPE
    SYNTAX     Counter32
    MAX-ACCESS read-only
    STATUS     current
    DESCRIPTION
            ""
    ::= { lcsStatusTcpIpTftp 12 }

-- {SCALAR} 1.3.6.1.4.1.2356.11.1.9.4.13
lcsStatusTcpIpTftpLanTxErrors OBJECT-TYPE
    SYNTAX     Counter32
    MAX-ACCESS read-only
    STATUS     current
    DESCRIPTION
            ""
    ::= { lcsStatusTcpIpTftp 13 }

-- {SCALAR} 1.3.6.1.4.1.2356.11.1.9.4.14
lcsStatusTcpIpTftpLanTxRepeats OBJECT-TYPE
    SYNTAX     Counter32
    MAX-ACCESS read-only
    STATUS     current
    DESCRIPTION
            ""
    ::= { lcsStatusTcpIpTftp 14 }

-- {SCALAR} 1.3.6.1.4.1.2356.11.1.9.4.15
lcsStatusTcpIpTftpLanConnections OBJECT-TYPE
    SYNTAX     Counter32
    MAX-ACCESS read-only
    STATUS     current
    DESCRIPTION
            ""
    ::= { lcsStatusTcpIpTftp 15 }

-- {SCALAR} 1.3.6.1.4.1.2356.11.1.9.4.16
lcsStatusTcpIpTftpWanRx OBJECT-TYPE
    SYNTAX     Counter32
    MAX-ACCESS read-only
    STATUS     current
    DESCRIPTION
            ""
    ::= { lcsStatusTcpIpTftp 16 }

-- {SCALAR} 1.3.6.1.4.1.2356.11.1.9.4.17
lcsStatusTcpIpTftpWanRxReadRequest OBJECT-TYPE
    SYNTAX     Counter32
    MAX-ACCESS read-only
    STATUS     current
    DESCRIPTION
            ""
    ::= { lcsStatusTcpIpTftp 17 }

-- {SCALAR} 1.3.6.1.4.1.2356.11.1.9.4.18
lcsStatusTcpIpTftpWanRxWriteRequest OBJECT-TYPE
    SYNTAX     Counter32
    MAX-ACCESS read-only
    STATUS     current
    DESCRIPTION
            ""
    ::= { lcsStatusTcpIpTftp 18 }

-- {SCALAR} 1.3.6.1.4.1.2356.11.1.9.4.19
lcsStatusTcpIpTftpWanRxData OBJECT-TYPE
    SYNTAX     Counter32
    MAX-ACCESS read-only
    STATUS     current
    DESCRIPTION
            ""
    ::= { lcsStatusTcpIpTftp 19 }

-- {SCALAR} 1.3.6.1.4.1.2356.11.1.9.4.20
lcsStatusTcpIpTftpWanRxAck OBJECT-TYPE
    SYNTAX     Counter32
    MAX-ACCESS read-only
    STATUS     current
    DESCRIPTION
            ""
    ::= { lcsStatusTcpIpTftp 20 }

-- {SCALAR} 1.3.6.1.4.1.2356.11.1.9.4.21
lcsStatusTcpIpTftpWanRxOptionAck OBJECT-TYPE
    SYNTAX     Counter32
    MAX-ACCESS read-only
    STATUS     current
    DESCRIPTION
            ""
    ::= { lcsStatusTcpIpTftp 21 }

-- {SCALAR} 1.3.6.1.4.1.2356.11.1.9.4.22
lcsStatusTcpIpTftpWanRxErrors OBJECT-TYPE
    SYNTAX     Counter32
    MAX-ACCESS read-only
    STATUS     current
    DESCRIPTION
            ""
    ::= { lcsStatusTcpIpTftp 22 }

-- {SCALAR} 1.3.6.1.4.1.2356.11.1.9.4.23
lcsStatusTcpIpTftpWanRxBadPackets OBJECT-TYPE
    SYNTAX     Counter32
    MAX-ACCESS read-only
    STATUS     current
    DESCRIPTION
            ""
    ::= { lcsStatusTcpIpTftp 23 }

-- {SCALAR} 1.3.6.1.4.1.2356.11.1.9.4.24
lcsStatusTcpIpTftpWanTx OBJECT-TYPE
    SYNTAX     Counter32
    MAX-ACCESS read-only
    STATUS     current
    DESCRIPTION
            ""
    ::= { lcsStatusTcpIpTftp 24 }

-- {SCALAR} 1.3.6.1.4.1.2356.11.1.9.4.25
lcsStatusTcpIpTftpWanTxData OBJECT-TYPE
    SYNTAX     Counter32
    MAX-ACCESS read-only
    STATUS     current
    DESCRIPTION
            ""
    ::= { lcsStatusTcpIpTftp 25 }

-- {SCALAR} 1.3.6.1.4.1.2356.11.1.9.4.26
lcsStatusTcpIpTftpWanTxAck OBJECT-TYPE
    SYNTAX     Counter32
    MAX-ACCESS read-only
    STATUS     current
    DESCRIPTION
            ""
    ::= { lcsStatusTcpIpTftp 26 }

-- {SCALAR} 1.3.6.1.4.1.2356.11.1.9.4.27
lcsStatusTcpIpTftpWanTxOptionAck OBJECT-TYPE
    SYNTAX     Counter32
    MAX-ACCESS read-only
    STATUS     current
    DESCRIPTION
            ""
    ::= { lcsStatusTcpIpTftp 27 }

-- {SCALAR} 1.3.6.1.4.1.2356.11.1.9.4.28
lcsStatusTcpIpTftpWanTxErrors OBJECT-TYPE
    SYNTAX     Counter32
    MAX-ACCESS read-only
    STATUS     current
    DESCRIPTION
            ""
    ::= { lcsStatusTcpIpTftp 28 }

-- {SCALAR} 1.3.6.1.4.1.2356.11.1.9.4.29
lcsStatusTcpIpTftpWanTxRepeats OBJECT-TYPE
    SYNTAX     Counter32
    MAX-ACCESS read-only
    STATUS     current
    DESCRIPTION
            ""
    ::= { lcsStatusTcpIpTftp 29 }

-- {SCALAR} 1.3.6.1.4.1.2356.11.1.9.4.30
lcsStatusTcpIpTftpWanConnections OBJECT-TYPE
    SYNTAX     Counter32
    MAX-ACCESS read-only
    STATUS     current
    DESCRIPTION
            ""
    ::= { lcsStatusTcpIpTftp 30 }

-- {SCALAR} 1.3.6.1.4.1.2356.11.1.9.4.31
lcsStatusTcpIpTftpDeleteValues OBJECT-TYPE
    SYNTAX     DisplayString
    MAX-ACCESS read-write
    STATUS     current
    DESCRIPTION
            ""
    ::= { lcsStatusTcpIpTftp 31 }

-- {NODE} 1.3.6.1.4.1.2356.11.1.9.5
lcsStatusTcpIpTcp OBJECT IDENTIFIER ::= { lcsStatusTcpIp 5 }

-- {SCALAR} 1.3.6.1.4.1.2356.11.1.9.5.1
lcsStatusTcpIpTcpLanRx OBJECT-TYPE
    SYNTAX     Counter32
    MAX-ACCESS read-only
    STATUS     current
    DESCRIPTION
            ""
    ::= { lcsStatusTcpIpTcp 1 }

-- {SCALAR} 1.3.6.1.4.1.2356.11.1.9.5.2
lcsStatusTcpIpTcpLanTx OBJECT-TYPE
    SYNTAX     Counter32
    MAX-ACCESS read-only
    STATUS     current
    DESCRIPTION
            ""
    ::= { lcsStatusTcpIpTcp 2 }

-- {SCALAR} 1.3.6.1.4.1.2356.11.1.9.5.3
lcsStatusTcpIpTcpLanTxRepeats OBJECT-TYPE
    SYNTAX     Counter32
    MAX-ACCESS read-only
    STATUS     current
    DESCRIPTION
            ""
    ::= { lcsStatusTcpIpTcp 3 }

-- {SCALAR} 1.3.6.1.4.1.2356.11.1.9.5.4
lcsStatusTcpIpTcpLanChecksumErrors OBJECT-TYPE
    SYNTAX     Counter32
    MAX-ACCESS read-only
    STATUS     current
    DESCRIPTION
            ""
    ::= { lcsStatusTcpIpTcp 4 }

-- {SCALAR} 1.3.6.1.4.1.2356.11.1.9.5.5
lcsStatusTcpIpTcpLanServiceErrors OBJECT-TYPE
    SYNTAX     Counter32
    MAX-ACCESS read-only
    STATUS     current
    DESCRIPTION
            ""
    ::= { lcsStatusTcpIpTcp 5 }

-- {SCALAR} 1.3.6.1.4.1.2356.11.1.9.5.6
lcsStatusTcpIpTcpLanConnections OBJECT-TYPE
    SYNTAX     Counter32
    MAX-ACCESS read-only
    STATUS     current
    DESCRIPTION
            ""
    ::= { lcsStatusTcpIpTcp 6 }

-- {SCALAR} 1.3.6.1.4.1.2356.11.1.9.5.7
lcsStatusTcpIpTcpWanRx OBJECT-TYPE
    SYNTAX     Counter32
    MAX-ACCESS read-only
    STATUS     current
    DESCRIPTION
            ""
    ::= { lcsStatusTcpIpTcp 7 }

-- {SCALAR} 1.3.6.1.4.1.2356.11.1.9.5.8
lcsStatusTcpIpTcpWanTx OBJECT-TYPE
    SYNTAX     Counter32
    MAX-ACCESS read-only
    STATUS     current
    DESCRIPTION
            ""
    ::= { lcsStatusTcpIpTcp 8 }

-- {SCALAR} 1.3.6.1.4.1.2356.11.1.9.5.9
lcsStatusTcpIpTcpWanTxRepeats OBJECT-TYPE
    SYNTAX     Counter32
    MAX-ACCESS read-only
    STATUS     current
    DESCRIPTION
            ""
    ::= { lcsStatusTcpIpTcp 9 }

-- {SCALAR} 1.3.6.1.4.1.2356.11.1.9.5.10
lcsStatusTcpIpTcpWanChecksumErrors OBJECT-TYPE
    SYNTAX     Counter32
    MAX-ACCESS read-only
    STATUS     current
    DESCRIPTION
            ""
    ::= { lcsStatusTcpIpTcp 10 }

-- {SCALAR} 1.3.6.1.4.1.2356.11.1.9.5.11
lcsStatusTcpIpTcpWanServiceErrors OBJECT-TYPE
    SYNTAX     Counter32
    MAX-ACCESS read-only
    STATUS     current
    DESCRIPTION
            ""
    ::= { lcsStatusTcpIpTcp 11 }

-- {SCALAR} 1.3.6.1.4.1.2356.11.1.9.5.12
lcsStatusTcpIpTcpWanConnections OBJECT-TYPE
    SYNTAX     Counter32
    MAX-ACCESS read-only
    STATUS     current
    DESCRIPTION
            ""
    ::= { lcsStatusTcpIpTcp 12 }

-- {SCALAR} 1.3.6.1.4.1.2356.11.1.9.5.13
lcsStatusTcpIpTcpDeleteValues OBJECT-TYPE
    SYNTAX     DisplayString
    MAX-ACCESS read-write
    STATUS     current
    DESCRIPTION
            ""
    ::= { lcsStatusTcpIpTcp 13 }

-- {NODE} 1.3.6.1.4.1.2356.11.1.9.6
lcsStatusTcpIpDhcp OBJECT IDENTIFIER ::= { lcsStatusTcpIp 6 }

-- {SCALAR} 1.3.6.1.4.1.2356.11.1.9.6.1
lcsStatusTcpIpDhcpLanRx OBJECT-TYPE
    SYNTAX     Counter32
    MAX-ACCESS read-only
    STATUS     current
    DESCRIPTION
            ""
    ::= { lcsStatusTcpIpDhcp 1 }

-- {SCALAR} 1.3.6.1.4.1.2356.11.1.9.6.2
lcsStatusTcpIpDhcpLanTx OBJECT-TYPE
    SYNTAX     Counter32
    MAX-ACCESS read-only
    STATUS     current
    DESCRIPTION
            ""
    ::= { lcsStatusTcpIpDhcp 2 }

-- {SCALAR} 1.3.6.1.4.1.2356.11.1.9.6.3
lcsStatusTcpIpDhcpWanRx OBJECT-TYPE
    SYNTAX     Counter32
    MAX-ACCESS read-only
    STATUS     current
    DESCRIPTION
            ""
    ::= { lcsStatusTcpIpDhcp 3 }

-- {SCALAR} 1.3.6.1.4.1.2356.11.1.9.6.4
lcsStatusTcpIpDhcpDiscard OBJECT-TYPE
    SYNTAX     Counter32
    MAX-ACCESS read-only
    STATUS     current
    DESCRIPTION
            ""
    ::= { lcsStatusTcpIpDhcp 4 }

-- {SCALAR} 1.3.6.1.4.1.2356.11.1.9.6.5
lcsStatusTcpIpDhcpRxDiscover OBJECT-TYPE
    SYNTAX     Counter32
    MAX-ACCESS read-only
    STATUS     current
    DESCRIPTION
            ""
    ::= { lcsStatusTcpIpDhcp 5 }

-- {SCALAR} 1.3.6.1.4.1.2356.11.1.9.6.6
lcsStatusTcpIpDhcpRxRequest OBJECT-TYPE
    SYNTAX     Counter32
    MAX-ACCESS read-only
    STATUS     current
    DESCRIPTION
            ""
    ::= { lcsStatusTcpIpDhcp 6 }

-- {SCALAR} 1.3.6.1.4.1.2356.11.1.9.6.7
lcsStatusTcpIpDhcpRxDecline OBJECT-TYPE
    SYNTAX     Counter32
    MAX-ACCESS read-only
    STATUS     current
    DESCRIPTION
            ""
    ::= { lcsStatusTcpIpDhcp 7 }

-- {SCALAR} 1.3.6.1.4.1.2356.11.1.9.6.8
lcsStatusTcpIpDhcpRxInform OBJECT-TYPE
    SYNTAX     Counter32
    MAX-ACCESS read-only
    STATUS     current
    DESCRIPTION
            ""
    ::= { lcsStatusTcpIpDhcp 8 }

-- {SCALAR} 1.3.6.1.4.1.2356.11.1.9.6.9
lcsStatusTcpIpDhcpRxRelease OBJECT-TYPE
    SYNTAX     Counter32
    MAX-ACCESS read-only
    STATUS     current
    DESCRIPTION
            ""
    ::= { lcsStatusTcpIpDhcp 9 }

-- {SCALAR} 1.3.6.1.4.1.2356.11.1.9.6.10
lcsStatusTcpIpDhcpTxOffer OBJECT-TYPE
    SYNTAX     Counter32
    MAX-ACCESS read-only
    STATUS     current
    DESCRIPTION
            ""
    ::= { lcsStatusTcpIpDhcp 10 }

-- {SCALAR} 1.3.6.1.4.1.2356.11.1.9.6.11
lcsStatusTcpIpDhcpTxAck OBJECT-TYPE
    SYNTAX     Counter32
    MAX-ACCESS read-only
    STATUS     current
    DESCRIPTION
            ""
    ::= { lcsStatusTcpIpDhcp 11 }

-- {SCALAR} 1.3.6.1.4.1.2356.11.1.9.6.12
lcsStatusTcpIpDhcpTxNak OBJECT-TYPE
    SYNTAX     Counter32
    MAX-ACCESS read-only
    STATUS     current
    DESCRIPTION
            ""
    ::= { lcsStatusTcpIpDhcp 12 }

-- {SCALAR} 1.3.6.1.4.1.2356.11.1.9.6.13
lcsStatusTcpIpDhcpServerError OBJECT-TYPE
    SYNTAX     Counter32
    MAX-ACCESS read-only
    STATUS     current
    DESCRIPTION
            ""
    ::= { lcsStatusTcpIpDhcp 13 }

-- {SCALAR} 1.3.6.1.4.1.2356.11.1.9.6.14
lcsStatusTcpIpDhcpAssigned OBJECT-TYPE
    SYNTAX     Integer32 (0..2147483647)
    MAX-ACCESS read-only
    STATUS     current
    DESCRIPTION
            ""
    ::= { lcsStatusTcpIpDhcp 14 }

-- {SCALAR} 1.3.6.1.4.1.2356.11.1.9.6.15
lcsStatusTcpIpDhcpMacConflicts OBJECT-TYPE
    SYNTAX     Counter32
    MAX-ACCESS read-only
    STATUS     current
    DESCRIPTION
            ""
    ::= { lcsStatusTcpIpDhcp 15 }

-- {TABLE} 1.3.6.1.4.1.2356.11.1.9.6.16
lcsStatusTcpIpDhcpDhcpTableTable OBJECT-TYPE
    SYNTAX     SEQUENCE OF LcsStatusTcpIpDhcpDhcpTableEntry
    MAX-ACCESS not-accessible
    STATUS     current
    DESCRIPTION
            ""
    ::= { lcsStatusTcpIpDhcp 16 }

-- {ROW} 1.3.6.1.4.1.2356.11.1.9.6.16.1
lcsStatusTcpIpDhcpDhcpTableEntry OBJECT-TYPE
    SYNTAX     LcsStatusTcpIpDhcpDhcpTableEntry
    MAX-ACCESS not-accessible
    STATUS     current
    DESCRIPTION
            ""
    INDEX {
            lcsStatusTcpIpDhcpDhcpTableEntryIpAddress,
            lcsStatusTcpIpDhcpDhcpTableEntryNetworkName
          }
    ::= { lcsStatusTcpIpDhcpDhcpTableTable 1 }

LcsStatusTcpIpDhcpDhcpTableEntry ::= SEQUENCE {
            lcsStatusTcpIpDhcpDhcpTableEntryIpAddress IpAddress,
            lcsStatusTcpIpDhcpDhcpTableEntryMacAddress DisplayString,
            lcsStatusTcpIpDhcpDhcpTableEntryTimeout Integer32,
            lcsStatusTcpIpDhcpDhcpTableEntryHostname DisplayString,
            lcsStatusTcpIpDhcpDhcpTableEntryType BITS,
            lcsStatusTcpIpDhcpDhcpTableEntryEthernetPort INTEGER,
            lcsStatusTcpIpDhcpDhcpTableEntryVlanId Integer32,
            lcsStatusTcpIpDhcpDhcpTableEntryNetworkName DisplayString,
            lcsStatusTcpIpDhcpDhcpTableEntryLanIfc INTEGER,
            lcsStatusTcpIpDhcpDhcpTableEntryAssignment DisplayString,
            lcsStatusTcpIpDhcpDhcpTableEntryAssignmentNumeric Gauge32
    }

-- {COLUMN} 1.3.6.1.4.1.2356.11.1.9.6.16.1.1
lcsStatusTcpIpDhcpDhcpTableEntryIpAddress OBJECT-TYPE
    SYNTAX     IpAddress
    MAX-ACCESS read-only
    STATUS     current
    DESCRIPTION
            ""
    ::= { lcsStatusTcpIpDhcpDhcpTableEntry 1 }

-- {COLUMN} 1.3.6.1.4.1.2356.11.1.9.6.16.1.2
lcsStatusTcpIpDhcpDhcpTableEntryMacAddress OBJECT-TYPE
    SYNTAX     DisplayString (SIZE(0..12))
    MAX-ACCESS read-only
    STATUS     current
    DESCRIPTION
            ""
    ::= { lcsStatusTcpIpDhcpDhcpTableEntry 2 }

-- {COLUMN} 1.3.6.1.4.1.2356.11.1.9.6.16.1.3
lcsStatusTcpIpDhcpDhcpTableEntryTimeout OBJECT-TYPE
    SYNTAX     Integer32 (0..2147483647)
    MAX-ACCESS read-only
    STATUS     current
    DESCRIPTION
            ""
    ::= { lcsStatusTcpIpDhcpDhcpTableEntry 3 }

-- {COLUMN} 1.3.6.1.4.1.2356.11.1.9.6.16.1.4
lcsStatusTcpIpDhcpDhcpTableEntryHostname OBJECT-TYPE
    SYNTAX     DisplayString (SIZE(0..65))
    MAX-ACCESS read-only
    STATUS     current
    DESCRIPTION
            ""
    ::= { lcsStatusTcpIpDhcpDhcpTableEntry 4 }

-- {COLUMN} 1.3.6.1.4.1.2356.11.1.9.6.16.1.5
lcsStatusTcpIpDhcpDhcpTableEntryType OBJECT-TYPE
    SYNTAX     BITS {
                  eRelay (4),
                  eCache (8),
                  eBootp (10),
                  eDyn (11),
                  eStat (12),
                  eUnkn (13),
                  enewreq (14),
                  enew (15)
            }
    MAX-ACCESS read-only
    STATUS     current
    DESCRIPTION
            ""
    ::= { lcsStatusTcpIpDhcpDhcpTableEntry 5 }

-- {COLUMN} 1.3.6.1.4.1.2356.11.1.9.6.16.1.7
lcsStatusTcpIpDhcpDhcpTableEntryEthernetPort OBJECT-TYPE
    SYNTAX     INTEGER {
                  eUnknown (0),
                  eUplink (1),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            ""
    ::= { lcsStatusTcpIpDhcpDhcpTableEntry 7 }

-- {COLUMN} 1.3.6.1.4.1.2356.11.1.9.6.16.1.8
lcsStatusTcpIpDhcpDhcpTableEntryVlanId OBJECT-TYPE
    SYNTAX     Integer32 (0..65535)
    MAX-ACCESS read-only
    STATUS     current
    DESCRIPTION
            ""
    ::= { lcsStatusTcpIpDhcpDhcpTableEntry 8 }

-- {COLUMN} 1.3.6.1.4.1.2356.11.1.9.6.16.1.9
lcsStatusTcpIpDhcpDhcpTableEntryNetworkName OBJECT-TYPE
    SYNTAX     DisplayString (SIZE(0..17))
    MAX-ACCESS read-only
    STATUS     current
    DESCRIPTION
            ""
    ::= { lcsStatusTcpIpDhcpDhcpTableEntry 9 }

-- {COLUMN} 1.3.6.1.4.1.2356.11.1.9.6.16.1.10
lcsStatusTcpIpDhcpDhcpTableEntryLanIfc OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsStatusTcpIpDhcpDhcpTableEntry 10 }

-- {COLUMN} 1.3.6.1.4.1.2356.11.1.9.6.16.1.11
lcsStatusTcpIpDhcpDhcpTableEntryAssignment OBJECT-TYPE
    SYNTAX     DisplayString (SIZE(0..21))
    MAX-ACCESS read-only
    STATUS     current
    DESCRIPTION
            "-- empty --"
    ::= { lcsStatusTcpIpDhcpDhcpTableEntry 11 }

-- {COLUMN} 1.3.6.1.4.1.2356.11.1.9.6.16.1.12
lcsStatusTcpIpDhcpDhcpTableEntryAssignmentNumeric OBJECT-TYPE
    SYNTAX     Gauge32
    MAX-ACCESS read-only
    STATUS     current
    DESCRIPTION
            "-- empty --"
    ::= { lcsStatusTcpIpDhcpDhcpTableEntry 12 }

-- {SCALAR} 1.3.6.1.4.1.2356.11.1.9.6.18
lcsStatusTcpIpDhcpDeleteValues OBJECT-TYPE
    SYNTAX     DisplayString
    MAX-ACCESS read-write
    STATUS     current
    DESCRIPTION
            ""
    ::= { lcsStatusTcpIpDhcp 18 }

-- {SCALAR} 1.3.6.1.4.1.2356.11.1.9.6.19
lcsStatusTcpIpDhcpWanTx OBJECT-TYPE
    SYNTAX     Counter32
    MAX-ACCESS read-only
    STATUS     current
    DESCRIPTION
            ""
    ::= { lcsStatusTcpIpDhcp 19 }

-- {TABLE} 1.3.6.1.4.1.2356.11.1.9.6.20
lcsStatusTcpIpDhcpNetworkListTable OBJECT-TYPE
    SYNTAX     SEQUENCE OF LcsStatusTcpIpDhcpNetworkListEntry
    MAX-ACCESS not-accessible
    STATUS     current
    DESCRIPTION
            ""
    ::= { lcsStatusTcpIpDhcp 20 }

-- {ROW} 1.3.6.1.4.1.2356.11.1.9.6.20.1
lcsStatusTcpIpDhcpNetworkListEntry OBJECT-TYPE
    SYNTAX     LcsStatusTcpIpDhcpNetworkListEntry
    MAX-ACCESS not-accessible
    STATUS     current
    DESCRIPTION
            ""
    INDEX {
            lcsStatusTcpIpDhcpNetworkListEntryNetworkName
          }
    ::= { lcsStatusTcpIpDhcpNetworkListTable 1 }

LcsStatusTcpIpDhcpNetworkListEntry ::= SEQUENCE {
            lcsStatusTcpIpDhcpNetworkListEntryNetworkName DisplayString,
            lcsStatusTcpIpDhcpNetworkListEntryStartAddressPool IpAddress,
            lcsStatusTcpIpDhcpNetworkListEntryEndAddressPool IpAddress,
            lcsStatusTcpIpDhcpNetworkListEntryNetmask IpAddress,
            lcsStatusTcpIpDhcpNetworkListEntryBroadcastAddress IpAddress,
            lcsStatusTcpIpDhcpNetworkListEntryGatewayAddress IpAddress,
            lcsStatusTcpIpDhcpNetworkListEntryDnsDefault IpAddress,
            lcsStatusTcpIpDhcpNetworkListEntryDnsBackup IpAddress,
            lcsStatusTcpIpDhcpNetworkListEntryNbnsDefault IpAddress,
            lcsStatusTcpIpDhcpNetworkListEntryNbnsBackup IpAddress,
            lcsStatusTcpIpDhcpNetworkListEntryServerFlags DisplayString,
            lcsStatusTcpIpDhcpNetworkListEntryBroadcastBit INTEGER,
            lcsStatusTcpIpDhcpNetworkListEntryServerId IpAddress,
            lcsStatusTcpIpDhcpNetworkListEntryVlanId Integer32,
            lcsStatusTcpIpDhcpNetworkListEntryMasterServer IpAddress,
            lcsStatusTcpIpDhcpNetworkListEntryCache INTEGER,
            lcsStatusTcpIpDhcpNetworkListEntryAdaption INTEGER,
            lcsStatusTcpIpDhcpNetworkListEntryCluster INTEGER,
            lcsStatusTcpIpDhcpNetworkListEntry2ndMasterServer IpAddress,
            lcsStatusTcpIpDhcpNetworkListEntry3rdMasterServer IpAddress,
            lcsStatusTcpIpDhcpNetworkListEntry4thMasterServer IpAddress,
            lcsStatusTcpIpDhcpNetworkListEntryLanIfc INTEGER,
            lcsStatusTcpIpDhcpNetworkListEntryMaxLease Integer32,
            lcsStatusTcpIpDhcpNetworkListEntryDefLease Integer32,
            lcsStatusTcpIpDhcpNetworkListEntryPoolTotal Integer32,
            lcsStatusTcpIpDhcpNetworkListEntryPoolReserved Integer32,
            lcsStatusTcpIpDhcpNetworkListEntryPoolInUse Integer32,
            lcsStatusTcpIpDhcpNetworkListEntryPoolUnused Integer32,
            lcsStatusTcpIpDhcpNetworkListEntryLoopbackAddress DisplayString,
            lcsStatusTcpIpDhcpNetworkListEntrySuppressArpCheck INTEGER
    }

-- {COLUMN} 1.3.6.1.4.1.2356.11.1.9.6.20.1.1
lcsStatusTcpIpDhcpNetworkListEntryNetworkName OBJECT-TYPE
    SYNTAX     DisplayString (SIZE(0..16))
    MAX-ACCESS read-only
    STATUS     current
    DESCRIPTION
            ""
    ::= { lcsStatusTcpIpDhcpNetworkListEntry 1 }

-- {COLUMN} 1.3.6.1.4.1.2356.11.1.9.6.20.1.2
lcsStatusTcpIpDhcpNetworkListEntryStartAddressPool OBJECT-TYPE
    SYNTAX     IpAddress
    MAX-ACCESS read-only
    STATUS     current
    DESCRIPTION
            ""
    ::= { lcsStatusTcpIpDhcpNetworkListEntry 2 }

-- {COLUMN} 1.3.6.1.4.1.2356.11.1.9.6.20.1.3
lcsStatusTcpIpDhcpNetworkListEntryEndAddressPool OBJECT-TYPE
    SYNTAX     IpAddress
    MAX-ACCESS read-only
    STATUS     current
    DESCRIPTION
            ""
    ::= { lcsStatusTcpIpDhcpNetworkListEntry 3 }

-- {COLUMN} 1.3.6.1.4.1.2356.11.1.9.6.20.1.4
lcsStatusTcpIpDhcpNetworkListEntryNetmask OBJECT-TYPE
    SYNTAX     IpAddress
    MAX-ACCESS read-only
    STATUS     current
    DESCRIPTION
            ""
    ::= { lcsStatusTcpIpDhcpNetworkListEntry 4 }

-- {COLUMN} 1.3.6.1.4.1.2356.11.1.9.6.20.1.5
lcsStatusTcpIpDhcpNetworkListEntryBroadcastAddress OBJECT-TYPE
    SYNTAX     IpAddress
    MAX-ACCESS read-only
    STATUS     current
    DESCRIPTION
            ""
    ::= { lcsStatusTcpIpDhcpNetworkListEntry 5 }

-- {COLUMN} 1.3.6.1.4.1.2356.11.1.9.6.20.1.6
lcsStatusTcpIpDhcpNetworkListEntryGatewayAddress OBJECT-TYPE
    SYNTAX     IpAddress
    MAX-ACCESS read-only
    STATUS     current
    DESCRIPTION
            ""
    ::= { lcsStatusTcpIpDhcpNetworkListEntry 6 }

-- {COLUMN} 1.3.6.1.4.1.2356.11.1.9.6.20.1.7
lcsStatusTcpIpDhcpNetworkListEntryDnsDefault OBJECT-TYPE
    SYNTAX     IpAddress
    MAX-ACCESS read-only
    STATUS     current
    DESCRIPTION
            ""
    ::= { lcsStatusTcpIpDhcpNetworkListEntry 7 }

-- {COLUMN} 1.3.6.1.4.1.2356.11.1.9.6.20.1.8
lcsStatusTcpIpDhcpNetworkListEntryDnsBackup OBJECT-TYPE
    SYNTAX     IpAddress
    MAX-ACCESS read-only
    STATUS     current
    DESCRIPTION
            ""
    ::= { lcsStatusTcpIpDhcpNetworkListEntry 8 }

-- {COLUMN} 1.3.6.1.4.1.2356.11.1.9.6.20.1.9
lcsStatusTcpIpDhcpNetworkListEntryNbnsDefault OBJECT-TYPE
    SYNTAX     IpAddress
    MAX-ACCESS read-only
    STATUS     current
    DESCRIPTION
            ""
    ::= { lcsStatusTcpIpDhcpNetworkListEntry 9 }

-- {COLUMN} 1.3.6.1.4.1.2356.11.1.9.6.20.1.10
lcsStatusTcpIpDhcpNetworkListEntryNbnsBackup OBJECT-TYPE
    SYNTAX     IpAddress
    MAX-ACCESS read-only
    STATUS     current
    DESCRIPTION
            ""
    ::= { lcsStatusTcpIpDhcpNetworkListEntry 10 }

-- {COLUMN} 1.3.6.1.4.1.2356.11.1.9.6.20.1.11
lcsStatusTcpIpDhcpNetworkListEntryServerFlags OBJECT-TYPE
    SYNTAX     DisplayString (SIZE(0..255))
    MAX-ACCESS read-only
    STATUS     current
    DESCRIPTION
            ""
    ::= { lcsStatusTcpIpDhcpNetworkListEntry 11 }

-- {COLUMN} 1.3.6.1.4.1.2356.11.1.9.6.20.1.13
lcsStatusTcpIpDhcpNetworkListEntryBroadcastBit OBJECT-TYPE
    SYNTAX     INTEGER {
                  eNo (0),
                  eYes (1)
            }
    MAX-ACCESS read-only
    STATUS     current
    DESCRIPTION
            ""
    ::= { lcsStatusTcpIpDhcpNetworkListEntry 13 }

-- {COLUMN} 1.3.6.1.4.1.2356.11.1.9.6.20.1.14
lcsStatusTcpIpDhcpNetworkListEntryServerId OBJECT-TYPE
    SYNTAX     IpAddress
    MAX-ACCESS read-only
    STATUS     current
    DESCRIPTION
            ""
    ::= { lcsStatusTcpIpDhcpNetworkListEntry 14 }

-- {COLUMN} 1.3.6.1.4.1.2356.11.1.9.6.20.1.16
lcsStatusTcpIpDhcpNetworkListEntryVlanId OBJECT-TYPE
    SYNTAX     Integer32 (0..65535)
    MAX-ACCESS read-only
    STATUS     current
    DESCRIPTION
            ""
    ::= { lcsStatusTcpIpDhcpNetworkListEntry 16 }

-- {COLUMN} 1.3.6.1.4.1.2356.11.1.9.6.20.1.17
lcsStatusTcpIpDhcpNetworkListEntryMasterServer OBJECT-TYPE
    SYNTAX     IpAddress
    MAX-ACCESS read-only
    STATUS     current
    DESCRIPTION
            ""
    ::= { lcsStatusTcpIpDhcpNetworkListEntry 17 }

-- {COLUMN} 1.3.6.1.4.1.2356.11.1.9.6.20.1.18
lcsStatusTcpIpDhcpNetworkListEntryCache OBJECT-TYPE
    SYNTAX     INTEGER {
                  eNo (0),
                  eYes (1)
            }
    MAX-ACCESS read-only
    STATUS     current
    DESCRIPTION
            ""
    ::= { lcsStatusTcpIpDhcpNetworkListEntry 18 }

-- {COLUMN} 1.3.6.1.4.1.2356.11.1.9.6.20.1.19
lcsStatusTcpIpDhcpNetworkListEntryAdaption OBJECT-TYPE
    SYNTAX     INTEGER {
                  eNo (0),
                  eYes (1)
            }
    MAX-ACCESS read-only
    STATUS     current
    DESCRIPTION
            ""
    ::= { lcsStatusTcpIpDhcpNetworkListEntry 19 }

-- {COLUMN} 1.3.6.1.4.1.2356.11.1.9.6.20.1.20
lcsStatusTcpIpDhcpNetworkListEntryCluster OBJECT-TYPE
    SYNTAX     INTEGER {
                  eNo (0),
                  eYes (1)
            }
    MAX-ACCESS read-only
    STATUS     current
    DESCRIPTION
            ""
    ::= { lcsStatusTcpIpDhcpNetworkListEntry 20 }

-- {COLUMN} 1.3.6.1.4.1.2356.11.1.9.6.20.1.21
lcsStatusTcpIpDhcpNetworkListEntry2ndMasterServer OBJECT-TYPE
    SYNTAX     IpAddress
    MAX-ACCESS read-only
    STATUS     current
    DESCRIPTION
            ""
    ::= { lcsStatusTcpIpDhcpNetworkListEntry 21 }

-- {COLUMN} 1.3.6.1.4.1.2356.11.1.9.6.20.1.22
lcsStatusTcpIpDhcpNetworkListEntry3rdMasterServer OBJECT-TYPE
    SYNTAX     IpAddress
    MAX-ACCESS read-only
    STATUS     current
    DESCRIPTION
            ""
    ::= { lcsStatusTcpIpDhcpNetworkListEntry 22 }

-- {COLUMN} 1.3.6.1.4.1.2356.11.1.9.6.20.1.23
lcsStatusTcpIpDhcpNetworkListEntry4thMasterServer OBJECT-TYPE
    SYNTAX     IpAddress
    MAX-ACCESS read-only
    STATUS     current
    DESCRIPTION
            ""
    ::= { lcsStatusTcpIpDhcpNetworkListEntry 23 }

-- {COLUMN} 1.3.6.1.4.1.2356.11.1.9.6.20.1.24
lcsStatusTcpIpDhcpNetworkListEntryLanIfc OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsStatusTcpIpDhcpNetworkListEntry 24 }

-- {COLUMN} 1.3.6.1.4.1.2356.11.1.9.6.20.1.25
lcsStatusTcpIpDhcpNetworkListEntryMaxLease OBJECT-TYPE
    SYNTAX     Integer32 (0..2147483647)
    MAX-ACCESS read-only
    STATUS     current
    DESCRIPTION
            "-- empty --"
    ::= { lcsStatusTcpIpDhcpNetworkListEntry 25 }

-- {COLUMN} 1.3.6.1.4.1.2356.11.1.9.6.20.1.26
lcsStatusTcpIpDhcpNetworkListEntryDefLease OBJECT-TYPE
    SYNTAX     Integer32 (0..2147483647)
    MAX-ACCESS read-only
    STATUS     current
    DESCRIPTION
            "-- empty --"
    ::= { lcsStatusTcpIpDhcpNetworkListEntry 26 }

-- {COLUMN} 1.3.6.1.4.1.2356.11.1.9.6.20.1.27
lcsStatusTcpIpDhcpNetworkListEntryPoolTotal OBJECT-TYPE
    SYNTAX     Integer32 (0..2147483647)
    MAX-ACCESS read-only
    STATUS     current
    DESCRIPTION
            "-- empty --"
    ::= { lcsStatusTcpIpDhcpNetworkListEntry 27 }

-- {COLUMN} 1.3.6.1.4.1.2356.11.1.9.6.20.1.28
lcsStatusTcpIpDhcpNetworkListEntryPoolReserved OBJECT-TYPE
    SYNTAX     Integer32 (0..2147483647)
    MAX-ACCESS read-only
    STATUS     current
    DESCRIPTION
            "-- empty --"
    ::= { lcsStatusTcpIpDhcpNetworkListEntry 28 }

-- {COLUMN} 1.3.6.1.4.1.2356.11.1.9.6.20.1.29
lcsStatusTcpIpDhcpNetworkListEntryPoolInUse OBJECT-TYPE
    SYNTAX     Integer32 (0..2147483647)
    MAX-ACCESS read-only
    STATUS     current
    DESCRIPTION
            "-- empty --"
    ::= { lcsStatusTcpIpDhcpNetworkListEntry 29 }

-- {COLUMN} 1.3.6.1.4.1.2356.11.1.9.6.20.1.30
lcsStatusTcpIpDhcpNetworkListEntryPoolUnused OBJECT-TYPE
    SYNTAX     Integer32 (0..2147483647)
    MAX-ACCESS read-only
    STATUS     current
    DESCRIPTION
            "-- empty --"
    ::= { lcsStatusTcpIpDhcpNetworkListEntry 30 }

-- {COLUMN} 1.3.6.1.4.1.2356.11.1.9.6.20.1.31
lcsStatusTcpIpDhcpNetworkListEntryLoopbackAddress OBJECT-TYPE
    SYNTAX     DisplayString (SIZE(0..16))
    MAX-ACCESS read-only
    STATUS     current
    DESCRIPTION
            "-- empty --"
    ::= { lcsStatusTcpIpDhcpNetworkListEntry 31 }

-- {COLUMN} 1.3.6.1.4.1.2356.11.1.9.6.20.1.32
lcsStatusTcpIpDhcpNetworkListEntrySuppressArpCheck OBJECT-TYPE
    SYNTAX     INTEGER {
                  eNo (0),
                  eYes (1)
            }
    MAX-ACCESS read-only
    STATUS     current
    DESCRIPTION
            "-- empty --"
    ::= { lcsStatusTcpIpDhcpNetworkListEntry 32 }

-- {SCALAR} 1.3.6.1.4.1.2356.11.1.9.7
lcsStatusTcpIpDeleteValues OBJECT-TYPE
    SYNTAX     DisplayString
    MAX-ACCESS read-write
    STATUS     current
    DESCRIPTION
            ""
    ::= { lcsStatusTcpIp 7 }

-- {NODE} 1.3.6.1.4.1.2356.11.1.9.8
lcsStatusTcpIpNetbios OBJECT IDENTIFIER ::= { lcsStatusTcpIp 8 }

-- {SCALAR} 1.3.6.1.4.1.2356.11.1.9.8.1
lcsStatusTcpIpNetbiosLanRx OBJECT-TYPE
    SYNTAX     Counter32
    MAX-ACCESS read-only
    STATUS     current
    DESCRIPTION
            ""
    ::= { lcsStatusTcpIpNetbios 1 }

-- {SCALAR} 1.3.6.1.4.1.2356.11.1.9.8.2
lcsStatusTcpIpNetbiosLanTx OBJECT-TYPE
    SYNTAX     Counter32
    MAX-ACCESS read-only
    STATUS     current
    DESCRIPTION
            ""
    ::= { lcsStatusTcpIpNetbios 2 }

-- {SCALAR} 1.3.6.1.4.1.2356.11.1.9.8.3
lcsStatusTcpIpNetbiosWanRx OBJECT-TYPE
    SYNTAX     Counter32
    MAX-ACCESS read-only
    STATUS     current
    DESCRIPTION
            ""
    ::= { lcsStatusTcpIpNetbios 3 }

-- {SCALAR} 1.3.6.1.4.1.2356.11.1.9.8.4
lcsStatusTcpIpNetbiosWanTx OBJECT-TYPE
    SYNTAX     Counter32
    MAX-ACCESS read-only
    STATUS     current
    DESCRIPTION
            ""
    ::= { lcsStatusTcpIpNetbios 4 }

-- {SCALAR} 1.3.6.1.4.1.2356.11.1.9.8.5
lcsStatusTcpIpNetbiosRegisters OBJECT-TYPE
    SYNTAX     Counter32
    MAX-ACCESS read-only
    STATUS     current
    DESCRIPTION
            ""
    ::= { lcsStatusTcpIpNetbios 5 }

-- {SCALAR} 1.3.6.1.4.1.2356.11.1.9.8.6
lcsStatusTcpIpNetbiosConflicts OBJECT-TYPE
    SYNTAX     Counter32
    MAX-ACCESS read-only
    STATUS     current
    DESCRIPTION
            ""
    ::= { lcsStatusTcpIpNetbios 6 }

-- {SCALAR} 1.3.6.1.4.1.2356.11.1.9.8.7
lcsStatusTcpIpNetbiosReleases OBJECT-TYPE
    SYNTAX     Counter32
    MAX-ACCESS read-only
    STATUS     current
    DESCRIPTION
            ""
    ::= { lcsStatusTcpIpNetbios 7 }

-- {SCALAR} 1.3.6.1.4.1.2356.11.1.9.8.8
lcsStatusTcpIpNetbiosRefreshs OBJECT-TYPE
    SYNTAX     Counter32
    MAX-ACCESS read-only
    STATUS     current
    DESCRIPTION
            ""
    ::= { lcsStatusTcpIpNetbios 8 }

-- {SCALAR} 1.3.6.1.4.1.2356.11.1.9.8.9
lcsStatusTcpIpNetbiosTimeouts OBJECT-TYPE
    SYNTAX     Counter32
    MAX-ACCESS read-only
    STATUS     current
    DESCRIPTION
            ""
    ::= { lcsStatusTcpIpNetbios 9 }

-- {SCALAR} 1.3.6.1.4.1.2356.11.1.9.8.10
lcsStatusTcpIpNetbiosHosts OBJECT-TYPE
    SYNTAX     Integer32 (0..2147483647)
    MAX-ACCESS read-only
    STATUS     current
    DESCRIPTION
            ""
    ::= { lcsStatusTcpIpNetbios 10 }

-- {SCALAR} 1.3.6.1.4.1.2356.11.1.9.8.11
lcsStatusTcpIpNetbiosGroups OBJECT-TYPE
    SYNTAX     Integer32 (0..2147483647)
    MAX-ACCESS read-only
    STATUS     current
    DESCRIPTION
            ""
    ::= { lcsStatusTcpIpNetbios 11 }

-- {SCALAR} 1.3.6.1.4.1.2356.11.1.9.8.12
lcsStatusTcpIpNetbiosBNodes OBJECT-TYPE
    SYNTAX     Integer32 (0..2147483647)
    MAX-ACCESS read-only
    STATUS     current
    DESCRIPTION
            ""
    ::= { lcsStatusTcpIpNetbios 12 }

-- {SCALAR} 1.3.6.1.4.1.2356.11.1.9.8.13
lcsStatusTcpIpNetbiosPNodes OBJECT-TYPE
    SYNTAX     Integer32 (0..2147483647)
    MAX-ACCESS read-only
    STATUS     current
    DESCRIPTION
            ""
    ::= { lcsStatusTcpIpNetbios 13 }

-- {SCALAR} 1.3.6.1.4.1.2356.11.1.9.8.14
lcsStatusTcpIpNetbiosMNodes OBJECT-TYPE
    SYNTAX     Integer32 (0..2147483647)
    MAX-ACCESS read-only
    STATUS     current
    DESCRIPTION
            ""
    ::= { lcsStatusTcpIpNetbios 14 }

-- {SCALAR} 1.3.6.1.4.1.2356.11.1.9.8.15
lcsStatusTcpIpNetbiosWNodes OBJECT-TYPE
    SYNTAX     Integer32 (0..2147483647)
    MAX-ACCESS read-only
    STATUS     current
    DESCRIPTION
            ""
    ::= { lcsStatusTcpIpNetbios 15 }

-- {TABLE} 1.3.6.1.4.1.2356.11.1.9.8.16
lcsStatusTcpIpNetbiosPeersTable OBJECT-TYPE
    SYNTAX     SEQUENCE OF LcsStatusTcpIpNetbiosPeersEntry
    MAX-ACCESS not-accessible
    STATUS     current
    DESCRIPTION
            ""
    ::= { lcsStatusTcpIpNetbios 16 }

-- {ROW} 1.3.6.1.4.1.2356.11.1.9.8.16.1
lcsStatusTcpIpNetbiosPeersEntry OBJECT-TYPE
    SYNTAX     LcsStatusTcpIpNetbiosPeersEntry
    MAX-ACCESS not-accessible
    STATUS     current
    DESCRIPTION
            ""
    INDEX {
            lcsStatusTcpIpNetbiosPeersEntryName
          }
    ::= { lcsStatusTcpIpNetbiosPeersTable 1 }

LcsStatusTcpIpNetbiosPeersEntry ::= SEQUENCE {
            lcsStatusTcpIpNetbiosPeersEntryName DisplayString,
            lcsStatusTcpIpNetbiosPeersEntryType INTEGER,
            lcsStatusTcpIpNetbiosPeersEntryBackoff Integer32,
            lcsStatusTcpIpNetbiosPeersEntryTime Integer32
    }

-- {COLUMN} 1.3.6.1.4.1.2356.11.1.9.8.16.1.1
lcsStatusTcpIpNetbiosPeersEntryName OBJECT-TYPE
    SYNTAX     DisplayString (SIZE(0..16))
    MAX-ACCESS read-only
    STATUS     current
    DESCRIPTION
            ""
    ::= { lcsStatusTcpIpNetbiosPeersEntry 1 }

-- {COLUMN} 1.3.6.1.4.1.2356.11.1.9.8.16.1.2
lcsStatusTcpIpNetbiosPeersEntryType OBJECT-TYPE
    SYNTAX     INTEGER {
                  eRouter (0),
                  eWorkstation (1)
            }
    MAX-ACCESS read-only
    STATUS     current
    DESCRIPTION
            ""
    ::= { lcsStatusTcpIpNetbiosPeersEntry 2 }

-- {COLUMN} 1.3.6.1.4.1.2356.11.1.9.8.16.1.3
lcsStatusTcpIpNetbiosPeersEntryBackoff OBJECT-TYPE
    SYNTAX     Integer32 (0..255)
    MAX-ACCESS read-only
    STATUS     current
    DESCRIPTION
            ""
    ::= { lcsStatusTcpIpNetbiosPeersEntry 3 }

-- {COLUMN} 1.3.6.1.4.1.2356.11.1.9.8.16.1.4
lcsStatusTcpIpNetbiosPeersEntryTime OBJECT-TYPE
    SYNTAX     Integer32 (0..65535)
    MAX-ACCESS read-only
    STATUS     current
    DESCRIPTION
            ""
    ::= { lcsStatusTcpIpNetbiosPeersEntry 4 }

-- {SCALAR} 1.3.6.1.4.1.2356.11.1.9.8.17
lcsStatusTcpIpNetbiosDeleteValues OBJECT-TYPE
    SYNTAX     DisplayString
    MAX-ACCESS read-write
    STATUS     current
    DESCRIPTION
            ""
    ::= { lcsStatusTcpIpNetbios 17 }

-- {TABLE} 1.3.6.1.4.1.2356.11.1.9.8.18
lcsStatusTcpIpNetbiosNetworksTable OBJECT-TYPE
    SYNTAX     SEQUENCE OF LcsStatusTcpIpNetbiosNetworksEntry
    MAX-ACCESS not-accessible
    STATUS     current
    DESCRIPTION
            ""
    ::= { lcsStatusTcpIpNetbios 18 }

-- {ROW} 1.3.6.1.4.1.2356.11.1.9.8.18.1
lcsStatusTcpIpNetbiosNetworksEntry OBJECT-TYPE
    SYNTAX     LcsStatusTcpIpNetbiosNetworksEntry
    MAX-ACCESS not-accessible
    STATUS     current
    DESCRIPTION
            ""
    INDEX {
            lcsStatusTcpIpNetbiosNetworksEntryNetworkName
          }
    ::= { lcsStatusTcpIpNetbiosNetworksTable 1 }

LcsStatusTcpIpNetbiosNetworksEntry ::= SEQUENCE {
            lcsStatusTcpIpNetbiosNetworksEntryNetworkName DisplayString,
            lcsStatusTcpIpNetbiosNetworksEntryNtDomain DisplayString,
            lcsStatusTcpIpNetbiosNetworksEntryRtgTag Integer32,
            lcsStatusTcpIpNetbiosNetworksEntryVlanId Integer32,
            lcsStatusTcpIpNetbiosNetworksEntryInterface INTEGER
    }

-- {COLUMN} 1.3.6.1.4.1.2356.11.1.9.8.18.1.1
lcsStatusTcpIpNetbiosNetworksEntryNetworkName OBJECT-TYPE
    SYNTAX     DisplayString (SIZE(0..16))
    MAX-ACCESS read-only
    STATUS     current
    DESCRIPTION
            ""
    ::= { lcsStatusTcpIpNetbiosNetworksEntry 1 }

-- {COLUMN} 1.3.6.1.4.1.2356.11.1.9.8.18.1.2
lcsStatusTcpIpNetbiosNetworksEntryNtDomain OBJECT-TYPE
    SYNTAX     DisplayString (SIZE(0..15))
    MAX-ACCESS read-only
    STATUS     current
    DESCRIPTION
            ""
    ::= { lcsStatusTcpIpNetbiosNetworksEntry 2 }

-- {COLUMN} 1.3.6.1.4.1.2356.11.1.9.8.18.1.3
lcsStatusTcpIpNetbiosNetworksEntryRtgTag OBJECT-TYPE
    SYNTAX     Integer32 (0..65535)
    MAX-ACCESS read-only
    STATUS     current
    DESCRIPTION
            ""
    ::= { lcsStatusTcpIpNetbiosNetworksEntry 3 }

-- {COLUMN} 1.3.6.1.4.1.2356.11.1.9.8.18.1.5
lcsStatusTcpIpNetbiosNetworksEntryVlanId OBJECT-TYPE
    SYNTAX     Integer32 (0..65535)
    MAX-ACCESS read-only
    STATUS     current
    DESCRIPTION
            ""
    ::= { lcsStatusTcpIpNetbiosNetworksEntry 5 }

-- {COLUMN} 1.3.6.1.4.1.2356.11.1.9.8.18.1.7
lcsStatusTcpIpNetbiosNetworksEntryInterface OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsStatusTcpIpNetbiosNetworksEntry 7 }

-- {TABLE} 1.3.6.1.4.1.2356.11.1.9.8.19
lcsStatusTcpIpNetbiosGroupListTable OBJECT-TYPE
    SYNTAX     SEQUENCE OF LcsStatusTcpIpNetbiosGroupListEntry
    MAX-ACCESS not-accessible
    STATUS     current
    DESCRIPTION
            ""
    ::= { lcsStatusTcpIpNetbios 19 }

-- {ROW} 1.3.6.1.4.1.2356.11.1.9.8.19.1
lcsStatusTcpIpNetbiosGroupListEntry OBJECT-TYPE
    SYNTAX     LcsStatusTcpIpNetbiosGroupListEntry
    MAX-ACCESS not-accessible
    STATUS     current
    DESCRIPTION
            ""
    INDEX {
            lcsStatusTcpIpNetbiosGroupListEntryGroupDomain,
            lcsStatusTcpIpNetbiosGroupListEntryType,
            lcsStatusTcpIpNetbiosGroupListEntryIpAddress,
            lcsStatusTcpIpNetbiosGroupListEntryRtgTag
          }
    ::= { lcsStatusTcpIpNetbiosGroupListTable 1 }

LcsStatusTcpIpNetbiosGroupListEntry ::= SEQUENCE {
            lcsStatusTcpIpNetbiosGroupListEntryGroupDomain DisplayString,
            lcsStatusTcpIpNetbiosGroupListEntryType DisplayString,
            lcsStatusTcpIpNetbiosGroupListEntryIpAddress IpAddress,
            lcsStatusTcpIpNetbiosGroupListEntryPeer DisplayString,
            lcsStatusTcpIpNetbiosGroupListEntryTimeout Integer32,
            lcsStatusTcpIpNetbiosGroupListEntryFlags DisplayString,
            lcsStatusTcpIpNetbiosGroupListEntryNetworkName DisplayString,
            lcsStatusTcpIpNetbiosGroupListEntryRtgTag Integer32
    }

-- {COLUMN} 1.3.6.1.4.1.2356.11.1.9.8.19.1.1
lcsStatusTcpIpNetbiosGroupListEntryGroupDomain OBJECT-TYPE
    SYNTAX     DisplayString (SIZE(0..15))
    MAX-ACCESS read-only
    STATUS     current
    DESCRIPTION
            ""
    ::= { lcsStatusTcpIpNetbiosGroupListEntry 1 }

-- {COLUMN} 1.3.6.1.4.1.2356.11.1.9.8.19.1.2
lcsStatusTcpIpNetbiosGroupListEntryType OBJECT-TYPE
    SYNTAX     DisplayString (SIZE(0..1))
    MAX-ACCESS read-only
    STATUS     current
    DESCRIPTION
            ""
    ::= { lcsStatusTcpIpNetbiosGroupListEntry 2 }

-- {COLUMN} 1.3.6.1.4.1.2356.11.1.9.8.19.1.3
lcsStatusTcpIpNetbiosGroupListEntryIpAddress OBJECT-TYPE
    SYNTAX     IpAddress
    MAX-ACCESS read-only
    STATUS     current
    DESCRIPTION
            ""
    ::= { lcsStatusTcpIpNetbiosGroupListEntry 3 }

-- {COLUMN} 1.3.6.1.4.1.2356.11.1.9.8.19.1.4
lcsStatusTcpIpNetbiosGroupListEntryPeer OBJECT-TYPE
    SYNTAX     DisplayString (SIZE(0..16))
    MAX-ACCESS read-only
    STATUS     current
    DESCRIPTION
            ""
    ::= { lcsStatusTcpIpNetbiosGroupListEntry 4 }

-- {COLUMN} 1.3.6.1.4.1.2356.11.1.9.8.19.1.5
lcsStatusTcpIpNetbiosGroupListEntryTimeout OBJECT-TYPE
    SYNTAX     Integer32 (0..2147483647)
    MAX-ACCESS read-only
    STATUS     current
    DESCRIPTION
            ""
    ::= { lcsStatusTcpIpNetbiosGroupListEntry 5 }

-- {COLUMN} 1.3.6.1.4.1.2356.11.1.9.8.19.1.6
lcsStatusTcpIpNetbiosGroupListEntryFlags OBJECT-TYPE
    SYNTAX     DisplayString (SIZE(0..2))
    MAX-ACCESS read-only
    STATUS     current
    DESCRIPTION
            ""
    ::= { lcsStatusTcpIpNetbiosGroupListEntry 6 }

-- {COLUMN} 1.3.6.1.4.1.2356.11.1.9.8.19.1.7
lcsStatusTcpIpNetbiosGroupListEntryNetworkName OBJECT-TYPE
    SYNTAX     DisplayString (SIZE(0..16))
    MAX-ACCESS read-only
    STATUS     current
    DESCRIPTION
            ""
    ::= { lcsStatusTcpIpNetbiosGroupListEntry 7 }

-- {COLUMN} 1.3.6.1.4.1.2356.11.1.9.8.19.1.8
lcsStatusTcpIpNetbiosGroupListEntryRtgTag OBJECT-TYPE
    SYNTAX     Integer32 (0..65535)
    MAX-ACCESS read-only
    STATUS     current
    DESCRIPTION
            ""
    ::= { lcsStatusTcpIpNetbiosGroupListEntry 8 }

-- {TABLE} 1.3.6.1.4.1.2356.11.1.9.8.20
lcsStatusTcpIpNetbiosHostListTable OBJECT-TYPE
    SYNTAX     SEQUENCE OF LcsStatusTcpIpNetbiosHostListEntry
    MAX-ACCESS not-accessible
    STATUS     current
    DESCRIPTION
            ""
    ::= { lcsStatusTcpIpNetbios 20 }

-- {ROW} 1.3.6.1.4.1.2356.11.1.9.8.20.1
lcsStatusTcpIpNetbiosHostListEntry OBJECT-TYPE
    SYNTAX     LcsStatusTcpIpNetbiosHostListEntry
    MAX-ACCESS not-accessible
    STATUS     current
    DESCRIPTION
            ""
    INDEX {
            lcsStatusTcpIpNetbiosHostListEntryName,
            lcsStatusTcpIpNetbiosHostListEntryType,
            lcsStatusTcpIpNetbiosHostListEntryIpAddress,
            lcsStatusTcpIpNetbiosHostListEntryRtgTag
          }
    ::= { lcsStatusTcpIpNetbiosHostListTable 1 }

LcsStatusTcpIpNetbiosHostListEntry ::= SEQUENCE {
            lcsStatusTcpIpNetbiosHostListEntryName DisplayString,
            lcsStatusTcpIpNetbiosHostListEntryType DisplayString,
            lcsStatusTcpIpNetbiosHostListEntryIpAddress IpAddress,
            lcsStatusTcpIpNetbiosHostListEntryPeer DisplayString,
            lcsStatusTcpIpNetbiosHostListEntryTimeout Integer32,
            lcsStatusTcpIpNetbiosHostListEntryFlags DisplayString,
            lcsStatusTcpIpNetbiosHostListEntryNetworkName DisplayString,
            lcsStatusTcpIpNetbiosHostListEntryRtgTag Integer32
    }

-- {COLUMN} 1.3.6.1.4.1.2356.11.1.9.8.20.1.1
lcsStatusTcpIpNetbiosHostListEntryName OBJECT-TYPE
    SYNTAX     DisplayString (SIZE(0..15))
    MAX-ACCESS read-only
    STATUS     current
    DESCRIPTION
            ""
    ::= { lcsStatusTcpIpNetbiosHostListEntry 1 }

-- {COLUMN} 1.3.6.1.4.1.2356.11.1.9.8.20.1.2
lcsStatusTcpIpNetbiosHostListEntryType OBJECT-TYPE
    SYNTAX     DisplayString (SIZE(0..1))
    MAX-ACCESS read-only
    STATUS     current
    DESCRIPTION
            ""
    ::= { lcsStatusTcpIpNetbiosHostListEntry 2 }

-- {COLUMN} 1.3.6.1.4.1.2356.11.1.9.8.20.1.3
lcsStatusTcpIpNetbiosHostListEntryIpAddress OBJECT-TYPE
    SYNTAX     IpAddress
    MAX-ACCESS read-only
    STATUS     current
    DESCRIPTION
            ""
    ::= { lcsStatusTcpIpNetbiosHostListEntry 3 }

-- {COLUMN} 1.3.6.1.4.1.2356.11.1.9.8.20.1.4
lcsStatusTcpIpNetbiosHostListEntryPeer OBJECT-TYPE
    SYNTAX     DisplayString (SIZE(0..16))
    MAX-ACCESS read-only
    STATUS     current
    DESCRIPTION
            ""
    ::= { lcsStatusTcpIpNetbiosHostListEntry 4 }

-- {COLUMN} 1.3.6.1.4.1.2356.11.1.9.8.20.1.5
lcsStatusTcpIpNetbiosHostListEntryTimeout OBJECT-TYPE
    SYNTAX     Integer32 (0..2147483647)
    MAX-ACCESS read-only
    STATUS     current
    DESCRIPTION
            ""
    ::= { lcsStatusTcpIpNetbiosHostListEntry 5 }

-- {COLUMN} 1.3.6.1.4.1.2356.11.1.9.8.20.1.6
lcsStatusTcpIpNetbiosHostListEntryFlags OBJECT-TYPE
    SYNTAX     DisplayString (SIZE(0..2))
    MAX-ACCESS read-only
    STATUS     current
    DESCRIPTION
            ""
    ::= { lcsStatusTcpIpNetbiosHostListEntry 6 }

-- {COLUMN} 1.3.6.1.4.1.2356.11.1.9.8.20.1.7
lcsStatusTcpIpNetbiosHostListEntryNetworkName OBJECT-TYPE
    SYNTAX     DisplayString (SIZE(0..16))
    MAX-ACCESS read-only
    STATUS     current
    DESCRIPTION
            ""
    ::= { lcsStatusTcpIpNetbiosHostListEntry 7 }

-- {COLUMN} 1.3.6.1.4.1.2356.11.1.9.8.20.1.8
lcsStatusTcpIpNetbiosHostListEntryRtgTag OBJECT-TYPE
    SYNTAX     Integer32 (0..65535)
    MAX-ACCESS read-only
    STATUS     current
    DESCRIPTION
            ""
    ::= { lcsStatusTcpIpNetbiosHostListEntry 8 }

-- {TABLE} 1.3.6.1.4.1.2356.11.1.9.8.21
lcsStatusTcpIpNetbiosServerListTable OBJECT-TYPE
    SYNTAX     SEQUENCE OF LcsStatusTcpIpNetbiosServerListEntry
    MAX-ACCESS not-accessible
    STATUS     current
    DESCRIPTION
            ""
    ::= { lcsStatusTcpIpNetbios 21 }

-- {ROW} 1.3.6.1.4.1.2356.11.1.9.8.21.1
lcsStatusTcpIpNetbiosServerListEntry OBJECT-TYPE
    SYNTAX     LcsStatusTcpIpNetbiosServerListEntry
    MAX-ACCESS not-accessible
    STATUS     current
    DESCRIPTION
            ""
    INDEX {
            lcsStatusTcpIpNetbiosServerListEntryHost,
            lcsStatusTcpIpNetbiosServerListEntryGroupDomain,
            lcsStatusTcpIpNetbiosServerListEntryIpAddress,
            lcsStatusTcpIpNetbiosServerListEntryRtgTag
          }
    ::= { lcsStatusTcpIpNetbiosServerListTable 1 }

LcsStatusTcpIpNetbiosServerListEntry ::= SEQUENCE {
            lcsStatusTcpIpNetbiosServerListEntryHost DisplayString,
            lcsStatusTcpIpNetbiosServerListEntryGroupDomain DisplayString,
            lcsStatusTcpIpNetbiosServerListEntryIpAddress DisplayString,
            lcsStatusTcpIpNetbiosServerListEntryOsVer DisplayString,
            lcsStatusTcpIpNetbiosServerListEntrySmbVer DisplayString,
            lcsStatusTcpIpNetbiosServerListEntryServerTyp DisplayString,
            lcsStatusTcpIpNetbiosServerListEntryPeer DisplayString,
            lcsStatusTcpIpNetbiosServerListEntryTimeout Integer32,
            lcsStatusTcpIpNetbiosServerListEntryFlags DisplayString,
            lcsStatusTcpIpNetbiosServerListEntryNetworkName DisplayString,
            lcsStatusTcpIpNetbiosServerListEntryRtgTag Integer32
    }

-- {COLUMN} 1.3.6.1.4.1.2356.11.1.9.8.21.1.1
lcsStatusTcpIpNetbiosServerListEntryHost OBJECT-TYPE
    SYNTAX     DisplayString (SIZE(0..15))
    MAX-ACCESS read-only
    STATUS     current
    DESCRIPTION
            ""
    ::= { lcsStatusTcpIpNetbiosServerListEntry 1 }

-- {COLUMN} 1.3.6.1.4.1.2356.11.1.9.8.21.1.2
lcsStatusTcpIpNetbiosServerListEntryGroupDomain OBJECT-TYPE
    SYNTAX     DisplayString (SIZE(0..16))
    MAX-ACCESS read-only
    STATUS     current
    DESCRIPTION
            ""
    ::= { lcsStatusTcpIpNetbiosServerListEntry 2 }

-- {COLUMN} 1.3.6.1.4.1.2356.11.1.9.8.21.1.4
lcsStatusTcpIpNetbiosServerListEntryIpAddress OBJECT-TYPE
    SYNTAX     DisplayString (SIZE(0..15))
    MAX-ACCESS read-only
    STATUS     current
    DESCRIPTION
            ""
    ::= { lcsStatusTcpIpNetbiosServerListEntry 4 }

-- {COLUMN} 1.3.6.1.4.1.2356.11.1.9.8.21.1.5
lcsStatusTcpIpNetbiosServerListEntryOsVer OBJECT-TYPE
    SYNTAX     DisplayString (SIZE(0..2))
    MAX-ACCESS read-only
    STATUS     current
    DESCRIPTION
            ""
    ::= { lcsStatusTcpIpNetbiosServerListEntry 5 }

-- {COLUMN} 1.3.6.1.4.1.2356.11.1.9.8.21.1.6
lcsStatusTcpIpNetbiosServerListEntrySmbVer OBJECT-TYPE
    SYNTAX     DisplayString (SIZE(0..2))
    MAX-ACCESS read-only
    STATUS     current
    DESCRIPTION
            ""
    ::= { lcsStatusTcpIpNetbiosServerListEntry 6 }

-- {COLUMN} 1.3.6.1.4.1.2356.11.1.9.8.21.1.7
lcsStatusTcpIpNetbiosServerListEntryServerTyp OBJECT-TYPE
    SYNTAX     DisplayString (SIZE(0..4))
    MAX-ACCESS read-only
    STATUS     current
    DESCRIPTION
            ""
    ::= { lcsStatusTcpIpNetbiosServerListEntry 7 }

-- {COLUMN} 1.3.6.1.4.1.2356.11.1.9.8.21.1.8
lcsStatusTcpIpNetbiosServerListEntryPeer OBJECT-TYPE
    SYNTAX     DisplayString (SIZE(0..16))
    MAX-ACCESS read-only
    STATUS     current
    DESCRIPTION
            ""
    ::= { lcsStatusTcpIpNetbiosServerListEntry 8 }

-- {COLUMN} 1.3.6.1.4.1.2356.11.1.9.8.21.1.9
lcsStatusTcpIpNetbiosServerListEntryTimeout OBJECT-TYPE
    SYNTAX     Integer32 (0..2147483647)
    MAX-ACCESS read-only
    STATUS     current
    DESCRIPTION
            ""
    ::= { lcsStatusTcpIpNetbiosServerListEntry 9 }

-- {COLUMN} 1.3.6.1.4.1.2356.11.1.9.8.21.1.10
lcsStatusTcpIpNetbiosServerListEntryFlags OBJECT-TYPE
    SYNTAX     DisplayString (SIZE(0..2))
    MAX-ACCESS read-only
    STATUS     current
    DESCRIPTION
            ""
    ::= { lcsStatusTcpIpNetbiosServerListEntry 10 }

-- {COLUMN} 1.3.6.1.4.1.2356.11.1.9.8.21.1.11
lcsStatusTcpIpNetbiosServerListEntryNetworkName OBJECT-TYPE
    SYNTAX     DisplayString (SIZE(0..16))
    MAX-ACCESS read-only
    STATUS     current
    DESCRIPTION
            ""
    ::= { lcsStatusTcpIpNetbiosServerListEntry 11 }

-- {COLUMN} 1.3.6.1.4.1.2356.11.1.9.8.21.1.12
lcsStatusTcpIpNetbiosServerListEntryRtgTag OBJECT-TYPE
    SYNTAX     Integer32 (0..65535)
    MAX-ACCESS read-only
    STATUS     current
    DESCRIPTION
            ""
    ::= { lcsStatusTcpIpNetbiosServerListEntry 12 }

-- {TABLE} 1.3.6.1.4.1.2356.11.1.9.8.22
lcsStatusTcpIpNetbiosBrowserListTable OBJECT-TYPE
    SYNTAX     SEQUENCE OF LcsStatusTcpIpNetbiosBrowserListEntry
    MAX-ACCESS not-accessible
    STATUS     current
    DESCRIPTION
            ""
    ::= { lcsStatusTcpIpNetbios 22 }

-- {ROW} 1.3.6.1.4.1.2356.11.1.9.8.22.1
lcsStatusTcpIpNetbiosBrowserListEntry OBJECT-TYPE
    SYNTAX     LcsStatusTcpIpNetbiosBrowserListEntry
    MAX-ACCESS not-accessible
    STATUS     current
    DESCRIPTION
            ""
    INDEX {
            lcsStatusTcpIpNetbiosBrowserListEntryBrowser,
            lcsStatusTcpIpNetbiosBrowserListEntryGroupDomain,
            lcsStatusTcpIpNetbiosBrowserListEntryIpAddress,
            lcsStatusTcpIpNetbiosBrowserListEntryRtgTag
          }
    ::= { lcsStatusTcpIpNetbiosBrowserListTable 1 }

LcsStatusTcpIpNetbiosBrowserListEntry ::= SEQUENCE {
            lcsStatusTcpIpNetbiosBrowserListEntryBrowser DisplayString,
            lcsStatusTcpIpNetbiosBrowserListEntryGroupDomain DisplayString,
            lcsStatusTcpIpNetbiosBrowserListEntryIpAddress DisplayString,
            lcsStatusTcpIpNetbiosBrowserListEntryOsVer DisplayString,
            lcsStatusTcpIpNetbiosBrowserListEntryServerTyp DisplayString,
            lcsStatusTcpIpNetbiosBrowserListEntryPeer DisplayString,
            lcsStatusTcpIpNetbiosBrowserListEntryTimeout Integer32,
            lcsStatusTcpIpNetbiosBrowserListEntryFlags DisplayString,
            lcsStatusTcpIpNetbiosBrowserListEntryNetworkName DisplayString,
            lcsStatusTcpIpNetbiosBrowserListEntryRtgTag Integer32
    }

-- {COLUMN} 1.3.6.1.4.1.2356.11.1.9.8.22.1.1
lcsStatusTcpIpNetbiosBrowserListEntryBrowser OBJECT-TYPE
    SYNTAX     DisplayString (SIZE(0..15))
    MAX-ACCESS read-only
    STATUS     current
    DESCRIPTION
            ""
    ::= { lcsStatusTcpIpNetbiosBrowserListEntry 1 }

-- {COLUMN} 1.3.6.1.4.1.2356.11.1.9.8.22.1.2
lcsStatusTcpIpNetbiosBrowserListEntryGroupDomain OBJECT-TYPE
    SYNTAX     DisplayString (SIZE(0..16))
    MAX-ACCESS read-only
    STATUS     current
    DESCRIPTION
            ""
    ::= { lcsStatusTcpIpNetbiosBrowserListEntry 2 }

-- {COLUMN} 1.3.6.1.4.1.2356.11.1.9.8.22.1.4
lcsStatusTcpIpNetbiosBrowserListEntryIpAddress OBJECT-TYPE
    SYNTAX     DisplayString (SIZE(0..15))
    MAX-ACCESS read-only
    STATUS     current
    DESCRIPTION
            ""
    ::= { lcsStatusTcpIpNetbiosBrowserListEntry 4 }

-- {COLUMN} 1.3.6.1.4.1.2356.11.1.9.8.22.1.5
lcsStatusTcpIpNetbiosBrowserListEntryOsVer OBJECT-TYPE
    SYNTAX     DisplayString (SIZE(0..2))
    MAX-ACCESS read-only
    STATUS     current
    DESCRIPTION
            ""
    ::= { lcsStatusTcpIpNetbiosBrowserListEntry 5 }

-- {COLUMN} 1.3.6.1.4.1.2356.11.1.9.8.22.1.7
lcsStatusTcpIpNetbiosBrowserListEntryServerTyp OBJECT-TYPE
    SYNTAX     DisplayString (SIZE(0..4))
    MAX-ACCESS read-only
    STATUS     current
    DESCRIPTION
            ""
    ::= { lcsStatusTcpIpNetbiosBrowserListEntry 7 }

-- {COLUMN} 1.3.6.1.4.1.2356.11.1.9.8.22.1.8
lcsStatusTcpIpNetbiosBrowserListEntryPeer OBJECT-TYPE
    SYNTAX     DisplayString (SIZE(0..16))
    MAX-ACCESS read-only
    STATUS     current
    DESCRIPTION
            ""
    ::= { lcsStatusTcpIpNetbiosBrowserListEntry 8 }

-- {COLUMN} 1.3.6.1.4.1.2356.11.1.9.8.22.1.9
lcsStatusTcpIpNetbiosBrowserListEntryTimeout OBJECT-TYPE
    SYNTAX     Integer32 (0..2147483647)
    MAX-ACCESS read-only
    STATUS     current
    DESCRIPTION
            ""
    ::= { lcsStatusTcpIpNetbiosBrowserListEntry 9 }

-- {COLUMN} 1.3.6.1.4.1.2356.11.1.9.8.22.1.10
lcsStatusTcpIpNetbiosBrowserListEntryFlags OBJECT-TYPE
    SYNTAX     DisplayString (SIZE(0..2))
    MAX-ACCESS read-only
    STATUS     current
    DESCRIPTION
            ""
    ::= { lcsStatusTcpIpNetbiosBrowserListEntry 10 }

-- {COLUMN} 1.3.6.1.4.1.2356.11.1.9.8.22.1.11
lcsStatusTcpIpNetbiosBrowserListEntryNetworkName OBJECT-TYPE
    SYNTAX     DisplayString (SIZE(0..16))
    MAX-ACCESS read-only
    STATUS     current
    DESCRIPTION
            ""
    ::= { lcsStatusTcpIpNetbiosBrowserListEntry 11 }

-- {COLUMN} 1.3.6.1.4.1.2356.11.1.9.8.22.1.12
lcsStatusTcpIpNetbiosBrowserListEntryRtgTag OBJECT-TYPE
    SYNTAX     Integer32 (0..65535)
    MAX-ACCESS read-only
    STATUS     current
    DESCRIPTION
            ""
    ::= { lcsStatusTcpIpNetbiosBrowserListEntry 12 }

-- {NODE} 1.3.6.1.4.1.2356.11.1.9.9
lcsStatusTcpIpDns OBJECT IDENTIFIER ::= { lcsStatusTcpIp 9 }

-- {SCALAR} 1.3.6.1.4.1.2356.11.1.9.9.1
lcsStatusTcpIpDnsLanRx OBJECT-TYPE
    SYNTAX     Counter32
    MAX-ACCESS read-only
    STATUS     current
    DESCRIPTION
            ""
    ::= { lcsStatusTcpIpDns 1 }

-- {SCALAR} 1.3.6.1.4.1.2356.11.1.9.9.2
lcsStatusTcpIpDnsLanTx OBJECT-TYPE
    SYNTAX     Counter32
    MAX-ACCESS read-only
    STATUS     current
    DESCRIPTION
            ""
    ::= { lcsStatusTcpIpDns 2 }

-- {SCALAR} 1.3.6.1.4.1.2356.11.1.9.9.3
lcsStatusTcpIpDnsWanRx OBJECT-TYPE
    SYNTAX     Counter32
    MAX-ACCESS read-only
    STATUS     current
    DESCRIPTION
            ""
    ::= { lcsStatusTcpIpDns 3 }

-- {SCALAR} 1.3.6.1.4.1.2356.11.1.9.9.4
lcsStatusTcpIpDnsWanTx OBJECT-TYPE
    SYNTAX     Counter32
    MAX-ACCESS read-only
    STATUS     current
    DESCRIPTION
            ""
    ::= { lcsStatusTcpIpDns 4 }

-- {SCALAR} 1.3.6.1.4.1.2356.11.1.9.9.5
lcsStatusTcpIpDnsForwarded OBJECT-TYPE
    SYNTAX     Counter32
    MAX-ACCESS read-only
    STATUS     current
    DESCRIPTION
            ""
    ::= { lcsStatusTcpIpDns 5 }

-- {SCALAR} 1.3.6.1.4.1.2356.11.1.9.9.6
lcsStatusTcpIpDnsErrors OBJECT-TYPE
    SYNTAX     Counter32
    MAX-ACCESS read-only
    STATUS     current
    DESCRIPTION
            ""
    ::= { lcsStatusTcpIpDns 6 }

-- {SCALAR} 1.3.6.1.4.1.2356.11.1.9.9.7
lcsStatusTcpIpDnsDnsAccess OBJECT-TYPE
    SYNTAX     Counter32
    MAX-ACCESS read-only
    STATUS     current
    DESCRIPTION
            ""
    ::= { lcsStatusTcpIpDns 7 }

-- {SCALAR} 1.3.6.1.4.1.2356.11.1.9.9.8
lcsStatusTcpIpDnsDhcpAccess OBJECT-TYPE
    SYNTAX     Counter32
    MAX-ACCESS read-only
    STATUS     current
    DESCRIPTION
            ""
    ::= { lcsStatusTcpIpDns 8 }

-- {SCALAR} 1.3.6.1.4.1.2356.11.1.9.9.9
lcsStatusTcpIpDnsNetbiosAccess OBJECT-TYPE
    SYNTAX     Counter32
    MAX-ACCESS read-only
    STATUS     current
    DESCRIPTION
            ""
    ::= { lcsStatusTcpIpDns 9 }

-- {SCALAR} 1.3.6.1.4.1.2356.11.1.9.9.10
lcsStatusTcpIpDnsFilter OBJECT-TYPE
    SYNTAX     Counter32
    MAX-ACCESS read-only
    STATUS     current
    DESCRIPTION
            ""
    ::= { lcsStatusTcpIpDns 10 }

-- {TABLE} 1.3.6.1.4.1.2356.11.1.9.9.11
lcsStatusTcpIpDnsHitListTable OBJECT-TYPE
    SYNTAX     SEQUENCE OF LcsStatusTcpIpDnsHitListEntry
    MAX-ACCESS not-accessible
    STATUS     current
    DESCRIPTION
            ""
    ::= { lcsStatusTcpIpDns 11 }

-- {ROW} 1.3.6.1.4.1.2356.11.1.9.9.11.1
lcsStatusTcpIpDnsHitListEntry OBJECT-TYPE
    SYNTAX     LcsStatusTcpIpDnsHitListEntry
    MAX-ACCESS not-accessible
    STATUS     current
    DESCRIPTION
            ""
    INDEX {
            lcsStatusTcpIpDnsHitListEntryDomain
          }
    ::= { lcsStatusTcpIpDnsHitListTable 1 }

LcsStatusTcpIpDnsHitListEntry ::= SEQUENCE {
            lcsStatusTcpIpDnsHitListEntryDomain DisplayString,
            lcsStatusTcpIpDnsHitListEntryRequests Integer32,
            lcsStatusTcpIpDnsHitListEntryTime DisplayString,
            lcsStatusTcpIpDnsHitListEntryIpAddress IpAddress,
            lcsStatusTcpIpDnsHitListEntryIpv6Address DisplayString
    }

-- {COLUMN} 1.3.6.1.4.1.2356.11.1.9.9.11.1.1
lcsStatusTcpIpDnsHitListEntryDomain OBJECT-TYPE
    SYNTAX     DisplayString (SIZE(0..64))
    MAX-ACCESS read-only
    STATUS     current
    DESCRIPTION
            ""
    ::= { lcsStatusTcpIpDnsHitListEntry 1 }

-- {COLUMN} 1.3.6.1.4.1.2356.11.1.9.9.11.1.2
lcsStatusTcpIpDnsHitListEntryRequests OBJECT-TYPE
    SYNTAX     Integer32 (0..2147483647)
    MAX-ACCESS read-only
    STATUS     current
    DESCRIPTION
            ""
    ::= { lcsStatusTcpIpDnsHitListEntry 2 }

-- {COLUMN} 1.3.6.1.4.1.2356.11.1.9.9.11.1.3
lcsStatusTcpIpDnsHitListEntryTime OBJECT-TYPE
    SYNTAX     DisplayString (SIZE(0..20))
    MAX-ACCESS read-only
    STATUS     current
    DESCRIPTION
            ""
    ::= { lcsStatusTcpIpDnsHitListEntry 3 }

-- {COLUMN} 1.3.6.1.4.1.2356.11.1.9.9.11.1.4
lcsStatusTcpIpDnsHitListEntryIpAddress OBJECT-TYPE
    SYNTAX     IpAddress
    MAX-ACCESS read-only
    STATUS     current
    DESCRIPTION
            ""
    ::= { lcsStatusTcpIpDnsHitListEntry 4 }

-- {COLUMN} 1.3.6.1.4.1.2356.11.1.9.9.11.1.5
lcsStatusTcpIpDnsHitListEntryIpv6Address OBJECT-TYPE
    SYNTAX     DisplayString (SIZE(0..255))
    MAX-ACCESS read-only
    STATUS     current
    DESCRIPTION
            "-- empty --"
    ::= { lcsStatusTcpIpDnsHitListEntry 5 }

-- {SCALAR} 1.3.6.1.4.1.2356.11.1.9.9.12
lcsStatusTcpIpDnsDeleteValues OBJECT-TYPE
    SYNTAX     DisplayString
    MAX-ACCESS read-write
    STATUS     current
    DESCRIPTION
            ""
    ::= { lcsStatusTcpIpDns 12 }

-- {TABLE} 1.3.6.1.4.1.2356.11.1.9.9.13
lcsStatusTcpIpDnsDynamicDestinationsTable OBJECT-TYPE
    SYNTAX     SEQUENCE OF LcsStatusTcpIpDnsDynamicDestinationsEntry
    MAX-ACCESS not-accessible
    STATUS     current
    DESCRIPTION
            "-- empty --"
    ::= { lcsStatusTcpIpDns 13 }

-- {ROW} 1.3.6.1.4.1.2356.11.1.9.9.13.1
lcsStatusTcpIpDnsDynamicDestinationsEntry OBJECT-TYPE
    SYNTAX     LcsStatusTcpIpDnsDynamicDestinationsEntry
    MAX-ACCESS not-accessible
    STATUS     current
    DESCRIPTION
            ""
    INDEX {
            lcsStatusTcpIpDnsDynamicDestinationsEntryDomainName,
            lcsStatusTcpIpDnsDynamicDestinationsEntryRtgTag
          }
    ::= { lcsStatusTcpIpDnsDynamicDestinationsTable 1 }

LcsStatusTcpIpDnsDynamicDestinationsEntry ::= SEQUENCE {
            lcsStatusTcpIpDnsDynamicDestinationsEntryDomainName OCTET STRING,
            lcsStatusTcpIpDnsDynamicDestinationsEntryRtgTag Unsigned32,
            lcsStatusTcpIpDnsDynamicDestinationsEntryDestination OCTET STRING
    }

-- {COLUMN} 1.3.6.1.4.1.2356.11.1.9.9.13.1.1
lcsStatusTcpIpDnsDynamicDestinationsEntryDomainName OBJECT-TYPE
    SYNTAX     OCTET STRING (SIZE(0..65))
    MAX-ACCESS read-only
    STATUS     current
    DESCRIPTION
            "-- empty --"
    ::= { lcsStatusTcpIpDnsDynamicDestinationsEntry 1 }

-- {COLUMN} 1.3.6.1.4.1.2356.11.1.9.9.13.1.2
lcsStatusTcpIpDnsDynamicDestinationsEntryRtgTag OBJECT-TYPE
    SYNTAX     Unsigned32 (0..65535)
    MAX-ACCESS read-only
    STATUS     current
    DESCRIPTION
            "-- empty --"
    ::= { lcsStatusTcpIpDnsDynamicDestinationsEntry 2 }

-- {COLUMN} 1.3.6.1.4.1.2356.11.1.9.9.13.1.3
lcsStatusTcpIpDnsDynamicDestinationsEntryDestination OBJECT-TYPE
    SYNTAX     OCTET STRING (SIZE(0..17))
    MAX-ACCESS read-only
    STATUS     current
    DESCRIPTION
            "-- empty --"
    ::= { lcsStatusTcpIpDnsDynamicDestinationsEntry 3 }

-- {NODE} 1.3.6.1.4.1.2356.11.1.9.10
lcsStatusTcpIpHttp OBJECT IDENTIFIER ::= { lcsStatusTcpIp 10 }

-- {SCALAR} 1.3.6.1.4.1.2356.11.1.9.10.1
lcsStatusTcpIpHttpHttpAccesses OBJECT-TYPE
    SYNTAX     Counter32
    MAX-ACCESS read-only
    STATUS     current
    DESCRIPTION
            ""
    ::= { lcsStatusTcpIpHttp 1 }

-- {SCALAR} 1.3.6.1.4.1.2356.11.1.9.10.2
lcsStatusTcpIpHttpHttpNotfoundErrors OBJECT-TYPE
    SYNTAX     Counter32
    MAX-ACCESS read-only
    STATUS     current
    DESCRIPTION
            ""
    ::= { lcsStatusTcpIpHttp 2 }

-- {SCALAR} 1.3.6.1.4.1.2356.11.1.9.10.3
lcsStatusTcpIpHttpHttpAuthenticationErrors OBJECT-TYPE
    SYNTAX     Counter32
    MAX-ACCESS read-only
    STATUS     current
    DESCRIPTION
            ""
    ::= { lcsStatusTcpIpHttp 3 }

-- {SCALAR} 1.3.6.1.4.1.2356.11.1.9.10.4
lcsStatusTcpIpHttpHttpProtocolErrors OBJECT-TYPE
    SYNTAX     Counter32
    MAX-ACCESS read-only
    STATUS     current
    DESCRIPTION
            ""
    ::= { lcsStatusTcpIpHttp 4 }

-- {SCALAR} 1.3.6.1.4.1.2356.11.1.9.10.5
lcsStatusTcpIpHttpDeleteValues OBJECT-TYPE
    SYNTAX     DisplayString
    MAX-ACCESS read-write
    STATUS     current
    DESCRIPTION
            ""
    ::= { lcsStatusTcpIpHttp 5 }

-- {SCALAR} 1.3.6.1.4.1.2356.11.1.9.10.6
lcsStatusTcpIpHttpHttpsAccesses OBJECT-TYPE
    SYNTAX     Counter32
    MAX-ACCESS read-only
    STATUS     current
    DESCRIPTION
            ""
    ::= { lcsStatusTcpIpHttp 6 }

-- {TABLE} 1.3.6.1.4.1.2356.11.1.9.10.7
lcsStatusTcpIpHttpAgentListTable OBJECT-TYPE
    SYNTAX     SEQUENCE OF LcsStatusTcpIpHttpAgentListEntry
    MAX-ACCESS not-accessible
    STATUS     current
    DESCRIPTION
            ""
    ::= { lcsStatusTcpIpHttp 7 }

-- {ROW} 1.3.6.1.4.1.2356.11.1.9.10.7.1
lcsStatusTcpIpHttpAgentListEntry OBJECT-TYPE
    SYNTAX     LcsStatusTcpIpHttpAgentListEntry
    MAX-ACCESS not-accessible
    STATUS     current
    DESCRIPTION
            ""
    INDEX {
            lcsStatusTcpIpHttpAgentListEntryAgentName
          }
    ::= { lcsStatusTcpIpHttpAgentListTable 1 }

LcsStatusTcpIpHttpAgentListEntry ::= SEQUENCE {
            lcsStatusTcpIpHttpAgentListEntryAgentName DisplayString,
            lcsStatusTcpIpHttpAgentListEntryAccesses Integer32
    }

-- {COLUMN} 1.3.6.1.4.1.2356.11.1.9.10.7.1.1
lcsStatusTcpIpHttpAgentListEntryAgentName OBJECT-TYPE
    SYNTAX     DisplayString (SIZE(0..67))
    MAX-ACCESS read-only
    STATUS     current
    DESCRIPTION
            ""
    ::= { lcsStatusTcpIpHttpAgentListEntry 1 }

-- {COLUMN} 1.3.6.1.4.1.2356.11.1.9.10.7.1.2
lcsStatusTcpIpHttpAgentListEntryAccesses OBJECT-TYPE
    SYNTAX     Integer32 (0..2147483647)
    MAX-ACCESS read-only
    STATUS     current
    DESCRIPTION
            ""
    ::= { lcsStatusTcpIpHttpAgentListEntry 2 }

-- {TABLE} 1.3.6.1.4.1.2356.11.1.9.10.8
lcsStatusTcpIpHttpActiveTunnelsTable OBJECT-TYPE
    SYNTAX     SEQUENCE OF LcsStatusTcpIpHttpActiveTunnelsEntry
    MAX-ACCESS not-accessible
    STATUS     current
    DESCRIPTION
            ""
    ::= { lcsStatusTcpIpHttp 8 }

-- {ROW} 1.3.6.1.4.1.2356.11.1.9.10.8.1
lcsStatusTcpIpHttpActiveTunnelsEntry OBJECT-TYPE
    SYNTAX     LcsStatusTcpIpHttpActiveTunnelsEntry
    MAX-ACCESS not-accessible
    STATUS     current
    DESCRIPTION
            ""
    INDEX {
            lcsStatusTcpIpHttpActiveTunnelsEntryIndex
          }
    ::= { lcsStatusTcpIpHttpActiveTunnelsTable 1 }

LcsStatusTcpIpHttpActiveTunnelsEntry ::= SEQUENCE {
            lcsStatusTcpIpHttpActiveTunnelsEntryIndex Integer32,
            lcsStatusTcpIpHttpActiveTunnelsEntryRemoteAddress IpAddress,
            lcsStatusTcpIpHttpActiveTunnelsEntryRemotePort Integer32,
            lcsStatusTcpIpHttpActiveTunnelsEntryLocalHost DisplayString,
            lcsStatusTcpIpHttpActiveTunnelsEntryLocalPort Integer32,
            lcsStatusTcpIpHttpActiveTunnelsEntryIdleTime Integer32,
            lcsStatusTcpIpHttpActiveTunnelsEntryLocalRtgTag Integer32,
            lcsStatusTcpIpHttpActiveTunnelsEntryNumConnections Integer32,
            lcsStatusTcpIpHttpActiveTunnelsEntryState INTEGER
    }

-- {COLUMN} 1.3.6.1.4.1.2356.11.1.9.10.8.1.1
lcsStatusTcpIpHttpActiveTunnelsEntryIndex OBJECT-TYPE
    SYNTAX     Integer32 (0..2147483647)
    MAX-ACCESS read-only
    STATUS     current
    DESCRIPTION
            ""
    ::= { lcsStatusTcpIpHttpActiveTunnelsEntry 1 }

-- {COLUMN} 1.3.6.1.4.1.2356.11.1.9.10.8.1.2
lcsStatusTcpIpHttpActiveTunnelsEntryRemoteAddress OBJECT-TYPE
    SYNTAX     IpAddress
    MAX-ACCESS read-only
    STATUS     current
    DESCRIPTION
            ""
    ::= { lcsStatusTcpIpHttpActiveTunnelsEntry 2 }

-- {COLUMN} 1.3.6.1.4.1.2356.11.1.9.10.8.1.3
lcsStatusTcpIpHttpActiveTunnelsEntryRemotePort OBJECT-TYPE
    SYNTAX     Integer32 (0..65535)
    MAX-ACCESS read-only
    STATUS     current
    DESCRIPTION
            ""
    ::= { lcsStatusTcpIpHttpActiveTunnelsEntry 3 }

-- {COLUMN} 1.3.6.1.4.1.2356.11.1.9.10.8.1.4
lcsStatusTcpIpHttpActiveTunnelsEntryLocalHost OBJECT-TYPE
    SYNTAX     DisplayString (SIZE(0..48))
    MAX-ACCESS read-only
    STATUS     current
    DESCRIPTION
            ""
    ::= { lcsStatusTcpIpHttpActiveTunnelsEntry 4 }

-- {COLUMN} 1.3.6.1.4.1.2356.11.1.9.10.8.1.5
lcsStatusTcpIpHttpActiveTunnelsEntryLocalPort OBJECT-TYPE
    SYNTAX     Integer32 (0..65535)
    MAX-ACCESS read-only
    STATUS     current
    DESCRIPTION
            ""
    ::= { lcsStatusTcpIpHttpActiveTunnelsEntry 5 }

-- {COLUMN} 1.3.6.1.4.1.2356.11.1.9.10.8.1.6
lcsStatusTcpIpHttpActiveTunnelsEntryIdleTime OBJECT-TYPE
    SYNTAX     Integer32 (0..2147483647)
    MAX-ACCESS read-only
    STATUS     current
    DESCRIPTION
            ""
    ::= { lcsStatusTcpIpHttpActiveTunnelsEntry 6 }

-- {COLUMN} 1.3.6.1.4.1.2356.11.1.9.10.8.1.7
lcsStatusTcpIpHttpActiveTunnelsEntryLocalRtgTag OBJECT-TYPE
    SYNTAX     Integer32 (0..65535)
    MAX-ACCESS read-only
    STATUS     current
    DESCRIPTION
            ""
    ::= { lcsStatusTcpIpHttpActiveTunnelsEntry 7 }

-- {COLUMN} 1.3.6.1.4.1.2356.11.1.9.10.8.1.8
lcsStatusTcpIpHttpActiveTunnelsEntryNumConnections OBJECT-TYPE
    SYNTAX     Integer32 (0..2147483647)
    MAX-ACCESS read-only
    STATUS     current
    DESCRIPTION
            ""
    ::= { lcsStatusTcpIpHttpActiveTunnelsEntry 8 }

-- {COLUMN} 1.3.6.1.4.1.2356.11.1.9.10.8.1.9
lcsStatusTcpIpHttpActiveTunnelsEntryState OBJECT-TYPE
    SYNTAX     INTEGER {
                  eActive (0),
                  eClosing (1)
            }
    MAX-ACCESS read-only
    STATUS     current
    DESCRIPTION
            ""
    ::= { lcsStatusTcpIpHttpActiveTunnelsEntry 9 }

-- {SCALAR} 1.3.6.1.4.1.2356.11.1.9.10.15
lcsStatusTcpIpHttpMaxHttpJobCount OBJECT-TYPE
    SYNTAX     Integer32 (0..2147483647)
    MAX-ACCESS read-only
    STATUS     current
    DESCRIPTION
            "-- empty --"
    ::= { lcsStatusTcpIpHttp 15 }

-- {SCALAR} 1.3.6.1.4.1.2356.11.1.9.10.16
lcsStatusTcpIpHttpJobCount OBJECT-TYPE
    SYNTAX     Integer32 (0..2147483647)
    MAX-ACCESS read-only
    STATUS     current
    DESCRIPTION
            "-- empty --"
    ::= { lcsStatusTcpIpHttp 16 }

-- {SCALAR} 1.3.6.1.4.1.2356.11.1.9.10.17
lcsStatusTcpIpHttpIdleJobs OBJECT-TYPE
    SYNTAX     Integer32 (0..2147483647)
    MAX-ACCESS read-only
    STATUS     current
    DESCRIPTION
            "-- empty --"
    ::= { lcsStatusTcpIpHttp 17 }

-- {SCALAR} 1.3.6.1.4.1.2356.11.1.9.10.21
lcsStatusTcpIpHttpHttpsConnectErrors OBJECT-TYPE
    SYNTAX     Counter32
    MAX-ACCESS read-only
    STATUS     current
    DESCRIPTION
            "-- empty --"
    ::= { lcsStatusTcpIpHttp 21 }

-- {SCALAR} 1.3.6.1.4.1.2356.11.1.9.10.22
lcsStatusTcpIpHttpHttpRedirectedAccesses OBJECT-TYPE
    SYNTAX     Counter32
    MAX-ACCESS read-only
    STATUS     current
    DESCRIPTION
            "-- empty --"
    ::= { lcsStatusTcpIpHttp 22 }

-- {SCALAR} 1.3.6.1.4.1.2356.11.1.9.10.23
lcsStatusTcpIpHttpHttpsRedirectedAccesses OBJECT-TYPE
    SYNTAX     Counter32
    MAX-ACCESS read-only
    STATUS     current
    DESCRIPTION
            "-- empty --"
    ::= { lcsStatusTcpIpHttp 23 }

-- {SCALAR} 1.3.6.1.4.1.2356.11.1.9.10.24
lcsStatusTcpIpHttpHttpsRedirectedConnectErrors OBJECT-TYPE
    SYNTAX     Counter32
    MAX-ACCESS read-only
    STATUS     current
    DESCRIPTION
            "-- empty --"
    ::= { lcsStatusTcpIpHttp 24 }

-- {SCALAR} 1.3.6.1.4.1.2356.11.1.9.10.25
lcsStatusTcpIpHttpHttpsRedirectedConnectWhileDelayErrors OBJECT-TYPE
    SYNTAX     Counter32
    MAX-ACCESS read-only
    STATUS     current
    DESCRIPTION
            "-- empty --"
    ::= { lcsStatusTcpIpHttp 25 }

-- {NODE} 1.3.6.1.4.1.2356.11.1.9.11
lcsStatusTcpIpSyslog OBJECT IDENTIFIER ::= { lcsStatusTcpIp 11 }

-- {TABLE} 1.3.6.1.4.1.2356.11.1.9.11.11
lcsStatusTcpIpSyslogLastMessagesTable OBJECT-TYPE
    SYNTAX     SEQUENCE OF LcsStatusTcpIpSyslogLastMessagesEntry
    MAX-ACCESS not-accessible
    STATUS     current
    DESCRIPTION
            ""
    ::= { lcsStatusTcpIpSyslog 11 }

-- {ROW} 1.3.6.1.4.1.2356.11.1.9.11.11.1
lcsStatusTcpIpSyslogLastMessagesEntry OBJECT-TYPE
    SYNTAX     LcsStatusTcpIpSyslogLastMessagesEntry
    MAX-ACCESS not-accessible
    STATUS     current
    DESCRIPTION
            ""
    INDEX {
            lcsStatusTcpIpSyslogLastMessagesEntryIdx
          }
    ::= { lcsStatusTcpIpSyslogLastMessagesTable 1 }

LcsStatusTcpIpSyslogLastMessagesEntry ::= SEQUENCE {
            lcsStatusTcpIpSyslogLastMessagesEntryIdx Integer32,
            lcsStatusTcpIpSyslogLastMessagesEntryTime DisplayString,
            lcsStatusTcpIpSyslogLastMessagesEntrySource INTEGER,
            lcsStatusTcpIpSyslogLastMessagesEntryLevel INTEGER,
            lcsStatusTcpIpSyslogLastMessagesEntryMessage DisplayString
    }

-- {COLUMN} 1.3.6.1.4.1.2356.11.1.9.11.11.1.1
lcsStatusTcpIpSyslogLastMessagesEntryIdx OBJECT-TYPE
    SYNTAX     Integer32 (0..2147483647)
    MAX-ACCESS read-only
    STATUS     current
    DESCRIPTION
            ""
    ::= { lcsStatusTcpIpSyslogLastMessagesEntry 1 }

-- {COLUMN} 1.3.6.1.4.1.2356.11.1.9.11.11.1.2
lcsStatusTcpIpSyslogLastMessagesEntryTime OBJECT-TYPE
    SYNTAX     DisplayString (SIZE(0..255))
    MAX-ACCESS read-only
    STATUS     current
    DESCRIPTION
            ""
    ::= { lcsStatusTcpIpSyslogLastMessagesEntry 2 }

-- {COLUMN} 1.3.6.1.4.1.2356.11.1.9.11.11.1.3
lcsStatusTcpIpSyslogLastMessagesEntrySource OBJECT-TYPE
    SYNTAX     INTEGER {
                  eKern (0),
                  eUser (1),
                  eMail (2),
                  eDaemon (3),
                  eAuth (4),
                  eSyslog (5),
                  eLpr (6),
                  eNews (7),
                  eUucp (8),
                  eCron (9),
                  eAuthpriv (10),
                  eLocal0 (16),
                  eLocal1 (17),
                  eLocal2 (18),
                  eLocal3 (19),
                  eLocal4 (20),
                  eLocal5 (21),
                  eLocal6 (22),
                  eLocal7 (23)
            }
    MAX-ACCESS read-only
    STATUS     current
    DESCRIPTION
            ""
    ::= { lcsStatusTcpIpSyslogLastMessagesEntry 3 }

-- {COLUMN} 1.3.6.1.4.1.2356.11.1.9.11.11.1.4
lcsStatusTcpIpSyslogLastMessagesEntryLevel OBJECT-TYPE
    SYNTAX     INTEGER {
                  eEmergency (0),
                  eAlarm (1),
                  eCritical (2),
                  eError (3),
                  eWarning (4),
                  eNotice (5),
                  eInfo (6),
                  eDebug (7)
            }
    MAX-ACCESS read-only
    STATUS     current
    DESCRIPTION
            ""
    ::= { lcsStatusTcpIpSyslogLastMessagesEntry 4 }

-- {COLUMN} 1.3.6.1.4.1.2356.11.1.9.11.11.1.5
lcsStatusTcpIpSyslogLastMessagesEntryMessage OBJECT-TYPE
    SYNTAX     DisplayString (SIZE(0..255))
    MAX-ACCESS read-only
    STATUS     current
    DESCRIPTION
            ""
    ::= { lcsStatusTcpIpSyslogLastMessagesEntry 5 }

-- {SCALAR} 1.3.6.1.4.1.2356.11.1.9.11.12
lcsStatusTcpIpSyslogSyslogCritical OBJECT-TYPE
    SYNTAX     INTEGER {
                  eNo (0),
                  eYes (1)
            }
    MAX-ACCESS read-only
    STATUS     current
    DESCRIPTION
            "-- empty --"
    ::= { lcsStatusTcpIpSyslog 12 }

-- {SCALAR} 1.3.6.1.4.1.2356.11.1.9.11.13
lcsStatusTcpIpSyslogQueuedMessages OBJECT-TYPE
    SYNTAX     Integer32 (0..2147483647)
    MAX-ACCESS read-only
    STATUS     current
    DESCRIPTION
            "-- empty --"
    ::= { lcsStatusTcpIpSyslog 13 }

-- {SCALAR} 1.3.6.1.4.1.2356.11.1.9.11.14
lcsStatusTcpIpSyslogLimitForQueuedMessages OBJECT-TYPE
    SYNTAX     Integer32 (0..2147483647)
    MAX-ACCESS read-only
    STATUS     current
    DESCRIPTION
            "-- empty --"
    ::= { lcsStatusTcpIpSyslog 14 }

-- {SCALAR} 1.3.6.1.4.1.2356.11.1.9.11.99
lcsStatusTcpIpSyslogDeleteValues OBJECT-TYPE
    SYNTAX     DisplayString
    MAX-ACCESS read-write
    STATUS     current
    DESCRIPTION
            ""
    ::= { lcsStatusTcpIpSyslog 99 }

-- {NODE} 1.3.6.1.4.1.2356.11.1.9.12
lcsStatusTcpIpRadiuss OBJECT IDENTIFIER ::= { lcsStatusTcpIp 12 }

-- {NODE} 1.3.6.1.4.1.2356.11.1.9.12.1
lcsStatusTcpIpRadiussAccess OBJECT IDENTIFIER ::= { lcsStatusTcpIpRadiuss 1 }

-- {SCALAR} 1.3.6.1.4.1.2356.11.1.9.12.1.5
lcsStatusTcpIpRadiussAccessTotalAccessRequests OBJECT-TYPE
    SYNTAX     Counter32
    MAX-ACCESS read-only
    STATUS     current
    DESCRIPTION
            ""
    ::= { lcsStatusTcpIpRadiussAccess 5 }

-- {SCALAR} 1.3.6.1.4.1.2356.11.1.9.12.1.6
lcsStatusTcpIpRadiussAccessTotalInvalidAccessRequests OBJECT-TYPE
    SYNTAX     Counter32
    MAX-ACCESS read-only
    STATUS     current
    DESCRIPTION
            ""
    ::= { lcsStatusTcpIpRadiussAccess 6 }

-- {SCALAR} 1.3.6.1.4.1.2356.11.1.9.12.1.7
lcsStatusTcpIpRadiussAccessTotalDuplicateAccessRequests OBJECT-TYPE
    SYNTAX     Counter32
    MAX-ACCESS read-only
    STATUS     current
    DESCRIPTION
            ""
    ::= { lcsStatusTcpIpRadiussAccess 7 }

-- {SCALAR} 1.3.6.1.4.1.2356.11.1.9.12.1.8
lcsStatusTcpIpRadiussAccessTotalAccessAccepts OBJECT-TYPE
    SYNTAX     Counter32
    MAX-ACCESS read-only
    STATUS     current
    DESCRIPTION
            ""
    ::= { lcsStatusTcpIpRadiussAccess 8 }

-- {SCALAR} 1.3.6.1.4.1.2356.11.1.9.12.1.9
lcsStatusTcpIpRadiussAccessTotalAccessRejects OBJECT-TYPE
    SYNTAX     Counter32
    MAX-ACCESS read-only
    STATUS     current
    DESCRIPTION
            ""
    ::= { lcsStatusTcpIpRadiussAccess 9 }

-- {SCALAR} 1.3.6.1.4.1.2356.11.1.9.12.1.10
lcsStatusTcpIpRadiussAccessTotalAccessChallenges OBJECT-TYPE
    SYNTAX     Counter32
    MAX-ACCESS read-only
    STATUS     current
    DESCRIPTION
            ""
    ::= { lcsStatusTcpIpRadiussAccess 10 }

-- {SCALAR} 1.3.6.1.4.1.2356.11.1.9.12.1.11
lcsStatusTcpIpRadiussAccessTotalMalformedAccessRequests OBJECT-TYPE
    SYNTAX     Counter32
    MAX-ACCESS read-only
    STATUS     current
    DESCRIPTION
            ""
    ::= { lcsStatusTcpIpRadiussAccess 11 }

-- {SCALAR} 1.3.6.1.4.1.2356.11.1.9.12.1.12
lcsStatusTcpIpRadiussAccessTotalAccessBadAuthenticator OBJECT-TYPE
    SYNTAX     Counter32
    MAX-ACCESS read-only
    STATUS     current
    DESCRIPTION
            ""
    ::= { lcsStatusTcpIpRadiussAccess 12 }

-- {SCALAR} 1.3.6.1.4.1.2356.11.1.9.12.1.13
lcsStatusTcpIpRadiussAccessTotalAccessDropped OBJECT-TYPE
    SYNTAX     Counter32
    MAX-ACCESS read-only
    STATUS     current
    DESCRIPTION
            ""
    ::= { lcsStatusTcpIpRadiussAccess 13 }

-- {SCALAR} 1.3.6.1.4.1.2356.11.1.9.12.1.14
lcsStatusTcpIpRadiussAccessTotalAccessUnknownType OBJECT-TYPE
    SYNTAX     Counter32
    MAX-ACCESS read-only
    STATUS     current
    DESCRIPTION
            ""
    ::= { lcsStatusTcpIpRadiussAccess 14 }

-- {TABLE} 1.3.6.1.4.1.2356.11.1.9.12.1.15
lcsStatusTcpIpRadiussAccessClientsTable OBJECT-TYPE
    SYNTAX     SEQUENCE OF LcsStatusTcpIpRadiussAccessClientsEntry
    MAX-ACCESS not-accessible
    STATUS     current
    DESCRIPTION
            ""
    ::= { lcsStatusTcpIpRadiussAccess 15 }

-- {ROW} 1.3.6.1.4.1.2356.11.1.9.12.1.15.1
lcsStatusTcpIpRadiussAccessClientsEntry OBJECT-TYPE
    SYNTAX     LcsStatusTcpIpRadiussAccessClientsEntry
    MAX-ACCESS not-accessible
    STATUS     current
    DESCRIPTION
            ""
    INDEX {
            lcsStatusTcpIpRadiussAccessClientsEntryIpAddress
          }
    ::= { lcsStatusTcpIpRadiussAccessClientsTable 1 }

LcsStatusTcpIpRadiussAccessClientsEntry ::= SEQUENCE {
            lcsStatusTcpIpRadiussAccessClientsEntryIpAddress IpAddress,
            lcsStatusTcpIpRadiussAccessClientsEntryAccessRequests Counter32,
            lcsStatusTcpIpRadiussAccessClientsEntryDuplicateRequests Counter32,
            lcsStatusTcpIpRadiussAccessClientsEntryAccessAccepts Counter32,
            lcsStatusTcpIpRadiussAccessClientsEntryAccessRejects Counter32,
            lcsStatusTcpIpRadiussAccessClientsEntryAccessChallenges Counter32,
            lcsStatusTcpIpRadiussAccessClientsEntryMalfAccReq Counter32,
            lcsStatusTcpIpRadiussAccessClientsEntryBadAuthenticator Counter32,
            lcsStatusTcpIpRadiussAccessClientsEntryDropped Counter32,
            lcsStatusTcpIpRadiussAccessClientsEntryUnknownType Counter32,
            lcsStatusTcpIpRadiussAccessClientsEntryLastRequest Integer32,
            lcsStatusTcpIpRadiussAccessClientsEntryNasIdent DisplayString,
            lcsStatusTcpIpRadiussAccessClientsEntryStatusRequests Counter32,
            lcsStatusTcpIpRadiussAccessClientsEntryStatusResponses Counter32,
            lcsStatusTcpIpRadiussAccessClientsEntryLastStatusRequest Integer32
    }

-- {COLUMN} 1.3.6.1.4.1.2356.11.1.9.12.1.15.1.1
lcsStatusTcpIpRadiussAccessClientsEntryIpAddress OBJECT-TYPE
    SYNTAX     IpAddress
    MAX-ACCESS read-only
    STATUS     current
    DESCRIPTION
            ""
    ::= { lcsStatusTcpIpRadiussAccessClientsEntry 1 }

-- {COLUMN} 1.3.6.1.4.1.2356.11.1.9.12.1.15.1.4
lcsStatusTcpIpRadiussAccessClientsEntryAccessRequests OBJECT-TYPE
    SYNTAX     Counter32
    MAX-ACCESS read-only
    STATUS     current
    DESCRIPTION
            ""
    ::= { lcsStatusTcpIpRadiussAccessClientsEntry 4 }

-- {COLUMN} 1.3.6.1.4.1.2356.11.1.9.12.1.15.1.5
lcsStatusTcpIpRadiussAccessClientsEntryDuplicateRequests OBJECT-TYPE
    SYNTAX     Counter32
    MAX-ACCESS read-only
    STATUS     current
    DESCRIPTION
            ""
    ::= { lcsStatusTcpIpRadiussAccessClientsEntry 5 }

-- {COLUMN} 1.3.6.1.4.1.2356.11.1.9.12.1.15.1.6
lcsStatusTcpIpRadiussAccessClientsEntryAccessAccepts OBJECT-TYPE
    SYNTAX     Counter32
    MAX-ACCESS read-only
    STATUS     current
    DESCRIPTION
            ""
    ::= { lcsStatusTcpIpRadiussAccessClientsEntry 6 }

-- {COLUMN} 1.3.6.1.4.1.2356.11.1.9.12.1.15.1.7
lcsStatusTcpIpRadiussAccessClientsEntryAccessRejects OBJECT-TYPE
    SYNTAX     Counter32
    MAX-ACCESS read-only
    STATUS     current
    DESCRIPTION
            ""
    ::= { lcsStatusTcpIpRadiussAccessClientsEntry 7 }

-- {COLUMN} 1.3.6.1.4.1.2356.11.1.9.12.1.15.1.8
lcsStatusTcpIpRadiussAccessClientsEntryAccessChallenges OBJECT-TYPE
    SYNTAX     Counter32
    MAX-ACCESS read-only
    STATUS     current
    DESCRIPTION
            ""
    ::= { lcsStatusTcpIpRadiussAccessClientsEntry 8 }

-- {COLUMN} 1.3.6.1.4.1.2356.11.1.9.12.1.15.1.9
lcsStatusTcpIpRadiussAccessClientsEntryMalfAccReq OBJECT-TYPE
    SYNTAX     Counter32
    MAX-ACCESS read-only
    STATUS     current
    DESCRIPTION
            ""
    ::= { lcsStatusTcpIpRadiussAccessClientsEntry 9 }

-- {COLUMN} 1.3.6.1.4.1.2356.11.1.9.12.1.15.1.10
lcsStatusTcpIpRadiussAccessClientsEntryBadAuthenticator OBJECT-TYPE
    SYNTAX     Counter32
    MAX-ACCESS read-only
    STATUS     current
    DESCRIPTION
            ""
    ::= { lcsStatusTcpIpRadiussAccessClientsEntry 10 }

-- {COLUMN} 1.3.6.1.4.1.2356.11.1.9.12.1.15.1.11
lcsStatusTcpIpRadiussAccessClientsEntryDropped OBJECT-TYPE
    SYNTAX     Counter32
    MAX-ACCESS read-only
    STATUS     current
    DESCRIPTION
            ""
    ::= { lcsStatusTcpIpRadiussAccessClientsEntry 11 }

-- {COLUMN} 1.3.6.1.4.1.2356.11.1.9.12.1.15.1.12
lcsStatusTcpIpRadiussAccessClientsEntryUnknownType OBJECT-TYPE
    SYNTAX     Counter32
    MAX-ACCESS read-only
    STATUS     current
    DESCRIPTION
            ""
    ::= { lcsStatusTcpIpRadiussAccessClientsEntry 12 }

-- {COLUMN} 1.3.6.1.4.1.2356.11.1.9.12.1.15.1.13
lcsStatusTcpIpRadiussAccessClientsEntryLastRequest OBJECT-TYPE
    SYNTAX     Integer32 (0..2147483647)
    MAX-ACCESS read-only
    STATUS     current
    DESCRIPTION
            ""
    ::= { lcsStatusTcpIpRadiussAccessClientsEntry 13 }

-- {COLUMN} 1.3.6.1.4.1.2356.11.1.9.12.1.15.1.14
lcsStatusTcpIpRadiussAccessClientsEntryNasIdent OBJECT-TYPE
    SYNTAX     DisplayString (SIZE(0..64))
    MAX-ACCESS read-only
    STATUS     current
    DESCRIPTION
            ""
    ::= { lcsStatusTcpIpRadiussAccessClientsEntry 14 }

-- {COLUMN} 1.3.6.1.4.1.2356.11.1.9.12.1.15.1.30
lcsStatusTcpIpRadiussAccessClientsEntryStatusRequests OBJECT-TYPE
    SYNTAX     Counter32
    MAX-ACCESS read-only
    STATUS     current
    DESCRIPTION
            ""
    ::= { lcsStatusTcpIpRadiussAccessClientsEntry 30 }

-- {COLUMN} 1.3.6.1.4.1.2356.11.1.9.12.1.15.1.31
lcsStatusTcpIpRadiussAccessClientsEntryStatusResponses OBJECT-TYPE
    SYNTAX     Counter32
    MAX-ACCESS read-only
    STATUS     current
    DESCRIPTION
            ""
    ::= { lcsStatusTcpIpRadiussAccessClientsEntry 31 }

-- {COLUMN} 1.3.6.1.4.1.2356.11.1.9.12.1.15.1.32
lcsStatusTcpIpRadiussAccessClientsEntryLastStatusRequest OBJECT-TYPE
    SYNTAX     Integer32 (0..2147483647)
    MAX-ACCESS read-only
    STATUS     current
    DESCRIPTION
            ""
    ::= { lcsStatusTcpIpRadiussAccessClientsEntry 32 }

-- {TABLE} 1.3.6.1.4.1.2356.11.1.9.12.1.20
lcsStatusTcpIpRadiussAccessIpv6ClientsTable OBJECT-TYPE
    SYNTAX     SEQUENCE OF LcsStatusTcpIpRadiussAccessIpv6ClientsEntry
    MAX-ACCESS not-accessible
    STATUS     current
    DESCRIPTION
            "-- empty --"
    ::= { lcsStatusTcpIpRadiussAccess 20 }

-- {ROW} 1.3.6.1.4.1.2356.11.1.9.12.1.20.1
lcsStatusTcpIpRadiussAccessIpv6ClientsEntry OBJECT-TYPE
    SYNTAX     LcsStatusTcpIpRadiussAccessIpv6ClientsEntry
    MAX-ACCESS not-accessible
    STATUS     current
    DESCRIPTION
            ""
    INDEX {
            lcsStatusTcpIpRadiussAccessIpv6ClientsEntryIpAddress
          }
    ::= { lcsStatusTcpIpRadiussAccessIpv6ClientsTable 1 }

LcsStatusTcpIpRadiussAccessIpv6ClientsEntry ::= SEQUENCE {
            lcsStatusTcpIpRadiussAccessIpv6ClientsEntryIpAddress IpAddress,
            lcsStatusTcpIpRadiussAccessIpv6ClientsEntryAccessRequests Counter32,
            lcsStatusTcpIpRadiussAccessIpv6ClientsEntryDuplicateRequests Counter32,
            lcsStatusTcpIpRadiussAccessIpv6ClientsEntryAccessAccepts Counter32,
            lcsStatusTcpIpRadiussAccessIpv6ClientsEntryAccessRejects Counter32,
            lcsStatusTcpIpRadiussAccessIpv6ClientsEntryAccessChallenges Counter32,
            lcsStatusTcpIpRadiussAccessIpv6ClientsEntryMalfAccReq Counter32,
            lcsStatusTcpIpRadiussAccessIpv6ClientsEntryBadAuthenticator Counter32,
            lcsStatusTcpIpRadiussAccessIpv6ClientsEntryDropped Counter32,
            lcsStatusTcpIpRadiussAccessIpv6ClientsEntryUnknownType Counter32,
            lcsStatusTcpIpRadiussAccessIpv6ClientsEntryLastRequest Integer32,
            lcsStatusTcpIpRadiussAccessIpv6ClientsEntryNasIdent DisplayString,
            lcsStatusTcpIpRadiussAccessIpv6ClientsEntryStatusRequests Counter32,
            lcsStatusTcpIpRadiussAccessIpv6ClientsEntryStatusResponses Counter32,
            lcsStatusTcpIpRadiussAccessIpv6ClientsEntryLastStatusRequest Integer32
    }

-- {COLUMN} 1.3.6.1.4.1.2356.11.1.9.12.1.20.1.1
lcsStatusTcpIpRadiussAccessIpv6ClientsEntryIpAddress OBJECT-TYPE
    SYNTAX     IpAddress
    MAX-ACCESS read-only
    STATUS     current
    DESCRIPTION
            "-- empty --"
    ::= { lcsStatusTcpIpRadiussAccessIpv6ClientsEntry 1 }

-- {COLUMN} 1.3.6.1.4.1.2356.11.1.9.12.1.20.1.4
lcsStatusTcpIpRadiussAccessIpv6ClientsEntryAccessRequests OBJECT-TYPE
    SYNTAX     Counter32
    MAX-ACCESS read-only
    STATUS     current
    DESCRIPTION
            "-- empty --"
    ::= { lcsStatusTcpIpRadiussAccessIpv6ClientsEntry 4 }

-- {COLUMN} 1.3.6.1.4.1.2356.11.1.9.12.1.20.1.5
lcsStatusTcpIpRadiussAccessIpv6ClientsEntryDuplicateRequests OBJECT-TYPE
    SYNTAX     Counter32
    MAX-ACCESS read-only
    STATUS     current
    DESCRIPTION
            "-- empty --"
    ::= { lcsStatusTcpIpRadiussAccessIpv6ClientsEntry 5 }

-- {COLUMN} 1.3.6.1.4.1.2356.11.1.9.12.1.20.1.6
lcsStatusTcpIpRadiussAccessIpv6ClientsEntryAccessAccepts OBJECT-TYPE
    SYNTAX     Counter32
    MAX-ACCESS read-only
    STATUS     current
    DESCRIPTION
            "-- empty --"
    ::= { lcsStatusTcpIpRadiussAccessIpv6ClientsEntry 6 }

-- {COLUMN} 1.3.6.1.4.1.2356.11.1.9.12.1.20.1.7
lcsStatusTcpIpRadiussAccessIpv6ClientsEntryAccessRejects OBJECT-TYPE
    SYNTAX     Counter32
    MAX-ACCESS read-only
    STATUS     current
    DESCRIPTION
            "-- empty --"
    ::= { lcsStatusTcpIpRadiussAccessIpv6ClientsEntry 7 }

-- {COLUMN} 1.3.6.1.4.1.2356.11.1.9.12.1.20.1.8
lcsStatusTcpIpRadiussAccessIpv6ClientsEntryAccessChallenges OBJECT-TYPE
    SYNTAX     Counter32
    MAX-ACCESS read-only
    STATUS     current
    DESCRIPTION
            "-- empty --"
    ::= { lcsStatusTcpIpRadiussAccessIpv6ClientsEntry 8 }

-- {COLUMN} 1.3.6.1.4.1.2356.11.1.9.12.1.20.1.9
lcsStatusTcpIpRadiussAccessIpv6ClientsEntryMalfAccReq OBJECT-TYPE
    SYNTAX     Counter32
    MAX-ACCESS read-only
    STATUS     current
    DESCRIPTION
            ""
    ::= { lcsStatusTcpIpRadiussAccessIpv6ClientsEntry 9 }

-- {COLUMN} 1.3.6.1.4.1.2356.11.1.9.12.1.20.1.10
lcsStatusTcpIpRadiussAccessIpv6ClientsEntryBadAuthenticator OBJECT-TYPE
    SYNTAX     Counter32
    MAX-ACCESS read-only
    STATUS     current
    DESCRIPTION
            "-- empty --"
    ::= { lcsStatusTcpIpRadiussAccessIpv6ClientsEntry 10 }

-- {COLUMN} 1.3.6.1.4.1.2356.11.1.9.12.1.20.1.11
lcsStatusTcpIpRadiussAccessIpv6ClientsEntryDropped OBJECT-TYPE
    SYNTAX     Counter32
    MAX-ACCESS read-only
    STATUS     current
    DESCRIPTION
            "-- empty --"
    ::= { lcsStatusTcpIpRadiussAccessIpv6ClientsEntry 11 }

-- {COLUMN} 1.3.6.1.4.1.2356.11.1.9.12.1.20.1.12
lcsStatusTcpIpRadiussAccessIpv6ClientsEntryUnknownType OBJECT-TYPE
    SYNTAX     Counter32
    MAX-ACCESS read-only
    STATUS     current
    DESCRIPTION
            "-- empty --"
    ::= { lcsStatusTcpIpRadiussAccessIpv6ClientsEntry 12 }

-- {COLUMN} 1.3.6.1.4.1.2356.11.1.9.12.1.20.1.13
lcsStatusTcpIpRadiussAccessIpv6ClientsEntryLastRequest OBJECT-TYPE
    SYNTAX     Integer32 (0..2147483647)
    MAX-ACCESS read-only
    STATUS     current
    DESCRIPTION
            "-- empty --"
    ::= { lcsStatusTcpIpRadiussAccessIpv6ClientsEntry 13 }

-- {COLUMN} 1.3.6.1.4.1.2356.11.1.9.12.1.20.1.14
lcsStatusTcpIpRadiussAccessIpv6ClientsEntryNasIdent OBJECT-TYPE
    SYNTAX     DisplayString (SIZE(0..64))
    MAX-ACCESS read-only
    STATUS     current
    DESCRIPTION
            "-- empty --"
    ::= { lcsStatusTcpIpRadiussAccessIpv6ClientsEntry 14 }

-- {COLUMN} 1.3.6.1.4.1.2356.11.1.9.12.1.20.1.30
lcsStatusTcpIpRadiussAccessIpv6ClientsEntryStatusRequests OBJECT-TYPE
    SYNTAX     Counter32
    MAX-ACCESS read-only
    STATUS     current
    DESCRIPTION
            "-- empty --"
    ::= { lcsStatusTcpIpRadiussAccessIpv6ClientsEntry 30 }

-- {COLUMN} 1.3.6.1.4.1.2356.11.1.9.12.1.20.1.31
lcsStatusTcpIpRadiussAccessIpv6ClientsEntryStatusResponses OBJECT-TYPE
    SYNTAX     Counter32
    MAX-ACCESS read-only
    STATUS     current
    DESCRIPTION
            "-- empty --"
    ::= { lcsStatusTcpIpRadiussAccessIpv6ClientsEntry 31 }

-- {COLUMN} 1.3.6.1.4.1.2356.11.1.9.12.1.20.1.32
lcsStatusTcpIpRadiussAccessIpv6ClientsEntryLastStatusRequest OBJECT-TYPE
    SYNTAX     Integer32 (0..2147483647)
    MAX-ACCESS read-only
    STATUS     current
    DESCRIPTION
            "-- empty --"
    ::= { lcsStatusTcpIpRadiussAccessIpv6ClientsEntry 32 }

-- {SCALAR} 1.3.6.1.4.1.2356.11.1.9.12.1.30
lcsStatusTcpIpRadiussAccessTotalStatusRequests OBJECT-TYPE
    SYNTAX     Counter32
    MAX-ACCESS read-only
    STATUS     current
    DESCRIPTION
            ""
    ::= { lcsStatusTcpIpRadiussAccess 30 }

-- {SCALAR} 1.3.6.1.4.1.2356.11.1.9.12.1.31
lcsStatusTcpIpRadiussAccessTotalStatusResponses OBJECT-TYPE
    SYNTAX     Counter32
    MAX-ACCESS read-only
    STATUS     current
    DESCRIPTION
            ""
    ::= { lcsStatusTcpIpRadiussAccess 31 }

-- {SCALAR} 1.3.6.1.4.1.2356.11.1.9.12.1.32
lcsStatusTcpIpRadiussAccessIpv4WanDiscards OBJECT-TYPE
    SYNTAX     Counter32
    MAX-ACCESS read-only
    STATUS     current
    DESCRIPTION
            "-- empty --"
    ::= { lcsStatusTcpIpRadiussAccess 32 }

-- {SCALAR} 1.3.6.1.4.1.2356.11.1.9.12.1.100
lcsStatusTcpIpRadiussAccessDeleteValues OBJECT-TYPE
    SYNTAX     DisplayString
    MAX-ACCESS read-write
    STATUS     current
    DESCRIPTION
            ""
    ::= { lcsStatusTcpIpRadiussAccess 100 }

-- {NODE} 1.3.6.1.4.1.2356.11.1.9.12.2
lcsStatusTcpIpRadiussAccnt OBJECT IDENTIFIER ::= { lcsStatusTcpIpRadiuss 2 }

-- {SCALAR} 1.3.6.1.4.1.2356.11.1.9.12.2.5
lcsStatusTcpIpRadiussAccntTotalAccountRequests OBJECT-TYPE
    SYNTAX     Counter32
    MAX-ACCESS read-only
    STATUS     current
    DESCRIPTION
            ""
    ::= { lcsStatusTcpIpRadiussAccnt 5 }

-- {SCALAR} 1.3.6.1.4.1.2356.11.1.9.12.2.6
lcsStatusTcpIpRadiussAccntTotalInvalidAccountRequests OBJECT-TYPE
    SYNTAX     Counter32
    MAX-ACCESS read-only
    STATUS     current
    DESCRIPTION
            ""
    ::= { lcsStatusTcpIpRadiussAccnt 6 }

-- {SCALAR} 1.3.6.1.4.1.2356.11.1.9.12.2.7
lcsStatusTcpIpRadiussAccntTotalDuplicateAccountRequests OBJECT-TYPE
    SYNTAX     Counter32
    MAX-ACCESS read-only
    STATUS     current
    DESCRIPTION
            ""
    ::= { lcsStatusTcpIpRadiussAccnt 7 }

-- {SCALAR} 1.3.6.1.4.1.2356.11.1.9.12.2.8
lcsStatusTcpIpRadiussAccntTotalAccountResponses OBJECT-TYPE
    SYNTAX     Counter32
    MAX-ACCESS read-only
    STATUS     current
    DESCRIPTION
            ""
    ::= { lcsStatusTcpIpRadiussAccnt 8 }

-- {SCALAR} 1.3.6.1.4.1.2356.11.1.9.12.2.9
lcsStatusTcpIpRadiussAccntTotalMalformedAccountRequests OBJECT-TYPE
    SYNTAX     Counter32
    MAX-ACCESS read-only
    STATUS     current
    DESCRIPTION
            ""
    ::= { lcsStatusTcpIpRadiussAccnt 9 }

-- {SCALAR} 1.3.6.1.4.1.2356.11.1.9.12.2.10
lcsStatusTcpIpRadiussAccntTotalAccountBadAuthenticator OBJECT-TYPE
    SYNTAX     Counter32
    MAX-ACCESS read-only
    STATUS     current
    DESCRIPTION
            ""
    ::= { lcsStatusTcpIpRadiussAccnt 10 }

-- {SCALAR} 1.3.6.1.4.1.2356.11.1.9.12.2.11
lcsStatusTcpIpRadiussAccntTotalAccountDropped OBJECT-TYPE
    SYNTAX     Counter32
    MAX-ACCESS read-only
    STATUS     current
    DESCRIPTION
            ""
    ::= { lcsStatusTcpIpRadiussAccnt 11 }

-- {SCALAR} 1.3.6.1.4.1.2356.11.1.9.12.2.12
lcsStatusTcpIpRadiussAccntTotalAccountNorecord OBJECT-TYPE
    SYNTAX     Counter32
    MAX-ACCESS read-only
    STATUS     current
    DESCRIPTION
            ""
    ::= { lcsStatusTcpIpRadiussAccnt 12 }

-- {SCALAR} 1.3.6.1.4.1.2356.11.1.9.12.2.13
lcsStatusTcpIpRadiussAccntTotalAccountUnknownType OBJECT-TYPE
    SYNTAX     Counter32
    MAX-ACCESS read-only
    STATUS     current
    DESCRIPTION
            ""
    ::= { lcsStatusTcpIpRadiussAccnt 13 }

-- {TABLE} 1.3.6.1.4.1.2356.11.1.9.12.2.15
lcsStatusTcpIpRadiussAccntClientsTable OBJECT-TYPE
    SYNTAX     SEQUENCE OF LcsStatusTcpIpRadiussAccntClientsEntry
    MAX-ACCESS not-accessible
    STATUS     current
    DESCRIPTION
            ""
    ::= { lcsStatusTcpIpRadiussAccnt 15 }

-- {ROW} 1.3.6.1.4.1.2356.11.1.9.12.2.15.1
lcsStatusTcpIpRadiussAccntClientsEntry OBJECT-TYPE
    SYNTAX     LcsStatusTcpIpRadiussAccntClientsEntry
    MAX-ACCESS not-accessible
    STATUS     current
    DESCRIPTION
            ""
    INDEX {
            lcsStatusTcpIpRadiussAccntClientsEntryIpAddress
          }
    ::= { lcsStatusTcpIpRadiussAccntClientsTable 1 }

LcsStatusTcpIpRadiussAccntClientsEntry ::= SEQUENCE {
            lcsStatusTcpIpRadiussAccntClientsEntryIpAddress IpAddress,
            lcsStatusTcpIpRadiussAccntClientsEntryAccountRequests Counter32,
            lcsStatusTcpIpRadiussAccntClientsEntryDuplicateRequests Counter32,
            lcsStatusTcpIpRadiussAccntClientsEntryAccountResponses Counter32,
            lcsStatusTcpIpRadiussAccntClientsEntryAccountNorecords Counter32,
            lcsStatusTcpIpRadiussAccntClientsEntryMalfAccReq Counter32,
            lcsStatusTcpIpRadiussAccntClientsEntryBadAuthenticator Counter32,
            lcsStatusTcpIpRadiussAccntClientsEntryDropped Counter32,
            lcsStatusTcpIpRadiussAccntClientsEntryUnknownType Counter32,
            lcsStatusTcpIpRadiussAccntClientsEntryLastRequest Integer32,
            lcsStatusTcpIpRadiussAccntClientsEntryNasIdent DisplayString,
            lcsStatusTcpIpRadiussAccntClientsEntryStatusRequests Counter32,
            lcsStatusTcpIpRadiussAccntClientsEntryStatusResponses Counter32,
            lcsStatusTcpIpRadiussAccntClientsEntryLastStatusRequest Integer32
    }

-- {COLUMN} 1.3.6.1.4.1.2356.11.1.9.12.2.15.1.1
lcsStatusTcpIpRadiussAccntClientsEntryIpAddress OBJECT-TYPE
    SYNTAX     IpAddress
    MAX-ACCESS read-only
    STATUS     current
    DESCRIPTION
            ""
    ::= { lcsStatusTcpIpRadiussAccntClientsEntry 1 }

-- {COLUMN} 1.3.6.1.4.1.2356.11.1.9.12.2.15.1.4
lcsStatusTcpIpRadiussAccntClientsEntryAccountRequests OBJECT-TYPE
    SYNTAX     Counter32
    MAX-ACCESS read-only
    STATUS     current
    DESCRIPTION
            ""
    ::= { lcsStatusTcpIpRadiussAccntClientsEntry 4 }

-- {COLUMN} 1.3.6.1.4.1.2356.11.1.9.12.2.15.1.5
lcsStatusTcpIpRadiussAccntClientsEntryDuplicateRequests OBJECT-TYPE
    SYNTAX     Counter32
    MAX-ACCESS read-only
    STATUS     current
    DESCRIPTION
            ""
    ::= { lcsStatusTcpIpRadiussAccntClientsEntry 5 }

-- {COLUMN} 1.3.6.1.4.1.2356.11.1.9.12.2.15.1.6
lcsStatusTcpIpRadiussAccntClientsEntryAccountResponses OBJECT-TYPE
    SYNTAX     Counter32
    MAX-ACCESS read-only
    STATUS     current
    DESCRIPTION
            ""
    ::= { lcsStatusTcpIpRadiussAccntClientsEntry 6 }

-- {COLUMN} 1.3.6.1.4.1.2356.11.1.9.12.2.15.1.7
lcsStatusTcpIpRadiussAccntClientsEntryAccountNorecords OBJECT-TYPE
    SYNTAX     Counter32
    MAX-ACCESS read-only
    STATUS     current
    DESCRIPTION
            ""
    ::= { lcsStatusTcpIpRadiussAccntClientsEntry 7 }

-- {COLUMN} 1.3.6.1.4.1.2356.11.1.9.12.2.15.1.9
lcsStatusTcpIpRadiussAccntClientsEntryMalfAccReq OBJECT-TYPE
    SYNTAX     Counter32
    MAX-ACCESS read-only
    STATUS     current
    DESCRIPTION
            ""
    ::= { lcsStatusTcpIpRadiussAccntClientsEntry 9 }

-- {COLUMN} 1.3.6.1.4.1.2356.11.1.9.12.2.15.1.10
lcsStatusTcpIpRadiussAccntClientsEntryBadAuthenticator OBJECT-TYPE
    SYNTAX     Counter32
    MAX-ACCESS read-only
    STATUS     current
    DESCRIPTION
            ""
    ::= { lcsStatusTcpIpRadiussAccntClientsEntry 10 }

-- {COLUMN} 1.3.6.1.4.1.2356.11.1.9.12.2.15.1.11
lcsStatusTcpIpRadiussAccntClientsEntryDropped OBJECT-TYPE
    SYNTAX     Counter32
    MAX-ACCESS read-only
    STATUS     current
    DESCRIPTION
            ""
    ::= { lcsStatusTcpIpRadiussAccntClientsEntry 11 }

-- {COLUMN} 1.3.6.1.4.1.2356.11.1.9.12.2.15.1.12
lcsStatusTcpIpRadiussAccntClientsEntryUnknownType OBJECT-TYPE
    SYNTAX     Counter32
    MAX-ACCESS read-only
    STATUS     current
    DESCRIPTION
            ""
    ::= { lcsStatusTcpIpRadiussAccntClientsEntry 12 }

-- {COLUMN} 1.3.6.1.4.1.2356.11.1.9.12.2.15.1.13
lcsStatusTcpIpRadiussAccntClientsEntryLastRequest OBJECT-TYPE
    SYNTAX     Integer32 (0..2147483647)
    MAX-ACCESS read-only
    STATUS     current
    DESCRIPTION
            ""
    ::= { lcsStatusTcpIpRadiussAccntClientsEntry 13 }

-- {COLUMN} 1.3.6.1.4.1.2356.11.1.9.12.2.15.1.14
lcsStatusTcpIpRadiussAccntClientsEntryNasIdent OBJECT-TYPE
    SYNTAX     DisplayString (SIZE(0..64))
    MAX-ACCESS read-only
    STATUS     current
    DESCRIPTION
            ""
    ::= { lcsStatusTcpIpRadiussAccntClientsEntry 14 }

-- {COLUMN} 1.3.6.1.4.1.2356.11.1.9.12.2.15.1.30
lcsStatusTcpIpRadiussAccntClientsEntryStatusRequests OBJECT-TYPE
    SYNTAX     Counter32
    MAX-ACCESS read-only
    STATUS     current
    DESCRIPTION
            ""
    ::= { lcsStatusTcpIpRadiussAccntClientsEntry 30 }

-- {COLUMN} 1.3.6.1.4.1.2356.11.1.9.12.2.15.1.31
lcsStatusTcpIpRadiussAccntClientsEntryStatusResponses OBJECT-TYPE
    SYNTAX     Counter32
    MAX-ACCESS read-only
    STATUS     current
    DESCRIPTION
            ""
    ::= { lcsStatusTcpIpRadiussAccntClientsEntry 31 }

-- {COLUMN} 1.3.6.1.4.1.2356.11.1.9.12.2.15.1.32
lcsStatusTcpIpRadiussAccntClientsEntryLastStatusRequest OBJECT-TYPE
    SYNTAX     Integer32 (0..2147483647)
    MAX-ACCESS read-only
    STATUS     current
    DESCRIPTION
            ""
    ::= { lcsStatusTcpIpRadiussAccntClientsEntry 32 }

-- {TABLE} 1.3.6.1.4.1.2356.11.1.9.12.2.16
lcsStatusTcpIpRadiussAccntActAccntSessTable OBJECT-TYPE
    SYNTAX     SEQUENCE OF LcsStatusTcpIpRadiussAccntActAccntSessEntry
    MAX-ACCESS not-accessible
    STATUS     current
    DESCRIPTION
            ""
    ::= { lcsStatusTcpIpRadiussAccnt 16 }

-- {ROW} 1.3.6.1.4.1.2356.11.1.9.12.2.16.1
lcsStatusTcpIpRadiussAccntActAccntSessEntry OBJECT-TYPE
    SYNTAX     LcsStatusTcpIpRadiussAccntActAccntSessEntry
    MAX-ACCESS not-accessible
    STATUS     current
    DESCRIPTION
            ""
    INDEX {
            lcsStatusTcpIpRadiussAccntActAccntSessEntryIndex
          }
    ::= { lcsStatusTcpIpRadiussAccntActAccntSessTable 1 }

LcsStatusTcpIpRadiussAccntActAccntSessEntry ::= SEQUENCE {
            lcsStatusTcpIpRadiussAccntActAccntSessEntryIndex Integer32,
            lcsStatusTcpIpRadiussAccntActAccntSessEntryNasIpAddress IpAddress,
            lcsStatusTcpIpRadiussAccntActAccntSessEntryNasIdent DisplayString,
            lcsStatusTcpIpRadiussAccntActAccntSessEntrySessionId DisplayString,
            lcsStatusTcpIpRadiussAccntActAccntSessEntryUserName DisplayString,
            lcsStatusTcpIpRadiussAccntActAccntSessEntrySessionTime Integer32,
            lcsStatusTcpIpRadiussAccntActAccntSessEntryInputPackets Counter32,
            lcsStatusTcpIpRadiussAccntActAccntSessEntryOutputPackets Counter32,
            lcsStatusTcpIpRadiussAccntActAccntSessEntryInputOctets Counter64,
            lcsStatusTcpIpRadiussAccntActAccntSessEntryOutputOctets Counter64,
            lcsStatusTcpIpRadiussAccntActAccntSessEntryIpAddress IpAddress,
            lcsStatusTcpIpRadiussAccntActAccntSessEntryStartTime DisplayString,
            lcsStatusTcpIpRadiussAccntActAccntSessEntryLastUpdate Integer32,
            lcsStatusTcpIpRadiussAccntActAccntSessEntryUpdateDelta Integer32,
            lcsStatusTcpIpRadiussAccntActAccntSessEntryNasPortType INTEGER,
            lcsStatusTcpIpRadiussAccntActAccntSessEntryNasPortId Integer32,
            lcsStatusTcpIpRadiussAccntActAccntSessEntryCalledStationId DisplayString,
            lcsStatusTcpIpRadiussAccntActAccntSessEntryCallingStationId DisplayString,
            lcsStatusTcpIpRadiussAccntActAccntSessEntryNasIpv6Address IpAddress
    }

-- {COLUMN} 1.3.6.1.4.1.2356.11.1.9.12.2.16.1.1
lcsStatusTcpIpRadiussAccntActAccntSessEntryIndex OBJECT-TYPE
    SYNTAX     Integer32 (0..2147483647)
    MAX-ACCESS read-only
    STATUS     current
    DESCRIPTION
            ""
    ::= { lcsStatusTcpIpRadiussAccntActAccntSessEntry 1 }

-- {COLUMN} 1.3.6.1.4.1.2356.11.1.9.12.2.16.1.2
lcsStatusTcpIpRadiussAccntActAccntSessEntryNasIpAddress OBJECT-TYPE
    SYNTAX     IpAddress
    MAX-ACCESS read-only
    STATUS     current
    DESCRIPTION
            ""
    ::= { lcsStatusTcpIpRadiussAccntActAccntSessEntry 2 }

-- {COLUMN} 1.3.6.1.4.1.2356.11.1.9.12.2.16.1.3
lcsStatusTcpIpRadiussAccntActAccntSessEntryNasIdent OBJECT-TYPE
    SYNTAX     DisplayString (SIZE(0..64))
    MAX-ACCESS read-only
    STATUS     current
    DESCRIPTION
            ""
    ::= { lcsStatusTcpIpRadiussAccntActAccntSessEntry 3 }

-- {COLUMN} 1.3.6.1.4.1.2356.11.1.9.12.2.16.1.4
lcsStatusTcpIpRadiussAccntActAccntSessEntrySessionId OBJECT-TYPE
    SYNTAX     DisplayString (SIZE(0..128))
    MAX-ACCESS read-only
    STATUS     current
    DESCRIPTION
            ""
    ::= { lcsStatusTcpIpRadiussAccntActAccntSessEntry 4 }

-- {COLUMN} 1.3.6.1.4.1.2356.11.1.9.12.2.16.1.5
lcsStatusTcpIpRadiussAccntActAccntSessEntryUserName OBJECT-TYPE
    SYNTAX     DisplayString (SIZE(0..48))
    MAX-ACCESS read-only
    STATUS     current
    DESCRIPTION
            ""
    ::= { lcsStatusTcpIpRadiussAccntActAccntSessEntry 5 }

-- {COLUMN} 1.3.6.1.4.1.2356.11.1.9.12.2.16.1.6
lcsStatusTcpIpRadiussAccntActAccntSessEntrySessionTime OBJECT-TYPE
    SYNTAX     Integer32 (0..2147483647)
    MAX-ACCESS read-only
    STATUS     current
    DESCRIPTION
            ""
    ::= { lcsStatusTcpIpRadiussAccntActAccntSessEntry 6 }

-- {COLUMN} 1.3.6.1.4.1.2356.11.1.9.12.2.16.1.7
lcsStatusTcpIpRadiussAccntActAccntSessEntryInputPackets OBJECT-TYPE
    SYNTAX     Counter32
    MAX-ACCESS read-only
    STATUS     current
    DESCRIPTION
            ""
    ::= { lcsStatusTcpIpRadiussAccntActAccntSessEntry 7 }

-- {COLUMN} 1.3.6.1.4.1.2356.11.1.9.12.2.16.1.8
lcsStatusTcpIpRadiussAccntActAccntSessEntryOutputPackets OBJECT-TYPE
    SYNTAX     Counter32
    MAX-ACCESS read-only
    STATUS     current
    DESCRIPTION
            ""
    ::= { lcsStatusTcpIpRadiussAccntActAccntSessEntry 8 }

-- {COLUMN} 1.3.6.1.4.1.2356.11.1.9.12.2.16.1.9
lcsStatusTcpIpRadiussAccntActAccntSessEntryInputOctets OBJECT-TYPE
    SYNTAX     Counter64
    MAX-ACCESS read-only
    STATUS     current
    DESCRIPTION
            ""
    ::= { lcsStatusTcpIpRadiussAccntActAccntSessEntry 9 }

-- {COLUMN} 1.3.6.1.4.1.2356.11.1.9.12.2.16.1.10
lcsStatusTcpIpRadiussAccntActAccntSessEntryOutputOctets OBJECT-TYPE
    SYNTAX     Counter64
    MAX-ACCESS read-only
    STATUS     current
    DESCRIPTION
            ""
    ::= { lcsStatusTcpIpRadiussAccntActAccntSessEntry 10 }

-- {COLUMN} 1.3.6.1.4.1.2356.11.1.9.12.2.16.1.11
lcsStatusTcpIpRadiussAccntActAccntSessEntryIpAddress OBJECT-TYPE
    SYNTAX     IpAddress
    MAX-ACCESS read-only
    STATUS     current
    DESCRIPTION
            ""
    ::= { lcsStatusTcpIpRadiussAccntActAccntSessEntry 11 }

-- {COLUMN} 1.3.6.1.4.1.2356.11.1.9.12.2.16.1.12
lcsStatusTcpIpRadiussAccntActAccntSessEntryStartTime OBJECT-TYPE
    SYNTAX     DisplayString (SIZE(0..19))
    MAX-ACCESS read-only
    STATUS     current
    DESCRIPTION
            ""
    ::= { lcsStatusTcpIpRadiussAccntActAccntSessEntry 12 }

-- {COLUMN} 1.3.6.1.4.1.2356.11.1.9.12.2.16.1.15
lcsStatusTcpIpRadiussAccntActAccntSessEntryLastUpdate OBJECT-TYPE
    SYNTAX     Integer32 (0..2147483647)
    MAX-ACCESS read-only
    STATUS     current
    DESCRIPTION
            ""
    ::= { lcsStatusTcpIpRadiussAccntActAccntSessEntry 15 }

-- {COLUMN} 1.3.6.1.4.1.2356.11.1.9.12.2.16.1.16
lcsStatusTcpIpRadiussAccntActAccntSessEntryUpdateDelta OBJECT-TYPE
    SYNTAX     Integer32 (0..2147483647)
    MAX-ACCESS read-only
    STATUS     current
    DESCRIPTION
            ""
    ::= { lcsStatusTcpIpRadiussAccntActAccntSessEntry 16 }

-- {COLUMN} 1.3.6.1.4.1.2356.11.1.9.12.2.16.1.17
lcsStatusTcpIpRadiussAccntActAccntSessEntryNasPortType OBJECT-TYPE
    SYNTAX     INTEGER {
                  eUnknown (-1),
                  eAsync (0),
                  eSync (1),
                  eIsdnSync (2),
                  eV120 (3),
                  eV110 (4),
                  eVirtual (5),
                  ePiafs (6),
                  eHdlcClearChannel (7),
                  eX25 (8),
                  eX75 (9),
                  eG3Fax (10),
                  eSdsl (11),
                  eAdslCap (12),
                  eAdslDmt (13),
                  eIdsl (14),
                  eEthernet (15),
                  eXdsl (16),
                  eCable (17),
                  eWirelessOther (18),
                  eWireless80211 (19),
                  eTokenRing (20),
                  eFddi (21),
                  eWirelessCdma2000 (22),
                  eWirelessUmts (23),
                  eWireless1xEv (24),
                  eIapp (25),
                  eFttp (26),
                  eWireless80216 (27),
                  eWireless80220 (28),
                  eWireless80222 (29),
                  ePppoa (30),
                  ePppoeoa (31),
                  ePppoeoe (32),
                  ePppoeovlan (33),
                  ePppoeoqinq (34),
                  eXpon (35)
            }
    MAX-ACCESS read-only
    STATUS     current
    DESCRIPTION
            ""
    ::= { lcsStatusTcpIpRadiussAccntActAccntSessEntry 17 }

-- {COLUMN} 1.3.6.1.4.1.2356.11.1.9.12.2.16.1.18
lcsStatusTcpIpRadiussAccntActAccntSessEntryNasPortId OBJECT-TYPE
    SYNTAX     Integer32 (0..2147483647)
    MAX-ACCESS read-only
    STATUS     current
    DESCRIPTION
            ""
    ::= { lcsStatusTcpIpRadiussAccntActAccntSessEntry 18 }

-- {COLUMN} 1.3.6.1.4.1.2356.11.1.9.12.2.16.1.19
lcsStatusTcpIpRadiussAccntActAccntSessEntryCalledStationId OBJECT-TYPE
    SYNTAX     DisplayString (SIZE(0..48))
    MAX-ACCESS read-only
    STATUS     current
    DESCRIPTION
            ""
    ::= { lcsStatusTcpIpRadiussAccntActAccntSessEntry 19 }

-- {COLUMN} 1.3.6.1.4.1.2356.11.1.9.12.2.16.1.20
lcsStatusTcpIpRadiussAccntActAccntSessEntryCallingStationId OBJECT-TYPE
    SYNTAX     DisplayString (SIZE(0..48))
    MAX-ACCESS read-only
    STATUS     current
    DESCRIPTION
            ""
    ::= { lcsStatusTcpIpRadiussAccntActAccntSessEntry 20 }

-- {COLUMN} 1.3.6.1.4.1.2356.11.1.9.12.2.16.1.21
lcsStatusTcpIpRadiussAccntActAccntSessEntryNasIpv6Address OBJECT-TYPE
    SYNTAX     IpAddress
    MAX-ACCESS read-only
    STATUS     current
    DESCRIPTION
            "-- empty --"
    ::= { lcsStatusTcpIpRadiussAccntActAccntSessEntry 21 }

-- {TABLE} 1.3.6.1.4.1.2356.11.1.9.12.2.17
lcsStatusTcpIpRadiussAccntComplAccntSessTable OBJECT-TYPE
    SYNTAX     SEQUENCE OF LcsStatusTcpIpRadiussAccntComplAccntSessEntry
    MAX-ACCESS not-accessible
    STATUS     current
    DESCRIPTION
            ""
    ::= { lcsStatusTcpIpRadiussAccnt 17 }

-- {ROW} 1.3.6.1.4.1.2356.11.1.9.12.2.17.1
lcsStatusTcpIpRadiussAccntComplAccntSessEntry OBJECT-TYPE
    SYNTAX     LcsStatusTcpIpRadiussAccntComplAccntSessEntry
    MAX-ACCESS not-accessible
    STATUS     current
    DESCRIPTION
            ""
    INDEX {
            lcsStatusTcpIpRadiussAccntComplAccntSessEntryIndex
          }
    ::= { lcsStatusTcpIpRadiussAccntComplAccntSessTable 1 }

LcsStatusTcpIpRadiussAccntComplAccntSessEntry ::= SEQUENCE {
            lcsStatusTcpIpRadiussAccntComplAccntSessEntryIndex Integer32,
            lcsStatusTcpIpRadiussAccntComplAccntSessEntryNasIpAddress IpAddress,
            lcsStatusTcpIpRadiussAccntComplAccntSessEntryNasIdent DisplayString,
            lcsStatusTcpIpRadiussAccntComplAccntSessEntrySessionId DisplayString,
            lcsStatusTcpIpRadiussAccntComplAccntSessEntryUserName DisplayString,
            lcsStatusTcpIpRadiussAccntComplAccntSessEntrySessionTime Integer32,
            lcsStatusTcpIpRadiussAccntComplAccntSessEntryInputPackets Counter32,
            lcsStatusTcpIpRadiussAccntComplAccntSessEntryOutputPackets Counter32,
            lcsStatusTcpIpRadiussAccntComplAccntSessEntryInputOctets Counter64,
            lcsStatusTcpIpRadiussAccntComplAccntSessEntryOutputOctets Counter64,
            lcsStatusTcpIpRadiussAccntComplAccntSessEntryIpAddress IpAddress,
            lcsStatusTcpIpRadiussAccntComplAccntSessEntryStartTime DisplayString,
            lcsStatusTcpIpRadiussAccntComplAccntSessEntryStopTime DisplayString,
            lcsStatusTcpIpRadiussAccntComplAccntSessEntryTerminateCause INTEGER,
            lcsStatusTcpIpRadiussAccntComplAccntSessEntryNasPortType INTEGER,
            lcsStatusTcpIpRadiussAccntComplAccntSessEntryNasPortId Integer32,
            lcsStatusTcpIpRadiussAccntComplAccntSessEntryCalledStationId DisplayString,
            lcsStatusTcpIpRadiussAccntComplAccntSessEntryCallingStationId DisplayString,
            lcsStatusTcpIpRadiussAccntComplAccntSessEntryNasIpv6Address IpAddress
    }

-- {COLUMN} 1.3.6.1.4.1.2356.11.1.9.12.2.17.1.1
lcsStatusTcpIpRadiussAccntComplAccntSessEntryIndex OBJECT-TYPE
    SYNTAX     Integer32 (0..2147483647)
    MAX-ACCESS read-only
    STATUS     current
    DESCRIPTION
            ""
    ::= { lcsStatusTcpIpRadiussAccntComplAccntSessEntry 1 }

-- {COLUMN} 1.3.6.1.4.1.2356.11.1.9.12.2.17.1.2
lcsStatusTcpIpRadiussAccntComplAccntSessEntryNasIpAddress OBJECT-TYPE
    SYNTAX     IpAddress
    MAX-ACCESS read-only
    STATUS     current
    DESCRIPTION
            ""
    ::= { lcsStatusTcpIpRadiussAccntComplAccntSessEntry 2 }

-- {COLUMN} 1.3.6.1.4.1.2356.11.1.9.12.2.17.1.3
lcsStatusTcpIpRadiussAccntComplAccntSessEntryNasIdent OBJECT-TYPE
    SYNTAX     DisplayString (SIZE(0..64))
    MAX-ACCESS read-only
    STATUS     current
    DESCRIPTION
            ""
    ::= { lcsStatusTcpIpRadiussAccntComplAccntSessEntry 3 }

-- {COLUMN} 1.3.6.1.4.1.2356.11.1.9.12.2.17.1.4
lcsStatusTcpIpRadiussAccntComplAccntSessEntrySessionId OBJECT-TYPE
    SYNTAX     DisplayString (SIZE(0..128))
    MAX-ACCESS read-only
    STATUS     current
    DESCRIPTION
            ""
    ::= { lcsStatusTcpIpRadiussAccntComplAccntSessEntry 4 }

-- {COLUMN} 1.3.6.1.4.1.2356.11.1.9.12.2.17.1.5
lcsStatusTcpIpRadiussAccntComplAccntSessEntryUserName OBJECT-TYPE
    SYNTAX     DisplayString (SIZE(0..48))
    MAX-ACCESS read-only
    STATUS     current
    DESCRIPTION
            ""
    ::= { lcsStatusTcpIpRadiussAccntComplAccntSessEntry 5 }

-- {COLUMN} 1.3.6.1.4.1.2356.11.1.9.12.2.17.1.6
lcsStatusTcpIpRadiussAccntComplAccntSessEntrySessionTime OBJECT-TYPE
    SYNTAX     Integer32 (0..2147483647)
    MAX-ACCESS read-only
    STATUS     current
    DESCRIPTION
            ""
    ::= { lcsStatusTcpIpRadiussAccntComplAccntSessEntry 6 }

-- {COLUMN} 1.3.6.1.4.1.2356.11.1.9.12.2.17.1.7
lcsStatusTcpIpRadiussAccntComplAccntSessEntryInputPackets OBJECT-TYPE
    SYNTAX     Counter32
    MAX-ACCESS read-only
    STATUS     current
    DESCRIPTION
            ""
    ::= { lcsStatusTcpIpRadiussAccntComplAccntSessEntry 7 }

-- {COLUMN} 1.3.6.1.4.1.2356.11.1.9.12.2.17.1.8
lcsStatusTcpIpRadiussAccntComplAccntSessEntryOutputPackets OBJECT-TYPE
    SYNTAX     Counter32
    MAX-ACCESS read-only
    STATUS     current
    DESCRIPTION
            ""
    ::= { lcsStatusTcpIpRadiussAccntComplAccntSessEntry 8 }

-- {COLUMN} 1.3.6.1.4.1.2356.11.1.9.12.2.17.1.9
lcsStatusTcpIpRadiussAccntComplAccntSessEntryInputOctets OBJECT-TYPE
    SYNTAX     Counter64
    MAX-ACCESS read-only
    STATUS     current
    DESCRIPTION
            ""
    ::= { lcsStatusTcpIpRadiussAccntComplAccntSessEntry 9 }

-- {COLUMN} 1.3.6.1.4.1.2356.11.1.9.12.2.17.1.10
lcsStatusTcpIpRadiussAccntComplAccntSessEntryOutputOctets OBJECT-TYPE
    SYNTAX     Counter64
    MAX-ACCESS read-only
    STATUS     current
    DESCRIPTION
            ""
    ::= { lcsStatusTcpIpRadiussAccntComplAccntSessEntry 10 }

-- {COLUMN} 1.3.6.1.4.1.2356.11.1.9.12.2.17.1.11
lcsStatusTcpIpRadiussAccntComplAccntSessEntryIpAddress OBJECT-TYPE
    SYNTAX     IpAddress
    MAX-ACCESS read-only
    STATUS     current
    DESCRIPTION
            ""
    ::= { lcsStatusTcpIpRadiussAccntComplAccntSessEntry 11 }

-- {COLUMN} 1.3.6.1.4.1.2356.11.1.9.12.2.17.1.12
lcsStatusTcpIpRadiussAccntComplAccntSessEntryStartTime OBJECT-TYPE
    SYNTAX     DisplayString (SIZE(0..19))
    MAX-ACCESS read-only
    STATUS     current
    DESCRIPTION
            ""
    ::= { lcsStatusTcpIpRadiussAccntComplAccntSessEntry 12 }

-- {COLUMN} 1.3.6.1.4.1.2356.11.1.9.12.2.17.1.13
lcsStatusTcpIpRadiussAccntComplAccntSessEntryStopTime OBJECT-TYPE
    SYNTAX     DisplayString (SIZE(0..19))
    MAX-ACCESS read-only
    STATUS     current
    DESCRIPTION
            ""
    ::= { lcsStatusTcpIpRadiussAccntComplAccntSessEntry 13 }

-- {COLUMN} 1.3.6.1.4.1.2356.11.1.9.12.2.17.1.14
lcsStatusTcpIpRadiussAccntComplAccntSessEntryTerminateCause OBJECT-TYPE
    SYNTAX     INTEGER {
                  eUserRequest (1),
                  eLostCarrier (2),
                  eLostService (3),
                  eIdleTimeout (4),
                  eSessionTimeout (5),
                  eAdminReset (6),
                  eAdminReboot (7),
                  ePortError (8),
                  eNasError (9),
                  eNasRequest (10),
                  eNasReboot (11),
                  ePortUnneeded (12),
                  ePortPreempted (13),
                  ePortSuspended (14),
                  eServiceUnavailable (15),
                  eCallback (16),
                  eUserError (17),
                  eHostRequest (18),
                  eSupplicantRestart (19),
                  eReauthenticationFailure (20),
                  ePortReinit (21),
                  ePortAdminDisabled (22)
            }
    MAX-ACCESS read-only
    STATUS     current
    DESCRIPTION
            ""
    ::= { lcsStatusTcpIpRadiussAccntComplAccntSessEntry 14 }

-- {COLUMN} 1.3.6.1.4.1.2356.11.1.9.12.2.17.1.17
lcsStatusTcpIpRadiussAccntComplAccntSessEntryNasPortType OBJECT-TYPE
    SYNTAX     INTEGER {
                  eUnknown (-1),
                  eAsync (0),
                  eSync (1),
                  eIsdnSync (2),
                  eV120 (3),
                  eV110 (4),
                  eVirtual (5),
                  ePiafs (6),
                  eHdlcClearChannel (7),
                  eX25 (8),
                  eX75 (9),
                  eG3Fax (10),
                  eSdsl (11),
                  eAdslCap (12),
                  eAdslDmt (13),
                  eIdsl (14),
                  eEthernet (15),
                  eXdsl (16),
                  eCable (17),
                  eWirelessOther (18),
                  eWireless80211 (19),
                  eTokenRing (20),
                  eFddi (21),
                  eWirelessCdma2000 (22),
                  eWirelessUmts (23),
                  eWireless1xEv (24),
                  eIapp (25),
                  eFttp (26),
                  eWireless80216 (27),
                  eWireless80220 (28),
                  eWireless80222 (29),
                  ePppoa (30),
                  ePppoeoa (31),
                  ePppoeoe (32),
                  ePppoeovlan (33),
                  ePppoeoqinq (34),
                  eXpon (35)
            }
    MAX-ACCESS read-only
    STATUS     current
    DESCRIPTION
            ""
    ::= { lcsStatusTcpIpRadiussAccntComplAccntSessEntry 17 }

-- {COLUMN} 1.3.6.1.4.1.2356.11.1.9.12.2.17.1.18
lcsStatusTcpIpRadiussAccntComplAccntSessEntryNasPortId OBJECT-TYPE
    SYNTAX     Integer32 (0..2147483647)
    MAX-ACCESS read-only
    STATUS     current
    DESCRIPTION
            ""
    ::= { lcsStatusTcpIpRadiussAccntComplAccntSessEntry 18 }

-- {COLUMN} 1.3.6.1.4.1.2356.11.1.9.12.2.17.1.19
lcsStatusTcpIpRadiussAccntComplAccntSessEntryCalledStationId OBJECT-TYPE
    SYNTAX     DisplayString (SIZE(0..48))
    MAX-ACCESS read-only
    STATUS     current
    DESCRIPTION
            ""
    ::= { lcsStatusTcpIpRadiussAccntComplAccntSessEntry 19 }

-- {COLUMN} 1.3.6.1.4.1.2356.11.1.9.12.2.17.1.20
lcsStatusTcpIpRadiussAccntComplAccntSessEntryCallingStationId OBJECT-TYPE
    SYNTAX     DisplayString (SIZE(0..48))
    MAX-ACCESS read-only
    STATUS     current
    DESCRIPTION
            ""
    ::= { lcsStatusTcpIpRadiussAccntComplAccntSessEntry 20 }

-- {COLUMN} 1.3.6.1.4.1.2356.11.1.9.12.2.17.1.21
lcsStatusTcpIpRadiussAccntComplAccntSessEntryNasIpv6Address OBJECT-TYPE
    SYNTAX     IpAddress
    MAX-ACCESS read-only
    STATUS     current
    DESCRIPTION
            "-- empty --"
    ::= { lcsStatusTcpIpRadiussAccntComplAccntSessEntry 21 }

-- {TABLE} 1.3.6.1.4.1.2356.11.1.9.12.2.18
lcsStatusTcpIpRadiussAccntAccountingTotalTable OBJECT-TYPE
    SYNTAX     SEQUENCE OF LcsStatusTcpIpRadiussAccntAccountingTotalEntry
    MAX-ACCESS not-accessible
    STATUS     current
    DESCRIPTION
            ""
    ::= { lcsStatusTcpIpRadiussAccnt 18 }

-- {ROW} 1.3.6.1.4.1.2356.11.1.9.12.2.18.1
lcsStatusTcpIpRadiussAccntAccountingTotalEntry OBJECT-TYPE
    SYNTAX     LcsStatusTcpIpRadiussAccntAccountingTotalEntry
    MAX-ACCESS not-accessible
    STATUS     current
    DESCRIPTION
            ""
    INDEX {
            lcsStatusTcpIpRadiussAccntAccountingTotalEntryUserName
          }
    ::= { lcsStatusTcpIpRadiussAccntAccountingTotalTable 1 }

LcsStatusTcpIpRadiussAccntAccountingTotalEntry ::= SEQUENCE {
            lcsStatusTcpIpRadiussAccntAccountingTotalEntryUserName DisplayString,
            lcsStatusTcpIpRadiussAccntAccountingTotalEntryTime Integer32,
            lcsStatusTcpIpRadiussAccntAccountingTotalEntryInputPackets Integer32,
            lcsStatusTcpIpRadiussAccntAccountingTotalEntryOutputPackets Integer32,
            lcsStatusTcpIpRadiussAccntAccountingTotalEntryInputOctets Integer32,
            lcsStatusTcpIpRadiussAccntAccountingTotalEntryOutputOctets Integer32,
            lcsStatusTcpIpRadiussAccntAccountingTotalEntryFirstLogin DisplayString
    }

-- {COLUMN} 1.3.6.1.4.1.2356.11.1.9.12.2.18.1.1
lcsStatusTcpIpRadiussAccntAccountingTotalEntryUserName OBJECT-TYPE
    SYNTAX     DisplayString (SIZE(0..48))
    MAX-ACCESS read-only
    STATUS     current
    DESCRIPTION
            ""
    ::= { lcsStatusTcpIpRadiussAccntAccountingTotalEntry 1 }

-- {COLUMN} 1.3.6.1.4.1.2356.11.1.9.12.2.18.1.2
lcsStatusTcpIpRadiussAccntAccountingTotalEntryTime OBJECT-TYPE
    SYNTAX     Integer32 (0..2147483647)
    MAX-ACCESS read-only
    STATUS     current
    DESCRIPTION
            ""
    ::= { lcsStatusTcpIpRadiussAccntAccountingTotalEntry 2 }

-- {COLUMN} 1.3.6.1.4.1.2356.11.1.9.12.2.18.1.3
lcsStatusTcpIpRadiussAccntAccountingTotalEntryInputPackets OBJECT-TYPE
    SYNTAX     Integer32 (0..2147483647)
    MAX-ACCESS read-only
    STATUS     current
    DESCRIPTION
            ""
    ::= { lcsStatusTcpIpRadiussAccntAccountingTotalEntry 3 }

-- {COLUMN} 1.3.6.1.4.1.2356.11.1.9.12.2.18.1.4
lcsStatusTcpIpRadiussAccntAccountingTotalEntryOutputPackets OBJECT-TYPE
    SYNTAX     Integer32 (0..2147483647)
    MAX-ACCESS read-only
    STATUS     current
    DESCRIPTION
            ""
    ::= { lcsStatusTcpIpRadiussAccntAccountingTotalEntry 4 }

-- {COLUMN} 1.3.6.1.4.1.2356.11.1.9.12.2.18.1.5
lcsStatusTcpIpRadiussAccntAccountingTotalEntryInputOctets OBJECT-TYPE
    SYNTAX     Integer32 (0..2147483647)
    MAX-ACCESS read-only
    STATUS     current
    DESCRIPTION
            ""
    ::= { lcsStatusTcpIpRadiussAccntAccountingTotalEntry 5 }

-- {COLUMN} 1.3.6.1.4.1.2356.11.1.9.12.2.18.1.6
lcsStatusTcpIpRadiussAccntAccountingTotalEntryOutputOctets OBJECT-TYPE
    SYNTAX     Integer32 (0..2147483647)
    MAX-ACCESS read-only
    STATUS     current
    DESCRIPTION
            ""
    ::= { lcsStatusTcpIpRadiussAccntAccountingTotalEntry 6 }

-- {COLUMN} 1.3.6.1.4.1.2356.11.1.9.12.2.18.1.7
lcsStatusTcpIpRadiussAccntAccountingTotalEntryFirstLogin OBJECT-TYPE
    SYNTAX     DisplayString (SIZE(0..21))
    MAX-ACCESS read-only
    STATUS     current
    DESCRIPTION
            ""
    ::= { lcsStatusTcpIpRadiussAccntAccountingTotalEntry 7 }

-- {SCALAR} 1.3.6.1.4.1.2356.11.1.9.12.2.19
lcsStatusTcpIpRadiussAccntDeleteAccountingTotal OBJECT-TYPE
    SYNTAX     DisplayString
    MAX-ACCESS read-write
    STATUS     current
    DESCRIPTION
            ""
    ::= { lcsStatusTcpIpRadiussAccnt 19 }

-- {TABLE} 1.3.6.1.4.1.2356.11.1.9.12.2.20
lcsStatusTcpIpRadiussAccntIpv6ClientsTable OBJECT-TYPE
    SYNTAX     SEQUENCE OF LcsStatusTcpIpRadiussAccntIpv6ClientsEntry
    MAX-ACCESS not-accessible
    STATUS     current
    DESCRIPTION
            "-- empty --"
    ::= { lcsStatusTcpIpRadiussAccnt 20 }

-- {ROW} 1.3.6.1.4.1.2356.11.1.9.12.2.20.1
lcsStatusTcpIpRadiussAccntIpv6ClientsEntry OBJECT-TYPE
    SYNTAX     LcsStatusTcpIpRadiussAccntIpv6ClientsEntry
    MAX-ACCESS not-accessible
    STATUS     current
    DESCRIPTION
            ""
    INDEX {
            lcsStatusTcpIpRadiussAccntIpv6ClientsEntryIpAddress
          }
    ::= { lcsStatusTcpIpRadiussAccntIpv6ClientsTable 1 }

LcsStatusTcpIpRadiussAccntIpv6ClientsEntry ::= SEQUENCE {
            lcsStatusTcpIpRadiussAccntIpv6ClientsEntryIpAddress IpAddress,
            lcsStatusTcpIpRadiussAccntIpv6ClientsEntryAccountRequests Counter32,
            lcsStatusTcpIpRadiussAccntIpv6ClientsEntryDuplicateRequests Counter32,
            lcsStatusTcpIpRadiussAccntIpv6ClientsEntryAccountResponses Counter32,
            lcsStatusTcpIpRadiussAccntIpv6ClientsEntryAccountNorecords Counter32,
            lcsStatusTcpIpRadiussAccntIpv6ClientsEntryMalfAccReq Counter32,
            lcsStatusTcpIpRadiussAccntIpv6ClientsEntryBadAuthenticator Counter32,
            lcsStatusTcpIpRadiussAccntIpv6ClientsEntryDropped Counter32,
            lcsStatusTcpIpRadiussAccntIpv6ClientsEntryUnknownType Counter32,
            lcsStatusTcpIpRadiussAccntIpv6ClientsEntryLastRequest Integer32,
            lcsStatusTcpIpRadiussAccntIpv6ClientsEntryNasIdent DisplayString,
            lcsStatusTcpIpRadiussAccntIpv6ClientsEntryStatusRequests Counter32,
            lcsStatusTcpIpRadiussAccntIpv6ClientsEntryStatusResponses Counter32,
            lcsStatusTcpIpRadiussAccntIpv6ClientsEntryLastStatusRequest Integer32
    }

-- {COLUMN} 1.3.6.1.4.1.2356.11.1.9.12.2.20.1.1
lcsStatusTcpIpRadiussAccntIpv6ClientsEntryIpAddress OBJECT-TYPE
    SYNTAX     IpAddress
    MAX-ACCESS read-only
    STATUS     current
    DESCRIPTION
            "-- empty --"
    ::= { lcsStatusTcpIpRadiussAccntIpv6ClientsEntry 1 }

-- {COLUMN} 1.3.6.1.4.1.2356.11.1.9.12.2.20.1.4
lcsStatusTcpIpRadiussAccntIpv6ClientsEntryAccountRequests OBJECT-TYPE
    SYNTAX     Counter32
    MAX-ACCESS read-only
    STATUS     current
    DESCRIPTION
            "-- empty --"
    ::= { lcsStatusTcpIpRadiussAccntIpv6ClientsEntry 4 }

-- {COLUMN} 1.3.6.1.4.1.2356.11.1.9.12.2.20.1.5
lcsStatusTcpIpRadiussAccntIpv6ClientsEntryDuplicateRequests OBJECT-TYPE
    SYNTAX     Counter32
    MAX-ACCESS read-only
    STATUS     current
    DESCRIPTION
            "-- empty --"
    ::= { lcsStatusTcpIpRadiussAccntIpv6ClientsEntry 5 }

-- {COLUMN} 1.3.6.1.4.1.2356.11.1.9.12.2.20.1.6
lcsStatusTcpIpRadiussAccntIpv6ClientsEntryAccountResponses OBJECT-TYPE
    SYNTAX     Counter32
    MAX-ACCESS read-only
    STATUS     current
    DESCRIPTION
            "-- empty --"
    ::= { lcsStatusTcpIpRadiussAccntIpv6ClientsEntry 6 }

-- {COLUMN} 1.3.6.1.4.1.2356.11.1.9.12.2.20.1.7
lcsStatusTcpIpRadiussAccntIpv6ClientsEntryAccountNorecords OBJECT-TYPE
    SYNTAX     Counter32
    MAX-ACCESS read-only
    STATUS     current
    DESCRIPTION
            "-- empty --"
    ::= { lcsStatusTcpIpRadiussAccntIpv6ClientsEntry 7 }

-- {COLUMN} 1.3.6.1.4.1.2356.11.1.9.12.2.20.1.9
lcsStatusTcpIpRadiussAccntIpv6ClientsEntryMalfAccReq OBJECT-TYPE
    SYNTAX     Counter32
    MAX-ACCESS read-only
    STATUS     current
    DESCRIPTION
            ""
    ::= { lcsStatusTcpIpRadiussAccntIpv6ClientsEntry 9 }

-- {COLUMN} 1.3.6.1.4.1.2356.11.1.9.12.2.20.1.10
lcsStatusTcpIpRadiussAccntIpv6ClientsEntryBadAuthenticator OBJECT-TYPE
    SYNTAX     Counter32
    MAX-ACCESS read-only
    STATUS     current
    DESCRIPTION
            "-- empty --"
    ::= { lcsStatusTcpIpRadiussAccntIpv6ClientsEntry 10 }

-- {COLUMN} 1.3.6.1.4.1.2356.11.1.9.12.2.20.1.11
lcsStatusTcpIpRadiussAccntIpv6ClientsEntryDropped OBJECT-TYPE
    SYNTAX     Counter32
    MAX-ACCESS read-only
    STATUS     current
    DESCRIPTION
            "-- empty --"
    ::= { lcsStatusTcpIpRadiussAccntIpv6ClientsEntry 11 }

-- {COLUMN} 1.3.6.1.4.1.2356.11.1.9.12.2.20.1.12
lcsStatusTcpIpRadiussAccntIpv6ClientsEntryUnknownType OBJECT-TYPE
    SYNTAX     Counter32
    MAX-ACCESS read-only
    STATUS     current
    DESCRIPTION
            "-- empty --"
    ::= { lcsStatusTcpIpRadiussAccntIpv6ClientsEntry 12 }

-- {COLUMN} 1.3.6.1.4.1.2356.11.1.9.12.2.20.1.13
lcsStatusTcpIpRadiussAccntIpv6ClientsEntryLastRequest OBJECT-TYPE
    SYNTAX     Integer32 (0..2147483647)
    MAX-ACCESS read-only
    STATUS     current
    DESCRIPTION
            "-- empty --"
    ::= { lcsStatusTcpIpRadiussAccntIpv6ClientsEntry 13 }

-- {COLUMN} 1.3.6.1.4.1.2356.11.1.9.12.2.20.1.14
lcsStatusTcpIpRadiussAccntIpv6ClientsEntryNasIdent OBJECT-TYPE
    SYNTAX     DisplayString (SIZE(0..64))
    MAX-ACCESS read-only
    STATUS     current
    DESCRIPTION
            "-- empty --"
    ::= { lcsStatusTcpIpRadiussAccntIpv6ClientsEntry 14 }

-- {COLUMN} 1.3.6.1.4.1.2356.11.1.9.12.2.20.1.30
lcsStatusTcpIpRadiussAccntIpv6ClientsEntryStatusRequests OBJECT-TYPE
    SYNTAX     Counter32
    MAX-ACCESS read-only
    STATUS     current
    DESCRIPTION
            "-- empty --"
    ::= { lcsStatusTcpIpRadiussAccntIpv6ClientsEntry 30 }

-- {COLUMN} 1.3.6.1.4.1.2356.11.1.9.12.2.20.1.31
lcsStatusTcpIpRadiussAccntIpv6ClientsEntryStatusResponses OBJECT-TYPE
    SYNTAX     Counter32
    MAX-ACCESS read-only
    STATUS     current
    DESCRIPTION
            "-- empty --"
    ::= { lcsStatusTcpIpRadiussAccntIpv6ClientsEntry 31 }

-- {COLUMN} 1.3.6.1.4.1.2356.11.1.9.12.2.20.1.32
lcsStatusTcpIpRadiussAccntIpv6ClientsEntryLastStatusRequest OBJECT-TYPE
    SYNTAX     Integer32 (0..2147483647)
    MAX-ACCESS read-only
    STATUS     current
    DESCRIPTION
            "-- empty --"
    ::= { lcsStatusTcpIpRadiussAccntIpv6ClientsEntry 32 }

-- {SCALAR} 1.3.6.1.4.1.2356.11.1.9.12.2.30
lcsStatusTcpIpRadiussAccntTotalStatusRequests OBJECT-TYPE
    SYNTAX     Counter32
    MAX-ACCESS read-only
    STATUS     current
    DESCRIPTION
            ""
    ::= { lcsStatusTcpIpRadiussAccnt 30 }

-- {SCALAR} 1.3.6.1.4.1.2356.11.1.9.12.2.31
lcsStatusTcpIpRadiussAccntTotalStatusResponses OBJECT-TYPE
    SYNTAX     Counter32
    MAX-ACCESS read-only
    STATUS     current
    DESCRIPTION
            ""
    ::= { lcsStatusTcpIpRadiussAccnt 31 }

-- {SCALAR} 1.3.6.1.4.1.2356.11.1.9.12.2.32
lcsStatusTcpIpRadiussAccntIpv4WanDiscards OBJECT-TYPE
    SYNTAX     Counter32
    MAX-ACCESS read-only
    STATUS     current
    DESCRIPTION
            "-- empty --"
    ::= { lcsStatusTcpIpRadiussAccnt 32 }

-- {SCALAR} 1.3.6.1.4.1.2356.11.1.9.12.2.100
lcsStatusTcpIpRadiussAccntDeleteValues OBJECT-TYPE
    SYNTAX     DisplayString
    MAX-ACCESS read-write
    STATUS     current
    DESCRIPTION
            ""
    ::= { lcsStatusTcpIpRadiussAccnt 100 }

-- {TABLE} 1.3.6.1.4.1.2356.11.1.9.12.10
lcsStatusTcpIpRadiussLogTableTable OBJECT-TYPE
    SYNTAX     SEQUENCE OF LcsStatusTcpIpRadiussLogTableEntry
    MAX-ACCESS not-accessible
    STATUS     current
    DESCRIPTION
            ""
    ::= { lcsStatusTcpIpRadiuss 10 }

-- {ROW} 1.3.6.1.4.1.2356.11.1.9.12.10.1
lcsStatusTcpIpRadiussLogTableEntry OBJECT-TYPE
    SYNTAX     LcsStatusTcpIpRadiussLogTableEntry
    MAX-ACCESS not-accessible
    STATUS     current
    DESCRIPTION
            ""
    INDEX {
            lcsStatusTcpIpRadiussLogTableEntryIndex
          }
    ::= { lcsStatusTcpIpRadiussLogTableTable 1 }

LcsStatusTcpIpRadiussLogTableEntry ::= SEQUENCE {
            lcsStatusTcpIpRadiussLogTableEntryIndex Integer32,
            lcsStatusTcpIpRadiussLogTableEntryTime DisplayString,
            lcsStatusTcpIpRadiussLogTableEntryEvent DisplayString
    }

-- {COLUMN} 1.3.6.1.4.1.2356.11.1.9.12.10.1.1
lcsStatusTcpIpRadiussLogTableEntryIndex OBJECT-TYPE
    SYNTAX     Integer32 (0..2147483647)
    MAX-ACCESS read-only
    STATUS     current
    DESCRIPTION
            ""
    ::= { lcsStatusTcpIpRadiussLogTableEntry 1 }

-- {COLUMN} 1.3.6.1.4.1.2356.11.1.9.12.10.1.2
lcsStatusTcpIpRadiussLogTableEntryTime OBJECT-TYPE
    SYNTAX     DisplayString (SIZE(0..21))
    MAX-ACCESS read-only
    STATUS     current
    DESCRIPTION
            ""
    ::= { lcsStatusTcpIpRadiussLogTableEntry 2 }

-- {COLUMN} 1.3.6.1.4.1.2356.11.1.9.12.10.1.3
lcsStatusTcpIpRadiussLogTableEntryEvent OBJECT-TYPE
    SYNTAX     DisplayString (SIZE(0..128))
    MAX-ACCESS read-only
    STATUS     current
    DESCRIPTION
            ""
    ::= { lcsStatusTcpIpRadiussLogTableEntry 3 }

-- {SCALAR} 1.3.6.1.4.1.2356.11.1.9.12.100
lcsStatusTcpIpRadiussDeleteValues OBJECT-TYPE
    SYNTAX     DisplayString
    MAX-ACCESS read-write
    STATUS     current
    DESCRIPTION
            ""
    ::= { lcsStatusTcpIpRadiuss 100 }

-- {NODE} 1.3.6.1.4.1.2356.11.1.9.13
lcsStatusTcpIpRadiusc OBJECT IDENTIFIER ::= { lcsStatusTcpIp 13 }

-- {SCALAR} 1.3.6.1.4.1.2356.11.1.9.13.1
lcsStatusTcpIpRadiuscInvalAuthAddrResp OBJECT-TYPE
    SYNTAX     Counter32
    MAX-ACCESS read-only
    STATUS     current
    DESCRIPTION
            ""
    ::= { lcsStatusTcpIpRadiusc 1 }

-- {TABLE} 1.3.6.1.4.1.2356.11.1.9.13.2
lcsStatusTcpIpRadiuscAuthServTable OBJECT-TYPE
    SYNTAX     SEQUENCE OF LcsStatusTcpIpRadiuscAuthServEntry
    MAX-ACCESS not-accessible
    STATUS     current
    DESCRIPTION
            ""
    ::= { lcsStatusTcpIpRadiusc 2 }

-- {ROW} 1.3.6.1.4.1.2356.11.1.9.13.2.1
lcsStatusTcpIpRadiuscAuthServEntry OBJECT-TYPE
    SYNTAX     LcsStatusTcpIpRadiuscAuthServEntry
    MAX-ACCESS not-accessible
    STATUS     current
    DESCRIPTION
            ""
    INDEX {
            lcsStatusTcpIpRadiuscAuthServEntryIpAddr,
            lcsStatusTcpIpRadiuscAuthServEntryPort
          }
    ::= { lcsStatusTcpIpRadiuscAuthServTable 1 }

LcsStatusTcpIpRadiuscAuthServEntry ::= SEQUENCE {
            lcsStatusTcpIpRadiuscAuthServEntryIpAddr IpAddress,
            lcsStatusTcpIpRadiuscAuthServEntryPort Integer32,
            lcsStatusTcpIpRadiuscAuthServEntryLastRequest Integer32,
            lcsStatusTcpIpRadiuscAuthServEntryRoundTripTime Counter32,
            lcsStatusTcpIpRadiuscAuthServEntryAccReq Counter32,
            lcsStatusTcpIpRadiuscAuthServEntryAccRetrs Counter32,
            lcsStatusTcpIpRadiuscAuthServEntryAccAccepts Counter32,
            lcsStatusTcpIpRadiuscAuthServEntryAccRej Counter32,
            lcsStatusTcpIpRadiuscAuthServEntryAccChallenges Counter32,
            lcsStatusTcpIpRadiuscAuthServEntryMalfAccResp Counter32,
            lcsStatusTcpIpRadiuscAuthServEntryBadAuth Counter32,
            lcsStatusTcpIpRadiuscAuthServEntryPendReq Counter32,
            lcsStatusTcpIpRadiuscAuthServEntryTimeouts Counter32,
            lcsStatusTcpIpRadiuscAuthServEntryUnknownTypes Counter32,
            lcsStatusTcpIpRadiuscAuthServEntryDropped Counter32
    }

-- {COLUMN} 1.3.6.1.4.1.2356.11.1.9.13.2.1.1
lcsStatusTcpIpRadiuscAuthServEntryIpAddr OBJECT-TYPE
    SYNTAX     IpAddress
    MAX-ACCESS read-only
    STATUS     current
    DESCRIPTION
            ""
    ::= { lcsStatusTcpIpRadiuscAuthServEntry 1 }

-- {COLUMN} 1.3.6.1.4.1.2356.11.1.9.13.2.1.2
lcsStatusTcpIpRadiuscAuthServEntryPort OBJECT-TYPE
    SYNTAX     Integer32 (0..65535)
    MAX-ACCESS read-only
    STATUS     current
    DESCRIPTION
            ""
    ::= { lcsStatusTcpIpRadiuscAuthServEntry 2 }

-- {COLUMN} 1.3.6.1.4.1.2356.11.1.9.13.2.1.3
lcsStatusTcpIpRadiuscAuthServEntryLastRequest OBJECT-TYPE
    SYNTAX     Integer32 (0..2147483647)
    MAX-ACCESS read-only
    STATUS     current
    DESCRIPTION
            ""
    ::= { lcsStatusTcpIpRadiuscAuthServEntry 3 }

-- {COLUMN} 1.3.6.1.4.1.2356.11.1.9.13.2.1.4
lcsStatusTcpIpRadiuscAuthServEntryRoundTripTime OBJECT-TYPE
    SYNTAX     Counter32
    MAX-ACCESS read-only
    STATUS     current
    DESCRIPTION
            ""
    ::= { lcsStatusTcpIpRadiuscAuthServEntry 4 }

-- {COLUMN} 1.3.6.1.4.1.2356.11.1.9.13.2.1.5
lcsStatusTcpIpRadiuscAuthServEntryAccReq OBJECT-TYPE
    SYNTAX     Counter32
    MAX-ACCESS read-only
    STATUS     current
    DESCRIPTION
            ""
    ::= { lcsStatusTcpIpRadiuscAuthServEntry 5 }

-- {COLUMN} 1.3.6.1.4.1.2356.11.1.9.13.2.1.6
lcsStatusTcpIpRadiuscAuthServEntryAccRetrs OBJECT-TYPE
    SYNTAX     Counter32
    MAX-ACCESS read-only
    STATUS     current
    DESCRIPTION
            ""
    ::= { lcsStatusTcpIpRadiuscAuthServEntry 6 }

-- {COLUMN} 1.3.6.1.4.1.2356.11.1.9.13.2.1.7
lcsStatusTcpIpRadiuscAuthServEntryAccAccepts OBJECT-TYPE
    SYNTAX     Counter32
    MAX-ACCESS read-only
    STATUS     current
    DESCRIPTION
            ""
    ::= { lcsStatusTcpIpRadiuscAuthServEntry 7 }

-- {COLUMN} 1.3.6.1.4.1.2356.11.1.9.13.2.1.8
lcsStatusTcpIpRadiuscAuthServEntryAccRej OBJECT-TYPE
    SYNTAX     Counter32
    MAX-ACCESS read-only
    STATUS     current
    DESCRIPTION
            ""
    ::= { lcsStatusTcpIpRadiuscAuthServEntry 8 }

-- {COLUMN} 1.3.6.1.4.1.2356.11.1.9.13.2.1.9
lcsStatusTcpIpRadiuscAuthServEntryAccChallenges OBJECT-TYPE
    SYNTAX     Counter32
    MAX-ACCESS read-only
    STATUS     current
    DESCRIPTION
            ""
    ::= { lcsStatusTcpIpRadiuscAuthServEntry 9 }

-- {COLUMN} 1.3.6.1.4.1.2356.11.1.9.13.2.1.10
lcsStatusTcpIpRadiuscAuthServEntryMalfAccResp OBJECT-TYPE
    SYNTAX     Counter32
    MAX-ACCESS read-only
    STATUS     current
    DESCRIPTION
            ""
    ::= { lcsStatusTcpIpRadiuscAuthServEntry 10 }

-- {COLUMN} 1.3.6.1.4.1.2356.11.1.9.13.2.1.11
lcsStatusTcpIpRadiuscAuthServEntryBadAuth OBJECT-TYPE
    SYNTAX     Counter32
    MAX-ACCESS read-only
    STATUS     current
    DESCRIPTION
            ""
    ::= { lcsStatusTcpIpRadiuscAuthServEntry 11 }

-- {COLUMN} 1.3.6.1.4.1.2356.11.1.9.13.2.1.12
lcsStatusTcpIpRadiuscAuthServEntryPendReq OBJECT-TYPE
    SYNTAX     Counter32
    MAX-ACCESS read-only
    STATUS     current
    DESCRIPTION
            ""
    ::= { lcsStatusTcpIpRadiuscAuthServEntry 12 }

-- {COLUMN} 1.3.6.1.4.1.2356.11.1.9.13.2.1.13
lcsStatusTcpIpRadiuscAuthServEntryTimeouts OBJECT-TYPE
    SYNTAX     Counter32
    MAX-ACCESS read-only
    STATUS     current
    DESCRIPTION
            ""
    ::= { lcsStatusTcpIpRadiuscAuthServEntry 13 }

-- {COLUMN} 1.3.6.1.4.1.2356.11.1.9.13.2.1.14
lcsStatusTcpIpRadiuscAuthServEntryUnknownTypes OBJECT-TYPE
    SYNTAX     Counter32
    MAX-ACCESS read-only
    STATUS     current
    DESCRIPTION
            ""
    ::= { lcsStatusTcpIpRadiuscAuthServEntry 14 }

-- {COLUMN} 1.3.6.1.4.1.2356.11.1.9.13.2.1.15
lcsStatusTcpIpRadiuscAuthServEntryDropped OBJECT-TYPE
    SYNTAX     Counter32
    MAX-ACCESS read-only
    STATUS     current
    DESCRIPTION
            ""
    ::= { lcsStatusTcpIpRadiuscAuthServEntry 15 }

-- {TABLE} 1.3.6.1.4.1.2356.11.1.9.13.3
lcsStatusTcpIpRadiuscIpv6AuthenticationServersTable OBJECT-TYPE
    SYNTAX     SEQUENCE OF LcsStatusTcpIpRadiuscIpv6AuthenticationServersEntry
    MAX-ACCESS not-accessible
    STATUS     current
    DESCRIPTION
            "-- empty --"
    ::= { lcsStatusTcpIpRadiusc 3 }

-- {ROW} 1.3.6.1.4.1.2356.11.1.9.13.3.1
lcsStatusTcpIpRadiuscIpv6AuthenticationServersEntry OBJECT-TYPE
    SYNTAX     LcsStatusTcpIpRadiuscIpv6AuthenticationServersEntry
    MAX-ACCESS not-accessible
    STATUS     current
    DESCRIPTION
            ""
    INDEX {
            lcsStatusTcpIpRadiuscIpv6AuthenticationServersEntryIpAddr,
            lcsStatusTcpIpRadiuscIpv6AuthenticationServersEntryPort
          }
    ::= { lcsStatusTcpIpRadiuscIpv6AuthenticationServersTable 1 }

LcsStatusTcpIpRadiuscIpv6AuthenticationServersEntry ::= SEQUENCE {
            lcsStatusTcpIpRadiuscIpv6AuthenticationServersEntryIpAddr IpAddress,
            lcsStatusTcpIpRadiuscIpv6AuthenticationServersEntryPort Integer32,
            lcsStatusTcpIpRadiuscIpv6AuthenticationServersEntryLastRequest Integer32,
            lcsStatusTcpIpRadiuscIpv6AuthenticationServersEntryRoundTripTime Counter32,
            lcsStatusTcpIpRadiuscIpv6AuthenticationServersEntryAccReq Counter32,
            lcsStatusTcpIpRadiuscIpv6AuthenticationServersEntryAccRetrs Counter32,
            lcsStatusTcpIpRadiuscIpv6AuthenticationServersEntryAccAccepts Counter32,
            lcsStatusTcpIpRadiuscIpv6AuthenticationServersEntryAccRej Counter32,
            lcsStatusTcpIpRadiuscIpv6AuthenticationServersEntryAccChallenges Counter32,
            lcsStatusTcpIpRadiuscIpv6AuthenticationServersEntryMalfAccResp Counter32,
            lcsStatusTcpIpRadiuscIpv6AuthenticationServersEntryBadAuth Counter32,
            lcsStatusTcpIpRadiuscIpv6AuthenticationServersEntryPendReq Counter32,
            lcsStatusTcpIpRadiuscIpv6AuthenticationServersEntryTimeouts Counter32,
            lcsStatusTcpIpRadiuscIpv6AuthenticationServersEntryUnknownTypes Counter32,
            lcsStatusTcpIpRadiuscIpv6AuthenticationServersEntryDropped Counter32
    }

-- {COLUMN} 1.3.6.1.4.1.2356.11.1.9.13.3.1.1
lcsStatusTcpIpRadiuscIpv6AuthenticationServersEntryIpAddr OBJECT-TYPE
    SYNTAX     IpAddress
    MAX-ACCESS read-only
    STATUS     current
    DESCRIPTION
            ""
    ::= { lcsStatusTcpIpRadiuscIpv6AuthenticationServersEntry 1 }

-- {COLUMN} 1.3.6.1.4.1.2356.11.1.9.13.3.1.2
lcsStatusTcpIpRadiuscIpv6AuthenticationServersEntryPort OBJECT-TYPE
    SYNTAX     Integer32 (0..65535)
    MAX-ACCESS read-only
    STATUS     current
    DESCRIPTION
            ""
    ::= { lcsStatusTcpIpRadiuscIpv6AuthenticationServersEntry 2 }

-- {COLUMN} 1.3.6.1.4.1.2356.11.1.9.13.3.1.3
lcsStatusTcpIpRadiuscIpv6AuthenticationServersEntryLastRequest OBJECT-TYPE
    SYNTAX     Integer32 (0..2147483647)
    MAX-ACCESS read-only
    STATUS     current
    DESCRIPTION
            ""
    ::= { lcsStatusTcpIpRadiuscIpv6AuthenticationServersEntry 3 }

-- {COLUMN} 1.3.6.1.4.1.2356.11.1.9.13.3.1.4
lcsStatusTcpIpRadiuscIpv6AuthenticationServersEntryRoundTripTime OBJECT-TYPE
    SYNTAX     Counter32
    MAX-ACCESS read-only
    STATUS     current
    DESCRIPTION
            ""
    ::= { lcsStatusTcpIpRadiuscIpv6AuthenticationServersEntry 4 }

-- {COLUMN} 1.3.6.1.4.1.2356.11.1.9.13.3.1.5
lcsStatusTcpIpRadiuscIpv6AuthenticationServersEntryAccReq OBJECT-TYPE
    SYNTAX     Counter32
    MAX-ACCESS read-only
    STATUS     current
    DESCRIPTION
            ""
    ::= { lcsStatusTcpIpRadiuscIpv6AuthenticationServersEntry 5 }

-- {COLUMN} 1.3.6.1.4.1.2356.11.1.9.13.3.1.6
lcsStatusTcpIpRadiuscIpv6AuthenticationServersEntryAccRetrs OBJECT-TYPE
    SYNTAX     Counter32
    MAX-ACCESS read-only
    STATUS     current
    DESCRIPTION
            ""
    ::= { lcsStatusTcpIpRadiuscIpv6AuthenticationServersEntry 6 }

-- {COLUMN} 1.3.6.1.4.1.2356.11.1.9.13.3.1.7
lcsStatusTcpIpRadiuscIpv6AuthenticationServersEntryAccAccepts OBJECT-TYPE
    SYNTAX     Counter32
    MAX-ACCESS read-only
    STATUS     current
    DESCRIPTION
            ""
    ::= { lcsStatusTcpIpRadiuscIpv6AuthenticationServersEntry 7 }

-- {COLUMN} 1.3.6.1.4.1.2356.11.1.9.13.3.1.8
lcsStatusTcpIpRadiuscIpv6AuthenticationServersEntryAccRej OBJECT-TYPE
    SYNTAX     Counter32
    MAX-ACCESS read-only
    STATUS     current
    DESCRIPTION
            ""
    ::= { lcsStatusTcpIpRadiuscIpv6AuthenticationServersEntry 8 }

-- {COLUMN} 1.3.6.1.4.1.2356.11.1.9.13.3.1.9
lcsStatusTcpIpRadiuscIpv6AuthenticationServersEntryAccChallenges OBJECT-TYPE
    SYNTAX     Counter32
    MAX-ACCESS read-only
    STATUS     current
    DESCRIPTION
            ""
    ::= { lcsStatusTcpIpRadiuscIpv6AuthenticationServersEntry 9 }

-- {COLUMN} 1.3.6.1.4.1.2356.11.1.9.13.3.1.10
lcsStatusTcpIpRadiuscIpv6AuthenticationServersEntryMalfAccResp OBJECT-TYPE
    SYNTAX     Counter32
    MAX-ACCESS read-only
    STATUS     current
    DESCRIPTION
            ""
    ::= { lcsStatusTcpIpRadiuscIpv6AuthenticationServersEntry 10 }

-- {COLUMN} 1.3.6.1.4.1.2356.11.1.9.13.3.1.11
lcsStatusTcpIpRadiuscIpv6AuthenticationServersEntryBadAuth OBJECT-TYPE
    SYNTAX     Counter32
    MAX-ACCESS read-only
    STATUS     current
    DESCRIPTION
            ""
    ::= { lcsStatusTcpIpRadiuscIpv6AuthenticationServersEntry 11 }

-- {COLUMN} 1.3.6.1.4.1.2356.11.1.9.13.3.1.12
lcsStatusTcpIpRadiuscIpv6AuthenticationServersEntryPendReq OBJECT-TYPE
    SYNTAX     Counter32
    MAX-ACCESS read-only
    STATUS     current
    DESCRIPTION
            ""
    ::= { lcsStatusTcpIpRadiuscIpv6AuthenticationServersEntry 12 }

-- {COLUMN} 1.3.6.1.4.1.2356.11.1.9.13.3.1.13
lcsStatusTcpIpRadiuscIpv6AuthenticationServersEntryTimeouts OBJECT-TYPE
    SYNTAX     Counter32
    MAX-ACCESS read-only
    STATUS     current
    DESCRIPTION
            ""
    ::= { lcsStatusTcpIpRadiuscIpv6AuthenticationServersEntry 13 }

-- {COLUMN} 1.3.6.1.4.1.2356.11.1.9.13.3.1.14
lcsStatusTcpIpRadiuscIpv6AuthenticationServersEntryUnknownTypes OBJECT-TYPE
    SYNTAX     Counter32
    MAX-ACCESS read-only
    STATUS     current
    DESCRIPTION
            ""
    ::= { lcsStatusTcpIpRadiuscIpv6AuthenticationServersEntry 14 }

-- {COLUMN} 1.3.6.1.4.1.2356.11.1.9.13.3.1.15
lcsStatusTcpIpRadiuscIpv6AuthenticationServersEntryDropped OBJECT-TYPE
    SYNTAX     Counter32
    MAX-ACCESS read-only
    STATUS     current
    DESCRIPTION
            ""
    ::= { lcsStatusTcpIpRadiuscIpv6AuthenticationServersEntry 15 }

-- {SCALAR} 1.3.6.1.4.1.2356.11.1.9.13.11
lcsStatusTcpIpRadiuscInvalAccntAddrResp OBJECT-TYPE
    SYNTAX     Counter32
    MAX-ACCESS read-only
    STATUS     current
    DESCRIPTION
            ""
    ::= { lcsStatusTcpIpRadiusc 11 }

-- {TABLE} 1.3.6.1.4.1.2356.11.1.9.13.12
lcsStatusTcpIpRadiuscAccntServTable OBJECT-TYPE
    SYNTAX     SEQUENCE OF LcsStatusTcpIpRadiuscAccntServEntry
    MAX-ACCESS not-accessible
    STATUS     current
    DESCRIPTION
            ""
    ::= { lcsStatusTcpIpRadiusc 12 }

-- {ROW} 1.3.6.1.4.1.2356.11.1.9.13.12.1
lcsStatusTcpIpRadiuscAccntServEntry OBJECT-TYPE
    SYNTAX     LcsStatusTcpIpRadiuscAccntServEntry
    MAX-ACCESS not-accessible
    STATUS     current
    DESCRIPTION
            ""
    INDEX {
            lcsStatusTcpIpRadiuscAccntServEntryIpAddr,
            lcsStatusTcpIpRadiuscAccntServEntryPort
          }
    ::= { lcsStatusTcpIpRadiuscAccntServTable 1 }

LcsStatusTcpIpRadiuscAccntServEntry ::= SEQUENCE {
            lcsStatusTcpIpRadiuscAccntServEntryIpAddr IpAddress,
            lcsStatusTcpIpRadiuscAccntServEntryPort Integer32,
            lcsStatusTcpIpRadiuscAccntServEntryLastRequest Integer32,
            lcsStatusTcpIpRadiuscAccntServEntryRoundTripTime Counter32,
            lcsStatusTcpIpRadiuscAccntServEntryAccntReq Counter32,
            lcsStatusTcpIpRadiuscAccntServEntryAccntRetrans Counter32,
            lcsStatusTcpIpRadiuscAccntServEntryAccntResp Counter32,
            lcsStatusTcpIpRadiuscAccntServEntryMalfAccntResp Counter32,
            lcsStatusTcpIpRadiuscAccntServEntryBadAuth Counter32,
            lcsStatusTcpIpRadiuscAccntServEntryPendReq Counter32,
            lcsStatusTcpIpRadiuscAccntServEntryTimeouts Counter32,
            lcsStatusTcpIpRadiuscAccntServEntryUnknownTypes Counter32,
            lcsStatusTcpIpRadiuscAccntServEntryDropped Counter32
    }

-- {COLUMN} 1.3.6.1.4.1.2356.11.1.9.13.12.1.1
lcsStatusTcpIpRadiuscAccntServEntryIpAddr OBJECT-TYPE
    SYNTAX     IpAddress
    MAX-ACCESS read-only
    STATUS     current
    DESCRIPTION
            ""
    ::= { lcsStatusTcpIpRadiuscAccntServEntry 1 }

-- {COLUMN} 1.3.6.1.4.1.2356.11.1.9.13.12.1.2
lcsStatusTcpIpRadiuscAccntServEntryPort OBJECT-TYPE
    SYNTAX     Integer32 (0..65535)
    MAX-ACCESS read-only
    STATUS     current
    DESCRIPTION
            ""
    ::= { lcsStatusTcpIpRadiuscAccntServEntry 2 }

-- {COLUMN} 1.3.6.1.4.1.2356.11.1.9.13.12.1.3
lcsStatusTcpIpRadiuscAccntServEntryLastRequest OBJECT-TYPE
    SYNTAX     Integer32 (0..2147483647)
    MAX-ACCESS read-only
    STATUS     current
    DESCRIPTION
            ""
    ::= { lcsStatusTcpIpRadiuscAccntServEntry 3 }

-- {COLUMN} 1.3.6.1.4.1.2356.11.1.9.13.12.1.4
lcsStatusTcpIpRadiuscAccntServEntryRoundTripTime OBJECT-TYPE
    SYNTAX     Counter32
    MAX-ACCESS read-only
    STATUS     current
    DESCRIPTION
            ""
    ::= { lcsStatusTcpIpRadiuscAccntServEntry 4 }

-- {COLUMN} 1.3.6.1.4.1.2356.11.1.9.13.12.1.5
lcsStatusTcpIpRadiuscAccntServEntryAccntReq OBJECT-TYPE
    SYNTAX     Counter32
    MAX-ACCESS read-only
    STATUS     current
    DESCRIPTION
            ""
    ::= { lcsStatusTcpIpRadiuscAccntServEntry 5 }

-- {COLUMN} 1.3.6.1.4.1.2356.11.1.9.13.12.1.6
lcsStatusTcpIpRadiuscAccntServEntryAccntRetrans OBJECT-TYPE
    SYNTAX     Counter32
    MAX-ACCESS read-only
    STATUS     current
    DESCRIPTION
            ""
    ::= { lcsStatusTcpIpRadiuscAccntServEntry 6 }

-- {COLUMN} 1.3.6.1.4.1.2356.11.1.9.13.12.1.7
lcsStatusTcpIpRadiuscAccntServEntryAccntResp OBJECT-TYPE
    SYNTAX     Counter32
    MAX-ACCESS read-only
    STATUS     current
    DESCRIPTION
            ""
    ::= { lcsStatusTcpIpRadiuscAccntServEntry 7 }

-- {COLUMN} 1.3.6.1.4.1.2356.11.1.9.13.12.1.8
lcsStatusTcpIpRadiuscAccntServEntryMalfAccntResp OBJECT-TYPE
    SYNTAX     Counter32
    MAX-ACCESS read-only
    STATUS     current
    DESCRIPTION
            ""
    ::= { lcsStatusTcpIpRadiuscAccntServEntry 8 }

-- {COLUMN} 1.3.6.1.4.1.2356.11.1.9.13.12.1.9
lcsStatusTcpIpRadiuscAccntServEntryBadAuth OBJECT-TYPE
    SYNTAX     Counter32
    MAX-ACCESS read-only
    STATUS     current
    DESCRIPTION
            ""
    ::= { lcsStatusTcpIpRadiuscAccntServEntry 9 }

-- {COLUMN} 1.3.6.1.4.1.2356.11.1.9.13.12.1.10
lcsStatusTcpIpRadiuscAccntServEntryPendReq OBJECT-TYPE
    SYNTAX     Counter32
    MAX-ACCESS read-only
    STATUS     current
    DESCRIPTION
            ""
    ::= { lcsStatusTcpIpRadiuscAccntServEntry 10 }

-- {COLUMN} 1.3.6.1.4.1.2356.11.1.9.13.12.1.11
lcsStatusTcpIpRadiuscAccntServEntryTimeouts OBJECT-TYPE
    SYNTAX     Counter32
    MAX-ACCESS read-only
    STATUS     current
    DESCRIPTION
            ""
    ::= { lcsStatusTcpIpRadiuscAccntServEntry 11 }

-- {COLUMN} 1.3.6.1.4.1.2356.11.1.9.13.12.1.12
lcsStatusTcpIpRadiuscAccntServEntryUnknownTypes OBJECT-TYPE
    SYNTAX     Counter32
    MAX-ACCESS read-only
    STATUS     current
    DESCRIPTION
            ""
    ::= { lcsStatusTcpIpRadiuscAccntServEntry 12 }

-- {COLUMN} 1.3.6.1.4.1.2356.11.1.9.13.12.1.13
lcsStatusTcpIpRadiuscAccntServEntryDropped OBJECT-TYPE
    SYNTAX     Counter32
    MAX-ACCESS read-only
    STATUS     current
    DESCRIPTION
            ""
    ::= { lcsStatusTcpIpRadiuscAccntServEntry 13 }

-- {TABLE} 1.3.6.1.4.1.2356.11.1.9.13.13
lcsStatusTcpIpRadiuscIpv6AccountingServersTable OBJECT-TYPE
    SYNTAX     SEQUENCE OF LcsStatusTcpIpRadiuscIpv6AccountingServersEntry
    MAX-ACCESS not-accessible
    STATUS     current
    DESCRIPTION
            "-- empty --"
    ::= { lcsStatusTcpIpRadiusc 13 }

-- {ROW} 1.3.6.1.4.1.2356.11.1.9.13.13.1
lcsStatusTcpIpRadiuscIpv6AccountingServersEntry OBJECT-TYPE
    SYNTAX     LcsStatusTcpIpRadiuscIpv6AccountingServersEntry
    MAX-ACCESS not-accessible
    STATUS     current
    DESCRIPTION
            ""
    INDEX {
            lcsStatusTcpIpRadiuscIpv6AccountingServersEntryIpAddr,
            lcsStatusTcpIpRadiuscIpv6AccountingServersEntryPort
          }
    ::= { lcsStatusTcpIpRadiuscIpv6AccountingServersTable 1 }

LcsStatusTcpIpRadiuscIpv6AccountingServersEntry ::= SEQUENCE {
            lcsStatusTcpIpRadiuscIpv6AccountingServersEntryIpAddr IpAddress,
            lcsStatusTcpIpRadiuscIpv6AccountingServersEntryPort Integer32,
            lcsStatusTcpIpRadiuscIpv6AccountingServersEntryLastRequest Integer32,
            lcsStatusTcpIpRadiuscIpv6AccountingServersEntryRoundTripTime Counter32,
            lcsStatusTcpIpRadiuscIpv6AccountingServersEntryAccntReq Counter32,
            lcsStatusTcpIpRadiuscIpv6AccountingServersEntryAccntRetrans Counter32,
            lcsStatusTcpIpRadiuscIpv6AccountingServersEntryAccntResp Counter32,
            lcsStatusTcpIpRadiuscIpv6AccountingServersEntryMalfAccntResp Counter32,
            lcsStatusTcpIpRadiuscIpv6AccountingServersEntryBadAuth Counter32,
            lcsStatusTcpIpRadiuscIpv6AccountingServersEntryPendReq Counter32,
            lcsStatusTcpIpRadiuscIpv6AccountingServersEntryTimeouts Counter32,
            lcsStatusTcpIpRadiuscIpv6AccountingServersEntryUnknownTypes Counter32,
            lcsStatusTcpIpRadiuscIpv6AccountingServersEntryDropped Counter32
    }

-- {COLUMN} 1.3.6.1.4.1.2356.11.1.9.13.13.1.1
lcsStatusTcpIpRadiuscIpv6AccountingServersEntryIpAddr OBJECT-TYPE
    SYNTAX     IpAddress
    MAX-ACCESS read-only
    STATUS     current
    DESCRIPTION
            ""
    ::= { lcsStatusTcpIpRadiuscIpv6AccountingServersEntry 1 }

-- {COLUMN} 1.3.6.1.4.1.2356.11.1.9.13.13.1.2
lcsStatusTcpIpRadiuscIpv6AccountingServersEntryPort OBJECT-TYPE
    SYNTAX     Integer32 (0..65535)
    MAX-ACCESS read-only
    STATUS     current
    DESCRIPTION
            ""
    ::= { lcsStatusTcpIpRadiuscIpv6AccountingServersEntry 2 }

-- {COLUMN} 1.3.6.1.4.1.2356.11.1.9.13.13.1.3
lcsStatusTcpIpRadiuscIpv6AccountingServersEntryLastRequest OBJECT-TYPE
    SYNTAX     Integer32 (0..2147483647)
    MAX-ACCESS read-only
    STATUS     current
    DESCRIPTION
            ""
    ::= { lcsStatusTcpIpRadiuscIpv6AccountingServersEntry 3 }

-- {COLUMN} 1.3.6.1.4.1.2356.11.1.9.13.13.1.4
lcsStatusTcpIpRadiuscIpv6AccountingServersEntryRoundTripTime OBJECT-TYPE
    SYNTAX     Counter32
    MAX-ACCESS read-only
    STATUS     current
    DESCRIPTION
            ""
    ::= { lcsStatusTcpIpRadiuscIpv6AccountingServersEntry 4 }

-- {COLUMN} 1.3.6.1.4.1.2356.11.1.9.13.13.1.5
lcsStatusTcpIpRadiuscIpv6AccountingServersEntryAccntReq OBJECT-TYPE
    SYNTAX     Counter32
    MAX-ACCESS read-only
    STATUS     current
    DESCRIPTION
            ""
    ::= { lcsStatusTcpIpRadiuscIpv6AccountingServersEntry 5 }

-- {COLUMN} 1.3.6.1.4.1.2356.11.1.9.13.13.1.6
lcsStatusTcpIpRadiuscIpv6AccountingServersEntryAccntRetrans OBJECT-TYPE
    SYNTAX     Counter32
    MAX-ACCESS read-only
    STATUS     current
    DESCRIPTION
            ""
    ::= { lcsStatusTcpIpRadiuscIpv6AccountingServersEntry 6 }

-- {COLUMN} 1.3.6.1.4.1.2356.11.1.9.13.13.1.7
lcsStatusTcpIpRadiuscIpv6AccountingServersEntryAccntResp OBJECT-TYPE
    SYNTAX     Counter32
    MAX-ACCESS read-only
    STATUS     current
    DESCRIPTION
            ""
    ::= { lcsStatusTcpIpRadiuscIpv6AccountingServersEntry 7 }

-- {COLUMN} 1.3.6.1.4.1.2356.11.1.9.13.13.1.8
lcsStatusTcpIpRadiuscIpv6AccountingServersEntryMalfAccntResp OBJECT-TYPE
    SYNTAX     Counter32
    MAX-ACCESS read-only
    STATUS     current
    DESCRIPTION
            ""
    ::= { lcsStatusTcpIpRadiuscIpv6AccountingServersEntry 8 }

-- {COLUMN} 1.3.6.1.4.1.2356.11.1.9.13.13.1.9
lcsStatusTcpIpRadiuscIpv6AccountingServersEntryBadAuth OBJECT-TYPE
    SYNTAX     Counter32
    MAX-ACCESS read-only
    STATUS     current
    DESCRIPTION
            ""
    ::= { lcsStatusTcpIpRadiuscIpv6AccountingServersEntry 9 }

-- {COLUMN} 1.3.6.1.4.1.2356.11.1.9.13.13.1.10
lcsStatusTcpIpRadiuscIpv6AccountingServersEntryPendReq OBJECT-TYPE
    SYNTAX     Counter32
    MAX-ACCESS read-only
    STATUS     current
    DESCRIPTION
            ""
    ::= { lcsStatusTcpIpRadiuscIpv6AccountingServersEntry 10 }

-- {COLUMN} 1.3.6.1.4.1.2356.11.1.9.13.13.1.11
lcsStatusTcpIpRadiuscIpv6AccountingServersEntryTimeouts OBJECT-TYPE
    SYNTAX     Counter32
    MAX-ACCESS read-only
    STATUS     current
    DESCRIPTION
            ""
    ::= { lcsStatusTcpIpRadiuscIpv6AccountingServersEntry 11 }

-- {COLUMN} 1.3.6.1.4.1.2356.11.1.9.13.13.1.12
lcsStatusTcpIpRadiuscIpv6AccountingServersEntryUnknownTypes OBJECT-TYPE
    SYNTAX     Counter32
    MAX-ACCESS read-only
    STATUS     current
    DESCRIPTION
            ""
    ::= { lcsStatusTcpIpRadiuscIpv6AccountingServersEntry 12 }

-- {COLUMN} 1.3.6.1.4.1.2356.11.1.9.13.13.1.13
lcsStatusTcpIpRadiuscIpv6AccountingServersEntryDropped OBJECT-TYPE
    SYNTAX     Counter32
    MAX-ACCESS read-only
    STATUS     current
    DESCRIPTION
            ""
    ::= { lcsStatusTcpIpRadiuscIpv6AccountingServersEntry 13 }

-- {SCALAR} 1.3.6.1.4.1.2356.11.1.9.13.100
lcsStatusTcpIpRadiuscDeleteValues OBJECT-TYPE
    SYNTAX     DisplayString
    MAX-ACCESS read-write
    STATUS     current
    DESCRIPTION
            "-- empty --"
    ::= { lcsStatusTcpIpRadiusc 100 }

-- {NODE} 1.3.6.1.4.1.2356.11.1.9.14
lcsStatusTcpIpRADSuperSrv OBJECT IDENTIFIER ::= { lcsStatusTcpIp 14 }

-- {TABLE} 1.3.6.1.4.1.2356.11.1.9.14.1
lcsStatusTcpIpRADSuperSrvServersTable OBJECT-TYPE
    SYNTAX     SEQUENCE OF LcsStatusTcpIpRADSuperSrvServersEntry
    MAX-ACCESS not-accessible
    STATUS     current
    DESCRIPTION
            "-- empty --"
    ::= { lcsStatusTcpIpRADSuperSrv 1 }

-- {ROW} 1.3.6.1.4.1.2356.11.1.9.14.1.1
lcsStatusTcpIpRADSuperSrvServersEntry OBJECT-TYPE
    SYNTAX     LcsStatusTcpIpRADSuperSrvServersEntry
    MAX-ACCESS not-accessible
    STATUS     current
    DESCRIPTION
            ""
    INDEX {
            lcsStatusTcpIpRADSuperSrvServersEntryIndex
          }
    ::= { lcsStatusTcpIpRADSuperSrvServersTable 1 }

LcsStatusTcpIpRADSuperSrvServersEntry ::= SEQUENCE {
            lcsStatusTcpIpRADSuperSrvServersEntryIndex Integer32,
            lcsStatusTcpIpRADSuperSrvServersEntryServerHostname DisplayString,
            lcsStatusTcpIpRADSuperSrvServersEntryPort Integer32,
            lcsStatusTcpIpRADSuperSrvServersEntryLoopbackAddress DisplayString,
            lcsStatusTcpIpRADSuperSrvServersEntryProtocol INTEGER,
            lcsStatusTcpIpRADSuperSrvServersEntryState INTEGER
    }

-- {COLUMN} 1.3.6.1.4.1.2356.11.1.9.14.1.1.1
lcsStatusTcpIpRADSuperSrvServersEntryIndex OBJECT-TYPE
    SYNTAX     Integer32 (0..2147483647)
    MAX-ACCESS read-only
    STATUS     current
    DESCRIPTION
            "-- empty --"
    ::= { lcsStatusTcpIpRADSuperSrvServersEntry 1 }

-- {COLUMN} 1.3.6.1.4.1.2356.11.1.9.14.1.1.2
lcsStatusTcpIpRADSuperSrvServersEntryServerHostname OBJECT-TYPE
    SYNTAX     DisplayString (SIZE(0..255))
    MAX-ACCESS read-only
    STATUS     current
    DESCRIPTION
            "-- empty --"
    ::= { lcsStatusTcpIpRADSuperSrvServersEntry 2 }

-- {COLUMN} 1.3.6.1.4.1.2356.11.1.9.14.1.1.3
lcsStatusTcpIpRADSuperSrvServersEntryPort OBJECT-TYPE
    SYNTAX     Integer32 (0..65535)
    MAX-ACCESS read-only
    STATUS     current
    DESCRIPTION
            "-- empty --"
    ::= { lcsStatusTcpIpRADSuperSrvServersEntry 3 }

-- {COLUMN} 1.3.6.1.4.1.2356.11.1.9.14.1.1.4
lcsStatusTcpIpRADSuperSrvServersEntryLoopbackAddress OBJECT-TYPE
    SYNTAX     DisplayString (SIZE(0..255))
    MAX-ACCESS read-only
    STATUS     current
    DESCRIPTION
            "-- empty --"
    ::= { lcsStatusTcpIpRADSuperSrvServersEntry 4 }

-- {COLUMN} 1.3.6.1.4.1.2356.11.1.9.14.1.1.5
lcsStatusTcpIpRADSuperSrvServersEntryProtocol OBJECT-TYPE
    SYNTAX     INTEGER {
                  eRadius (0),
                  eRadsec (1)
            }
    MAX-ACCESS read-only
    STATUS     current
    DESCRIPTION
            "-- empty --"
    ::= { lcsStatusTcpIpRADSuperSrvServersEntry 5 }

-- {COLUMN} 1.3.6.1.4.1.2356.11.1.9.14.1.1.6
lcsStatusTcpIpRADSuperSrvServersEntryState OBJECT-TYPE
    SYNTAX     INTEGER {
                  eUnknown (0),
                  eUp (1),
                  eDnsError (2),
                  eAuthenticatorMismatch (3),
                  eHostUnreachable (4),
                  ePortUnreachable (5),
                  eNetworkUnreachable (6),
                  eTimeout (7)
            }
    MAX-ACCESS read-only
    STATUS     current
    DESCRIPTION
            "-- empty --"
    ::= { lcsStatusTcpIpRADSuperSrvServersEntry 6 }

-- {TABLE} 1.3.6.1.4.1.2356.11.1.9.20
lcsStatusTcpIpNetworkListTable OBJECT-TYPE
    SYNTAX     SEQUENCE OF LcsStatusTcpIpNetworkListEntry
    MAX-ACCESS not-accessible
    STATUS     current
    DESCRIPTION
            ""
    ::= { lcsStatusTcpIp 20 }

-- {ROW} 1.3.6.1.4.1.2356.11.1.9.20.1
lcsStatusTcpIpNetworkListEntry OBJECT-TYPE
    SYNTAX     LcsStatusTcpIpNetworkListEntry
    MAX-ACCESS not-accessible
    STATUS     current
    DESCRIPTION
            ""
    INDEX {
            lcsStatusTcpIpNetworkListEntryNetworkName
          }
    ::= { lcsStatusTcpIpNetworkListTable 1 }

LcsStatusTcpIpNetworkListEntry ::= SEQUENCE {
            lcsStatusTcpIpNetworkListEntryNetworkName DisplayString,
            lcsStatusTcpIpNetworkListEntryIpAddress IpAddress,
            lcsStatusTcpIpNetworkListEntryIpNetmask IpAddress,
            lcsStatusTcpIpNetworkListEntryVlanId Integer32,
            lcsStatusTcpIpNetworkListEntryInterface INTEGER,
            lcsStatusTcpIpNetworkListEntrySrcCheck INTEGER,
            lcsStatusTcpIpNetworkListEntryType INTEGER,
            lcsStatusTcpIpNetworkListEntryRtgTag Integer32
    }

-- {COLUMN} 1.3.6.1.4.1.2356.11.1.9.20.1.1
lcsStatusTcpIpNetworkListEntryNetworkName OBJECT-TYPE
    SYNTAX     DisplayString (SIZE(0..17))
    MAX-ACCESS read-only
    STATUS     current
    DESCRIPTION
            ""
    ::= { lcsStatusTcpIpNetworkListEntry 1 }

-- {COLUMN} 1.3.6.1.4.1.2356.11.1.9.20.1.2
lcsStatusTcpIpNetworkListEntryIpAddress OBJECT-TYPE
    SYNTAX     IpAddress
    MAX-ACCESS read-only
    STATUS     current
    DESCRIPTION
            ""
    ::= { lcsStatusTcpIpNetworkListEntry 2 }

-- {COLUMN} 1.3.6.1.4.1.2356.11.1.9.20.1.3
lcsStatusTcpIpNetworkListEntryIpNetmask OBJECT-TYPE
    SYNTAX     IpAddress
    MAX-ACCESS read-only
    STATUS     current
    DESCRIPTION
            ""
    ::= { lcsStatusTcpIpNetworkListEntry 3 }

-- {COLUMN} 1.3.6.1.4.1.2356.11.1.9.20.1.4
lcsStatusTcpIpNetworkListEntryVlanId OBJECT-TYPE
    SYNTAX     Integer32 (0..65535)
    MAX-ACCESS read-only
    STATUS     current
    DESCRIPTION
            ""
    ::= { lcsStatusTcpIpNetworkListEntry 4 }

-- {COLUMN} 1.3.6.1.4.1.2356.11.1.9.20.1.5
lcsStatusTcpIpNetworkListEntryInterface OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsStatusTcpIpNetworkListEntry 5 }

-- {COLUMN} 1.3.6.1.4.1.2356.11.1.9.20.1.6
lcsStatusTcpIpNetworkListEntrySrcCheck OBJECT-TYPE
    SYNTAX     INTEGER {
                  eLoose (0),
                  eStrict (1)
            }
    MAX-ACCESS read-only
    STATUS     current
    DESCRIPTION
            ""
    ::= { lcsStatusTcpIpNetworkListEntry 6 }

-- {COLUMN} 1.3.6.1.4.1.2356.11.1.9.20.1.7
lcsStatusTcpIpNetworkListEntryType OBJECT-TYPE
    SYNTAX     INTEGER {
                  eDisabled (0),
                  eIntranet (1),
                  eDmz (2)
            }
    MAX-ACCESS read-only
    STATUS     current
    DESCRIPTION
            ""
    ::= { lcsStatusTcpIpNetworkListEntry 7 }

-- {COLUMN} 1.3.6.1.4.1.2356.11.1.9.20.1.8
lcsStatusTcpIpNetworkListEntryRtgTag OBJECT-TYPE
    SYNTAX     Integer32 (0..65535)
    MAX-ACCESS read-only
    STATUS     current
    DESCRIPTION
            ""
    ::= { lcsStatusTcpIpNetworkListEntry 8 }

-- {NODE} 1.3.6.1.4.1.2356.11.1.10
lcsStatusIpRouter OBJECT IDENTIFIER ::= { lcsStatus 10 }

-- {SCALAR} 1.3.6.1.4.1.2356.11.1.10.1
lcsStatusIpRouterLanRx OBJECT-TYPE
    SYNTAX     Counter32
    MAX-ACCESS read-only
    STATUS     current
    DESCRIPTION
            ""
    ::= { lcsStatusIpRouter 1 }

-- {SCALAR} 1.3.6.1.4.1.2356.11.1.10.2
lcsStatusIpRouterLanTx OBJECT-TYPE
    SYNTAX     Counter32
    MAX-ACCESS read-only
    STATUS     current
    DESCRIPTION
            ""
    ::= { lcsStatusIpRouter 2 }

-- {SCALAR} 1.3.6.1.4.1.2356.11.1.10.3
lcsStatusIpRouterLanLocalRoutings OBJECT-TYPE
    SYNTAX     Counter32
    MAX-ACCESS read-only
    STATUS     current
    DESCRIPTION
            ""
    ::= { lcsStatusIpRouter 3 }

-- {SCALAR} 1.3.6.1.4.1.2356.11.1.10.4
lcsStatusIpRouterLanNetworkErrors OBJECT-TYPE
    SYNTAX     Counter32
    MAX-ACCESS read-only
    STATUS     current
    DESCRIPTION
            ""
    ::= { lcsStatusIpRouter 4 }

-- {SCALAR} 1.3.6.1.4.1.2356.11.1.10.5
lcsStatusIpRouterLanRoutingErrors OBJECT-TYPE
    SYNTAX     Counter32
    MAX-ACCESS read-only
    STATUS     current
    DESCRIPTION
            ""
    ::= { lcsStatusIpRouter 5 }

-- {SCALAR} 1.3.6.1.4.1.2356.11.1.10.6
lcsStatusIpRouterLanTtlErrors OBJECT-TYPE
    SYNTAX     Counter32
    MAX-ACCESS read-only
    STATUS     current
    DESCRIPTION
            ""
    ::= { lcsStatusIpRouter 6 }

-- {SCALAR} 1.3.6.1.4.1.2356.11.1.10.7
lcsStatusIpRouterLanFilters OBJECT-TYPE
    SYNTAX     Counter32
    MAX-ACCESS read-only
    STATUS     current
    DESCRIPTION
            ""
    ::= { lcsStatusIpRouter 7 }

-- {SCALAR} 1.3.6.1.4.1.2356.11.1.10.8
lcsStatusIpRouterLanDiscards OBJECT-TYPE
    SYNTAX     Counter32
    MAX-ACCESS read-only
    STATUS     current
    DESCRIPTION
            ""
    ::= { lcsStatusIpRouter 8 }

-- {SCALAR} 1.3.6.1.4.1.2356.11.1.10.9
lcsStatusIpRouterWanRx OBJECT-TYPE
    SYNTAX     Counter32
    MAX-ACCESS read-only
    STATUS     current
    DESCRIPTION
            ""
    ::= { lcsStatusIpRouter 9 }

-- {SCALAR} 1.3.6.1.4.1.2356.11.1.10.10
lcsStatusIpRouterWanTx OBJECT-TYPE
    SYNTAX     Counter32
    MAX-ACCESS read-only
    STATUS     current
    DESCRIPTION
            ""
    ::= { lcsStatusIpRouter 10 }

-- {SCALAR} 1.3.6.1.4.1.2356.11.1.10.11
lcsStatusIpRouterWanNetworkErrors OBJECT-TYPE
    SYNTAX     Counter32
    MAX-ACCESS read-only
    STATUS     current
    DESCRIPTION
            ""
    ::= { lcsStatusIpRouter 11 }

-- {SCALAR} 1.3.6.1.4.1.2356.11.1.10.12
lcsStatusIpRouterWanTtlErrors OBJECT-TYPE
    SYNTAX     Counter32
    MAX-ACCESS read-only
    STATUS     current
    DESCRIPTION
            ""
    ::= { lcsStatusIpRouter 12 }

-- {SCALAR} 1.3.6.1.4.1.2356.11.1.10.13
lcsStatusIpRouterWanFilters OBJECT-TYPE
    SYNTAX     Counter32
    MAX-ACCESS read-only
    STATUS     current
    DESCRIPTION
            ""
    ::= { lcsStatusIpRouter 13 }

-- {SCALAR} 1.3.6.1.4.1.2356.11.1.10.14
lcsStatusIpRouterWanDiscards OBJECT-TYPE
    SYNTAX     Counter32
    MAX-ACCESS read-only
    STATUS     current
    DESCRIPTION
            ""
    ::= { lcsStatusIpRouter 14 }

-- {SCALAR} 1.3.6.1.4.1.2356.11.1.10.15
lcsStatusIpRouterWanTypeErrors OBJECT-TYPE
    SYNTAX     Counter32
    MAX-ACCESS read-only
    STATUS     current
    DESCRIPTION
            ""
    ::= { lcsStatusIpRouter 15 }

-- {SCALAR} 1.3.6.1.4.1.2356.11.1.10.16
lcsStatusIpRouterArpErrors OBJECT-TYPE
    SYNTAX     Counter32
    MAX-ACCESS read-only
    STATUS     current
    DESCRIPTION
            ""
    ::= { lcsStatusIpRouter 16 }

-- {TABLE} 1.3.6.1.4.1.2356.11.1.10.17
lcsStatusIpRouterEstablishTableTable OBJECT-TYPE
    SYNTAX     SEQUENCE OF LcsStatusIpRouterEstablishTableEntry
    MAX-ACCESS not-accessible
    STATUS     current
    DESCRIPTION
            ""
    ::= { lcsStatusIpRouter 17 }

-- {ROW} 1.3.6.1.4.1.2356.11.1.10.17.1
lcsStatusIpRouterEstablishTableEntry OBJECT-TYPE
    SYNTAX     LcsStatusIpRouterEstablishTableEntry
    MAX-ACCESS not-accessible
    STATUS     current
    DESCRIPTION
            ""
    INDEX {
            lcsStatusIpRouterEstablishTableEntryTime,
            lcsStatusIpRouterEstablishTableEntryCounter
          }
    ::= { lcsStatusIpRouterEstablishTableTable 1 }

LcsStatusIpRouterEstablishTableEntry ::= SEQUENCE {
            lcsStatusIpRouterEstablishTableEntryTime DisplayString,
            lcsStatusIpRouterEstablishTableEntryDestAddress IpAddress,
            lcsStatusIpRouterEstablishTableEntrySrcAddress IpAddress,
            lcsStatusIpRouterEstablishTableEntryProt INTEGER,
            lcsStatusIpRouterEstablishTableEntryDstPort Integer32,
            lcsStatusIpRouterEstablishTableEntrySrcPort Integer32,
            lcsStatusIpRouterEstablishTableEntryCounter Integer32
    }

-- {COLUMN} 1.3.6.1.4.1.2356.11.1.10.17.1.1
lcsStatusIpRouterEstablishTableEntryTime OBJECT-TYPE
    SYNTAX     DisplayString (SIZE(0..19))
    MAX-ACCESS read-only
    STATUS     current
    DESCRIPTION
            ""
    ::= { lcsStatusIpRouterEstablishTableEntry 1 }

-- {COLUMN} 1.3.6.1.4.1.2356.11.1.10.17.1.2
lcsStatusIpRouterEstablishTableEntryDestAddress OBJECT-TYPE
    SYNTAX     IpAddress
    MAX-ACCESS read-only
    STATUS     current
    DESCRIPTION
            ""
    ::= { lcsStatusIpRouterEstablishTableEntry 2 }

-- {COLUMN} 1.3.6.1.4.1.2356.11.1.10.17.1.3
lcsStatusIpRouterEstablishTableEntrySrcAddress OBJECT-TYPE
    SYNTAX     IpAddress
    MAX-ACCESS read-only
    STATUS     current
    DESCRIPTION
            ""
    ::= { lcsStatusIpRouterEstablishTableEntry 3 }

-- {COLUMN} 1.3.6.1.4.1.2356.11.1.10.17.1.4
lcsStatusIpRouterEstablishTableEntryProt OBJECT-TYPE
    SYNTAX     INTEGER {
                  eIcmp (1),
                  eIgmp (2),
                  eGgt (3),
                  eIpip (4),
                  eTcp (6),
                  eEgp (8),
                  eUdp (17),
                  eGre (47),
                  eEsp (50),
                  eAh (51),
                  eCftp (62),
                  eIpcomp (108),
                  eVrrp (112),
                  eSrp (119)
            }
    MAX-ACCESS read-only
    STATUS     current
    DESCRIPTION
            ""
    ::= { lcsStatusIpRouterEstablishTableEntry 4 }

-- {COLUMN} 1.3.6.1.4.1.2356.11.1.10.17.1.5
lcsStatusIpRouterEstablishTableEntryDstPort OBJECT-TYPE
    SYNTAX     Integer32 (0..65535)
    MAX-ACCESS read-only
    STATUS     current
    DESCRIPTION
            ""
    ::= { lcsStatusIpRouterEstablishTableEntry 5 }

-- {COLUMN} 1.3.6.1.4.1.2356.11.1.10.17.1.6
lcsStatusIpRouterEstablishTableEntrySrcPort OBJECT-TYPE
    SYNTAX     Integer32 (0..65535)
    MAX-ACCESS read-only
    STATUS     current
    DESCRIPTION
            ""
    ::= { lcsStatusIpRouterEstablishTableEntry 6 }

-- {COLUMN} 1.3.6.1.4.1.2356.11.1.10.17.1.7
lcsStatusIpRouterEstablishTableEntryCounter OBJECT-TYPE
    SYNTAX     Integer32 (0..2147483647)
    MAX-ACCESS read-only
    STATUS     current
    DESCRIPTION
            ""
    ::= { lcsStatusIpRouterEstablishTableEntry 7 }

-- {TABLE} 1.3.6.1.4.1.2356.11.1.10.18
lcsStatusIpRouterProtocolTableTable OBJECT-TYPE
    SYNTAX     SEQUENCE OF LcsStatusIpRouterProtocolTableEntry
    MAX-ACCESS not-accessible
    STATUS     current
    DESCRIPTION
            ""
    ::= { lcsStatusIpRouter 18 }

-- {ROW} 1.3.6.1.4.1.2356.11.1.10.18.1
lcsStatusIpRouterProtocolTableEntry OBJECT-TYPE
    SYNTAX     LcsStatusIpRouterProtocolTableEntry
    MAX-ACCESS not-accessible
    STATUS     current
    DESCRIPTION
            ""
    INDEX {
            lcsStatusIpRouterProtocolTableEntryProt
          }
    ::= { lcsStatusIpRouterProtocolTableTable 1 }

LcsStatusIpRouterProtocolTableEntry ::= SEQUENCE {
            lcsStatusIpRouterProtocolTableEntryProt INTEGER,
            lcsStatusIpRouterProtocolTableEntryLanTx Counter32,
            lcsStatusIpRouterProtocolTableEntryWanTx Counter32
    }

-- {COLUMN} 1.3.6.1.4.1.2356.11.1.10.18.1.1
lcsStatusIpRouterProtocolTableEntryProt OBJECT-TYPE
    SYNTAX     INTEGER {
                  eIcmp (1),
                  eIgmp (2),
                  eGgt (3),
                  eIpip (4),
                  eTcp (6),
                  eEgp (8),
                  eUdp (17),
                  eGre (47),
                  eEsp (50),
                  eAh (51),
                  eCftp (62),
                  eIpcomp (108),
                  eVrrp (112),
                  eSrp (119)
            }
    MAX-ACCESS read-only
    STATUS     current
    DESCRIPTION
            ""
    ::= { lcsStatusIpRouterProtocolTableEntry 1 }

-- {COLUMN} 1.3.6.1.4.1.2356.11.1.10.18.1.2
lcsStatusIpRouterProtocolTableEntryLanTx OBJECT-TYPE
    SYNTAX     Counter32
    MAX-ACCESS read-only
    STATUS     current
    DESCRIPTION
            ""
    ::= { lcsStatusIpRouterProtocolTableEntry 2 }

-- {COLUMN} 1.3.6.1.4.1.2356.11.1.10.18.1.3
lcsStatusIpRouterProtocolTableEntryWanTx OBJECT-TYPE
    SYNTAX     Counter32
    MAX-ACCESS read-only
    STATUS     current
    DESCRIPTION
            ""
    ::= { lcsStatusIpRouterProtocolTableEntry 3 }

-- {NODE} 1.3.6.1.4.1.2356.11.1.10.19
lcsStatusIpRouterRip OBJECT IDENTIFIER ::= { lcsStatusIpRouter 19 }

-- {SCALAR} 1.3.6.1.4.1.2356.11.1.10.19.1
lcsStatusIpRouterRipRx OBJECT-TYPE
    SYNTAX     Counter32
    MAX-ACCESS read-only
    STATUS     current
    DESCRIPTION
            ""
    ::= { lcsStatusIpRouterRip 1 }

-- {SCALAR} 1.3.6.1.4.1.2356.11.1.10.19.2
lcsStatusIpRouterRipRequests OBJECT-TYPE
    SYNTAX     Counter32
    MAX-ACCESS read-only
    STATUS     current
    DESCRIPTION
            ""
    ::= { lcsStatusIpRouterRip 2 }

-- {SCALAR} 1.3.6.1.4.1.2356.11.1.10.19.3
lcsStatusIpRouterRipResponse OBJECT-TYPE
    SYNTAX     Counter32
    MAX-ACCESS read-only
    STATUS     current
    DESCRIPTION
            ""
    ::= { lcsStatusIpRouterRip 3 }

-- {SCALAR} 1.3.6.1.4.1.2356.11.1.10.19.4
lcsStatusIpRouterRipDiscards OBJECT-TYPE
    SYNTAX     Counter32
    MAX-ACCESS read-only
    STATUS     current
    DESCRIPTION
            ""
    ::= { lcsStatusIpRouterRip 4 }

-- {SCALAR} 1.3.6.1.4.1.2356.11.1.10.19.5
lcsStatusIpRouterRipErrors OBJECT-TYPE
    SYNTAX     Counter32
    MAX-ACCESS read-only
    STATUS     current
    DESCRIPTION
            ""
    ::= { lcsStatusIpRouterRip 5 }

-- {SCALAR} 1.3.6.1.4.1.2356.11.1.10.19.6
lcsStatusIpRouterRipEntryErrors OBJECT-TYPE
    SYNTAX     Counter32
    MAX-ACCESS read-only
    STATUS     current
    DESCRIPTION
            ""
    ::= { lcsStatusIpRouterRip 6 }

-- {SCALAR} 1.3.6.1.4.1.2356.11.1.10.19.7
lcsStatusIpRouterRipTx OBJECT-TYPE
    SYNTAX     Counter32
    MAX-ACCESS read-only
    STATUS     current
    DESCRIPTION
            ""
    ::= { lcsStatusIpRouterRip 7 }

-- {TABLE} 1.3.6.1.4.1.2356.11.1.10.19.8
lcsStatusIpRouterRipBestRoutesTable OBJECT-TYPE
    SYNTAX     SEQUENCE OF LcsStatusIpRouterRipBestRoutesEntry
    MAX-ACCESS not-accessible
    STATUS     current
    DESCRIPTION
            ""
    ::= { lcsStatusIpRouterRip 8 }

-- {ROW} 1.3.6.1.4.1.2356.11.1.10.19.8.1
lcsStatusIpRouterRipBestRoutesEntry OBJECT-TYPE
    SYNTAX     LcsStatusIpRouterRipBestRoutesEntry
    MAX-ACCESS not-accessible
    STATUS     current
    DESCRIPTION
            ""
    INDEX {
            lcsStatusIpRouterRipBestRoutesEntryIpAddress,
            lcsStatusIpRouterRipBestRoutesEntryIpNetmask,
            lcsStatusIpRouterRipBestRoutesEntryRtgTag,
            lcsStatusIpRouterRipBestRoutesEntryGateway
          }
    ::= { lcsStatusIpRouterRipBestRoutesTable 1 }

LcsStatusIpRouterRipBestRoutesEntry ::= SEQUENCE {
            lcsStatusIpRouterRipBestRoutesEntryIpAddress IpAddress,
            lcsStatusIpRouterRipBestRoutesEntryIpNetmask IpAddress,
            lcsStatusIpRouterRipBestRoutesEntryTime Integer32,
            lcsStatusIpRouterRipBestRoutesEntryDistance Integer32,
            lcsStatusIpRouterRipBestRoutesEntryGateway IpAddress,
            lcsStatusIpRouterRipBestRoutesEntryRtgTag Integer32,
            lcsStatusIpRouterRipBestRoutesEntryPeer DisplayString,
            lcsStatusIpRouterRipBestRoutesEntryVlanId Integer32,
            lcsStatusIpRouterRipBestRoutesEntryNetworkName DisplayString,
            lcsStatusIpRouterRipBestRoutesEntryPort INTEGER
    }

-- {COLUMN} 1.3.6.1.4.1.2356.11.1.10.19.8.1.1
lcsStatusIpRouterRipBestRoutesEntryIpAddress OBJECT-TYPE
    SYNTAX     IpAddress
    MAX-ACCESS read-only
    STATUS     current
    DESCRIPTION
            ""
    ::= { lcsStatusIpRouterRipBestRoutesEntry 1 }

-- {COLUMN} 1.3.6.1.4.1.2356.11.1.10.19.8.1.2
lcsStatusIpRouterRipBestRoutesEntryIpNetmask OBJECT-TYPE
    SYNTAX     IpAddress
    MAX-ACCESS read-only
    STATUS     current
    DESCRIPTION
            ""
    ::= { lcsStatusIpRouterRipBestRoutesEntry 2 }

-- {COLUMN} 1.3.6.1.4.1.2356.11.1.10.19.8.1.3
lcsStatusIpRouterRipBestRoutesEntryTime OBJECT-TYPE
    SYNTAX     Integer32 (0..65535)
    MAX-ACCESS read-only
    STATUS     current
    DESCRIPTION
            ""
    ::= { lcsStatusIpRouterRipBestRoutesEntry 3 }

-- {COLUMN} 1.3.6.1.4.1.2356.11.1.10.19.8.1.4
lcsStatusIpRouterRipBestRoutesEntryDistance OBJECT-TYPE
    SYNTAX     Integer32 (0..65535)
    MAX-ACCESS read-only
    STATUS     current
    DESCRIPTION
            ""
    ::= { lcsStatusIpRouterRipBestRoutesEntry 4 }

-- {COLUMN} 1.3.6.1.4.1.2356.11.1.10.19.8.1.5
lcsStatusIpRouterRipBestRoutesEntryGateway OBJECT-TYPE
    SYNTAX     IpAddress
    MAX-ACCESS read-only
    STATUS     current
    DESCRIPTION
            ""
    ::= { lcsStatusIpRouterRipBestRoutesEntry 5 }

-- {COLUMN} 1.3.6.1.4.1.2356.11.1.10.19.8.1.6
lcsStatusIpRouterRipBestRoutesEntryRtgTag OBJECT-TYPE
    SYNTAX     Integer32 (0..65535)
    MAX-ACCESS read-only
    STATUS     current
    DESCRIPTION
            ""
    ::= { lcsStatusIpRouterRipBestRoutesEntry 6 }

-- {COLUMN} 1.3.6.1.4.1.2356.11.1.10.19.8.1.8
lcsStatusIpRouterRipBestRoutesEntryPeer OBJECT-TYPE
    SYNTAX     DisplayString (SIZE(0..255))
    MAX-ACCESS read-only
    STATUS     current
    DESCRIPTION
            ""
    ::= { lcsStatusIpRouterRipBestRoutesEntry 8 }

-- {COLUMN} 1.3.6.1.4.1.2356.11.1.10.19.8.1.10
lcsStatusIpRouterRipBestRoutesEntryVlanId OBJECT-TYPE
    SYNTAX     Integer32 (0..65535)
    MAX-ACCESS read-only
    STATUS     current
    DESCRIPTION
            ""
    ::= { lcsStatusIpRouterRipBestRoutesEntry 10 }

-- {COLUMN} 1.3.6.1.4.1.2356.11.1.10.19.8.1.11
lcsStatusIpRouterRipBestRoutesEntryNetworkName OBJECT-TYPE
    SYNTAX     DisplayString (SIZE(0..255))
    MAX-ACCESS read-only
    STATUS     current
    DESCRIPTION
            ""
    ::= { lcsStatusIpRouterRipBestRoutesEntry 11 }

-- {COLUMN} 1.3.6.1.4.1.2356.11.1.10.19.8.1.12
lcsStatusIpRouterRipBestRoutesEntryPort OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsStatusIpRouterRipBestRoutesEntry 12 }

-- {SCALAR} 1.3.6.1.4.1.2356.11.1.10.19.9
lcsStatusIpRouterRipDeleteValues OBJECT-TYPE
    SYNTAX     DisplayString
    MAX-ACCESS read-write
    STATUS     current
    DESCRIPTION
            ""
    ::= { lcsStatusIpRouterRip 9 }

-- {TABLE} 1.3.6.1.4.1.2356.11.1.10.19.10
lcsStatusIpRouterRipLanSitesTable OBJECT-TYPE
    SYNTAX     SEQUENCE OF LcsStatusIpRouterRipLanSitesEntry
    MAX-ACCESS not-accessible
    STATUS     current
    DESCRIPTION
            ""
    ::= { lcsStatusIpRouterRip 10 }

-- {ROW} 1.3.6.1.4.1.2356.11.1.10.19.10.1
lcsStatusIpRouterRipLanSitesEntry OBJECT-TYPE
    SYNTAX     LcsStatusIpRouterRipLanSitesEntry
    MAX-ACCESS not-accessible
    STATUS     current
    DESCRIPTION
            ""
    INDEX {
            lcsStatusIpRouterRipLanSitesEntryNetworkName
          }
    ::= { lcsStatusIpRouterRipLanSitesTable 1 }

LcsStatusIpRouterRipLanSitesEntry ::= SEQUENCE {
            lcsStatusIpRouterRipLanSitesEntryNetworkName DisplayString,
            lcsStatusIpRouterRipLanSitesEntryRipType INTEGER,
            lcsStatusIpRouterRipLanSitesEntryRipAccept INTEGER,
            lcsStatusIpRouterRipLanSitesEntryPropagate INTEGER,
            lcsStatusIpRouterRipLanSitesEntryDftRtgTag Integer32,
            lcsStatusIpRouterRipLanSitesEntryRtgTagList DisplayString,
            lcsStatusIpRouterRipLanSitesEntryVlanId Integer32,
            lcsStatusIpRouterRipLanSitesEntryPoisonedReverse INTEGER,
            lcsStatusIpRouterRipLanSitesEntryRxFilter DisplayString,
            lcsStatusIpRouterRipLanSitesEntryTxFilter DisplayString,
            lcsStatusIpRouterRipLanSitesEntryRipSend INTEGER,
            lcsStatusIpRouterRipLanSitesEntryIgnoreTags INTEGER,
            lcsStatusIpRouterRipLanSitesEntryPort INTEGER
    }

-- {COLUMN} 1.3.6.1.4.1.2356.11.1.10.19.10.1.1
lcsStatusIpRouterRipLanSitesEntryNetworkName OBJECT-TYPE
    SYNTAX     DisplayString (SIZE(0..16))
    MAX-ACCESS read-only
    STATUS     current
    DESCRIPTION
            ""
    ::= { lcsStatusIpRouterRipLanSitesEntry 1 }

-- {COLUMN} 1.3.6.1.4.1.2356.11.1.10.19.10.1.2
lcsStatusIpRouterRipLanSitesEntryRipType OBJECT-TYPE
    SYNTAX     INTEGER {
                  eOff (0),
                  eRip1 (1),
                  eR1Comp (2),
                  eRip2 (3)
            }
    MAX-ACCESS read-only
    STATUS     current
    DESCRIPTION
            ""
    ::= { lcsStatusIpRouterRipLanSitesEntry 2 }

-- {COLUMN} 1.3.6.1.4.1.2356.11.1.10.19.10.1.3
lcsStatusIpRouterRipLanSitesEntryRipAccept OBJECT-TYPE
    SYNTAX     INTEGER {
                  eNo (0),
                  eYes (1)
            }
    MAX-ACCESS read-only
    STATUS     current
    DESCRIPTION
            ""
    ::= { lcsStatusIpRouterRipLanSitesEntry 3 }

-- {COLUMN} 1.3.6.1.4.1.2356.11.1.10.19.10.1.4
lcsStatusIpRouterRipLanSitesEntryPropagate OBJECT-TYPE
    SYNTAX     INTEGER {
                  eNo (0),
                  eYes (1)
            }
    MAX-ACCESS read-only
    STATUS     current
    DESCRIPTION
            ""
    ::= { lcsStatusIpRouterRipLanSitesEntry 4 }

-- {COLUMN} 1.3.6.1.4.1.2356.11.1.10.19.10.1.5
lcsStatusIpRouterRipLanSitesEntryDftRtgTag OBJECT-TYPE
    SYNTAX     Integer32 (0..65535)
    MAX-ACCESS read-only
    STATUS     current
    DESCRIPTION
            ""
    ::= { lcsStatusIpRouterRipLanSitesEntry 5 }

-- {COLUMN} 1.3.6.1.4.1.2356.11.1.10.19.10.1.6
lcsStatusIpRouterRipLanSitesEntryRtgTagList OBJECT-TYPE
    SYNTAX     DisplayString (SIZE(0..33))
    MAX-ACCESS read-only
    STATUS     current
    DESCRIPTION
            ""
    ::= { lcsStatusIpRouterRipLanSitesEntry 6 }

-- {COLUMN} 1.3.6.1.4.1.2356.11.1.10.19.10.1.8
lcsStatusIpRouterRipLanSitesEntryVlanId OBJECT-TYPE
    SYNTAX     Integer32 (0..65535)
    MAX-ACCESS read-only
    STATUS     current
    DESCRIPTION
            ""
    ::= { lcsStatusIpRouterRipLanSitesEntry 8 }

-- {COLUMN} 1.3.6.1.4.1.2356.11.1.10.19.10.1.9
lcsStatusIpRouterRipLanSitesEntryPoisonedReverse OBJECT-TYPE
    SYNTAX     INTEGER {
                  eNo (0),
                  eYes (1)
            }
    MAX-ACCESS read-only
    STATUS     current
    DESCRIPTION
            ""
    ::= { lcsStatusIpRouterRipLanSitesEntry 9 }

-- {COLUMN} 1.3.6.1.4.1.2356.11.1.10.19.10.1.10
lcsStatusIpRouterRipLanSitesEntryRxFilter OBJECT-TYPE
    SYNTAX     DisplayString (SIZE(0..16))
    MAX-ACCESS read-only
    STATUS     current
    DESCRIPTION
            ""
    ::= { lcsStatusIpRouterRipLanSitesEntry 10 }

-- {COLUMN} 1.3.6.1.4.1.2356.11.1.10.19.10.1.11
lcsStatusIpRouterRipLanSitesEntryTxFilter OBJECT-TYPE
    SYNTAX     DisplayString (SIZE(0..16))
    MAX-ACCESS read-only
    STATUS     current
    DESCRIPTION
            ""
    ::= { lcsStatusIpRouterRipLanSitesEntry 11 }

-- {COLUMN} 1.3.6.1.4.1.2356.11.1.10.19.10.1.12
lcsStatusIpRouterRipLanSitesEntryRipSend OBJECT-TYPE
    SYNTAX     INTEGER {
                  eNo (0),
                  eYes (1)
            }
    MAX-ACCESS read-only
    STATUS     current
    DESCRIPTION
            ""
    ::= { lcsStatusIpRouterRipLanSitesEntry 12 }

-- {COLUMN} 1.3.6.1.4.1.2356.11.1.10.19.10.1.14
lcsStatusIpRouterRipLanSitesEntryIgnoreTags OBJECT-TYPE
    SYNTAX     INTEGER {
                  eNo (0),
                  eYes (1)
            }
    MAX-ACCESS read-only
    STATUS     current
    DESCRIPTION
            "-- empty --"
    ::= { lcsStatusIpRouterRipLanSitesEntry 14 }

-- {COLUMN} 1.3.6.1.4.1.2356.11.1.10.19.10.1.31
lcsStatusIpRouterRipLanSitesEntryPort OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsStatusIpRouterRipLanSitesEntry 31 }

-- {TABLE} 1.3.6.1.4.1.2356.11.1.10.19.11
lcsStatusIpRouterRipWanSitesTable OBJECT-TYPE
    SYNTAX     SEQUENCE OF LcsStatusIpRouterRipWanSitesEntry
    MAX-ACCESS not-accessible
    STATUS     current
    DESCRIPTION
            ""
    ::= { lcsStatusIpRouterRip 11 }

-- {ROW} 1.3.6.1.4.1.2356.11.1.10.19.11.1
lcsStatusIpRouterRipWanSitesEntry OBJECT-TYPE
    SYNTAX     LcsStatusIpRouterRipWanSitesEntry
    MAX-ACCESS not-accessible
    STATUS     current
    DESCRIPTION
            ""
    INDEX {
            lcsStatusIpRouterRipWanSitesEntryPeer
          }
    ::= { lcsStatusIpRouterRipWanSitesTable 1 }

LcsStatusIpRouterRipWanSitesEntry ::= SEQUENCE {
            lcsStatusIpRouterRipWanSitesEntryPeer DisplayString,
            lcsStatusIpRouterRipWanSitesEntryRipType INTEGER,
            lcsStatusIpRouterRipWanSitesEntryRipAccept INTEGER,
            lcsStatusIpRouterRipWanSitesEntryMasquerade INTEGER,
            lcsStatusIpRouterRipWanSitesEntryDftRtgTag Integer32,
            lcsStatusIpRouterRipWanSitesEntryRtgTagList DisplayString,
            lcsStatusIpRouterRipWanSitesEntryPoisonedReverse INTEGER,
            lcsStatusIpRouterRipWanSitesEntryRfc2091 INTEGER,
            lcsStatusIpRouterRipWanSitesEntryGateway IpAddress,
            lcsStatusIpRouterRipWanSitesEntryRxFilter DisplayString,
            lcsStatusIpRouterRipWanSitesEntryTxFilter DisplayString,
            lcsStatusIpRouterRipWanSitesEntryRipSend INTEGER,
            lcsStatusIpRouterRipWanSitesEntryIgnoreTags INTEGER
    }

-- {COLUMN} 1.3.6.1.4.1.2356.11.1.10.19.11.1.1
lcsStatusIpRouterRipWanSitesEntryPeer OBJECT-TYPE
    SYNTAX     DisplayString (SIZE(0..16))
    MAX-ACCESS read-only
    STATUS     current
    DESCRIPTION
            ""
    ::= { lcsStatusIpRouterRipWanSitesEntry 1 }

-- {COLUMN} 1.3.6.1.4.1.2356.11.1.10.19.11.1.2
lcsStatusIpRouterRipWanSitesEntryRipType OBJECT-TYPE
    SYNTAX     INTEGER {
                  eOff (0),
                  eRip1 (1),
                  eR1Comp (2),
                  eRip2 (3)
            }
    MAX-ACCESS read-only
    STATUS     current
    DESCRIPTION
            ""
    ::= { lcsStatusIpRouterRipWanSitesEntry 2 }

-- {COLUMN} 1.3.6.1.4.1.2356.11.1.10.19.11.1.3
lcsStatusIpRouterRipWanSitesEntryRipAccept OBJECT-TYPE
    SYNTAX     INTEGER {
                  eNo (0),
                  eYes (1)
            }
    MAX-ACCESS read-only
    STATUS     current
    DESCRIPTION
            ""
    ::= { lcsStatusIpRouterRipWanSitesEntry 3 }

-- {COLUMN} 1.3.6.1.4.1.2356.11.1.10.19.11.1.4
lcsStatusIpRouterRipWanSitesEntryMasquerade OBJECT-TYPE
    SYNTAX     INTEGER {
                  eAuto (0),
                  eOn (1),
                  eIntranet (2)
            }
    MAX-ACCESS read-only
    STATUS     current
    DESCRIPTION
            ""
    ::= { lcsStatusIpRouterRipWanSitesEntry 4 }

-- {COLUMN} 1.3.6.1.4.1.2356.11.1.10.19.11.1.5
lcsStatusIpRouterRipWanSitesEntryDftRtgTag OBJECT-TYPE
    SYNTAX     Integer32 (0..65535)
    MAX-ACCESS read-only
    STATUS     current
    DESCRIPTION
            ""
    ::= { lcsStatusIpRouterRipWanSitesEntry 5 }

-- {COLUMN} 1.3.6.1.4.1.2356.11.1.10.19.11.1.6
lcsStatusIpRouterRipWanSitesEntryRtgTagList OBJECT-TYPE
    SYNTAX     DisplayString (SIZE(0..33))
    MAX-ACCESS read-only
    STATUS     current
    DESCRIPTION
            ""
    ::= { lcsStatusIpRouterRipWanSitesEntry 6 }

-- {COLUMN} 1.3.6.1.4.1.2356.11.1.10.19.11.1.7
lcsStatusIpRouterRipWanSitesEntryPoisonedReverse OBJECT-TYPE
    SYNTAX     INTEGER {
                  eNo (0),
                  eYes (1)
            }
    MAX-ACCESS read-only
    STATUS     current
    DESCRIPTION
            ""
    ::= { lcsStatusIpRouterRipWanSitesEntry 7 }

-- {COLUMN} 1.3.6.1.4.1.2356.11.1.10.19.11.1.8
lcsStatusIpRouterRipWanSitesEntryRfc2091 OBJECT-TYPE
    SYNTAX     INTEGER {
                  eNo (0),
                  eYes (1)
            }
    MAX-ACCESS read-only
    STATUS     current
    DESCRIPTION
            ""
    ::= { lcsStatusIpRouterRipWanSitesEntry 8 }

-- {COLUMN} 1.3.6.1.4.1.2356.11.1.10.19.11.1.9
lcsStatusIpRouterRipWanSitesEntryGateway OBJECT-TYPE
    SYNTAX     IpAddress
    MAX-ACCESS read-only
    STATUS     current
    DESCRIPTION
            ""
    ::= { lcsStatusIpRouterRipWanSitesEntry 9 }

-- {COLUMN} 1.3.6.1.4.1.2356.11.1.10.19.11.1.10
lcsStatusIpRouterRipWanSitesEntryRxFilter OBJECT-TYPE
    SYNTAX     DisplayString (SIZE(0..16))
    MAX-ACCESS read-only
    STATUS     current
    DESCRIPTION
            ""
    ::= { lcsStatusIpRouterRipWanSitesEntry 10 }

-- {COLUMN} 1.3.6.1.4.1.2356.11.1.10.19.11.1.11
lcsStatusIpRouterRipWanSitesEntryTxFilter OBJECT-TYPE
    SYNTAX     DisplayString (SIZE(0..16))
    MAX-ACCESS read-only
    STATUS     current
    DESCRIPTION
            ""
    ::= { lcsStatusIpRouterRipWanSitesEntry 11 }

-- {COLUMN} 1.3.6.1.4.1.2356.11.1.10.19.11.1.12
lcsStatusIpRouterRipWanSitesEntryRipSend OBJECT-TYPE
    SYNTAX     INTEGER {
                  eNo (0),
                  eYes (1)
            }
    MAX-ACCESS read-only
    STATUS     current
    DESCRIPTION
            ""
    ::= { lcsStatusIpRouterRipWanSitesEntry 12 }

-- {COLUMN} 1.3.6.1.4.1.2356.11.1.10.19.11.1.14
lcsStatusIpRouterRipWanSitesEntryIgnoreTags OBJECT-TYPE
    SYNTAX     INTEGER {
                  eNo (0),
                  eYes (1)
            }
    MAX-ACCESS read-only
    STATUS     current
    DESCRIPTION
            "-- empty --"
    ::= { lcsStatusIpRouterRipWanSitesEntry 14 }

-- {TABLE} 1.3.6.1.4.1.2356.11.1.10.19.12
lcsStatusIpRouterRipVrrpSitesTable OBJECT-TYPE
    SYNTAX     SEQUENCE OF LcsStatusIpRouterRipVrrpSitesEntry
    MAX-ACCESS not-accessible
    STATUS     current
    DESCRIPTION
            ""
    ::= { lcsStatusIpRouterRip 12 }

-- {ROW} 1.3.6.1.4.1.2356.11.1.10.19.12.1
lcsStatusIpRouterRipVrrpSitesEntry OBJECT-TYPE
    SYNTAX     LcsStatusIpRouterRipVrrpSitesEntry
    MAX-ACCESS not-accessible
    STATUS     current
    DESCRIPTION
            ""
    INDEX {
            lcsStatusIpRouterRipVrrpSitesEntryNetworkName,
            lcsStatusIpRouterRipVrrpSitesEntryRouterId
          }
    ::= { lcsStatusIpRouterRipVrrpSitesTable 1 }

LcsStatusIpRouterRipVrrpSitesEntry ::= SEQUENCE {
            lcsStatusIpRouterRipVrrpSitesEntryNetworkName DisplayString,
            lcsStatusIpRouterRipVrrpSitesEntryRipType INTEGER,
            lcsStatusIpRouterRipVrrpSitesEntryRouterId Integer32
    }

-- {COLUMN} 1.3.6.1.4.1.2356.11.1.10.19.12.1.1
lcsStatusIpRouterRipVrrpSitesEntryNetworkName OBJECT-TYPE
    SYNTAX     DisplayString (SIZE(0..16))
    MAX-ACCESS read-only
    STATUS     current
    DESCRIPTION
            ""
    ::= { lcsStatusIpRouterRipVrrpSitesEntry 1 }

-- {COLUMN} 1.3.6.1.4.1.2356.11.1.10.19.12.1.2
lcsStatusIpRouterRipVrrpSitesEntryRipType OBJECT-TYPE
    SYNTAX     INTEGER {
                  eOff (0),
                  eRip1 (1),
                  eR1Comp (2),
                  eRip2 (3)
            }
    MAX-ACCESS read-only
    STATUS     current
    DESCRIPTION
            ""
    ::= { lcsStatusIpRouterRipVrrpSitesEntry 2 }

-- {COLUMN} 1.3.6.1.4.1.2356.11.1.10.19.12.1.3
lcsStatusIpRouterRipVrrpSitesEntryRouterId OBJECT-TYPE
    SYNTAX     Integer32 (0..255)
    MAX-ACCESS read-only
    STATUS     current
    DESCRIPTION
            ""
    ::= { lcsStatusIpRouterRipVrrpSitesEntry 3 }

-- {TABLE} 1.3.6.1.4.1.2356.11.1.10.19.13
lcsStatusIpRouterRipDynLanSitesTable OBJECT-TYPE
    SYNTAX     SEQUENCE OF LcsStatusIpRouterRipDynLanSitesEntry
    MAX-ACCESS not-accessible
    STATUS     current
    DESCRIPTION
            ""
    ::= { lcsStatusIpRouterRip 13 }

-- {ROW} 1.3.6.1.4.1.2356.11.1.10.19.13.1
lcsStatusIpRouterRipDynLanSitesEntry OBJECT-TYPE
    SYNTAX     LcsStatusIpRouterRipDynLanSitesEntry
    MAX-ACCESS not-accessible
    STATUS     current
    DESCRIPTION
            ""
    INDEX {
            lcsStatusIpRouterRipDynLanSitesEntryGateway
          }
    ::= { lcsStatusIpRouterRipDynLanSitesTable 1 }

LcsStatusIpRouterRipDynLanSitesEntry ::= SEQUENCE {
            lcsStatusIpRouterRipDynLanSitesEntryGateway DisplayString,
            lcsStatusIpRouterRipDynLanSitesEntryRipType INTEGER,
            lcsStatusIpRouterRipDynLanSitesEntryRipAccept INTEGER,
            lcsStatusIpRouterRipDynLanSitesEntryPoisonedReverse INTEGER,
            lcsStatusIpRouterRipDynLanSitesEntryDftRtgTag Integer32,
            lcsStatusIpRouterRipDynLanSitesEntryRtgTagList DisplayString,
            lcsStatusIpRouterRipDynLanSitesEntryVlanId Integer32,
            lcsStatusIpRouterRipDynLanSitesEntryRxFilter DisplayString,
            lcsStatusIpRouterRipDynLanSitesEntryTxFilter DisplayString,
            lcsStatusIpRouterRipDynLanSitesEntryRipSend INTEGER,
            lcsStatusIpRouterRipDynLanSitesEntryIgnoreTags INTEGER,
            lcsStatusIpRouterRipDynLanSitesEntryPort INTEGER
    }

-- {COLUMN} 1.3.6.1.4.1.2356.11.1.10.19.13.1.1
lcsStatusIpRouterRipDynLanSitesEntryGateway OBJECT-TYPE
    SYNTAX     DisplayString (SIZE(0..16))
    MAX-ACCESS read-only
    STATUS     current
    DESCRIPTION
            ""
    ::= { lcsStatusIpRouterRipDynLanSitesEntry 1 }

-- {COLUMN} 1.3.6.1.4.1.2356.11.1.10.19.13.1.2
lcsStatusIpRouterRipDynLanSitesEntryRipType OBJECT-TYPE
    SYNTAX     INTEGER {
                  eOff (0),
                  eRip1 (1),
                  eR1Comp (2),
                  eRip2 (3)
            }
    MAX-ACCESS read-only
    STATUS     current
    DESCRIPTION
            ""
    ::= { lcsStatusIpRouterRipDynLanSitesEntry 2 }

-- {COLUMN} 1.3.6.1.4.1.2356.11.1.10.19.13.1.3
lcsStatusIpRouterRipDynLanSitesEntryRipAccept OBJECT-TYPE
    SYNTAX     INTEGER {
                  eNo (0),
                  eYes (1)
            }
    MAX-ACCESS read-only
    STATUS     current
    DESCRIPTION
            ""
    ::= { lcsStatusIpRouterRipDynLanSitesEntry 3 }

-- {COLUMN} 1.3.6.1.4.1.2356.11.1.10.19.13.1.4
lcsStatusIpRouterRipDynLanSitesEntryPoisonedReverse OBJECT-TYPE
    SYNTAX     INTEGER {
                  eNo (0),
                  eYes (1)
            }
    MAX-ACCESS read-only
    STATUS     current
    DESCRIPTION
            ""
    ::= { lcsStatusIpRouterRipDynLanSitesEntry 4 }

-- {COLUMN} 1.3.6.1.4.1.2356.11.1.10.19.13.1.5
lcsStatusIpRouterRipDynLanSitesEntryDftRtgTag OBJECT-TYPE
    SYNTAX     Integer32 (0..65535)
    MAX-ACCESS read-only
    STATUS     current
    DESCRIPTION
            ""
    ::= { lcsStatusIpRouterRipDynLanSitesEntry 5 }

-- {COLUMN} 1.3.6.1.4.1.2356.11.1.10.19.13.1.6
lcsStatusIpRouterRipDynLanSitesEntryRtgTagList OBJECT-TYPE
    SYNTAX     DisplayString (SIZE(0..33))
    MAX-ACCESS read-only
    STATUS     current
    DESCRIPTION
            ""
    ::= { lcsStatusIpRouterRipDynLanSitesEntry 6 }

-- {COLUMN} 1.3.6.1.4.1.2356.11.1.10.19.13.1.8
lcsStatusIpRouterRipDynLanSitesEntryVlanId OBJECT-TYPE
    SYNTAX     Integer32 (0..65535)
    MAX-ACCESS read-only
    STATUS     current
    DESCRIPTION
            ""
    ::= { lcsStatusIpRouterRipDynLanSitesEntry 8 }

-- {COLUMN} 1.3.6.1.4.1.2356.11.1.10.19.13.1.10
lcsStatusIpRouterRipDynLanSitesEntryRxFilter OBJECT-TYPE
    SYNTAX     DisplayString (SIZE(0..16))
    MAX-ACCESS read-only
    STATUS     current
    DESCRIPTION
            ""
    ::= { lcsStatusIpRouterRipDynLanSitesEntry 10 }

-- {COLUMN} 1.3.6.1.4.1.2356.11.1.10.19.13.1.11
lcsStatusIpRouterRipDynLanSitesEntryTxFilter OBJECT-TYPE
    SYNTAX     DisplayString (SIZE(0..16))
    MAX-ACCESS read-only
    STATUS     current
    DESCRIPTION
            ""
    ::= { lcsStatusIpRouterRipDynLanSitesEntry 11 }

-- {COLUMN} 1.3.6.1.4.1.2356.11.1.10.19.13.1.12
lcsStatusIpRouterRipDynLanSitesEntryRipSend OBJECT-TYPE
    SYNTAX     INTEGER {
                  eNo (0),
                  eYes (1)
            }
    MAX-ACCESS read-only
    STATUS     current
    DESCRIPTION
            ""
    ::= { lcsStatusIpRouterRipDynLanSitesEntry 12 }

-- {COLUMN} 1.3.6.1.4.1.2356.11.1.10.19.13.1.14
lcsStatusIpRouterRipDynLanSitesEntryIgnoreTags OBJECT-TYPE
    SYNTAX     INTEGER {
                  eNo (0),
                  eYes (1)
            }
    MAX-ACCESS read-only
    STATUS     current
    DESCRIPTION
            "-- empty --"
    ::= { lcsStatusIpRouterRipDynLanSitesEntry 14 }

-- {COLUMN} 1.3.6.1.4.1.2356.11.1.10.19.13.1.31
lcsStatusIpRouterRipDynLanSitesEntryPort OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsStatusIpRouterRipDynLanSitesEntry 31 }

-- {TABLE} 1.3.6.1.4.1.2356.11.1.10.19.14
lcsStatusIpRouterRipDynWanSitesTable OBJECT-TYPE
    SYNTAX     SEQUENCE OF LcsStatusIpRouterRipDynWanSitesEntry
    MAX-ACCESS not-accessible
    STATUS     current
    DESCRIPTION
            ""
    ::= { lcsStatusIpRouterRip 14 }

-- {ROW} 1.3.6.1.4.1.2356.11.1.10.19.14.1
lcsStatusIpRouterRipDynWanSitesEntry OBJECT-TYPE
    SYNTAX     LcsStatusIpRouterRipDynWanSitesEntry
    MAX-ACCESS not-accessible
    STATUS     current
    DESCRIPTION
            ""
    INDEX {
            lcsStatusIpRouterRipDynWanSitesEntryPeer
          }
    ::= { lcsStatusIpRouterRipDynWanSitesTable 1 }

LcsStatusIpRouterRipDynWanSitesEntry ::= SEQUENCE {
            lcsStatusIpRouterRipDynWanSitesEntryPeer DisplayString,
            lcsStatusIpRouterRipDynWanSitesEntryRipType INTEGER,
            lcsStatusIpRouterRipDynWanSitesEntryRipAccept INTEGER,
            lcsStatusIpRouterRipDynWanSitesEntryMasquerade INTEGER,
            lcsStatusIpRouterRipDynWanSitesEntryDftRtgTag Integer32,
            lcsStatusIpRouterRipDynWanSitesEntryRtgTagList DisplayString,
            lcsStatusIpRouterRipDynWanSitesEntryPoisonedReverse INTEGER,
            lcsStatusIpRouterRipDynWanSitesEntryRfc2091 INTEGER,
            lcsStatusIpRouterRipDynWanSitesEntryGateway IpAddress,
            lcsStatusIpRouterRipDynWanSitesEntryRxFilter DisplayString,
            lcsStatusIpRouterRipDynWanSitesEntryTxFilter DisplayString,
            lcsStatusIpRouterRipDynWanSitesEntryRipSend INTEGER,
            lcsStatusIpRouterRipDynWanSitesEntryIgnoreTags INTEGER
    }

-- {COLUMN} 1.3.6.1.4.1.2356.11.1.10.19.14.1.1
lcsStatusIpRouterRipDynWanSitesEntryPeer OBJECT-TYPE
    SYNTAX     DisplayString (SIZE(0..16))
    MAX-ACCESS read-only
    STATUS     current
    DESCRIPTION
            ""
    ::= { lcsStatusIpRouterRipDynWanSitesEntry 1 }

-- {COLUMN} 1.3.6.1.4.1.2356.11.1.10.19.14.1.2
lcsStatusIpRouterRipDynWanSitesEntryRipType OBJECT-TYPE
    SYNTAX     INTEGER {
                  eOff (0),
                  eRip1 (1),
                  eR1Comp (2),
                  eRip2 (3)
            }
    MAX-ACCESS read-only
    STATUS     current
    DESCRIPTION
            ""
    ::= { lcsStatusIpRouterRipDynWanSitesEntry 2 }

-- {COLUMN} 1.3.6.1.4.1.2356.11.1.10.19.14.1.3
lcsStatusIpRouterRipDynWanSitesEntryRipAccept OBJECT-TYPE
    SYNTAX     INTEGER {
                  eNo (0),
                  eYes (1)
            }
    MAX-ACCESS read-only
    STATUS     current
    DESCRIPTION
            ""
    ::= { lcsStatusIpRouterRipDynWanSitesEntry 3 }

-- {COLUMN} 1.3.6.1.4.1.2356.11.1.10.19.14.1.4
lcsStatusIpRouterRipDynWanSitesEntryMasquerade OBJECT-TYPE
    SYNTAX     INTEGER {
                  eAuto (0),
                  eOn (1),
                  eIntranet (2)
            }
    MAX-ACCESS read-only
    STATUS     current
    DESCRIPTION
            ""
    ::= { lcsStatusIpRouterRipDynWanSitesEntry 4 }

-- {COLUMN} 1.3.6.1.4.1.2356.11.1.10.19.14.1.5
lcsStatusIpRouterRipDynWanSitesEntryDftRtgTag OBJECT-TYPE
    SYNTAX     Integer32 (0..65535)
    MAX-ACCESS read-only
    STATUS     current
    DESCRIPTION
            ""
    ::= { lcsStatusIpRouterRipDynWanSitesEntry 5 }

-- {COLUMN} 1.3.6.1.4.1.2356.11.1.10.19.14.1.6
lcsStatusIpRouterRipDynWanSitesEntryRtgTagList OBJECT-TYPE
    SYNTAX     DisplayString (SIZE(0..33))
    MAX-ACCESS read-only
    STATUS     current
    DESCRIPTION
            ""
    ::= { lcsStatusIpRouterRipDynWanSitesEntry 6 }

-- {COLUMN} 1.3.6.1.4.1.2356.11.1.10.19.14.1.7
lcsStatusIpRouterRipDynWanSitesEntryPoisonedReverse OBJECT-TYPE
    SYNTAX     INTEGER {
                  eNo (0),
                  eYes (1)
            }
    MAX-ACCESS read-only
    STATUS     current
    DESCRIPTION
            ""
    ::= { lcsStatusIpRouterRipDynWanSitesEntry 7 }

-- {COLUMN} 1.3.6.1.4.1.2356.11.1.10.19.14.1.8
lcsStatusIpRouterRipDynWanSitesEntryRfc2091 OBJECT-TYPE
    SYNTAX     INTEGER {
                  eNo (0),
                  eYes (1)
            }
    MAX-ACCESS read-only
    STATUS     current
    DESCRIPTION
            ""
    ::= { lcsStatusIpRouterRipDynWanSitesEntry 8 }

-- {COLUMN} 1.3.6.1.4.1.2356.11.1.10.19.14.1.9
lcsStatusIpRouterRipDynWanSitesEntryGateway OBJECT-TYPE
    SYNTAX     IpAddress
    MAX-ACCESS read-only
    STATUS     current
    DESCRIPTION
            ""
    ::= { lcsStatusIpRouterRipDynWanSitesEntry 9 }

-- {COLUMN} 1.3.6.1.4.1.2356.11.1.10.19.14.1.10
lcsStatusIpRouterRipDynWanSitesEntryRxFilter OBJECT-TYPE
    SYNTAX     DisplayString (SIZE(0..16))
    MAX-ACCESS read-only
    STATUS     current
    DESCRIPTION
            ""
    ::= { lcsStatusIpRouterRipDynWanSitesEntry 10 }

-- {COLUMN} 1.3.6.1.4.1.2356.11.1.10.19.14.1.11
lcsStatusIpRouterRipDynWanSitesEntryTxFilter OBJECT-TYPE
    SYNTAX     DisplayString (SIZE(0..16))
    MAX-ACCESS read-only
    STATUS     current
    DESCRIPTION
            ""
    ::= { lcsStatusIpRouterRipDynWanSitesEntry 11 }

-- {COLUMN} 1.3.6.1.4.1.2356.11.1.10.19.14.1.12
lcsStatusIpRouterRipDynWanSitesEntryRipSend OBJECT-TYPE
    SYNTAX     INTEGER {
                  eNo (0),
                  eYes (1)
            }
    MAX-ACCESS read-only
    STATUS     current
    DESCRIPTION
            ""
    ::= { lcsStatusIpRouterRipDynWanSitesEntry 12 }

-- {COLUMN} 1.3.6.1.4.1.2356.11.1.10.19.14.1.14
lcsStatusIpRouterRipDynWanSitesEntryIgnoreTags OBJECT-TYPE
    SYNTAX     INTEGER {
                  eNo (0),
                  eYes (1)
            }
    MAX-ACCESS read-only
    STATUS     current
    DESCRIPTION
            "-- empty --"
    ::= { lcsStatusIpRouterRipDynWanSitesEntry 14 }

-- {TABLE} 1.3.6.1.4.1.2356.11.1.10.19.15
lcsStatusIpRouterRipFilterTable OBJECT-TYPE
    SYNTAX     SEQUENCE OF LcsStatusIpRouterRipFilterEntry
    MAX-ACCESS not-accessible
    STATUS     current
    DESCRIPTION
            ""
    ::= { lcsStatusIpRouterRip 15 }

-- {ROW} 1.3.6.1.4.1.2356.11.1.10.19.15.1
lcsStatusIpRouterRipFilterEntry OBJECT-TYPE
    SYNTAX     LcsStatusIpRouterRipFilterEntry
    MAX-ACCESS not-accessible
    STATUS     current
    DESCRIPTION
            ""
    INDEX {
            lcsStatusIpRouterRipFilterEntryIdx
          }
    ::= { lcsStatusIpRouterRipFilterTable 1 }

LcsStatusIpRouterRipFilterEntry ::= SEQUENCE {
            lcsStatusIpRouterRipFilterEntryIdx Integer32,
            lcsStatusIpRouterRipFilterEntryType INTEGER,
            lcsStatusIpRouterRipFilterEntryName DisplayString,
            lcsStatusIpRouterRipFilterEntryIpAddress IpAddress,
            lcsStatusIpRouterRipFilterEntryIpNetmask IpAddress
    }

-- {COLUMN} 1.3.6.1.4.1.2356.11.1.10.19.15.1.1
lcsStatusIpRouterRipFilterEntryIdx OBJECT-TYPE
    SYNTAX     Integer32 (0..65535)
    MAX-ACCESS read-only
    STATUS     current
    DESCRIPTION
            ""
    ::= { lcsStatusIpRouterRipFilterEntry 1 }

-- {COLUMN} 1.3.6.1.4.1.2356.11.1.10.19.15.1.2
lcsStatusIpRouterRipFilterEntryType OBJECT-TYPE
    SYNTAX     INTEGER {
                  eUnknown (0),
                  ePositive (1),
                  eNegative (2)
            }
    MAX-ACCESS read-only
    STATUS     current
    DESCRIPTION
            ""
    ::= { lcsStatusIpRouterRipFilterEntry 2 }

-- {COLUMN} 1.3.6.1.4.1.2356.11.1.10.19.15.1.3
lcsStatusIpRouterRipFilterEntryName OBJECT-TYPE
    SYNTAX     DisplayString (SIZE(0..255))
    MAX-ACCESS read-only
    STATUS     current
    DESCRIPTION
            ""
    ::= { lcsStatusIpRouterRipFilterEntry 3 }

-- {COLUMN} 1.3.6.1.4.1.2356.11.1.10.19.15.1.4
lcsStatusIpRouterRipFilterEntryIpAddress OBJECT-TYPE
    SYNTAX     IpAddress
    MAX-ACCESS read-only
    STATUS     current
    DESCRIPTION
            ""
    ::= { lcsStatusIpRouterRipFilterEntry 4 }

-- {COLUMN} 1.3.6.1.4.1.2356.11.1.10.19.15.1.5
lcsStatusIpRouterRipFilterEntryIpNetmask OBJECT-TYPE
    SYNTAX     IpAddress
    MAX-ACCESS read-only
    STATUS     current
    DESCRIPTION
            ""
    ::= { lcsStatusIpRouterRipFilterEntry 5 }

-- {TABLE} 1.3.6.1.4.1.2356.11.1.10.19.16
lcsStatusIpRouterRipWildcardSitesTable OBJECT-TYPE
    SYNTAX     SEQUENCE OF LcsStatusIpRouterRipWildcardSitesEntry
    MAX-ACCESS not-accessible
    STATUS     current
    DESCRIPTION
            ""
    ::= { lcsStatusIpRouterRip 16 }

-- {ROW} 1.3.6.1.4.1.2356.11.1.10.19.16.1
lcsStatusIpRouterRipWildcardSitesEntry OBJECT-TYPE
    SYNTAX     LcsStatusIpRouterRipWildcardSitesEntry
    MAX-ACCESS not-accessible
    STATUS     current
    DESCRIPTION
            ""
    INDEX {
            lcsStatusIpRouterRipWildcardSitesEntryPeer
          }
    ::= { lcsStatusIpRouterRipWildcardSitesTable 1 }

LcsStatusIpRouterRipWildcardSitesEntry ::= SEQUENCE {
            lcsStatusIpRouterRipWildcardSitesEntryPeer DisplayString,
            lcsStatusIpRouterRipWildcardSitesEntryRipType INTEGER,
            lcsStatusIpRouterRipWildcardSitesEntryRipAccept INTEGER,
            lcsStatusIpRouterRipWildcardSitesEntryMasquerade INTEGER,
            lcsStatusIpRouterRipWildcardSitesEntryDftRtgTag Integer32,
            lcsStatusIpRouterRipWildcardSitesEntryRtgTagList DisplayString,
            lcsStatusIpRouterRipWildcardSitesEntryPoisonedReverse INTEGER,
            lcsStatusIpRouterRipWildcardSitesEntryRfc2091 INTEGER,
            lcsStatusIpRouterRipWildcardSitesEntryGateway IpAddress,
            lcsStatusIpRouterRipWildcardSitesEntryRxFilter DisplayString,
            lcsStatusIpRouterRipWildcardSitesEntryTxFilter DisplayString,
            lcsStatusIpRouterRipWildcardSitesEntryRipSend INTEGER,
            lcsStatusIpRouterRipWildcardSitesEntryIgnoreTags INTEGER
    }

-- {COLUMN} 1.3.6.1.4.1.2356.11.1.10.19.16.1.1
lcsStatusIpRouterRipWildcardSitesEntryPeer OBJECT-TYPE
    SYNTAX     DisplayString (SIZE(0..16))
    MAX-ACCESS read-only
    STATUS     current
    DESCRIPTION
            ""
    ::= { lcsStatusIpRouterRipWildcardSitesEntry 1 }

-- {COLUMN} 1.3.6.1.4.1.2356.11.1.10.19.16.1.2
lcsStatusIpRouterRipWildcardSitesEntryRipType OBJECT-TYPE
    SYNTAX     INTEGER {
                  eOff (0),
                  eRip1 (1),
                  eR1Comp (2),
                  eRip2 (3)
            }
    MAX-ACCESS read-only
    STATUS     current
    DESCRIPTION
            ""
    ::= { lcsStatusIpRouterRipWildcardSitesEntry 2 }

-- {COLUMN} 1.3.6.1.4.1.2356.11.1.10.19.16.1.3
lcsStatusIpRouterRipWildcardSitesEntryRipAccept OBJECT-TYPE
    SYNTAX     INTEGER {
                  eNo (0),
                  eYes (1)
            }
    MAX-ACCESS read-only
    STATUS     current
    DESCRIPTION
            ""
    ::= { lcsStatusIpRouterRipWildcardSitesEntry 3 }

-- {COLUMN} 1.3.6.1.4.1.2356.11.1.10.19.16.1.4
lcsStatusIpRouterRipWildcardSitesEntryMasquerade OBJECT-TYPE
    SYNTAX     INTEGER {
                  eAuto (0),
                  eOn (1),
                  eIntranet (2)
            }
    MAX-ACCESS read-only
    STATUS     current
    DESCRIPTION
            ""
    ::= { lcsStatusIpRouterRipWildcardSitesEntry 4 }

-- {COLUMN} 1.3.6.1.4.1.2356.11.1.10.19.16.1.5
lcsStatusIpRouterRipWildcardSitesEntryDftRtgTag OBJECT-TYPE
    SYNTAX     Integer32 (0..65535)
    MAX-ACCESS read-only
    STATUS     current
    DESCRIPTION
            ""
    ::= { lcsStatusIpRouterRipWildcardSitesEntry 5 }

-- {COLUMN} 1.3.6.1.4.1.2356.11.1.10.19.16.1.6
lcsStatusIpRouterRipWildcardSitesEntryRtgTagList OBJECT-TYPE
    SYNTAX     DisplayString (SIZE(0..33))
    MAX-ACCESS read-only
    STATUS     current
    DESCRIPTION
            ""
    ::= { lcsStatusIpRouterRipWildcardSitesEntry 6 }

-- {COLUMN} 1.3.6.1.4.1.2356.11.1.10.19.16.1.7
lcsStatusIpRouterRipWildcardSitesEntryPoisonedReverse OBJECT-TYPE
    SYNTAX     INTEGER {
                  eNo (0),
                  eYes (1)
            }
    MAX-ACCESS read-only
    STATUS     current
    DESCRIPTION
            ""
    ::= { lcsStatusIpRouterRipWildcardSitesEntry 7 }

-- {COLUMN} 1.3.6.1.4.1.2356.11.1.10.19.16.1.8
lcsStatusIpRouterRipWildcardSitesEntryRfc2091 OBJECT-TYPE
    SYNTAX     INTEGER {
                  eNo (0),
                  eYes (1)
            }
    MAX-ACCESS read-only
    STATUS     current
    DESCRIPTION
            ""
    ::= { lcsStatusIpRouterRipWildcardSitesEntry 8 }

-- {COLUMN} 1.3.6.1.4.1.2356.11.1.10.19.16.1.9
lcsStatusIpRouterRipWildcardSitesEntryGateway OBJECT-TYPE
    SYNTAX     IpAddress
    MAX-ACCESS read-only
    STATUS     current
    DESCRIPTION
            ""
    ::= { lcsStatusIpRouterRipWildcardSitesEntry 9 }

-- {COLUMN} 1.3.6.1.4.1.2356.11.1.10.19.16.1.10
lcsStatusIpRouterRipWildcardSitesEntryRxFilter OBJECT-TYPE
    SYNTAX     DisplayString (SIZE(0..16))
    MAX-ACCESS read-only
    STATUS     current
    DESCRIPTION
            ""
    ::= { lcsStatusIpRouterRipWildcardSitesEntry 10 }

-- {COLUMN} 1.3.6.1.4.1.2356.11.1.10.19.16.1.11
lcsStatusIpRouterRipWildcardSitesEntryTxFilter OBJECT-TYPE
    SYNTAX     DisplayString (SIZE(0..16))
    MAX-ACCESS read-only
    STATUS     current
    DESCRIPTION
            ""
    ::= { lcsStatusIpRouterRipWildcardSitesEntry 11 }

-- {COLUMN} 1.3.6.1.4.1.2356.11.1.10.19.16.1.12
lcsStatusIpRouterRipWildcardSitesEntryRipSend OBJECT-TYPE
    SYNTAX     INTEGER {
                  eNo (0),
                  eYes (1)
            }
    MAX-ACCESS read-only
    STATUS     current
    DESCRIPTION
            ""
    ::= { lcsStatusIpRouterRipWildcardSitesEntry 12 }

-- {COLUMN} 1.3.6.1.4.1.2356.11.1.10.19.16.1.14
lcsStatusIpRouterRipWildcardSitesEntryIgnoreTags OBJECT-TYPE
    SYNTAX     INTEGER {
                  eNo (0),
                  eYes (1)
            }
    MAX-ACCESS read-only
    STATUS     current
    DESCRIPTION
            "-- empty --"
    ::= { lcsStatusIpRouterRipWildcardSitesEntry 14 }

-- {TABLE} 1.3.6.1.4.1.2356.11.1.10.19.20
lcsStatusIpRouterRipAllRoutesTable OBJECT-TYPE
    SYNTAX     SEQUENCE OF LcsStatusIpRouterRipAllRoutesEntry
    MAX-ACCESS not-accessible
    STATUS     current
    DESCRIPTION
            ""
    ::= { lcsStatusIpRouterRip 20 }

-- {ROW} 1.3.6.1.4.1.2356.11.1.10.19.20.1
lcsStatusIpRouterRipAllRoutesEntry OBJECT-TYPE
    SYNTAX     LcsStatusIpRouterRipAllRoutesEntry
    MAX-ACCESS not-accessible
    STATUS     current
    DESCRIPTION
            ""
    INDEX {
            lcsStatusIpRouterRipAllRoutesEntryIpAddress,
            lcsStatusIpRouterRipAllRoutesEntryIpNetmask,
            lcsStatusIpRouterRipAllRoutesEntryRtgTag,
            lcsStatusIpRouterRipAllRoutesEntryGateway
          }
    ::= { lcsStatusIpRouterRipAllRoutesTable 1 }

LcsStatusIpRouterRipAllRoutesEntry ::= SEQUENCE {
            lcsStatusIpRouterRipAllRoutesEntryIpAddress IpAddress,
            lcsStatusIpRouterRipAllRoutesEntryIpNetmask IpAddress,
            lcsStatusIpRouterRipAllRoutesEntryTime Integer32,
            lcsStatusIpRouterRipAllRoutesEntryDistance Integer32,
            lcsStatusIpRouterRipAllRoutesEntryGateway IpAddress,
            lcsStatusIpRouterRipAllRoutesEntryRtgTag Integer32,
            lcsStatusIpRouterRipAllRoutesEntryPeer DisplayString,
            lcsStatusIpRouterRipAllRoutesEntryVlanId Integer32,
            lcsStatusIpRouterRipAllRoutesEntryNetworkName DisplayString,
            lcsStatusIpRouterRipAllRoutesEntryPort INTEGER
    }

-- {COLUMN} 1.3.6.1.4.1.2356.11.1.10.19.20.1.1
lcsStatusIpRouterRipAllRoutesEntryIpAddress OBJECT-TYPE
    SYNTAX     IpAddress
    MAX-ACCESS read-only
    STATUS     current
    DESCRIPTION
            ""
    ::= { lcsStatusIpRouterRipAllRoutesEntry 1 }

-- {COLUMN} 1.3.6.1.4.1.2356.11.1.10.19.20.1.2
lcsStatusIpRouterRipAllRoutesEntryIpNetmask OBJECT-TYPE
    SYNTAX     IpAddress
    MAX-ACCESS read-only
    STATUS     current
    DESCRIPTION
            ""
    ::= { lcsStatusIpRouterRipAllRoutesEntry 2 }

-- {COLUMN} 1.3.6.1.4.1.2356.11.1.10.19.20.1.3
lcsStatusIpRouterRipAllRoutesEntryTime OBJECT-TYPE
    SYNTAX     Integer32 (0..65535)
    MAX-ACCESS read-only
    STATUS     current
    DESCRIPTION
            ""
    ::= { lcsStatusIpRouterRipAllRoutesEntry 3 }

-- {COLUMN} 1.3.6.1.4.1.2356.11.1.10.19.20.1.4
lcsStatusIpRouterRipAllRoutesEntryDistance OBJECT-TYPE
    SYNTAX     Integer32 (0..65535)
    MAX-ACCESS read-only
    STATUS     current
    DESCRIPTION
            ""
    ::= { lcsStatusIpRouterRipAllRoutesEntry 4 }

-- {COLUMN} 1.3.6.1.4.1.2356.11.1.10.19.20.1.5
lcsStatusIpRouterRipAllRoutesEntryGateway OBJECT-TYPE
    SYNTAX     IpAddress
    MAX-ACCESS read-only
    STATUS     current
    DESCRIPTION
            ""
    ::= { lcsStatusIpRouterRipAllRoutesEntry 5 }

-- {COLUMN} 1.3.6.1.4.1.2356.11.1.10.19.20.1.6
lcsStatusIpRouterRipAllRoutesEntryRtgTag OBJECT-TYPE
    SYNTAX     Integer32 (0..65535)
    MAX-ACCESS read-only
    STATUS     current
    DESCRIPTION
            ""
    ::= { lcsStatusIpRouterRipAllRoutesEntry 6 }

-- {COLUMN} 1.3.6.1.4.1.2356.11.1.10.19.20.1.8
lcsStatusIpRouterRipAllRoutesEntryPeer OBJECT-TYPE
    SYNTAX     DisplayString (SIZE(0..255))
    MAX-ACCESS read-only
    STATUS     current
    DESCRIPTION
            ""
    ::= { lcsStatusIpRouterRipAllRoutesEntry 8 }

-- {COLUMN} 1.3.6.1.4.1.2356.11.1.10.19.20.1.10
lcsStatusIpRouterRipAllRoutesEntryVlanId OBJECT-TYPE
    SYNTAX     Integer32 (0..65535)
    MAX-ACCESS read-only
    STATUS     current
    DESCRIPTION
            ""
    ::= { lcsStatusIpRouterRipAllRoutesEntry 10 }

-- {COLUMN} 1.3.6.1.4.1.2356.11.1.10.19.20.1.11
lcsStatusIpRouterRipAllRoutesEntryNetworkName OBJECT-TYPE
    SYNTAX     DisplayString (SIZE(0..255))
    MAX-ACCESS read-only
    STATUS     current
    DESCRIPTION
            ""
    ::= { lcsStatusIpRouterRipAllRoutesEntry 11 }

-- {COLUMN} 1.3.6.1.4.1.2356.11.1.10.19.20.1.12
lcsStatusIpRouterRipAllRoutesEntryPort OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsStatusIpRouterRipAllRoutesEntry 12 }

-- {SCALAR} 1.3.6.1.4.1.2356.11.1.10.20
lcsStatusIpRouterDeleteValues OBJECT-TYPE
    SYNTAX     DisplayString
    MAX-ACCESS read-write
    STATUS     current
    DESCRIPTION
            ""
    ::= { lcsStatusIpRouter 20 }

-- {TABLE} 1.3.6.1.4.1.2356.11.1.10.21
lcsStatusIpRouterServiceTableTable OBJECT-TYPE
    SYNTAX     SEQUENCE OF LcsStatusIpRouterServiceTableEntry
    MAX-ACCESS not-accessible
    STATUS     current
    DESCRIPTION
            ""
    ::= { lcsStatusIpRouter 21 }

-- {ROW} 1.3.6.1.4.1.2356.11.1.10.21.1
lcsStatusIpRouterServiceTableEntry OBJECT-TYPE
    SYNTAX     LcsStatusIpRouterServiceTableEntry
    MAX-ACCESS not-accessible
    STATUS     current
    DESCRIPTION
            ""
    INDEX {
            lcsStatusIpRouterServiceTableEntryService
          }
    ::= { lcsStatusIpRouterServiceTableTable 1 }

LcsStatusIpRouterServiceTableEntry ::= SEQUENCE {
            lcsStatusIpRouterServiceTableEntryService INTEGER,
            lcsStatusIpRouterServiceTableEntryPacketRx Counter32,
            lcsStatusIpRouterServiceTableEntryPacketTx Counter32,
            lcsStatusIpRouterServiceTableEntryPacketRel DisplayString,
            lcsStatusIpRouterServiceTableEntryKbytesRx Counter32,
            lcsStatusIpRouterServiceTableEntryKbytesTx Counter32,
            lcsStatusIpRouterServiceTableEntryKbytesRel DisplayString
    }

-- {COLUMN} 1.3.6.1.4.1.2356.11.1.10.21.1.1
lcsStatusIpRouterServiceTableEntryService OBJECT-TYPE
    SYNTAX     INTEGER {
                  eIcmp (1),
                  eFtp (2),
                  eHttp (3),
                  eSmtp (4),
                  eDns (5),
                  eTelnet (6),
                  eTftp (7),
                  eDhcp (8),
                  ePop3 (9),
                  eNetbios (10),
                  eImap2 (11),
                  eNews (12),
                  eIrc (13),
                  eSnmp (14),
                  eOther (15),
                  eTotal (16)
            }
    MAX-ACCESS read-only
    STATUS     current
    DESCRIPTION
            ""
    ::= { lcsStatusIpRouterServiceTableEntry 1 }

-- {COLUMN} 1.3.6.1.4.1.2356.11.1.10.21.1.2
lcsStatusIpRouterServiceTableEntryPacketRx OBJECT-TYPE
    SYNTAX     Counter32
    MAX-ACCESS read-only
    STATUS     current
    DESCRIPTION
            ""
    ::= { lcsStatusIpRouterServiceTableEntry 2 }

-- {COLUMN} 1.3.6.1.4.1.2356.11.1.10.21.1.3
lcsStatusIpRouterServiceTableEntryPacketTx OBJECT-TYPE
    SYNTAX     Counter32
    MAX-ACCESS read-only
    STATUS     current
    DESCRIPTION
            ""
    ::= { lcsStatusIpRouterServiceTableEntry 3 }

-- {COLUMN} 1.3.6.1.4.1.2356.11.1.10.21.1.4
lcsStatusIpRouterServiceTableEntryPacketRel OBJECT-TYPE
    SYNTAX     DisplayString (SIZE(0..255))
    MAX-ACCESS read-only
    STATUS     current
    DESCRIPTION
            ""
    ::= { lcsStatusIpRouterServiceTableEntry 4 }

-- {COLUMN} 1.3.6.1.4.1.2356.11.1.10.21.1.5
lcsStatusIpRouterServiceTableEntryKbytesRx OBJECT-TYPE
    SYNTAX     Counter32
    MAX-ACCESS read-only
    STATUS     current
    DESCRIPTION
            ""
    ::= { lcsStatusIpRouterServiceTableEntry 5 }

-- {COLUMN} 1.3.6.1.4.1.2356.11.1.10.21.1.6
lcsStatusIpRouterServiceTableEntryKbytesTx OBJECT-TYPE
    SYNTAX     Counter32
    MAX-ACCESS read-only
    STATUS     current
    DESCRIPTION
            ""
    ::= { lcsStatusIpRouterServiceTableEntry 6 }

-- {COLUMN} 1.3.6.1.4.1.2356.11.1.10.21.1.7
lcsStatusIpRouterServiceTableEntryKbytesRel OBJECT-TYPE
    SYNTAX     DisplayString (SIZE(0..255))
    MAX-ACCESS read-only
    STATUS     current
    DESCRIPTION
            ""
    ::= { lcsStatusIpRouterServiceTableEntry 7 }

-- {TABLE} 1.3.6.1.4.1.2356.11.1.10.22
lcsStatusIpRouterFilterListTable OBJECT-TYPE
    SYNTAX     SEQUENCE OF LcsStatusIpRouterFilterListEntry
    MAX-ACCESS not-accessible
    STATUS     current
    DESCRIPTION
            ""
    ::= { lcsStatusIpRouter 22 }

-- {ROW} 1.3.6.1.4.1.2356.11.1.10.22.1
lcsStatusIpRouterFilterListEntry OBJECT-TYPE
    SYNTAX     LcsStatusIpRouterFilterListEntry
    MAX-ACCESS not-accessible
    STATUS     current
    DESCRIPTION
            ""
    INDEX {
            lcsStatusIpRouterFilterListEntryIdx
          }
    ::= { lcsStatusIpRouterFilterListTable 1 }

LcsStatusIpRouterFilterListEntry ::= SEQUENCE {
            lcsStatusIpRouterFilterListEntryIdx Integer32,
            lcsStatusIpRouterFilterListEntryProt Integer32,
            lcsStatusIpRouterFilterListEntrySrcAddress IpAddress,
            lcsStatusIpRouterFilterListEntrySrcNetmask IpAddress,
            lcsStatusIpRouterFilterListEntrySSt Integer32,
            lcsStatusIpRouterFilterListEntrySEnd Integer32,
            lcsStatusIpRouterFilterListEntryDstAddress IpAddress,
            lcsStatusIpRouterFilterListEntryDstNetmask IpAddress,
            lcsStatusIpRouterFilterListEntryDSt Integer32,
            lcsStatusIpRouterFilterListEntryDEnd Integer32,
            lcsStatusIpRouterFilterListEntryAction DisplayString,
            lcsStatusIpRouterFilterListEntrySrcMac DisplayString,
            lcsStatusIpRouterFilterListEntryDstMac DisplayString,
            lcsStatusIpRouterFilterListEntryLinked INTEGER,
            lcsStatusIpRouterFilterListEntryPrio Integer32,
            lcsStatusIpRouterFilterListEntryRtgTag Integer32,
            lcsStatusIpRouterFilterListEntrySrcTag Integer32,
            lcsStatusIpRouterFilterListEntrySource DisplayString,
            lcsStatusIpRouterFilterListEntryDestination DisplayString
    }

-- {COLUMN} 1.3.6.1.4.1.2356.11.1.10.22.1.1
lcsStatusIpRouterFilterListEntryIdx OBJECT-TYPE
    SYNTAX     Integer32 (0..2147483647)
    MAX-ACCESS read-only
    STATUS     current
    DESCRIPTION
            ""
    ::= { lcsStatusIpRouterFilterListEntry 1 }

-- {COLUMN} 1.3.6.1.4.1.2356.11.1.10.22.1.2
lcsStatusIpRouterFilterListEntryProt OBJECT-TYPE
    SYNTAX     Integer32 (0..255)
    MAX-ACCESS read-only
    STATUS     current
    DESCRIPTION
            ""
    ::= { lcsStatusIpRouterFilterListEntry 2 }

-- {COLUMN} 1.3.6.1.4.1.2356.11.1.10.22.1.3
lcsStatusIpRouterFilterListEntrySrcAddress OBJECT-TYPE
    SYNTAX     IpAddress
    MAX-ACCESS read-only
    STATUS     current
    DESCRIPTION
            ""
    ::= { lcsStatusIpRouterFilterListEntry 3 }

-- {COLUMN} 1.3.6.1.4.1.2356.11.1.10.22.1.4
lcsStatusIpRouterFilterListEntrySrcNetmask OBJECT-TYPE
    SYNTAX     IpAddress
    MAX-ACCESS read-only
    STATUS     current
    DESCRIPTION
            ""
    ::= { lcsStatusIpRouterFilterListEntry 4 }

-- {COLUMN} 1.3.6.1.4.1.2356.11.1.10.22.1.5
lcsStatusIpRouterFilterListEntrySSt OBJECT-TYPE
    SYNTAX     Integer32 (0..65535)
    MAX-ACCESS read-only
    STATUS     current
    DESCRIPTION
            ""
    ::= { lcsStatusIpRouterFilterListEntry 5 }

-- {COLUMN} 1.3.6.1.4.1.2356.11.1.10.22.1.6
lcsStatusIpRouterFilterListEntrySEnd OBJECT-TYPE
    SYNTAX     Integer32 (0..65535)
    MAX-ACCESS read-only
    STATUS     current
    DESCRIPTION
            ""
    ::= { lcsStatusIpRouterFilterListEntry 6 }

-- {COLUMN} 1.3.6.1.4.1.2356.11.1.10.22.1.7
lcsStatusIpRouterFilterListEntryDstAddress OBJECT-TYPE
    SYNTAX     IpAddress
    MAX-ACCESS read-only
    STATUS     current
    DESCRIPTION
            ""
    ::= { lcsStatusIpRouterFilterListEntry 7 }

-- {COLUMN} 1.3.6.1.4.1.2356.11.1.10.22.1.8
lcsStatusIpRouterFilterListEntryDstNetmask OBJECT-TYPE
    SYNTAX     IpAddress
    MAX-ACCESS read-only
    STATUS     current
    DESCRIPTION
            ""
    ::= { lcsStatusIpRouterFilterListEntry 8 }

-- {COLUMN} 1.3.6.1.4.1.2356.11.1.10.22.1.9
lcsStatusIpRouterFilterListEntryDSt OBJECT-TYPE
    SYNTAX     Integer32 (0..65535)
    MAX-ACCESS read-only
    STATUS     current
    DESCRIPTION
            ""
    ::= { lcsStatusIpRouterFilterListEntry 9 }

-- {COLUMN} 1.3.6.1.4.1.2356.11.1.10.22.1.10
lcsStatusIpRouterFilterListEntryDEnd OBJECT-TYPE
    SYNTAX     Integer32 (0..65535)
    MAX-ACCESS read-only
    STATUS     current
    DESCRIPTION
            ""
    ::= { lcsStatusIpRouterFilterListEntry 10 }

-- {COLUMN} 1.3.6.1.4.1.2356.11.1.10.22.1.11
lcsStatusIpRouterFilterListEntryAction OBJECT-TYPE
    SYNTAX     DisplayString (SIZE(0..255))
    MAX-ACCESS read-only
    STATUS     current
    DESCRIPTION
            ""
    ::= { lcsStatusIpRouterFilterListEntry 11 }

-- {COLUMN} 1.3.6.1.4.1.2356.11.1.10.22.1.13
lcsStatusIpRouterFilterListEntrySrcMac OBJECT-TYPE
    SYNTAX     DisplayString (SIZE(0..255))
    MAX-ACCESS read-only
    STATUS     current
    DESCRIPTION
            ""
    ::= { lcsStatusIpRouterFilterListEntry 13 }

-- {COLUMN} 1.3.6.1.4.1.2356.11.1.10.22.1.14
lcsStatusIpRouterFilterListEntryDstMac OBJECT-TYPE
    SYNTAX     DisplayString (SIZE(0..255))
    MAX-ACCESS read-only
    STATUS     current
    DESCRIPTION
            ""
    ::= { lcsStatusIpRouterFilterListEntry 14 }

-- {COLUMN} 1.3.6.1.4.1.2356.11.1.10.22.1.15
lcsStatusIpRouterFilterListEntryLinked OBJECT-TYPE
    SYNTAX     INTEGER {
                  eNo (0),
                  eYes (1)
            }
    MAX-ACCESS read-only
    STATUS     current
    DESCRIPTION
            ""
    ::= { lcsStatusIpRouterFilterListEntry 15 }

-- {COLUMN} 1.3.6.1.4.1.2356.11.1.10.22.1.16
lcsStatusIpRouterFilterListEntryPrio OBJECT-TYPE
    SYNTAX     Integer32 (0..65535)
    MAX-ACCESS read-only
    STATUS     current
    DESCRIPTION
            ""
    ::= { lcsStatusIpRouterFilterListEntry 16 }

-- {COLUMN} 1.3.6.1.4.1.2356.11.1.10.22.1.17
lcsStatusIpRouterFilterListEntryRtgTag OBJECT-TYPE
    SYNTAX     Integer32 (0..65535)
    MAX-ACCESS read-only
    STATUS     current
    DESCRIPTION
            ""
    ::= { lcsStatusIpRouterFilterListEntry 17 }

-- {COLUMN} 1.3.6.1.4.1.2356.11.1.10.22.1.18
lcsStatusIpRouterFilterListEntrySrcTag OBJECT-TYPE
    SYNTAX     Integer32 (0..65535)
    MAX-ACCESS read-only
    STATUS     current
    DESCRIPTION
            "-- empty --"
    ::= { lcsStatusIpRouterFilterListEntry 18 }

-- {COLUMN} 1.3.6.1.4.1.2356.11.1.10.22.1.19
lcsStatusIpRouterFilterListEntrySource OBJECT-TYPE
    SYNTAX     DisplayString (SIZE(0..255))
    MAX-ACCESS read-only
    STATUS     current
    DESCRIPTION
            "-- empty --"
    ::= { lcsStatusIpRouterFilterListEntry 19 }

-- {COLUMN} 1.3.6.1.4.1.2356.11.1.10.22.1.20
lcsStatusIpRouterFilterListEntryDestination OBJECT-TYPE
    SYNTAX     DisplayString (SIZE(0..255))
    MAX-ACCESS read-only
    STATUS     current
    DESCRIPTION
            "-- empty --"
    ::= { lcsStatusIpRouterFilterListEntry 20 }

-- {TABLE} 1.3.6.1.4.1.2356.11.1.10.23
lcsStatusIpRouterConnectionListTable OBJECT-TYPE
    SYNTAX     SEQUENCE OF LcsStatusIpRouterConnectionListEntry
    MAX-ACCESS not-accessible
    STATUS     current
    DESCRIPTION
            ""
    ::= { lcsStatusIpRouter 23 }

-- {ROW} 1.3.6.1.4.1.2356.11.1.10.23.1
lcsStatusIpRouterConnectionListEntry OBJECT-TYPE
    SYNTAX     LcsStatusIpRouterConnectionListEntry
    MAX-ACCESS not-accessible
    STATUS     current
    DESCRIPTION
            ""
    INDEX {
            lcsStatusIpRouterConnectionListEntrySrcAddress,
            lcsStatusIpRouterConnectionListEntryDstAddress,
            lcsStatusIpRouterConnectionListEntryProt,
            lcsStatusIpRouterConnectionListEntrySrcPort,
            lcsStatusIpRouterConnectionListEntryDstPort
          }
    ::= { lcsStatusIpRouterConnectionListTable 1 }

LcsStatusIpRouterConnectionListEntry ::= SEQUENCE {
            lcsStatusIpRouterConnectionListEntrySrcAddress IpAddress,
            lcsStatusIpRouterConnectionListEntryDstAddress IpAddress,
            lcsStatusIpRouterConnectionListEntryProt Integer32,
            lcsStatusIpRouterConnectionListEntrySrcPort Integer32,
            lcsStatusIpRouterConnectionListEntryDstPort Integer32,
            lcsStatusIpRouterConnectionListEntryTimeout Integer32,
            lcsStatusIpRouterConnectionListEntryFlags Integer32,
            lcsStatusIpRouterConnectionListEntryFilterRule DisplayString,
            lcsStatusIpRouterConnectionListEntrySrcRoute DisplayString,
            lcsStatusIpRouterConnectionListEntryDestRoute DisplayString,
            lcsStatusIpRouterConnectionListEntryRtgTag Integer32
    }

-- {COLUMN} 1.3.6.1.4.1.2356.11.1.10.23.1.1
lcsStatusIpRouterConnectionListEntrySrcAddress OBJECT-TYPE
    SYNTAX     IpAddress
    MAX-ACCESS read-only
    STATUS     current
    DESCRIPTION
            ""
    ::= { lcsStatusIpRouterConnectionListEntry 1 }

-- {COLUMN} 1.3.6.1.4.1.2356.11.1.10.23.1.2
lcsStatusIpRouterConnectionListEntryDstAddress OBJECT-TYPE
    SYNTAX     IpAddress
    MAX-ACCESS read-only
    STATUS     current
    DESCRIPTION
            ""
    ::= { lcsStatusIpRouterConnectionListEntry 2 }

-- {COLUMN} 1.3.6.1.4.1.2356.11.1.10.23.1.3
lcsStatusIpRouterConnectionListEntryProt OBJECT-TYPE
    SYNTAX     Integer32 (0..255)
    MAX-ACCESS read-only
    STATUS     current
    DESCRIPTION
            ""
    ::= { lcsStatusIpRouterConnectionListEntry 3 }

-- {COLUMN} 1.3.6.1.4.1.2356.11.1.10.23.1.4
lcsStatusIpRouterConnectionListEntrySrcPort OBJECT-TYPE
    SYNTAX     Integer32 (0..65535)
    MAX-ACCESS read-only
    STATUS     current
    DESCRIPTION
            ""
    ::= { lcsStatusIpRouterConnectionListEntry 4 }

-- {COLUMN} 1.3.6.1.4.1.2356.11.1.10.23.1.5
lcsStatusIpRouterConnectionListEntryDstPort OBJECT-TYPE
    SYNTAX     Integer32 (0..65535)
    MAX-ACCESS read-only
    STATUS     current
    DESCRIPTION
            ""
    ::= { lcsStatusIpRouterConnectionListEntry 5 }

-- {COLUMN} 1.3.6.1.4.1.2356.11.1.10.23.1.6
lcsStatusIpRouterConnectionListEntryTimeout OBJECT-TYPE
    SYNTAX     Integer32 (0..65535)
    MAX-ACCESS read-only
    STATUS     current
    DESCRIPTION
            ""
    ::= { lcsStatusIpRouterConnectionListEntry 6 }

-- {COLUMN} 1.3.6.1.4.1.2356.11.1.10.23.1.7
lcsStatusIpRouterConnectionListEntryFlags OBJECT-TYPE
    SYNTAX     Integer32 (0..2147483647)
    MAX-ACCESS read-only
    STATUS     current
    DESCRIPTION
            ""
    ::= { lcsStatusIpRouterConnectionListEntry 7 }

-- {COLUMN} 1.3.6.1.4.1.2356.11.1.10.23.1.8
lcsStatusIpRouterConnectionListEntryFilterRule OBJECT-TYPE
    SYNTAX     DisplayString (SIZE(0..255))
    MAX-ACCESS read-only
    STATUS     current
    DESCRIPTION
            ""
    ::= { lcsStatusIpRouterConnectionListEntry 8 }

-- {COLUMN} 1.3.6.1.4.1.2356.11.1.10.23.1.9
lcsStatusIpRouterConnectionListEntrySrcRoute OBJECT-TYPE
    SYNTAX     DisplayString (SIZE(0..255))
    MAX-ACCESS read-only
    STATUS     current
    DESCRIPTION
            ""
    ::= { lcsStatusIpRouterConnectionListEntry 9 }

-- {COLUMN} 1.3.6.1.4.1.2356.11.1.10.23.1.10
lcsStatusIpRouterConnectionListEntryDestRoute OBJECT-TYPE
    SYNTAX     DisplayString (SIZE(0..255))
    MAX-ACCESS read-only
    STATUS     current
    DESCRIPTION
            ""
    ::= { lcsStatusIpRouterConnectionListEntry 10 }

-- {COLUMN} 1.3.6.1.4.1.2356.11.1.10.23.1.11
lcsStatusIpRouterConnectionListEntryRtgTag OBJECT-TYPE
    SYNTAX     Integer32 (0..65535)
    MAX-ACCESS read-only
    STATUS     current
    DESCRIPTION
            ""
    ::= { lcsStatusIpRouterConnectionListEntry 11 }

-- {TABLE} 1.3.6.1.4.1.2356.11.1.10.24
lcsStatusIpRouterHostBlockListTable OBJECT-TYPE
    SYNTAX     SEQUENCE OF LcsStatusIpRouterHostBlockListEntry
    MAX-ACCESS not-accessible
    STATUS     current
    DESCRIPTION
            ""
    ::= { lcsStatusIpRouter 24 }

-- {ROW} 1.3.6.1.4.1.2356.11.1.10.24.1
lcsStatusIpRouterHostBlockListEntry OBJECT-TYPE
    SYNTAX     LcsStatusIpRouterHostBlockListEntry
    MAX-ACCESS not-accessible
    STATUS     current
    DESCRIPTION
            ""
    INDEX {
            lcsStatusIpRouterHostBlockListEntrySrcAddress
          }
    ::= { lcsStatusIpRouterHostBlockListTable 1 }

LcsStatusIpRouterHostBlockListEntry ::= SEQUENCE {
            lcsStatusIpRouterHostBlockListEntrySrcAddress IpAddress,
            lcsStatusIpRouterHostBlockListEntryTimeout Integer32,
            lcsStatusIpRouterHostBlockListEntryFilterRule DisplayString
    }

-- {COLUMN} 1.3.6.1.4.1.2356.11.1.10.24.1.1
lcsStatusIpRouterHostBlockListEntrySrcAddress OBJECT-TYPE
    SYNTAX     IpAddress
    MAX-ACCESS read-only
    STATUS     current
    DESCRIPTION
            ""
    ::= { lcsStatusIpRouterHostBlockListEntry 1 }

-- {COLUMN} 1.3.6.1.4.1.2356.11.1.10.24.1.2
lcsStatusIpRouterHostBlockListEntryTimeout OBJECT-TYPE
    SYNTAX     Integer32 (0..2147483647)
    MAX-ACCESS read-only
    STATUS     current
    DESCRIPTION
            ""
    ::= { lcsStatusIpRouterHostBlockListEntry 2 }

-- {COLUMN} 1.3.6.1.4.1.2356.11.1.10.24.1.3
lcsStatusIpRouterHostBlockListEntryFilterRule OBJECT-TYPE
    SYNTAX     DisplayString (SIZE(0..255))
    MAX-ACCESS read-only
    STATUS     current
    DESCRIPTION
            ""
    ::= { lcsStatusIpRouterHostBlockListEntry 3 }

-- {TABLE} 1.3.6.1.4.1.2356.11.1.10.25
lcsStatusIpRouterPortBlockListTable OBJECT-TYPE
    SYNTAX     SEQUENCE OF LcsStatusIpRouterPortBlockListEntry
    MAX-ACCESS not-accessible
    STATUS     current
    DESCRIPTION
            ""
    ::= { lcsStatusIpRouter 25 }

-- {ROW} 1.3.6.1.4.1.2356.11.1.10.25.1
lcsStatusIpRouterPortBlockListEntry OBJECT-TYPE
    SYNTAX     LcsStatusIpRouterPortBlockListEntry
    MAX-ACCESS not-accessible
    STATUS     current
    DESCRIPTION
            ""
    INDEX {
            lcsStatusIpRouterPortBlockListEntryDstAddress
          }
    ::= { lcsStatusIpRouterPortBlockListTable 1 }

LcsStatusIpRouterPortBlockListEntry ::= SEQUENCE {
            lcsStatusIpRouterPortBlockListEntryDstAddress IpAddress,
            lcsStatusIpRouterPortBlockListEntryProt Integer32,
            lcsStatusIpRouterPortBlockListEntryDstPort Integer32,
            lcsStatusIpRouterPortBlockListEntryTimeout Integer32,
            lcsStatusIpRouterPortBlockListEntryFilterRule DisplayString
    }

-- {COLUMN} 1.3.6.1.4.1.2356.11.1.10.25.1.1
lcsStatusIpRouterPortBlockListEntryDstAddress OBJECT-TYPE
    SYNTAX     IpAddress
    MAX-ACCESS read-only
    STATUS     current
    DESCRIPTION
            ""
    ::= { lcsStatusIpRouterPortBlockListEntry 1 }

-- {COLUMN} 1.3.6.1.4.1.2356.11.1.10.25.1.2
lcsStatusIpRouterPortBlockListEntryProt OBJECT-TYPE
    SYNTAX     Integer32 (0..65535)
    MAX-ACCESS read-only
    STATUS     current
    DESCRIPTION
            ""
    ::= { lcsStatusIpRouterPortBlockListEntry 2 }

-- {COLUMN} 1.3.6.1.4.1.2356.11.1.10.25.1.3
lcsStatusIpRouterPortBlockListEntryDstPort OBJECT-TYPE
    SYNTAX     Integer32 (0..65535)
    MAX-ACCESS read-only
    STATUS     current
    DESCRIPTION
            ""
    ::= { lcsStatusIpRouterPortBlockListEntry 3 }

-- {COLUMN} 1.3.6.1.4.1.2356.11.1.10.25.1.4
lcsStatusIpRouterPortBlockListEntryTimeout OBJECT-TYPE
    SYNTAX     Integer32 (0..2147483647)
    MAX-ACCESS read-only
    STATUS     current
    DESCRIPTION
            ""
    ::= { lcsStatusIpRouterPortBlockListEntry 4 }

-- {COLUMN} 1.3.6.1.4.1.2356.11.1.10.25.1.5
lcsStatusIpRouterPortBlockListEntryFilterRule OBJECT-TYPE
    SYNTAX     DisplayString (SIZE(0..255))
    MAX-ACCESS read-only
    STATUS     current
    DESCRIPTION
            ""
    ::= { lcsStatusIpRouterPortBlockListEntry 5 }

-- {TABLE} 1.3.6.1.4.1.2356.11.1.10.26
lcsStatusIpRouterLogTableTable OBJECT-TYPE
    SYNTAX     SEQUENCE OF LcsStatusIpRouterLogTableEntry
    MAX-ACCESS not-accessible
    STATUS     current
    DESCRIPTION
            ""
    ::= { lcsStatusIpRouter 26 }

-- {ROW} 1.3.6.1.4.1.2356.11.1.10.26.1
lcsStatusIpRouterLogTableEntry OBJECT-TYPE
    SYNTAX     LcsStatusIpRouterLogTableEntry
    MAX-ACCESS not-accessible
    STATUS     current
    DESCRIPTION
            ""
    INDEX {
            lcsStatusIpRouterLogTableEntryIdx
          }
    ::= { lcsStatusIpRouterLogTableTable 1 }

LcsStatusIpRouterLogTableEntry ::= SEQUENCE {
            lcsStatusIpRouterLogTableEntryIdx Integer32,
            lcsStatusIpRouterLogTableEntrySystemTime DisplayString,
            lcsStatusIpRouterLogTableEntrySrcAddress IpAddress,
            lcsStatusIpRouterLogTableEntryDstAddress IpAddress,
            lcsStatusIpRouterLogTableEntryProt Integer32,
            lcsStatusIpRouterLogTableEntrySrcPort Integer32,
            lcsStatusIpRouterLogTableEntryDstPort Integer32,
            lcsStatusIpRouterLogTableEntryFilterRule DisplayString,
            lcsStatusIpRouterLogTableEntryLimit Integer32,
            lcsStatusIpRouterLogTableEntryThreshold Integer32,
            lcsStatusIpRouterLogTableEntryAction Integer32
    }

-- {COLUMN} 1.3.6.1.4.1.2356.11.1.10.26.1.1
lcsStatusIpRouterLogTableEntryIdx OBJECT-TYPE
    SYNTAX     Integer32 (0..65535)
    MAX-ACCESS read-only
    STATUS     current
    DESCRIPTION
            ""
    ::= { lcsStatusIpRouterLogTableEntry 1 }

-- {COLUMN} 1.3.6.1.4.1.2356.11.1.10.26.1.2
lcsStatusIpRouterLogTableEntrySystemTime OBJECT-TYPE
    SYNTAX     DisplayString (SIZE(0..19))
    MAX-ACCESS read-only
    STATUS     current
    DESCRIPTION
            ""
    ::= { lcsStatusIpRouterLogTableEntry 2 }

-- {COLUMN} 1.3.6.1.4.1.2356.11.1.10.26.1.3
lcsStatusIpRouterLogTableEntrySrcAddress OBJECT-TYPE
    SYNTAX     IpAddress
    MAX-ACCESS read-only
    STATUS     current
    DESCRIPTION
            ""
    ::= { lcsStatusIpRouterLogTableEntry 3 }

-- {COLUMN} 1.3.6.1.4.1.2356.11.1.10.26.1.4
lcsStatusIpRouterLogTableEntryDstAddress OBJECT-TYPE
    SYNTAX     IpAddress
    MAX-ACCESS read-only
    STATUS     current
    DESCRIPTION
            ""
    ::= { lcsStatusIpRouterLogTableEntry 4 }

-- {COLUMN} 1.3.6.1.4.1.2356.11.1.10.26.1.5
lcsStatusIpRouterLogTableEntryProt OBJECT-TYPE
    SYNTAX     Integer32 (0..255)
    MAX-ACCESS read-only
    STATUS     current
    DESCRIPTION
            ""
    ::= { lcsStatusIpRouterLogTableEntry 5 }

-- {COLUMN} 1.3.6.1.4.1.2356.11.1.10.26.1.6
lcsStatusIpRouterLogTableEntrySrcPort OBJECT-TYPE
    SYNTAX     Integer32 (0..65535)
    MAX-ACCESS read-only
    STATUS     current
    DESCRIPTION
            ""
    ::= { lcsStatusIpRouterLogTableEntry 6 }

-- {COLUMN} 1.3.6.1.4.1.2356.11.1.10.26.1.7
lcsStatusIpRouterLogTableEntryDstPort OBJECT-TYPE
    SYNTAX     Integer32 (0..65535)
    MAX-ACCESS read-only
    STATUS     current
    DESCRIPTION
            ""
    ::= { lcsStatusIpRouterLogTableEntry 7 }

-- {COLUMN} 1.3.6.1.4.1.2356.11.1.10.26.1.8
lcsStatusIpRouterLogTableEntryFilterRule OBJECT-TYPE
    SYNTAX     DisplayString (SIZE(0..32))
    MAX-ACCESS read-only
    STATUS     current
    DESCRIPTION
            ""
    ::= { lcsStatusIpRouterLogTableEntry 8 }

-- {COLUMN} 1.3.6.1.4.1.2356.11.1.10.26.1.9
lcsStatusIpRouterLogTableEntryLimit OBJECT-TYPE
    SYNTAX     Integer32 (0..2147483647)
    MAX-ACCESS read-only
    STATUS     current
    DESCRIPTION
            ""
    ::= { lcsStatusIpRouterLogTableEntry 9 }

-- {COLUMN} 1.3.6.1.4.1.2356.11.1.10.26.1.10
lcsStatusIpRouterLogTableEntryThreshold OBJECT-TYPE
    SYNTAX     Integer32 (0..2147483647)
    MAX-ACCESS read-only
    STATUS     current
    DESCRIPTION
            ""
    ::= { lcsStatusIpRouterLogTableEntry 10 }

-- {COLUMN} 1.3.6.1.4.1.2356.11.1.10.26.1.11
lcsStatusIpRouterLogTableEntryAction OBJECT-TYPE
    SYNTAX     Integer32 (0..2147483647)
    MAX-ACCESS read-only
    STATUS     current
    DESCRIPTION
            ""
    ::= { lcsStatusIpRouterLogTableEntry 11 }

-- {TABLE} 1.3.6.1.4.1.2356.11.1.10.27
lcsStatusIpRouterHoConnListTable OBJECT-TYPE
    SYNTAX     SEQUENCE OF LcsStatusIpRouterHoConnListEntry
    MAX-ACCESS not-accessible
    STATUS     current
    DESCRIPTION
            ""
    ::= { lcsStatusIpRouter 27 }

-- {ROW} 1.3.6.1.4.1.2356.11.1.10.27.1
lcsStatusIpRouterHoConnListEntry OBJECT-TYPE
    SYNTAX     LcsStatusIpRouterHoConnListEntry
    MAX-ACCESS not-accessible
    STATUS     current
    DESCRIPTION
            ""
    INDEX {
            lcsStatusIpRouterHoConnListEntryDstAddress
          }
    ::= { lcsStatusIpRouterHoConnListTable 1 }

LcsStatusIpRouterHoConnListEntry ::= SEQUENCE {
            lcsStatusIpRouterHoConnListEntryDstAddress IpAddress,
            lcsStatusIpRouterHoConnListEntryNumHoConn Integer32,
            lcsStatusIpRouterHoConnListEntryTimeout Integer32
    }

-- {COLUMN} 1.3.6.1.4.1.2356.11.1.10.27.1.1
lcsStatusIpRouterHoConnListEntryDstAddress OBJECT-TYPE
    SYNTAX     IpAddress
    MAX-ACCESS read-only
    STATUS     current
    DESCRIPTION
            ""
    ::= { lcsStatusIpRouterHoConnListEntry 1 }

-- {COLUMN} 1.3.6.1.4.1.2356.11.1.10.27.1.2
lcsStatusIpRouterHoConnListEntryNumHoConn OBJECT-TYPE
    SYNTAX     Integer32 (0..2147483647)
    MAX-ACCESS read-only
    STATUS     current
    DESCRIPTION
            ""
    ::= { lcsStatusIpRouterHoConnListEntry 2 }

-- {COLUMN} 1.3.6.1.4.1.2356.11.1.10.27.1.3
lcsStatusIpRouterHoConnListEntryTimeout OBJECT-TYPE
    SYNTAX     Integer32 (0..65535)
    MAX-ACCESS read-only
    STATUS     current
    DESCRIPTION
            ""
    ::= { lcsStatusIpRouterHoConnListEntry 3 }

-- {TABLE} 1.3.6.1.4.1.2356.11.1.10.28
lcsStatusIpRouterQosTable OBJECT-TYPE
    SYNTAX     SEQUENCE OF LcsStatusIpRouterQosEntry
    MAX-ACCESS not-accessible
    STATUS     current
    DESCRIPTION
            ""
    ::= { lcsStatusIpRouter 28 }

-- {ROW} 1.3.6.1.4.1.2356.11.1.10.28.1
lcsStatusIpRouterQosEntry OBJECT-TYPE
    SYNTAX     LcsStatusIpRouterQosEntry
    MAX-ACCESS not-accessible
    STATUS     current
    DESCRIPTION
            ""
    INDEX {
            lcsStatusIpRouterQosEntryIfc
          }
    ::= { lcsStatusIpRouterQosTable 1 }

LcsStatusIpRouterQosEntry ::= SEQUENCE {
            lcsStatusIpRouterQosEntryIfc INTEGER,
            lcsStatusIpRouterQosEntryPeer DisplayString,
            lcsStatusIpRouterQosEntryDownstreamRate Integer32,
            lcsStatusIpRouterQosEntryRxReserved Integer32,
            lcsStatusIpRouterQosEntryRxBlocksPending Integer32,
            lcsStatusIpRouterQosEntryFragmentSize Integer32,
            lcsStatusIpRouterQosEntryPmtuSize Integer32,
            lcsStatusIpRouterQosEntryUpstreamRate Integer32,
            lcsStatusIpRouterQosEntryTxReserved Integer32,
            lcsStatusIpRouterQosEntryTxBlocksPending Integer32,
            lcsStatusIpRouterQosEntryRxRequested Integer32,
            lcsStatusIpRouterQosEntryTxRequested Integer32,
            lcsStatusIpRouterQosEntryTxFavoured Integer32
    }

-- {COLUMN} 1.3.6.1.4.1.2356.11.1.10.28.1.1
lcsStatusIpRouterQosEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusIpRouterQosEntry 1 }

-- {COLUMN} 1.3.6.1.4.1.2356.11.1.10.28.1.2
lcsStatusIpRouterQosEntryPeer OBJECT-TYPE
    SYNTAX     DisplayString (SIZE(0..16))
    MAX-ACCESS read-only
    STATUS     current
    DESCRIPTION
            ""
    ::= { lcsStatusIpRouterQosEntry 2 }

-- {COLUMN} 1.3.6.1.4.1.2356.11.1.10.28.1.3
lcsStatusIpRouterQosEntryDownstreamRate OBJECT-TYPE
    SYNTAX     Integer32 (0..2147483647)
    MAX-ACCESS read-only
    STATUS     current
    DESCRIPTION
            ""
    ::= { lcsStatusIpRouterQosEntry 3 }

-- {COLUMN} 1.3.6.1.4.1.2356.11.1.10.28.1.4
lcsStatusIpRouterQosEntryRxReserved OBJECT-TYPE
    SYNTAX     Integer32 (0..2147483647)
    MAX-ACCESS read-only
    STATUS     current
    DESCRIPTION
            ""
    ::= { lcsStatusIpRouterQosEntry 4 }

-- {COLUMN} 1.3.6.1.4.1.2356.11.1.10.28.1.5
lcsStatusIpRouterQosEntryRxBlocksPending OBJECT-TYPE
    SYNTAX     Integer32 (0..65535)
    MAX-ACCESS read-only
    STATUS     current
    DESCRIPTION
            ""
    ::= { lcsStatusIpRouterQosEntry 5 }

-- {COLUMN} 1.3.6.1.4.1.2356.11.1.10.28.1.6
lcsStatusIpRouterQosEntryFragmentSize OBJECT-TYPE
    SYNTAX     Integer32 (0..65535)
    MAX-ACCESS read-only
    STATUS     current
    DESCRIPTION
            ""
    ::= { lcsStatusIpRouterQosEntry 6 }

-- {COLUMN} 1.3.6.1.4.1.2356.11.1.10.28.1.7
lcsStatusIpRouterQosEntryPmtuSize OBJECT-TYPE
    SYNTAX     Integer32 (0..65535)
    MAX-ACCESS read-only
    STATUS     current
    DESCRIPTION
            ""
    ::= { lcsStatusIpRouterQosEntry 7 }

-- {COLUMN} 1.3.6.1.4.1.2356.11.1.10.28.1.8
lcsStatusIpRouterQosEntryUpstreamRate OBJECT-TYPE
    SYNTAX     Integer32 (0..2147483647)
    MAX-ACCESS read-only
    STATUS     current
    DESCRIPTION
            ""
    ::= { lcsStatusIpRouterQosEntry 8 }

-- {COLUMN} 1.3.6.1.4.1.2356.11.1.10.28.1.9
lcsStatusIpRouterQosEntryTxReserved OBJECT-TYPE
    SYNTAX     Integer32 (0..2147483647)
    MAX-ACCESS read-only
    STATUS     current
    DESCRIPTION
            ""
    ::= { lcsStatusIpRouterQosEntry 9 }

-- {COLUMN} 1.3.6.1.4.1.2356.11.1.10.28.1.10
lcsStatusIpRouterQosEntryTxBlocksPending OBJECT-TYPE
    SYNTAX     Integer32 (0..65535)
    MAX-ACCESS read-only
    STATUS     current
    DESCRIPTION
            ""
    ::= { lcsStatusIpRouterQosEntry 10 }

-- {COLUMN} 1.3.6.1.4.1.2356.11.1.10.28.1.11
lcsStatusIpRouterQosEntryRxRequested OBJECT-TYPE
    SYNTAX     Integer32 (0..2147483647)
    MAX-ACCESS read-only
    STATUS     current
    DESCRIPTION
            ""
    ::= { lcsStatusIpRouterQosEntry 11 }

-- {COLUMN} 1.3.6.1.4.1.2356.11.1.10.28.1.12
lcsStatusIpRouterQosEntryTxRequested OBJECT-TYPE
    SYNTAX     Integer32 (0..2147483647)
    MAX-ACCESS read-only
    STATUS     current
    DESCRIPTION
            ""
    ::= { lcsStatusIpRouterQosEntry 12 }

-- {COLUMN} 1.3.6.1.4.1.2356.11.1.10.28.1.13
lcsStatusIpRouterQosEntryTxFavoured OBJECT-TYPE
    SYNTAX     Integer32 (0..2147483647)
    MAX-ACCESS read-only
    STATUS     current
    DESCRIPTION
            ""
    ::= { lcsStatusIpRouterQosEntry 13 }

-- {TABLE} 1.3.6.1.4.1.2356.11.1.10.29
lcsStatusIpRouterOpenPortListTable OBJECT-TYPE
    SYNTAX     SEQUENCE OF LcsStatusIpRouterOpenPortListEntry
    MAX-ACCESS not-accessible
    STATUS     current
    DESCRIPTION
            ""
    ::= { lcsStatusIpRouter 29 }

-- {ROW} 1.3.6.1.4.1.2356.11.1.10.29.1
lcsStatusIpRouterOpenPortListEntry OBJECT-TYPE
    SYNTAX     LcsStatusIpRouterOpenPortListEntry
    MAX-ACCESS not-accessible
    STATUS     current
    DESCRIPTION
            ""
    INDEX {
            lcsStatusIpRouterOpenPortListEntrySrcAddress,
            lcsStatusIpRouterOpenPortListEntryDstAddress,
            lcsStatusIpRouterOpenPortListEntryProt,
            lcsStatusIpRouterOpenPortListEntryDstPort
          }
    ::= { lcsStatusIpRouterOpenPortListTable 1 }

LcsStatusIpRouterOpenPortListEntry ::= SEQUENCE {
            lcsStatusIpRouterOpenPortListEntrySrcAddress IpAddress,
            lcsStatusIpRouterOpenPortListEntryDstAddress IpAddress,
            lcsStatusIpRouterOpenPortListEntryProt Integer32,
            lcsStatusIpRouterOpenPortListEntryDstPort Integer32,
            lcsStatusIpRouterOpenPortListEntryTimeout Integer32,
            lcsStatusIpRouterOpenPortListEntryFilterRule DisplayString,
            lcsStatusIpRouterOpenPortListEntrySrcRoute DisplayString
    }

-- {COLUMN} 1.3.6.1.4.1.2356.11.1.10.29.1.1
lcsStatusIpRouterOpenPortListEntrySrcAddress OBJECT-TYPE
    SYNTAX     IpAddress
    MAX-ACCESS read-only
    STATUS     current
    DESCRIPTION
            ""
    ::= { lcsStatusIpRouterOpenPortListEntry 1 }

-- {COLUMN} 1.3.6.1.4.1.2356.11.1.10.29.1.2
lcsStatusIpRouterOpenPortListEntryDstAddress OBJECT-TYPE
    SYNTAX     IpAddress
    MAX-ACCESS read-only
    STATUS     current
    DESCRIPTION
            ""
    ::= { lcsStatusIpRouterOpenPortListEntry 2 }

-- {COLUMN} 1.3.6.1.4.1.2356.11.1.10.29.1.3
lcsStatusIpRouterOpenPortListEntryProt OBJECT-TYPE
    SYNTAX     Integer32 (0..255)
    MAX-ACCESS read-only
    STATUS     current
    DESCRIPTION
            ""
    ::= { lcsStatusIpRouterOpenPortListEntry 3 }

-- {COLUMN} 1.3.6.1.4.1.2356.11.1.10.29.1.5
lcsStatusIpRouterOpenPortListEntryDstPort OBJECT-TYPE
    SYNTAX     Integer32 (0..65535)
    MAX-ACCESS read-only
    STATUS     current
    DESCRIPTION
            ""
    ::= { lcsStatusIpRouterOpenPortListEntry 5 }

-- {COLUMN} 1.3.6.1.4.1.2356.11.1.10.29.1.6
lcsStatusIpRouterOpenPortListEntryTimeout OBJECT-TYPE
    SYNTAX     Integer32 (0..65535)
    MAX-ACCESS read-only
    STATUS     current
    DESCRIPTION
            ""
    ::= { lcsStatusIpRouterOpenPortListEntry 6 }

-- {COLUMN} 1.3.6.1.4.1.2356.11.1.10.29.1.8
lcsStatusIpRouterOpenPortListEntryFilterRule OBJECT-TYPE
    SYNTAX     DisplayString (SIZE(0..255))
    MAX-ACCESS read-only
    STATUS     current
    DESCRIPTION
            ""
    ::= { lcsStatusIpRouterOpenPortListEntry 8 }

-- {COLUMN} 1.3.6.1.4.1.2356.11.1.10.29.1.9
lcsStatusIpRouterOpenPortListEntrySrcRoute OBJECT-TYPE
    SYNTAX     DisplayString (SIZE(0..255))
    MAX-ACCESS read-only
    STATUS     current
    DESCRIPTION
            ""
    ::= { lcsStatusIpRouterOpenPortListEntry 9 }

-- {TABLE} 1.3.6.1.4.1.2356.11.1.10.30
lcsStatusIpRouterActIpRoutingTabTable OBJECT-TYPE
    SYNTAX     SEQUENCE OF LcsStatusIpRouterActIpRoutingTabEntry
    MAX-ACCESS not-accessible
    STATUS     current
    DESCRIPTION
            ""
    ::= { lcsStatusIpRouter 30 }

-- {ROW} 1.3.6.1.4.1.2356.11.1.10.30.1
lcsStatusIpRouterActIpRoutingTabEntry OBJECT-TYPE
    SYNTAX     LcsStatusIpRouterActIpRoutingTabEntry
    MAX-ACCESS not-accessible
    STATUS     current
    DESCRIPTION
            ""
    INDEX {
            lcsStatusIpRouterActIpRoutingTabEntryIpAddress,
            lcsStatusIpRouterActIpRoutingTabEntryIpNetmask,
            lcsStatusIpRouterActIpRoutingTabEntryRtgTag
          }
    ::= { lcsStatusIpRouterActIpRoutingTabTable 1 }

LcsStatusIpRouterActIpRoutingTabEntry ::= SEQUENCE {
            lcsStatusIpRouterActIpRoutingTabEntryIpAddress IpAddress,
            lcsStatusIpRouterActIpRoutingTabEntryIpNetmask IpAddress,
            lcsStatusIpRouterActIpRoutingTabEntryRtgTag Integer32,
            lcsStatusIpRouterActIpRoutingTabEntryGateway IpAddress,
            lcsStatusIpRouterActIpRoutingTabEntryPeer DisplayString,
            lcsStatusIpRouterActIpRoutingTabEntryDistance Integer32,
            lcsStatusIpRouterActIpRoutingTabEntryMasquerade INTEGER,
            lcsStatusIpRouterActIpRoutingTabEntryType INTEGER
    }

-- {COLUMN} 1.3.6.1.4.1.2356.11.1.10.30.1.1
lcsStatusIpRouterActIpRoutingTabEntryIpAddress OBJECT-TYPE
    SYNTAX     IpAddress
    MAX-ACCESS read-only
    STATUS     current
    DESCRIPTION
            ""
    ::= { lcsStatusIpRouterActIpRoutingTabEntry 1 }

-- {COLUMN} 1.3.6.1.4.1.2356.11.1.10.30.1.2
lcsStatusIpRouterActIpRoutingTabEntryIpNetmask OBJECT-TYPE
    SYNTAX     IpAddress
    MAX-ACCESS read-only
    STATUS     current
    DESCRIPTION
            ""
    ::= { lcsStatusIpRouterActIpRoutingTabEntry 2 }

-- {COLUMN} 1.3.6.1.4.1.2356.11.1.10.30.1.3
lcsStatusIpRouterActIpRoutingTabEntryRtgTag OBJECT-TYPE
    SYNTAX     Integer32 (0..65535)
    MAX-ACCESS read-only
    STATUS     current
    DESCRIPTION
            ""
    ::= { lcsStatusIpRouterActIpRoutingTabEntry 3 }

-- {COLUMN} 1.3.6.1.4.1.2356.11.1.10.30.1.4
lcsStatusIpRouterActIpRoutingTabEntryGateway OBJECT-TYPE
    SYNTAX     IpAddress
    MAX-ACCESS read-only
    STATUS     current
    DESCRIPTION
            ""
    ::= { lcsStatusIpRouterActIpRoutingTabEntry 4 }

-- {COLUMN} 1.3.6.1.4.1.2356.11.1.10.30.1.5
lcsStatusIpRouterActIpRoutingTabEntryPeer OBJECT-TYPE
    SYNTAX     DisplayString (SIZE(0..255))
    MAX-ACCESS read-only
    STATUS     current
    DESCRIPTION
            ""
    ::= { lcsStatusIpRouterActIpRoutingTabEntry 5 }

-- {COLUMN} 1.3.6.1.4.1.2356.11.1.10.30.1.6
lcsStatusIpRouterActIpRoutingTabEntryDistance OBJECT-TYPE
    SYNTAX     Integer32 (0..255)
    MAX-ACCESS read-only
    STATUS     current
    DESCRIPTION
            ""
    ::= { lcsStatusIpRouterActIpRoutingTabEntry 6 }

-- {COLUMN} 1.3.6.1.4.1.2356.11.1.10.30.1.7
lcsStatusIpRouterActIpRoutingTabEntryMasquerade OBJECT-TYPE
    SYNTAX     INTEGER {
                  eNo (0),
                  eOn (1),
                  eIntranet (2),
                  eUnknown (255)
            }
    MAX-ACCESS read-only
    STATUS     current
    DESCRIPTION
            ""
    ::= { lcsStatusIpRouterActIpRoutingTabEntry 7 }

-- {COLUMN} 1.3.6.1.4.1.2356.11.1.10.30.1.8
lcsStatusIpRouterActIpRoutingTabEntryType OBJECT-TYPE
    SYNTAX     INTEGER {
                  eUnknown (0),
                  eStatic (1),
                  eRip (2),
                  eVpn (3),
                  eCapwap (4),
                  eRas (5),
                  eIntranet (6),
                  eDmz (7),
                  eDisabled (8),
                  eEbgp (9),
                  eIbgp (10),
                  eOspf (11),
                  eLisp (12),
                  eDhcp (13)
            }
    MAX-ACCESS read-only
    STATUS     current
    DESCRIPTION
            ""
    ::= { lcsStatusIpRouterActIpRoutingTabEntry 8 }

-- {SCALAR} 1.3.6.1.4.1.2356.11.1.10.31
lcsStatusIpRouterL4Errors OBJECT-TYPE
    SYNTAX     Counter32
    MAX-ACCESS read-only
    STATUS     current
    DESCRIPTION
            ""
    ::= { lcsStatusIpRouter 31 }

-- {NODE} 1.3.6.1.4.1.2356.11.1.10.32
lcsStatusIpRouterLoadBalancer OBJECT IDENTIFIER ::= { lcsStatusIpRouter 32 }

-- {SCALAR} 1.3.6.1.4.1.2356.11.1.10.32.1
lcsStatusIpRouterLoadBalancerOperating OBJECT-TYPE
    SYNTAX     INTEGER {
                  eNo (0),
                  eYes (1)
            }
    MAX-ACCESS read-only
    STATUS     current
    DESCRIPTION
            ""
    ::= { lcsStatusIpRouterLoadBalancer 1 }

-- {TABLE} 1.3.6.1.4.1.2356.11.1.10.32.2
lcsStatusIpRouterLoadBalancerConnectionsTable OBJECT-TYPE
    SYNTAX     SEQUENCE OF LcsStatusIpRouterLoadBalancerConnectionsEntry
    MAX-ACCESS not-accessible
    STATUS     current
    DESCRIPTION
            ""
    ::= { lcsStatusIpRouterLoadBalancer 2 }

-- {ROW} 1.3.6.1.4.1.2356.11.1.10.32.2.1
lcsStatusIpRouterLoadBalancerConnectionsEntry OBJECT-TYPE
    SYNTAX     LcsStatusIpRouterLoadBalancerConnectionsEntry
    MAX-ACCESS not-accessible
    STATUS     current
    DESCRIPTION
            ""
    INDEX {
            lcsStatusIpRouterLoadBalancerConnectionsEntryPeer,
            lcsStatusIpRouterLoadBalancerConnectionsEntryBundlePeer
          }
    ::= { lcsStatusIpRouterLoadBalancerConnectionsTable 1 }

LcsStatusIpRouterLoadBalancerConnectionsEntry ::= SEQUENCE {
            lcsStatusIpRouterLoadBalancerConnectionsEntryPeer DisplayString,
            lcsStatusIpRouterLoadBalancerConnectionsEntryBundlePeer DisplayString,
            lcsStatusIpRouterLoadBalancerConnectionsEntryState INTEGER,
            lcsStatusIpRouterLoadBalancerConnectionsEntryTcpIpSessions Unsigned32,
            lcsStatusIpRouterLoadBalancerConnectionsEntryPptpSessions Integer32,
            lcsStatusIpRouterLoadBalancerConnectionsEntryVpnSessions Integer32,
            lcsStatusIpRouterLoadBalancerConnectionsEntryIpv4Masq INTEGER
    }

-- {COLUMN} 1.3.6.1.4.1.2356.11.1.10.32.2.1.1
lcsStatusIpRouterLoadBalancerConnectionsEntryPeer OBJECT-TYPE
    SYNTAX     DisplayString (SIZE(0..16))
    MAX-ACCESS read-only
    STATUS     current
    DESCRIPTION
            ""
    ::= { lcsStatusIpRouterLoadBalancerConnectionsEntry 1 }

-- {COLUMN} 1.3.6.1.4.1.2356.11.1.10.32.2.1.2
lcsStatusIpRouterLoadBalancerConnectionsEntryBundlePeer OBJECT-TYPE
    SYNTAX     DisplayString (SIZE(0..16))
    MAX-ACCESS read-only
    STATUS     current
    DESCRIPTION
            ""
    ::= { lcsStatusIpRouterLoadBalancerConnectionsEntry 2 }

-- {COLUMN} 1.3.6.1.4.1.2356.11.1.10.32.2.1.3
lcsStatusIpRouterLoadBalancerConnectionsEntryState OBJECT-TYPE
    SYNTAX     INTEGER {
                  eReady (2),
                  eConnection (7),
                  eDisconnecting (8)
            }
    MAX-ACCESS read-only
    STATUS     current
    DESCRIPTION
            ""
    ::= { lcsStatusIpRouterLoadBalancerConnectionsEntry 3 }

-- {COLUMN} 1.3.6.1.4.1.2356.11.1.10.32.2.1.4
lcsStatusIpRouterLoadBalancerConnectionsEntryTcpIpSessions OBJECT-TYPE
    SYNTAX     Unsigned32 (0..4294967295)
    MAX-ACCESS read-only
    STATUS     current
    DESCRIPTION
            ""
    ::= { lcsStatusIpRouterLoadBalancerConnectionsEntry 4 }

-- {COLUMN} 1.3.6.1.4.1.2356.11.1.10.32.2.1.5
lcsStatusIpRouterLoadBalancerConnectionsEntryPptpSessions OBJECT-TYPE
    SYNTAX     Integer32 (0..2147483647)
    MAX-ACCESS read-only
    STATUS     current
    DESCRIPTION
            ""
    ::= { lcsStatusIpRouterLoadBalancerConnectionsEntry 5 }

-- {COLUMN} 1.3.6.1.4.1.2356.11.1.10.32.2.1.6
lcsStatusIpRouterLoadBalancerConnectionsEntryVpnSessions OBJECT-TYPE
    SYNTAX     Integer32 (0..2147483647)
    MAX-ACCESS read-only
    STATUS     current
    DESCRIPTION
            ""
    ::= { lcsStatusIpRouterLoadBalancerConnectionsEntry 6 }

-- {COLUMN} 1.3.6.1.4.1.2356.11.1.10.32.2.1.7
lcsStatusIpRouterLoadBalancerConnectionsEntryIpv4Masq OBJECT-TYPE
    SYNTAX     INTEGER {
                  eNo (0),
                  eOn (1),
                  eIntranet (2)
            }
    MAX-ACCESS read-only
    STATUS     current
    DESCRIPTION
            "-- empty --"
    ::= { lcsStatusIpRouterLoadBalancerConnectionsEntry 7 }

-- {TABLE} 1.3.6.1.4.1.2356.11.1.10.32.3
lcsStatusIpRouterLoadBalancerClientBindingTable OBJECT-TYPE
    SYNTAX     SEQUENCE OF LcsStatusIpRouterLoadBalancerClientBindingEntry
    MAX-ACCESS not-accessible
    STATUS     current
    DESCRIPTION
            "-- empty --"
    ::= { lcsStatusIpRouterLoadBalancer 3 }

-- {ROW} 1.3.6.1.4.1.2356.11.1.10.32.3.1
lcsStatusIpRouterLoadBalancerClientBindingEntry OBJECT-TYPE
    SYNTAX     LcsStatusIpRouterLoadBalancerClientBindingEntry
    MAX-ACCESS not-accessible
    STATUS     current
    DESCRIPTION
            ""
    INDEX {
            lcsStatusIpRouterLoadBalancerClientBindingEntrySourceIp
          }
    ::= { lcsStatusIpRouterLoadBalancerClientBindingTable 1 }

LcsStatusIpRouterLoadBalancerClientBindingEntry ::= SEQUENCE {
            lcsStatusIpRouterLoadBalancerClientBindingEntrySourceIp IpAddress,
            lcsStatusIpRouterLoadBalancerClientBindingEntryBundlePeer OCTET STRING,
            lcsStatusIpRouterLoadBalancerClientBindingEntryTimeout Unsigned32,
            lcsStatusIpRouterLoadBalancerClientBindingEntryBalance INTEGER
    }

-- {COLUMN} 1.3.6.1.4.1.2356.11.1.10.32.3.1.1
lcsStatusIpRouterLoadBalancerClientBindingEntrySourceIp OBJECT-TYPE
    SYNTAX     IpAddress
    MAX-ACCESS read-only
    STATUS     current
    DESCRIPTION
            "-- empty --"
    ::= { lcsStatusIpRouterLoadBalancerClientBindingEntry 1 }

-- {COLUMN} 1.3.6.1.4.1.2356.11.1.10.32.3.1.2
lcsStatusIpRouterLoadBalancerClientBindingEntryBundlePeer OBJECT-TYPE
    SYNTAX     OCTET STRING (SIZE(0..16))
    MAX-ACCESS read-only
    STATUS     current
    DESCRIPTION
            "-- empty --"
    ::= { lcsStatusIpRouterLoadBalancerClientBindingEntry 2 }

-- {COLUMN} 1.3.6.1.4.1.2356.11.1.10.32.3.1.3
lcsStatusIpRouterLoadBalancerClientBindingEntryTimeout OBJECT-TYPE
    SYNTAX     Unsigned32 (0..4294967295)
    MAX-ACCESS read-only
    STATUS     current
    DESCRIPTION
            "-- empty --"
    ::= { lcsStatusIpRouterLoadBalancerClientBindingEntry 3 }

-- {COLUMN} 1.3.6.1.4.1.2356.11.1.10.32.3.1.4
lcsStatusIpRouterLoadBalancerClientBindingEntryBalance OBJECT-TYPE
    SYNTAX     INTEGER {
                  eNo (0),
                  eYes (1)
            }
    MAX-ACCESS read-only
    STATUS     current
    DESCRIPTION
            "-- empty --"
    ::= { lcsStatusIpRouterLoadBalancerClientBindingEntry 4 }

-- {TABLE} 1.3.6.1.4.1.2356.11.1.10.32.5
lcsStatusIpRouterLoadBalancerV4ClientBindingsTable OBJECT-TYPE
    SYNTAX     SEQUENCE OF LcsStatusIpRouterLoadBalancerV4ClientBindingsEntry
    MAX-ACCESS not-accessible
    STATUS     current
    DESCRIPTION
            "-- empty --"
    ::= { lcsStatusIpRouterLoadBalancer 5 }

-- {ROW} 1.3.6.1.4.1.2356.11.1.10.32.5.1
lcsStatusIpRouterLoadBalancerV4ClientBindingsEntry OBJECT-TYPE
    SYNTAX     LcsStatusIpRouterLoadBalancerV4ClientBindingsEntry
    MAX-ACCESS not-accessible
    STATUS     current
    DESCRIPTION
            ""
    INDEX {
            lcsStatusIpRouterLoadBalancerV4ClientBindingsEntryLoadBalancer,
            lcsStatusIpRouterLoadBalancerV4ClientBindingsEntrySourceIp
          }
    ::= { lcsStatusIpRouterLoadBalancerV4ClientBindingsTable 1 }

LcsStatusIpRouterLoadBalancerV4ClientBindingsEntry ::= SEQUENCE {
            lcsStatusIpRouterLoadBalancerV4ClientBindingsEntryLoadBalancer OCTET STRING,
            lcsStatusIpRouterLoadBalancerV4ClientBindingsEntrySourceIp IpAddress,
            lcsStatusIpRouterLoadBalancerV4ClientBindingsEntryBundlePeer OCTET STRING,
            lcsStatusIpRouterLoadBalancerV4ClientBindingsEntryTimeout Unsigned32,
            lcsStatusIpRouterLoadBalancerV4ClientBindingsEntryBalance INTEGER
    }

-- {COLUMN} 1.3.6.1.4.1.2356.11.1.10.32.5.1.1
lcsStatusIpRouterLoadBalancerV4ClientBindingsEntryLoadBalancer OBJECT-TYPE
    SYNTAX     OCTET STRING (SIZE(0..16))
    MAX-ACCESS read-only
    STATUS     current
    DESCRIPTION
            "-- empty --"
    ::= { lcsStatusIpRouterLoadBalancerV4ClientBindingsEntry 1 }

-- {COLUMN} 1.3.6.1.4.1.2356.11.1.10.32.5.1.2
lcsStatusIpRouterLoadBalancerV4ClientBindingsEntrySourceIp OBJECT-TYPE
    SYNTAX     IpAddress
    MAX-ACCESS read-only
    STATUS     current
    DESCRIPTION
            "-- empty --"
    ::= { lcsStatusIpRouterLoadBalancerV4ClientBindingsEntry 2 }

-- {COLUMN} 1.3.6.1.4.1.2356.11.1.10.32.5.1.3
lcsStatusIpRouterLoadBalancerV4ClientBindingsEntryBundlePeer OBJECT-TYPE
    SYNTAX     OCTET STRING (SIZE(0..16))
    MAX-ACCESS read-only
    STATUS     current
    DESCRIPTION
            "-- empty --"
    ::= { lcsStatusIpRouterLoadBalancerV4ClientBindingsEntry 3 }

-- {COLUMN} 1.3.6.1.4.1.2356.11.1.10.32.5.1.4
lcsStatusIpRouterLoadBalancerV4ClientBindingsEntryTimeout OBJECT-TYPE
    SYNTAX     Unsigned32 (0..4294967295)
    MAX-ACCESS read-only
    STATUS     current
    DESCRIPTION
            "-- empty --"
    ::= { lcsStatusIpRouterLoadBalancerV4ClientBindingsEntry 4 }

-- {COLUMN} 1.3.6.1.4.1.2356.11.1.10.32.5.1.5
lcsStatusIpRouterLoadBalancerV4ClientBindingsEntryBalance OBJECT-TYPE
    SYNTAX     INTEGER {
                  eNo (0),
                  eYes (1)
            }
    MAX-ACCESS read-only
    STATUS     current
    DESCRIPTION
            "-- empty --"
    ::= { lcsStatusIpRouterLoadBalancerV4ClientBindingsEntry 5 }

-- {SCALAR} 1.3.6.1.4.1.2356.11.1.10.32.7
lcsStatusIpRouterLoadBalancerDeleteValues OBJECT-TYPE
    SYNTAX     DisplayString
    MAX-ACCESS read-write
    STATUS     current
    DESCRIPTION
            "-- empty --"
    ::= { lcsStatusIpRouterLoadBalancer 7 }

-- {NODE} 1.3.6.1.4.1.2356.11.1.10.33
lcsStatusIpRouterVrrp OBJECT IDENTIFIER ::= { lcsStatusIpRouter 33 }

-- {SCALAR} 1.3.6.1.4.1.2356.11.1.10.33.1
lcsStatusIpRouterVrrpRx OBJECT-TYPE
    SYNTAX     Counter32
    MAX-ACCESS read-only
    STATUS     current
    DESCRIPTION
            ""
    ::= { lcsStatusIpRouterVrrp 1 }

-- {SCALAR} 1.3.6.1.4.1.2356.11.1.10.33.2
lcsStatusIpRouterVrrpTx OBJECT-TYPE
    SYNTAX     Counter32
    MAX-ACCESS read-only
    STATUS     current
    DESCRIPTION
            ""
    ::= { lcsStatusIpRouterVrrp 2 }

-- {SCALAR} 1.3.6.1.4.1.2356.11.1.10.33.3
lcsStatusIpRouterVrrpError OBJECT-TYPE
    SYNTAX     Counter32
    MAX-ACCESS read-only
    STATUS     current
    DESCRIPTION
            ""
    ::= { lcsStatusIpRouterVrrp 3 }

-- {SCALAR} 1.3.6.1.4.1.2356.11.1.10.33.4
lcsStatusIpRouterVrrpDrop OBJECT-TYPE
    SYNTAX     Counter32
    MAX-ACCESS read-only
    STATUS     current
    DESCRIPTION
            ""
    ::= { lcsStatusIpRouterVrrp 4 }

-- {SCALAR} 1.3.6.1.4.1.2356.11.1.10.33.5
lcsStatusIpRouterVrrpOperating OBJECT-TYPE
    SYNTAX     INTEGER {
                  eNo (0),
                  eYes (1)
            }
    MAX-ACCESS read-only
    STATUS     current
    DESCRIPTION
            ""
    ::= { lcsStatusIpRouterVrrp 5 }

-- {SCALAR} 1.3.6.1.4.1.2356.11.1.10.33.6
lcsStatusIpRouterVrrpInternalServices OBJECT-TYPE
    SYNTAX     INTEGER {
                  eNo (0),
                  eYes (1)
            }
    MAX-ACCESS read-only
    STATUS     current
    DESCRIPTION
            ""
    ::= { lcsStatusIpRouterVrrp 6 }

-- {SCALAR} 1.3.6.1.4.1.2356.11.1.10.33.7
lcsStatusIpRouterVrrpQueueErrors OBJECT-TYPE
    SYNTAX     Counter32
    MAX-ACCESS read-only
    STATUS     current
    DESCRIPTION
            ""
    ::= { lcsStatusIpRouterVrrp 7 }

-- {TABLE} 1.3.6.1.4.1.2356.11.1.10.33.10
lcsStatusIpRouterVrrpVirtualRouterTable OBJECT-TYPE
    SYNTAX     SEQUENCE OF LcsStatusIpRouterVrrpVirtualRouterEntry
    MAX-ACCESS not-accessible
    STATUS     current
    DESCRIPTION
            ""
    ::= { lcsStatusIpRouterVrrp 10 }

-- {ROW} 1.3.6.1.4.1.2356.11.1.10.33.10.1
lcsStatusIpRouterVrrpVirtualRouterEntry OBJECT-TYPE
    SYNTAX     LcsStatusIpRouterVrrpVirtualRouterEntry
    MAX-ACCESS not-accessible
    STATUS     current
    DESCRIPTION
            ""
    INDEX {
            lcsStatusIpRouterVrrpVirtualRouterEntryRouterId
          }
    ::= { lcsStatusIpRouterVrrpVirtualRouterTable 1 }

LcsStatusIpRouterVrrpVirtualRouterEntry ::= SEQUENCE {
            lcsStatusIpRouterVrrpVirtualRouterEntryRouterId Integer32,
            lcsStatusIpRouterVrrpVirtualRouterEntryVirtAddress IpAddress,
            lcsStatusIpRouterVrrpVirtualRouterEntryPrio Integer32,
            lcsStatusIpRouterVrrpVirtualRouterEntryBPrio Integer32,
            lcsStatusIpRouterVrrpVirtualRouterEntryPeer DisplayString,
            lcsStatusIpRouterVrrpVirtualRouterEntryState INTEGER,
            lcsStatusIpRouterVrrpVirtualRouterEntryBackup INTEGER,
            lcsStatusIpRouterVrrpVirtualRouterEntryMaster IpAddress,
            lcsStatusIpRouterVrrpVirtualRouterEntryVlanId Integer32,
            lcsStatusIpRouterVrrpVirtualRouterEntryNetworkName DisplayString,
            lcsStatusIpRouterVrrpVirtualRouterEntryPort INTEGER
    }

-- {COLUMN} 1.3.6.1.4.1.2356.11.1.10.33.10.1.1
lcsStatusIpRouterVrrpVirtualRouterEntryRouterId OBJECT-TYPE
    SYNTAX     Integer32 (0..255)
    MAX-ACCESS read-only
    STATUS     current
    DESCRIPTION
            ""
    ::= { lcsStatusIpRouterVrrpVirtualRouterEntry 1 }

-- {COLUMN} 1.3.6.1.4.1.2356.11.1.10.33.10.1.2
lcsStatusIpRouterVrrpVirtualRouterEntryVirtAddress OBJECT-TYPE
    SYNTAX     IpAddress
    MAX-ACCESS read-only
    STATUS     current
    DESCRIPTION
            ""
    ::= { lcsStatusIpRouterVrrpVirtualRouterEntry 2 }

-- {COLUMN} 1.3.6.1.4.1.2356.11.1.10.33.10.1.3
lcsStatusIpRouterVrrpVirtualRouterEntryPrio OBJECT-TYPE
    SYNTAX     Integer32 (0..255)
    MAX-ACCESS read-only
    STATUS     current
    DESCRIPTION
            ""
    ::= { lcsStatusIpRouterVrrpVirtualRouterEntry 3 }

-- {COLUMN} 1.3.6.1.4.1.2356.11.1.10.33.10.1.4
lcsStatusIpRouterVrrpVirtualRouterEntryBPrio OBJECT-TYPE
    SYNTAX     Integer32 (0..255)
    MAX-ACCESS read-only
    STATUS     current
    DESCRIPTION
            ""
    ::= { lcsStatusIpRouterVrrpVirtualRouterEntry 4 }

-- {COLUMN} 1.3.6.1.4.1.2356.11.1.10.33.10.1.5
lcsStatusIpRouterVrrpVirtualRouterEntryPeer OBJECT-TYPE
    SYNTAX     DisplayString (SIZE(0..16))
    MAX-ACCESS read-only
    STATUS     current
    DESCRIPTION
            ""
    ::= { lcsStatusIpRouterVrrpVirtualRouterEntry 5 }

-- {COLUMN} 1.3.6.1.4.1.2356.11.1.10.33.10.1.6
lcsStatusIpRouterVrrpVirtualRouterEntryState OBJECT-TYPE
    SYNTAX     INTEGER {
                  eInit (0),
                  eListen (1),
                  eStandby (2),
                  eMaster (3),
                  eDown (4),
                  eReconnect (5)
            }
    MAX-ACCESS read-only
    STATUS     current
    DESCRIPTION
            ""
    ::= { lcsStatusIpRouterVrrpVirtualRouterEntry 6 }

-- {COLUMN} 1.3.6.1.4.1.2356.11.1.10.33.10.1.7
lcsStatusIpRouterVrrpVirtualRouterEntryBackup OBJECT-TYPE
    SYNTAX     INTEGER {
                  eNo (0),
                  eYes (1)
            }
    MAX-ACCESS read-only
    STATUS     current
    DESCRIPTION
            ""
    ::= { lcsStatusIpRouterVrrpVirtualRouterEntry 7 }

-- {COLUMN} 1.3.6.1.4.1.2356.11.1.10.33.10.1.8
lcsStatusIpRouterVrrpVirtualRouterEntryMaster OBJECT-TYPE
    SYNTAX     IpAddress
    MAX-ACCESS read-only
    STATUS     current
    DESCRIPTION
            ""
    ::= { lcsStatusIpRouterVrrpVirtualRouterEntry 8 }

-- {COLUMN} 1.3.6.1.4.1.2356.11.1.10.33.10.1.10
lcsStatusIpRouterVrrpVirtualRouterEntryVlanId OBJECT-TYPE
    SYNTAX     Integer32 (0..65535)
    MAX-ACCESS read-only
    STATUS     current
    DESCRIPTION
            ""
    ::= { lcsStatusIpRouterVrrpVirtualRouterEntry 10 }

-- {COLUMN} 1.3.6.1.4.1.2356.11.1.10.33.10.1.11
lcsStatusIpRouterVrrpVirtualRouterEntryNetworkName OBJECT-TYPE
    SYNTAX     DisplayString (SIZE(0..16))
    MAX-ACCESS read-only
    STATUS     current
    DESCRIPTION
            ""
    ::= { lcsStatusIpRouterVrrpVirtualRouterEntry 11 }

-- {COLUMN} 1.3.6.1.4.1.2356.11.1.10.33.10.1.12
lcsStatusIpRouterVrrpVirtualRouterEntryPort OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsStatusIpRouterVrrpVirtualRouterEntry 12 }

-- {TABLE} 1.3.6.1.4.1.2356.11.1.10.33.11
lcsStatusIpRouterVrrpMacListTable OBJECT-TYPE
    SYNTAX     SEQUENCE OF LcsStatusIpRouterVrrpMacListEntry
    MAX-ACCESS not-accessible
    STATUS     current
    DESCRIPTION
            ""
    ::= { lcsStatusIpRouterVrrp 11 }

-- {ROW} 1.3.6.1.4.1.2356.11.1.10.33.11.1
lcsStatusIpRouterVrrpMacListEntry OBJECT-TYPE
    SYNTAX     LcsStatusIpRouterVrrpMacListEntry
    MAX-ACCESS not-accessible
    STATUS     current
    DESCRIPTION
            ""
    INDEX {
            lcsStatusIpRouterVrrpMacListEntryVirtAddress
          }
    ::= { lcsStatusIpRouterVrrpMacListTable 1 }

LcsStatusIpRouterVrrpMacListEntry ::= SEQUENCE {
            lcsStatusIpRouterVrrpMacListEntryVirtAddress IpAddress,
            lcsStatusIpRouterVrrpMacListEntryMacAddress MacAddress,
            lcsStatusIpRouterVrrpMacListEntryRouterId Integer32
    }

-- {COLUMN} 1.3.6.1.4.1.2356.11.1.10.33.11.1.1
lcsStatusIpRouterVrrpMacListEntryVirtAddress OBJECT-TYPE
    SYNTAX     IpAddress
    MAX-ACCESS read-only
    STATUS     current
    DESCRIPTION
            ""
    ::= { lcsStatusIpRouterVrrpMacListEntry 1 }

-- {COLUMN} 1.3.6.1.4.1.2356.11.1.10.33.11.1.2
lcsStatusIpRouterVrrpMacListEntryMacAddress OBJECT-TYPE
    SYNTAX     MacAddress
    MAX-ACCESS read-only
    STATUS     current
    DESCRIPTION
            ""
    ::= { lcsStatusIpRouterVrrpMacListEntry 2 }

-- {COLUMN} 1.3.6.1.4.1.2356.11.1.10.33.11.1.3
lcsStatusIpRouterVrrpMacListEntryRouterId OBJECT-TYPE
    SYNTAX     Integer32 (0..255)
    MAX-ACCESS read-only
    STATUS     current
    DESCRIPTION
            ""
    ::= { lcsStatusIpRouterVrrpMacListEntry 3 }

-- {TABLE} 1.3.6.1.4.1.2356.11.1.10.33.12
lcsStatusIpRouterVrrpEventLogTable OBJECT-TYPE
    SYNTAX     SEQUENCE OF LcsStatusIpRouterVrrpEventLogEntry
    MAX-ACCESS not-accessible
    STATUS     current
    DESCRIPTION
            ""
    ::= { lcsStatusIpRouterVrrp 12 }

-- {ROW} 1.3.6.1.4.1.2356.11.1.10.33.12.1
lcsStatusIpRouterVrrpEventLogEntry OBJECT-TYPE
    SYNTAX     LcsStatusIpRouterVrrpEventLogEntry
    MAX-ACCESS not-accessible
    STATUS     current
    DESCRIPTION
            ""
    INDEX {
            lcsStatusIpRouterVrrpEventLogEntryIdx
          }
    ::= { lcsStatusIpRouterVrrpEventLogTable 1 }

LcsStatusIpRouterVrrpEventLogEntry ::= SEQUENCE {
            lcsStatusIpRouterVrrpEventLogEntryIdx Integer32,
            lcsStatusIpRouterVrrpEventLogEntrySystemTime DisplayString,
            lcsStatusIpRouterVrrpEventLogEntrySrcAddress IpAddress,
            lcsStatusIpRouterVrrpEventLogEntryVrid Integer32,
            lcsStatusIpRouterVrrpEventLogEntryEvent INTEGER,
            lcsStatusIpRouterVrrpEventLogEntryInfo DisplayString
    }

-- {COLUMN} 1.3.6.1.4.1.2356.11.1.10.33.12.1.1
lcsStatusIpRouterVrrpEventLogEntryIdx OBJECT-TYPE
    SYNTAX     Integer32 (0..65535)
    MAX-ACCESS read-only
    STATUS     current
    DESCRIPTION
            ""
    ::= { lcsStatusIpRouterVrrpEventLogEntry 1 }

-- {COLUMN} 1.3.6.1.4.1.2356.11.1.10.33.12.1.2
lcsStatusIpRouterVrrpEventLogEntrySystemTime OBJECT-TYPE
    SYNTAX     DisplayString (SIZE(0..19))
    MAX-ACCESS read-only
    STATUS     current
    DESCRIPTION
            ""
    ::= { lcsStatusIpRouterVrrpEventLogEntry 2 }

-- {COLUMN} 1.3.6.1.4.1.2356.11.1.10.33.12.1.3
lcsStatusIpRouterVrrpEventLogEntrySrcAddress OBJECT-TYPE
    SYNTAX     IpAddress
    MAX-ACCESS read-only
    STATUS     current
    DESCRIPTION
            ""
    ::= { lcsStatusIpRouterVrrpEventLogEntry 3 }

-- {COLUMN} 1.3.6.1.4.1.2356.11.1.10.33.12.1.4
lcsStatusIpRouterVrrpEventLogEntryVrid OBJECT-TYPE
    SYNTAX     Integer32 (0..255)
    MAX-ACCESS read-only
    STATUS     current
    DESCRIPTION
            ""
    ::= { lcsStatusIpRouterVrrpEventLogEntry 4 }

-- {COLUMN} 1.3.6.1.4.1.2356.11.1.10.33.12.1.5
lcsStatusIpRouterVrrpEventLogEntryEvent OBJECT-TYPE
    SYNTAX     INTEGER {
                  eInvalidTtl (1),
                  eInvalidVersion (2),
                  eBadNumberOfVirtualAddresses (3),
                  eBadAuthenticationType (4),
                  eBadAdvertisementInterval (5),
                  eInvalidVrid (6),
                  eInvalidRouterAddress (7),
                  eInvalidPriority (8),
                  eVirtualRouterStopped (9),
                  eVirtualRouterStarted (10),
                  eLinkUp (11),
                  eLinkDown (12),
                  eNewMaster (13),
                  eBackupStarted (14),
                  eBackupEnded (15)
            }
    MAX-ACCESS read-only
    STATUS     current
    DESCRIPTION
            ""
    ::= { lcsStatusIpRouterVrrpEventLogEntry 5 }

-- {COLUMN} 1.3.6.1.4.1.2356.11.1.10.33.12.1.6
lcsStatusIpRouterVrrpEventLogEntryInfo OBJECT-TYPE
    SYNTAX     DisplayString (SIZE(0..255))
    MAX-ACCESS read-only
    STATUS     current
    DESCRIPTION
            ""
    ::= { lcsStatusIpRouterVrrpEventLogEntry 6 }

-- {SCALAR} 1.3.6.1.4.1.2356.11.1.10.33.20
lcsStatusIpRouterVrrpDeleteValues OBJECT-TYPE
    SYNTAX     DisplayString
    MAX-ACCESS read-write
    STATUS     current
    DESCRIPTION
            ""
    ::= { lcsStatusIpRouterVrrp 20 }

-- {SCALAR} 1.3.6.1.4.1.2356.11.1.10.34
lcsStatusIpRouterRules OBJECT-TYPE
    SYNTAX     Integer32 (0..2147483647)
    MAX-ACCESS read-only
    STATUS     current
    DESCRIPTION
            ""
    ::= { lcsStatusIpRouter 34 }

-- {SCALAR} 1.3.6.1.4.1.2356.11.1.10.35
lcsStatusIpRouterFilter OBJECT-TYPE
    SYNTAX     Integer32 (0..2147483647)
    MAX-ACCESS read-only
    STATUS     current
    DESCRIPTION
            ""
    ::= { lcsStatusIpRouter 35 }

-- {NODE} 1.3.6.1.4.1.2356.11.1.11
lcsStatusConfig OBJECT IDENTIFIER ::= { lcsStatus 11 }

-- {SCALAR} 1.3.6.1.4.1.2356.11.1.11.1
lcsStatusConfigLanActiveConnections OBJECT-TYPE
    SYNTAX     Integer32 (0..65535)
    MAX-ACCESS read-only
    STATUS     current
    DESCRIPTION
            ""
    ::= { lcsStatusConfig 1 }

-- {SCALAR} 1.3.6.1.4.1.2356.11.1.11.2
lcsStatusConfigLanTotalConnections OBJECT-TYPE
    SYNTAX     Counter32
    MAX-ACCESS read-only
    STATUS     current
    DESCRIPTION
            ""
    ::= { lcsStatusConfig 2 }

-- {SCALAR} 1.3.6.1.4.1.2356.11.1.11.3
lcsStatusConfigWanActiveConnections OBJECT-TYPE
    SYNTAX     Integer32 (0..65535)
    MAX-ACCESS read-only
    STATUS     current
    DESCRIPTION
            ""
    ::= { lcsStatusConfig 3 }

-- {SCALAR} 1.3.6.1.4.1.2356.11.1.11.4
lcsStatusConfigWanTotalConnections OBJECT-TYPE
    SYNTAX     Counter32
    MAX-ACCESS read-only
    STATUS     current
    DESCRIPTION
            ""
    ::= { lcsStatusConfig 4 }

-- {SCALAR} 1.3.6.1.4.1.2356.11.1.11.5
lcsStatusConfigOutbandActiveConnections OBJECT-TYPE
    SYNTAX     Integer32 (0..65535)
    MAX-ACCESS read-only
    STATUS     current
    DESCRIPTION
            ""
    ::= { lcsStatusConfig 5 }

-- {SCALAR} 1.3.6.1.4.1.2356.11.1.11.6
lcsStatusConfigOutbandTotalConnections OBJECT-TYPE
    SYNTAX     Counter32
    MAX-ACCESS read-only
    STATUS     current
    DESCRIPTION
            ""
    ::= { lcsStatusConfig 6 }

-- {SCALAR} 1.3.6.1.4.1.2356.11.1.11.7
lcsStatusConfigOutbandBitrate OBJECT-TYPE
    SYNTAX     Integer32 (0..2147483647)
    MAX-ACCESS read-only
    STATUS     current
    DESCRIPTION
            ""
    ::= { lcsStatusConfig 7 }

-- {SCALAR} 1.3.6.1.4.1.2356.11.1.11.8
lcsStatusConfigLoginErrors OBJECT-TYPE
    SYNTAX     Counter32
    MAX-ACCESS read-only
    STATUS     current
    DESCRIPTION
            ""
    ::= { lcsStatusConfig 8 }

-- {SCALAR} 1.3.6.1.4.1.2356.11.1.11.9
lcsStatusConfigLoginLocks OBJECT-TYPE
    SYNTAX     Counter32
    MAX-ACCESS read-only
    STATUS     current
    DESCRIPTION
            ""
    ::= { lcsStatusConfig 9 }

-- {SCALAR} 1.3.6.1.4.1.2356.11.1.11.10
lcsStatusConfigLoginRejects OBJECT-TYPE
    SYNTAX     Counter32
    MAX-ACCESS read-only
    STATUS     current
    DESCRIPTION
            ""
    ::= { lcsStatusConfig 10 }

-- {SCALAR} 1.3.6.1.4.1.2356.11.1.11.11
lcsStatusConfigDeleteValues OBJECT-TYPE
    SYNTAX     DisplayString
    MAX-ACCESS read-write
    STATUS     current
    DESCRIPTION
            ""
    ::= { lcsStatusConfig 11 }

-- {TABLE} 1.3.6.1.4.1.2356.11.1.11.12
lcsStatusConfigEventLogTable OBJECT-TYPE
    SYNTAX     SEQUENCE OF LcsStatusConfigEventLogEntry
    MAX-ACCESS not-accessible
    STATUS     current
    DESCRIPTION
            ""
    ::= { lcsStatusConfig 12 }

-- {ROW} 1.3.6.1.4.1.2356.11.1.11.12.1
lcsStatusConfigEventLogEntry OBJECT-TYPE
    SYNTAX     LcsStatusConfigEventLogEntry
    MAX-ACCESS not-accessible
    STATUS     current
    DESCRIPTION
            ""
    INDEX {
            lcsStatusConfigEventLogEntryIdx
          }
    ::= { lcsStatusConfigEventLogTable 1 }

LcsStatusConfigEventLogEntry ::= SEQUENCE {
            lcsStatusConfigEventLogEntryIdx Integer32,
            lcsStatusConfigEventLogEntryEvent INTEGER,
            lcsStatusConfigEventLogEntryAccess INTEGER,
            lcsStatusConfigEventLogEntryIpAddress IpAddress,
            lcsStatusConfigEventLogEntryInfo1 DisplayString,
            lcsStatusConfigEventLogEntryInfo2 DisplayString,
            lcsStatusConfigEventLogEntrySystemTime DisplayString,
            lcsStatusConfigEventLogEntryIpAddressNew DisplayString,
            lcsStatusConfigEventLogEntryInfo3 DisplayString
    }

-- {COLUMN} 1.3.6.1.4.1.2356.11.1.11.12.1.1
lcsStatusConfigEventLogEntryIdx OBJECT-TYPE
    SYNTAX     Integer32 (0..255)
    MAX-ACCESS read-only
    STATUS     current
    DESCRIPTION
            ""
    ::= { lcsStatusConfigEventLogEntry 1 }

-- {COLUMN} 1.3.6.1.4.1.2356.11.1.11.12.1.2
lcsStatusConfigEventLogEntryEvent OBJECT-TYPE
    SYNTAX     INTEGER {
                  eFwUplStart (4),
                  eUplsucc (5),
                  eUplfailto (6),
                  eUplfailincl (7),
                  eUplfailbaddev (8),
                  eLogin (9),
                  eLogout (10),
                  eCnfuplstart (11),
                  eCnfdnlstart (12),
                  eCnfdnlsucc (13),
                  eErrlogin (29),
                  eScrptuplstart (79),
                  eScrptdnlstart (80),
                  eLoginBlocked (87),
                  eUplinvversion (7000),
                  eUplfileexists (7001)
            }
    MAX-ACCESS read-only
    STATUS     current
    DESCRIPTION
            ""
    ::= { lcsStatusConfigEventLogEntry 2 }

-- {COLUMN} 1.3.6.1.4.1.2356.11.1.11.12.1.3
lcsStatusConfigEventLogEntryAccess OBJECT-TYPE
    SYNTAX     INTEGER {
                  eOutband (0),
                  eTelnet (1),
                  eTftp (2),
                  eHttp (3),
                  eSnmp (4),
                  eHttps (5),
                  eTelnetSsl (6),
                  eSsh (7),
                  eLl2m (8),
                  eLmc (11),
                  eConsole (253),
                  ePpp (254),
                  eUnknown (255)
            }
    MAX-ACCESS read-only
    STATUS     current
    DESCRIPTION
            ""
    ::= { lcsStatusConfigEventLogEntry 3 }

-- {COLUMN} 1.3.6.1.4.1.2356.11.1.11.12.1.4
lcsStatusConfigEventLogEntryIpAddress OBJECT-TYPE
    SYNTAX     IpAddress
    MAX-ACCESS read-only
    STATUS     obsolete
    DESCRIPTION
            ""
    ::= { lcsStatusConfigEventLogEntry 4 }

-- {COLUMN} 1.3.6.1.4.1.2356.11.1.11.12.1.5
lcsStatusConfigEventLogEntryInfo1 OBJECT-TYPE
    SYNTAX     DisplayString (SIZE(0..32))
    MAX-ACCESS read-only
    STATUS     current
    DESCRIPTION
            ""
    ::= { lcsStatusConfigEventLogEntry 5 }

-- {COLUMN} 1.3.6.1.4.1.2356.11.1.11.12.1.6
lcsStatusConfigEventLogEntryInfo2 OBJECT-TYPE
    SYNTAX     DisplayString (SIZE(0..64))
    MAX-ACCESS read-only
    STATUS     current
    DESCRIPTION
            ""
    ::= { lcsStatusConfigEventLogEntry 6 }

-- {COLUMN} 1.3.6.1.4.1.2356.11.1.11.12.1.7
lcsStatusConfigEventLogEntrySystemTime OBJECT-TYPE
    SYNTAX     DisplayString (SIZE(0..19))
    MAX-ACCESS read-only
    STATUS     current
    DESCRIPTION
            ""
    ::= { lcsStatusConfigEventLogEntry 7 }

-- {COLUMN} 1.3.6.1.4.1.2356.11.1.11.12.1.8
lcsStatusConfigEventLogEntryIpAddressNew OBJECT-TYPE
    SYNTAX     DisplayString (SIZE(0..255))
    MAX-ACCESS read-only
    STATUS     current
    DESCRIPTION
            ""
    ::= { lcsStatusConfigEventLogEntry 8 }

-- {COLUMN} 1.3.6.1.4.1.2356.11.1.11.12.1.9
lcsStatusConfigEventLogEntryInfo3 OBJECT-TYPE
    SYNTAX     DisplayString (SIZE(0..128))
    MAX-ACCESS read-only
    STATUS     current
    DESCRIPTION
            "-- empty --"
    ::= { lcsStatusConfigEventLogEntry 9 }

-- {SCALAR} 1.3.6.1.4.1.2356.11.1.11.13
lcsStatusConfigStartScan OBJECT-TYPE
    SYNTAX     DisplayString
    MAX-ACCESS read-write
    STATUS     current
    DESCRIPTION
            ""
    ::= { lcsStatusConfig 13 }

-- {TABLE} 1.3.6.1.4.1.2356.11.1.11.14
lcsStatusConfigScanResultsTable OBJECT-TYPE
    SYNTAX     SEQUENCE OF LcsStatusConfigScanResultsEntry
    MAX-ACCESS not-accessible
    STATUS     current
    DESCRIPTION
            ""
    ::= { lcsStatusConfig 14 }

-- {ROW} 1.3.6.1.4.1.2356.11.1.11.14.1
lcsStatusConfigScanResultsEntry OBJECT-TYPE
    SYNTAX     LcsStatusConfigScanResultsEntry
    MAX-ACCESS not-accessible
    STATUS     current
    DESCRIPTION
            ""
    INDEX {
            lcsStatusConfigScanResultsEntryIpAddress,
            lcsStatusConfigScanResultsEntryRtgTag
          }
    ::= { lcsStatusConfigScanResultsTable 1 }

LcsStatusConfigScanResultsEntry ::= SEQUENCE {
            lcsStatusConfigScanResultsEntryIpAddress IpAddress,
            lcsStatusConfigScanResultsEntryName DisplayString,
            lcsStatusConfigScanResultsEntryDeviceType DisplayString,
            lcsStatusConfigScanResultsEntryVersion DisplayString,
            lcsStatusConfigScanResultsEntryState INTEGER,
            lcsStatusConfigScanResultsEntryCapiPort Integer32,
            lcsStatusConfigScanResultsEntryHttpPort Integer32,
            lcsStatusConfigScanResultsEntryHttpsPort Integer32,
            lcsStatusConfigScanResultsEntryRtgTag Integer32
    }

-- {COLUMN} 1.3.6.1.4.1.2356.11.1.11.14.1.1
lcsStatusConfigScanResultsEntryIpAddress OBJECT-TYPE
    SYNTAX     IpAddress
    MAX-ACCESS read-only
    STATUS     current
    DESCRIPTION
            ""
    ::= { lcsStatusConfigScanResultsEntry 1 }

-- {COLUMN} 1.3.6.1.4.1.2356.11.1.11.14.1.2
lcsStatusConfigScanResultsEntryName OBJECT-TYPE
    SYNTAX     DisplayString (SIZE(0..65))
    MAX-ACCESS read-only
    STATUS     current
    DESCRIPTION
            ""
    ::= { lcsStatusConfigScanResultsEntry 2 }

-- {COLUMN} 1.3.6.1.4.1.2356.11.1.11.14.1.3
lcsStatusConfigScanResultsEntryDeviceType OBJECT-TYPE
    SYNTAX     DisplayString (SIZE(0..64))
    MAX-ACCESS read-only
    STATUS     current
    DESCRIPTION
            ""
    ::= { lcsStatusConfigScanResultsEntry 3 }

-- {COLUMN} 1.3.6.1.4.1.2356.11.1.11.14.1.4
lcsStatusConfigScanResultsEntryVersion OBJECT-TYPE
    SYNTAX     DisplayString (SIZE(0..30))
    MAX-ACCESS read-only
    STATUS     current
    DESCRIPTION
            ""
    ::= { lcsStatusConfigScanResultsEntry 4 }

-- {COLUMN} 1.3.6.1.4.1.2356.11.1.11.14.1.5
lcsStatusConfigScanResultsEntryState OBJECT-TYPE
    SYNTAX     INTEGER {
                  eScanning (0),
                  eReady (1),
                  eError (2)
            }
    MAX-ACCESS read-only
    STATUS     current
    DESCRIPTION
            ""
    ::= { lcsStatusConfigScanResultsEntry 5 }

-- {COLUMN} 1.3.6.1.4.1.2356.11.1.11.14.1.6
lcsStatusConfigScanResultsEntryCapiPort OBJECT-TYPE
    SYNTAX     Integer32 (0..65535)
    MAX-ACCESS read-only
    STATUS     current
    DESCRIPTION
            ""
    ::= { lcsStatusConfigScanResultsEntry 6 }

-- {COLUMN} 1.3.6.1.4.1.2356.11.1.11.14.1.7
lcsStatusConfigScanResultsEntryHttpPort OBJECT-TYPE
    SYNTAX     Integer32 (0..65535)
    MAX-ACCESS read-only
    STATUS     current
    DESCRIPTION
            ""
    ::= { lcsStatusConfigScanResultsEntry 7 }

-- {COLUMN} 1.3.6.1.4.1.2356.11.1.11.14.1.8
lcsStatusConfigScanResultsEntryHttpsPort OBJECT-TYPE
    SYNTAX     Integer32 (0..65535)
    MAX-ACCESS read-only
    STATUS     current
    DESCRIPTION
            ""
    ::= { lcsStatusConfigScanResultsEntry 8 }

-- {COLUMN} 1.3.6.1.4.1.2356.11.1.11.14.1.9
lcsStatusConfigScanResultsEntryRtgTag OBJECT-TYPE
    SYNTAX     Integer32 (0..65535)
    MAX-ACCESS read-only
    STATUS     current
    DESCRIPTION
            ""
    ::= { lcsStatusConfigScanResultsEntry 9 }

-- {NODE} 1.3.6.1.4.1.2356.11.1.11.15
lcsStatusConfigAntiTheftProtection OBJECT IDENTIFIER ::= { lcsStatusConfig 15 }

-- {SCALAR} 1.3.6.1.4.1.2356.11.1.11.15.1
lcsStatusConfigAntiTheftProtectionState OBJECT-TYPE
    SYNTAX     INTEGER {
                  eDisabled (0),
                  eActive (1),
                  eSuccessful (2),
                  eLocked (3)
            }
    MAX-ACCESS read-only
    STATUS     current
    DESCRIPTION
            ""
    ::= { lcsStatusConfigAntiTheftProtection 1 }

-- {SCALAR} 1.3.6.1.4.1.2356.11.1.11.15.2
lcsStatusConfigAntiTheftProtectionSendingCallTo OBJECT-TYPE
    SYNTAX     DisplayString (SIZE(0..14))
    MAX-ACCESS read-only
    STATUS     current
    DESCRIPTION
            ""
    ::= { lcsStatusConfigAntiTheftProtection 2 }

-- {SCALAR} 1.3.6.1.4.1.2356.11.1.11.15.3
lcsStatusConfigAntiTheftProtectionWaitingForCallFrom OBJECT-TYPE
    SYNTAX     DisplayString (SIZE(0..14))
    MAX-ACCESS read-only
    STATUS     current
    DESCRIPTION
            ""
    ::= { lcsStatusConfigAntiTheftProtection 3 }

-- {SCALAR} 1.3.6.1.4.1.2356.11.1.11.15.4
lcsStatusConfigAntiTheftProtectionLastSeenCallFrom OBJECT-TYPE
    SYNTAX     DisplayString (SIZE(0..14))
    MAX-ACCESS read-only
    STATUS     current
    DESCRIPTION
            ""
    ::= { lcsStatusConfigAntiTheftProtection 4 }

-- {SCALAR} 1.3.6.1.4.1.2356.11.1.11.15.5
lcsStatusConfigAntiTheftProtectionCallAccepted OBJECT-TYPE
    SYNTAX     INTEGER {
                  eNo (0),
                  eYes (1)
            }
    MAX-ACCESS read-only
    STATUS     current
    DESCRIPTION
            ""
    ::= { lcsStatusConfigAntiTheftProtection 5 }

-- {SCALAR} 1.3.6.1.4.1.2356.11.1.11.15.6
lcsStatusConfigAntiTheftProtectionLastError OBJECT-TYPE
    SYNTAX     INTEGER {
                  eNone (0),
                  eUnallocatedNumber (1),
                  eNoRouteToDestination (3),
                  eNormalCallClearing (16),
                  eUserBusy (17),
                  eNoUserResponding (18),
                  eUserAlertingNoAnswer (19),
                  eCallRejected (21),
                  eNumberChanged (22),
                  eNonSelectedUserClearing (26),
                  eDestinationOutOfOrder (27),
                  eNormalUnspecified (31),
                  eNoChannelAvailable (34),
                  eTempFailure (41),
                  eSwitchingEquipmentCongestion (42),
                  eFacilityNotSubscribed (50),
                  eFacilityNotAvailable (63),
                  eInvalidCallReferenceNumber (81),
                  eIncompatibleDestination (88)
            }
    MAX-ACCESS read-only
    STATUS     current
    DESCRIPTION
            ""
    ::= { lcsStatusConfigAntiTheftProtection 6 }

-- {SCALAR} 1.3.6.1.4.1.2356.11.1.11.15.7
lcsStatusConfigAntiTheftProtectionIncomingCall OBJECT-TYPE
    SYNTAX     INTEGER {
                  eNo (0),
                  eYes (1)
            }
    MAX-ACCESS read-only
    STATUS     current
    DESCRIPTION
            ""
    ::= { lcsStatusConfigAntiTheftProtection 7 }

-- {SCALAR} 1.3.6.1.4.1.2356.11.1.11.15.8
lcsStatusConfigAntiTheftProtectionMethod OBJECT-TYPE
    SYNTAX     INTEGER {
                  eBasicCall (0),
                  eFacility (1),
                  eGps (2)
            }
    MAX-ACCESS read-only
    STATUS     current
    DESCRIPTION
            ""
    ::= { lcsStatusConfigAntiTheftProtection 8 }

-- {SCALAR} 1.3.6.1.4.1.2356.11.1.11.15.9
lcsStatusConfigAntiTheftProtectionPositionValid OBJECT-TYPE
    SYNTAX     INTEGER {
                  eNo (0),
                  eYes (1)
            }
    MAX-ACCESS read-only
    STATUS     current
    DESCRIPTION
            ""
    ::= { lcsStatusConfigAntiTheftProtection 9 }

-- {SCALAR} 1.3.6.1.4.1.2356.11.1.11.15.10
lcsStatusConfigAntiTheftProtectionExpectedLongitudeDeg OBJECT-TYPE
    SYNTAX     DisplayString (SIZE(0..12))
    MAX-ACCESS read-only
    STATUS     current
    DESCRIPTION
            ""
    ::= { lcsStatusConfigAntiTheftProtection 10 }

-- {SCALAR} 1.3.6.1.4.1.2356.11.1.11.15.11
lcsStatusConfigAntiTheftProtectionCurrentLongitudeDeg OBJECT-TYPE
    SYNTAX     DisplayString (SIZE(0..12))
    MAX-ACCESS read-only
    STATUS     current
    DESCRIPTION
            ""
    ::= { lcsStatusConfigAntiTheftProtection 11 }

-- {SCALAR} 1.3.6.1.4.1.2356.11.1.11.15.12
lcsStatusConfigAntiTheftProtectionExpectedLatitudeDeg OBJECT-TYPE
    SYNTAX     DisplayString (SIZE(0..11))
    MAX-ACCESS read-only
    STATUS     current
    DESCRIPTION
            ""
    ::= { lcsStatusConfigAntiTheftProtection 12 }

-- {SCALAR} 1.3.6.1.4.1.2356.11.1.11.15.13
lcsStatusConfigAntiTheftProtectionCurrentLatitudeDeg OBJECT-TYPE
    SYNTAX     DisplayString (SIZE(0..11))
    MAX-ACCESS read-only
    STATUS     current
    DESCRIPTION
            ""
    ::= { lcsStatusConfigAntiTheftProtection 13 }

-- {SCALAR} 1.3.6.1.4.1.2356.11.1.11.15.14
lcsStatusConfigAntiTheftProtectionDeltaLongitudeM OBJECT-TYPE
    SYNTAX     Integer32 (-2147483648..2147483647)
    MAX-ACCESS read-only
    STATUS     current
    DESCRIPTION
            ""
    ::= { lcsStatusConfigAntiTheftProtection 14 }

-- {SCALAR} 1.3.6.1.4.1.2356.11.1.11.15.15
lcsStatusConfigAntiTheftProtectionDeltaLatitudeM OBJECT-TYPE
    SYNTAX     Integer32 (-2147483648..2147483647)
    MAX-ACCESS read-only
    STATUS     current
    DESCRIPTION
            ""
    ::= { lcsStatusConfigAntiTheftProtection 15 }

-- {TABLE} 1.3.6.1.4.1.2356.11.1.11.16
lcsStatusConfigFeaturesTable OBJECT-TYPE
    SYNTAX     SEQUENCE OF LcsStatusConfigFeaturesEntry
    MAX-ACCESS not-accessible
    STATUS     current
    DESCRIPTION
            ""
    ::= { lcsStatusConfig 16 }

-- {ROW} 1.3.6.1.4.1.2356.11.1.11.16.1
lcsStatusConfigFeaturesEntry OBJECT-TYPE
    SYNTAX     LcsStatusConfigFeaturesEntry
    MAX-ACCESS not-accessible
    STATUS     current
    DESCRIPTION
            ""
    INDEX {
            lcsStatusConfigFeaturesEntryFeature,
            lcsStatusConfigFeaturesEntryIndex
          }
    ::= { lcsStatusConfigFeaturesTable 1 }

LcsStatusConfigFeaturesEntry ::= SEQUENCE {
            lcsStatusConfigFeaturesEntryFeature INTEGER,
            lcsStatusConfigFeaturesEntryExpires DisplayString,
            lcsStatusConfigFeaturesEntryExpire Gauge32,
            lcsStatusConfigFeaturesEntryState INTEGER,
            lcsStatusConfigFeaturesEntryIndex Integer32,
            lcsStatusConfigFeaturesEntryCount Gauge32,
            lcsStatusConfigFeaturesEntryLicense-count DisplayString,
            lcsStatusConfigFeaturesEntryAttributes DisplayString
    }

-- {COLUMN} 1.3.6.1.4.1.2356.11.1.11.16.1.1
lcsStatusConfigFeaturesEntryFeature OBJECT-TYPE
    SYNTAX     INTEGER {
                  eIpx (1),
                  eLanBridge (2),
                  eLancapi (3),
                  eLeasedLine (4),
                  eSwitchedLine (5),
                  eDslInterface (6),
                  eFax (7),
                  eModem (8),
                  eVpn5 (9),
                  eVpn25 (10),
                  eCommonCriteria (11),
                  eProductionOk (12),
                  eVpn100 (13),
                  eWlc4025100 (14),
                  eWlanPointToPoint (15),
                  ePublicSpot (16),
                  eVpn200 (17),
                  eVpn500 (18),
                  eVpn1000 (19),
                  eHermes1Wpa (20),
                  eVpn3 (21),
                  eMobileModem (22),
                  eDynamicVpn (23),
                  eWlan5ghz (24),
                  eWlanNoEncryption (25),
                  eVoipAdvanced32 (26),
                  eAllIp (27),
                  eWlanFccRestrictions (28),
                  eWlc402550 (29),
                  eWlc400612 (30),
                  eVoipAdvanced8 (31),
                  eContentfilterAdditive (36),
                  eWlcPublicSpot (37),
                  eWlanMonitorMode (38),
                  eWlanNo5ghz (39),
                  eWlcApUpgrade (40),
                  eWlanDfs3 (41),
                  eInProduction (42),
                  eNetioServer (43),
                  eLanWlanBridge (44),
                  eEthernetIp (45),
                  eProfinet (46),
                  eWlanFilteredAveraging (47),
                  eVpn50 (48),
                  eWlcApBasic (49),
                  ePms (50),
                  ePrp (53),
                  eAllIpAdditive (55),
                  eClustering (56),
                  eR8xxEnterpriseOption (57),
                  eArfContexts (58),
                  eVpn (59),
                  eBandwidth (60),
                  eSfpEedataFileAccess (62),
                  eVrouter (63),
                  eSystemtest (64)
            }
    MAX-ACCESS read-only
    STATUS     current
    DESCRIPTION
            ""
    ::= { lcsStatusConfigFeaturesEntry 1 }

-- {COLUMN} 1.3.6.1.4.1.2356.11.1.11.16.1.2
lcsStatusConfigFeaturesEntryExpires OBJECT-TYPE
    SYNTAX     DisplayString (SIZE(0..255))
    MAX-ACCESS read-only
    STATUS     current
    DESCRIPTION
            ""
    ::= { lcsStatusConfigFeaturesEntry 2 }

-- {COLUMN} 1.3.6.1.4.1.2356.11.1.11.16.1.3
lcsStatusConfigFeaturesEntryExpire OBJECT-TYPE
    SYNTAX     Gauge32
    MAX-ACCESS read-only
    STATUS     current
    DESCRIPTION
            ""
    ::= { lcsStatusConfigFeaturesEntry 3 }

-- {COLUMN} 1.3.6.1.4.1.2356.11.1.11.16.1.4
lcsStatusConfigFeaturesEntryState OBJECT-TYPE
    SYNTAX     INTEGER {
                  eLocked (0),
                  eActive (1),
                  eHidden (2),
                  eExpired (3),
                  eUnused (4)
            }
    MAX-ACCESS read-only
    STATUS     current
    DESCRIPTION
            ""
    ::= { lcsStatusConfigFeaturesEntry 4 }

-- {COLUMN} 1.3.6.1.4.1.2356.11.1.11.16.1.5
lcsStatusConfigFeaturesEntryIndex OBJECT-TYPE
    SYNTAX     Integer32 (0..2147483647)
    MAX-ACCESS read-only
    STATUS     current
    DESCRIPTION
            ""
    ::= { lcsStatusConfigFeaturesEntry 5 }

-- {COLUMN} 1.3.6.1.4.1.2356.11.1.11.16.1.6
lcsStatusConfigFeaturesEntryCount OBJECT-TYPE
    SYNTAX     Gauge32
    MAX-ACCESS read-only
    STATUS     current
    DESCRIPTION
            ""
    ::= { lcsStatusConfigFeaturesEntry 6 }

-- {COLUMN} 1.3.6.1.4.1.2356.11.1.11.16.1.7
lcsStatusConfigFeaturesEntryLicense-count OBJECT-TYPE
    SYNTAX     DisplayString (SIZE(0..255))
    MAX-ACCESS read-only
    STATUS     current
    DESCRIPTION
            ""
    ::= { lcsStatusConfigFeaturesEntry 7 }

-- {COLUMN} 1.3.6.1.4.1.2356.11.1.11.16.1.8
lcsStatusConfigFeaturesEntryAttributes OBJECT-TYPE
    SYNTAX     DisplayString (SIZE(0..255))
    MAX-ACCESS read-only
    STATUS     current
    DESCRIPTION
            "-- empty --"
    ::= { lcsStatusConfigFeaturesEntry 8 }

-- {SCALAR} 1.3.6.1.4.1.2356.11.1.11.20
lcsStatusConfigConfigDateNew OBJECT-TYPE
    SYNTAX     Counter32
    MAX-ACCESS read-only
    STATUS     current
    DESCRIPTION
            ""
    ::= { lcsStatusConfig 20 }

-- {SCALAR} 1.3.6.1.4.1.2356.11.1.11.21
lcsStatusConfigConfigHash OBJECT-TYPE
    SYNTAX     OCTET STRING
    MAX-ACCESS read-only
    STATUS     current
    DESCRIPTION
            "-- empty --"
    ::= { lcsStatusConfig 21 }

-- {SCALAR} 1.3.6.1.4.1.2356.11.1.11.22
lcsStatusConfigConfigVersion OBJECT-TYPE
    SYNTAX     Integer32 (0..2147483647)
    MAX-ACCESS read-only
    STATUS     current
    DESCRIPTION
            "-- empty --"
    ::= { lcsStatusConfig 22 }

-- {TABLE} 1.3.6.1.4.1.2356.11.1.11.23
lcsStatusConfigScriptLogTable OBJECT-TYPE
    SYNTAX     SEQUENCE OF LcsStatusConfigScriptLogEntry
    MAX-ACCESS not-accessible
    STATUS     current
    DESCRIPTION
            "-- empty --"
    ::= { lcsStatusConfig 23 }

-- {ROW} 1.3.6.1.4.1.2356.11.1.11.23.1
lcsStatusConfigScriptLogEntry OBJECT-TYPE
    SYNTAX     LcsStatusConfigScriptLogEntry
    MAX-ACCESS not-accessible
    STATUS     current
    DESCRIPTION
            ""
    INDEX {
            lcsStatusConfigScriptLogEntryIndex
          }
    ::= { lcsStatusConfigScriptLogTable 1 }

LcsStatusConfigScriptLogEntry ::= SEQUENCE {
            lcsStatusConfigScriptLogEntryIndex Integer32,
            lcsStatusConfigScriptLogEntryTime DisplayString,
            lcsStatusConfigScriptLogEntryComment DisplayString,
            lcsStatusConfigScriptLogEntrySuccessful INTEGER,
            lcsStatusConfigScriptLogEntryErrorLine Integer32
    }

-- {COLUMN} 1.3.6.1.4.1.2356.11.1.11.23.1.1
lcsStatusConfigScriptLogEntryIndex OBJECT-TYPE
    SYNTAX     Integer32 (0..2147483647)
    MAX-ACCESS read-only
    STATUS     current
    DESCRIPTION
            "-- empty --"
    ::= { lcsStatusConfigScriptLogEntry 1 }

-- {COLUMN} 1.3.6.1.4.1.2356.11.1.11.23.1.2
lcsStatusConfigScriptLogEntryTime OBJECT-TYPE
    SYNTAX     DisplayString (SIZE(0..19))
    MAX-ACCESS read-only
    STATUS     current
    DESCRIPTION
            "-- empty --"
    ::= { lcsStatusConfigScriptLogEntry 2 }

-- {COLUMN} 1.3.6.1.4.1.2356.11.1.11.23.1.3
lcsStatusConfigScriptLogEntryComment OBJECT-TYPE
    SYNTAX     DisplayString (SIZE(0..80))
    MAX-ACCESS read-only
    STATUS     current
    DESCRIPTION
            "-- empty --"
    ::= { lcsStatusConfigScriptLogEntry 3 }

-- {COLUMN} 1.3.6.1.4.1.2356.11.1.11.23.1.4
lcsStatusConfigScriptLogEntrySuccessful OBJECT-TYPE
    SYNTAX     INTEGER {
                  eNo (0),
                  eYes (1)
            }
    MAX-ACCESS read-only
    STATUS     current
    DESCRIPTION
            "-- empty --"
    ::= { lcsStatusConfigScriptLogEntry 4 }

-- {COLUMN} 1.3.6.1.4.1.2356.11.1.11.23.1.5
lcsStatusConfigScriptLogEntryErrorLine OBJECT-TYPE
    SYNTAX     Integer32 (0..2147483647)
    MAX-ACCESS read-only
    STATUS     current
    DESCRIPTION
            "-- empty --"
    ::= { lcsStatusConfigScriptLogEntry 5 }

-- {SCALAR} 1.3.6.1.4.1.2356.11.1.11.24
lcsStatusConfigLoginSuccessful OBJECT-TYPE
    SYNTAX     Counter32
    MAX-ACCESS read-only
    STATUS     current
    DESCRIPTION
            "-- empty --"
    ::= { lcsStatusConfig 24 }

-- {NODE} 1.3.6.1.4.1.2356.11.1.11.51
lcsStatusConfigSync OBJECT IDENTIFIER ::= { lcsStatusConfig 51 }

-- {SCALAR} 1.3.6.1.4.1.2356.11.1.11.51.1
lcsStatusConfigSyncState OBJECT-TYPE
    SYNTAX     INTEGER {
                  eOff (0),
                  eTcpListenFailure (2),
                  eNotYetLaunched (3),
                  eIncompatibleFirmware (4),
                  eIncompatibleMenuNodes (5),
                  eWrongOwnAddress (6),
                  eNoSnapshot (7),
                  eTimeUnknown (8),
                  eOk (9)
            }
    MAX-ACCESS read-only
    STATUS     current
    DESCRIPTION
            "-- empty --"
    ::= { lcsStatusConfigSync 1 }

-- {NODE} 1.3.6.1.4.1.2356.11.1.11.51.2
lcsStatusConfigSyncNewCluster OBJECT IDENTIFIER ::= { lcsStatusConfigSync 2 }

-- {SCALAR} 1.3.6.1.4.1.2356.11.1.11.51.2.1
lcsStatusConfigSyncNewClusterName OBJECT-TYPE
    SYNTAX     DisplayString (SIZE(0..254))
    MAX-ACCESS read-only
    STATUS     current
    DESCRIPTION
            "-- empty --"
    ::= { lcsStatusConfigSyncNewCluster 1 }

-- {TABLE} 1.3.6.1.4.1.2356.11.1.11.51.2.2
lcsStatusConfigSyncNewClusterGroupMembersTable OBJECT-TYPE
    SYNTAX     SEQUENCE OF LcsStatusConfigSyncNewClusterGroupMembersEntry
    MAX-ACCESS not-accessible
    STATUS     current
    DESCRIPTION
            "-- empty --"
    ::= { lcsStatusConfigSyncNewCluster 2 }

-- {ROW} 1.3.6.1.4.1.2356.11.1.11.51.2.2.1
lcsStatusConfigSyncNewClusterGroupMembersEntry OBJECT-TYPE
    SYNTAX     LcsStatusConfigSyncNewClusterGroupMembersEntry
    MAX-ACCESS not-accessible
    STATUS     current
    DESCRIPTION
            ""
    INDEX {
            lcsStatusConfigSyncNewClusterGroupMembersEntryIdx
          }
    ::= { lcsStatusConfigSyncNewClusterGroupMembersTable 1 }

LcsStatusConfigSyncNewClusterGroupMembersEntry ::= SEQUENCE {
            lcsStatusConfigSyncNewClusterGroupMembersEntryIdx Integer32,
            lcsStatusConfigSyncNewClusterGroupMembersEntryId Integer32,
            lcsStatusConfigSyncNewClusterGroupMembersEntryAddress DisplayString,
            lcsStatusConfigSyncNewClusterGroupMembersEntryThisDevice INTEGER
    }

-- {COLUMN} 1.3.6.1.4.1.2356.11.1.11.51.2.2.1.1
lcsStatusConfigSyncNewClusterGroupMembersEntryIdx OBJECT-TYPE
    SYNTAX     Integer32 (0..65535)
    MAX-ACCESS read-only
    STATUS     current
    DESCRIPTION
            "-- empty --"
    ::= { lcsStatusConfigSyncNewClusterGroupMembersEntry 1 }

-- {COLUMN} 1.3.6.1.4.1.2356.11.1.11.51.2.2.1.2
lcsStatusConfigSyncNewClusterGroupMembersEntryId OBJECT-TYPE
    SYNTAX     Integer32 (0..65535)
    MAX-ACCESS read-only
    STATUS     current
    DESCRIPTION
            "-- empty --"
    ::= { lcsStatusConfigSyncNewClusterGroupMembersEntry 2 }

-- {COLUMN} 1.3.6.1.4.1.2356.11.1.11.51.2.2.1.3
lcsStatusConfigSyncNewClusterGroupMembersEntryAddress OBJECT-TYPE
    SYNTAX     DisplayString (SIZE(0..63))
    MAX-ACCESS read-only
    STATUS     current
    DESCRIPTION
            "-- empty --"
    ::= { lcsStatusConfigSyncNewClusterGroupMembersEntry 3 }

-- {COLUMN} 1.3.6.1.4.1.2356.11.1.11.51.2.2.1.4
lcsStatusConfigSyncNewClusterGroupMembersEntryThisDevice OBJECT-TYPE
    SYNTAX     INTEGER {
                  eNo (0),
                  eYes (1)
            }
    MAX-ACCESS read-only
    STATUS     current
    DESCRIPTION
            "-- empty --"
    ::= { lcsStatusConfigSyncNewClusterGroupMembersEntry 4 }

-- {TABLE} 1.3.6.1.4.1.2356.11.1.11.51.2.3
lcsStatusConfigSyncNewClusterMenuNodesTable OBJECT-TYPE
    SYNTAX     SEQUENCE OF LcsStatusConfigSyncNewClusterMenuNodesEntry
    MAX-ACCESS not-accessible
    STATUS     current
    DESCRIPTION
            "-- empty --"
    ::= { lcsStatusConfigSyncNewCluster 3 }

-- {ROW} 1.3.6.1.4.1.2356.11.1.11.51.2.3.1
lcsStatusConfigSyncNewClusterMenuNodesEntry OBJECT-TYPE
    SYNTAX     LcsStatusConfigSyncNewClusterMenuNodesEntry
    MAX-ACCESS not-accessible
    STATUS     current
    DESCRIPTION
            ""
    INDEX {
            lcsStatusConfigSyncNewClusterMenuNodesEntryIdx
          }
    ::= { lcsStatusConfigSyncNewClusterMenuNodesTable 1 }

LcsStatusConfigSyncNewClusterMenuNodesEntry ::= SEQUENCE {
            lcsStatusConfigSyncNewClusterMenuNodesEntryIdx Integer32,
            lcsStatusConfigSyncNewClusterMenuNodesEntryId Integer32,
            lcsStatusConfigSyncNewClusterMenuNodesEntryPath DisplayString,
            lcsStatusConfigSyncNewClusterMenuNodesEntrySnmpOid DisplayString,
            lcsStatusConfigSyncNewClusterMenuNodesEntryIndexColumns DisplayString
    }

-- {COLUMN} 1.3.6.1.4.1.2356.11.1.11.51.2.3.1.1
lcsStatusConfigSyncNewClusterMenuNodesEntryIdx OBJECT-TYPE
    SYNTAX     Integer32 (0..2147483647)
    MAX-ACCESS read-only
    STATUS     current
    DESCRIPTION
            "-- empty --"
    ::= { lcsStatusConfigSyncNewClusterMenuNodesEntry 1 }

-- {COLUMN} 1.3.6.1.4.1.2356.11.1.11.51.2.3.1.2
lcsStatusConfigSyncNewClusterMenuNodesEntryId OBJECT-TYPE
    SYNTAX     Integer32 (0..2147483647)
    MAX-ACCESS read-only
    STATUS     current
    DESCRIPTION
            "-- empty --"
    ::= { lcsStatusConfigSyncNewClusterMenuNodesEntry 2 }

-- {COLUMN} 1.3.6.1.4.1.2356.11.1.11.51.2.3.1.3
lcsStatusConfigSyncNewClusterMenuNodesEntryPath OBJECT-TYPE
    SYNTAX     DisplayString (SIZE(0..127))
    MAX-ACCESS read-only
    STATUS     current
    DESCRIPTION
            "-- empty --"
    ::= { lcsStatusConfigSyncNewClusterMenuNodesEntry 3 }

-- {COLUMN} 1.3.6.1.4.1.2356.11.1.11.51.2.3.1.4
lcsStatusConfigSyncNewClusterMenuNodesEntrySnmpOid OBJECT-TYPE
    SYNTAX     DisplayString (SIZE(0..63))
    MAX-ACCESS read-only
    STATUS     current
    DESCRIPTION
            "-- empty --"
    ::= { lcsStatusConfigSyncNewClusterMenuNodesEntry 4 }

-- {COLUMN} 1.3.6.1.4.1.2356.11.1.11.51.2.3.1.5
lcsStatusConfigSyncNewClusterMenuNodesEntryIndexColumns OBJECT-TYPE
    SYNTAX     DisplayString (SIZE(0..127))
    MAX-ACCESS read-only
    STATUS     current
    DESCRIPTION
            "-- empty --"
    ::= { lcsStatusConfigSyncNewClusterMenuNodesEntry 5 }

-- {TABLE} 1.3.6.1.4.1.2356.11.1.11.51.2.4
lcsStatusConfigSyncNewClusterIgnoredRowsTable OBJECT-TYPE
    SYNTAX     SEQUENCE OF LcsStatusConfigSyncNewClusterIgnoredRowsEntry
    MAX-ACCESS not-accessible
    STATUS     current
    DESCRIPTION
            "-- empty --"
    ::= { lcsStatusConfigSyncNewCluster 4 }

-- {ROW} 1.3.6.1.4.1.2356.11.1.11.51.2.4.1
lcsStatusConfigSyncNewClusterIgnoredRowsEntry OBJECT-TYPE
    SYNTAX     LcsStatusConfigSyncNewClusterIgnoredRowsEntry
    MAX-ACCESS not-accessible
    STATUS     current
    DESCRIPTION
            ""
    INDEX {
            lcsStatusConfigSyncNewClusterIgnoredRowsEntryIdx
          }
    ::= { lcsStatusConfigSyncNewClusterIgnoredRowsTable 1 }

LcsStatusConfigSyncNewClusterIgnoredRowsEntry ::= SEQUENCE {
            lcsStatusConfigSyncNewClusterIgnoredRowsEntryIdx Integer32,
            lcsStatusConfigSyncNewClusterIgnoredRowsEntryId Integer32,
            lcsStatusConfigSyncNewClusterIgnoredRowsEntryPath DisplayString,
            lcsStatusConfigSyncNewClusterIgnoredRowsEntrySnmpOid DisplayString,
            lcsStatusConfigSyncNewClusterIgnoredRowsEntryRowIndex DisplayString
    }

-- {COLUMN} 1.3.6.1.4.1.2356.11.1.11.51.2.4.1.1
lcsStatusConfigSyncNewClusterIgnoredRowsEntryIdx OBJECT-TYPE
    SYNTAX     Integer32 (0..2147483647)
    MAX-ACCESS read-only
    STATUS     current
    DESCRIPTION
            "-- empty --"
    ::= { lcsStatusConfigSyncNewClusterIgnoredRowsEntry 1 }

-- {COLUMN} 1.3.6.1.4.1.2356.11.1.11.51.2.4.1.2
lcsStatusConfigSyncNewClusterIgnoredRowsEntryId OBJECT-TYPE
    SYNTAX     Integer32 (0..2147483647)
    MAX-ACCESS read-only
    STATUS     current
    DESCRIPTION
            "-- empty --"
    ::= { lcsStatusConfigSyncNewClusterIgnoredRowsEntry 2 }

-- {COLUMN} 1.3.6.1.4.1.2356.11.1.11.51.2.4.1.3
lcsStatusConfigSyncNewClusterIgnoredRowsEntryPath OBJECT-TYPE
    SYNTAX     DisplayString (SIZE(0..127))
    MAX-ACCESS read-only
    STATUS     current
    DESCRIPTION
            "-- empty --"
    ::= { lcsStatusConfigSyncNewClusterIgnoredRowsEntry 3 }

-- {COLUMN} 1.3.6.1.4.1.2356.11.1.11.51.2.4.1.4
lcsStatusConfigSyncNewClusterIgnoredRowsEntrySnmpOid OBJECT-TYPE
    SYNTAX     DisplayString (SIZE(0..63))
    MAX-ACCESS read-only
    STATUS     current
    DESCRIPTION
            "-- empty --"
    ::= { lcsStatusConfigSyncNewClusterIgnoredRowsEntry 4 }

-- {COLUMN} 1.3.6.1.4.1.2356.11.1.11.51.2.4.1.5
lcsStatusConfigSyncNewClusterIgnoredRowsEntryRowIndex OBJECT-TYPE
    SYNTAX     DisplayString (SIZE(0..127))
    MAX-ACCESS read-only
    STATUS     current
    DESCRIPTION
            "-- empty --"
    ::= { lcsStatusConfigSyncNewClusterIgnoredRowsEntry 5 }

-- {SCALAR} 1.3.6.1.4.1.2356.11.1.11.51.2.5
lcsStatusConfigSyncNewClusterState OBJECT-TYPE
    SYNTAX     INTEGER {
                  eOff (0),
                  eInvalid (1),
                  eNotRunning (2),
                  eRunning (3),
                  eChanged (4)
            }
    MAX-ACCESS read-only
    STATUS     current
    DESCRIPTION
            "-- empty --"
    ::= { lcsStatusConfigSyncNewCluster 5 }

-- {SCALAR} 1.3.6.1.4.1.2356.11.1.11.51.2.6
lcsStatusConfigSyncNewClusterInfo OBJECT-TYPE
    SYNTAX     DisplayString (SIZE(0..254))
    MAX-ACCESS read-only
    STATUS     current
    DESCRIPTION
            "-- empty --"
    ::= { lcsStatusConfigSyncNewCluster 6 }

-- {SCALAR} 1.3.6.1.4.1.2356.11.1.11.51.2.7
lcsStatusConfigSyncNewClusterLaunch OBJECT-TYPE
    SYNTAX     DisplayString
    MAX-ACCESS read-write
    STATUS     current
    DESCRIPTION
            "-- empty --"
    ::= { lcsStatusConfigSyncNewCluster 7 }

-- {SCALAR} 1.3.6.1.4.1.2356.11.1.11.51.3
lcsStatusConfigSyncClusterTime OBJECT-TYPE
    SYNTAX     DisplayString
    MAX-ACCESS read-only
    STATUS     current
    DESCRIPTION
            "-- empty --"
    ::= { lcsStatusConfigSync 3 }

-- {NODE} 1.3.6.1.4.1.2356.11.1.11.51.4
lcsStatusConfigSyncLocalConfig OBJECT IDENTIFIER ::= { lcsStatusConfigSync 4 }

-- {TABLE} 1.3.6.1.4.1.2356.11.1.11.51.4.1
lcsStatusConfigSyncLocalConfigDetectedTable OBJECT-TYPE
    SYNTAX     SEQUENCE OF LcsStatusConfigSyncLocalConfigDetectedEntry
    MAX-ACCESS not-accessible
    STATUS     current
    DESCRIPTION
            ""
    ::= { lcsStatusConfigSyncLocalConfig 1 }

-- {ROW} 1.3.6.1.4.1.2356.11.1.11.51.4.1.1
lcsStatusConfigSyncLocalConfigDetectedEntry OBJECT-TYPE
    SYNTAX     LcsStatusConfigSyncLocalConfigDetectedEntry
    MAX-ACCESS not-accessible
    STATUS     current
    DESCRIPTION
            ""
    INDEX {
            lcsStatusConfigSyncLocalConfigDetectedEntryIdx
          }
    ::= { lcsStatusConfigSyncLocalConfigDetectedTable 1 }

LcsStatusConfigSyncLocalConfigDetectedEntry ::= SEQUENCE {
            lcsStatusConfigSyncLocalConfigDetectedEntryIdx Integer32,
            lcsStatusConfigSyncLocalConfigDetectedEntryDetectedAt DisplayString,
            lcsStatusConfigSyncLocalConfigDetectedEntryDetectedAtNumerical Counter32,
            lcsStatusConfigSyncLocalConfigDetectedEntryPath DisplayString,
            lcsStatusConfigSyncLocalConfigDetectedEntryType INTEGER,
            lcsStatusConfigSyncLocalConfigDetectedEntryValue DisplayString
    }

-- {COLUMN} 1.3.6.1.4.1.2356.11.1.11.51.4.1.1.1
lcsStatusConfigSyncLocalConfigDetectedEntryIdx OBJECT-TYPE
    SYNTAX     Integer32 (0..2147483647)
    MAX-ACCESS read-only
    STATUS     current
    DESCRIPTION
            "-- empty --"
    ::= { lcsStatusConfigSyncLocalConfigDetectedEntry 1 }

-- {COLUMN} 1.3.6.1.4.1.2356.11.1.11.51.4.1.1.2
lcsStatusConfigSyncLocalConfigDetectedEntryDetectedAt OBJECT-TYPE
    SYNTAX     DisplayString (SIZE(0..255))
    MAX-ACCESS read-only
    STATUS     current
    DESCRIPTION
            "-- empty --"
    ::= { lcsStatusConfigSyncLocalConfigDetectedEntry 2 }

-- {COLUMN} 1.3.6.1.4.1.2356.11.1.11.51.4.1.1.3
lcsStatusConfigSyncLocalConfigDetectedEntryDetectedAtNumerical OBJECT-TYPE
    SYNTAX     Counter32
    MAX-ACCESS read-only
    STATUS     current
    DESCRIPTION
            "-- empty --"
    ::= { lcsStatusConfigSyncLocalConfigDetectedEntry 3 }

-- {COLUMN} 1.3.6.1.4.1.2356.11.1.11.51.4.1.1.4
lcsStatusConfigSyncLocalConfigDetectedEntryPath OBJECT-TYPE
    SYNTAX     DisplayString (SIZE(0..255))
    MAX-ACCESS read-only
    STATUS     current
    DESCRIPTION
            "-- empty --"
    ::= { lcsStatusConfigSyncLocalConfigDetectedEntry 4 }

-- {COLUMN} 1.3.6.1.4.1.2356.11.1.11.51.4.1.1.5
lcsStatusConfigSyncLocalConfigDetectedEntryType OBJECT-TYPE
    SYNTAX     INTEGER {
                  eSetScalar (1),
                  eSetRow (2),
                  eDeleteRow (3)
            }
    MAX-ACCESS read-only
    STATUS     current
    DESCRIPTION
            "-- empty --"
    ::= { lcsStatusConfigSyncLocalConfigDetectedEntry 5 }

-- {COLUMN} 1.3.6.1.4.1.2356.11.1.11.51.4.1.1.6
lcsStatusConfigSyncLocalConfigDetectedEntryValue OBJECT-TYPE
    SYNTAX     DisplayString (SIZE(0..255))
    MAX-ACCESS read-only
    STATUS     current
    DESCRIPTION
            "-- empty --"
    ::= { lcsStatusConfigSyncLocalConfigDetectedEntry 6 }

-- {TABLE} 1.3.6.1.4.1.2356.11.1.11.51.4.2
lcsStatusConfigSyncLocalConfigAppliedTable OBJECT-TYPE
    SYNTAX     SEQUENCE OF LcsStatusConfigSyncLocalConfigAppliedEntry
    MAX-ACCESS not-accessible
    STATUS     current
    DESCRIPTION
            ""
    ::= { lcsStatusConfigSyncLocalConfig 2 }

-- {ROW} 1.3.6.1.4.1.2356.11.1.11.51.4.2.1
lcsStatusConfigSyncLocalConfigAppliedEntry OBJECT-TYPE
    SYNTAX     LcsStatusConfigSyncLocalConfigAppliedEntry
    MAX-ACCESS not-accessible
    STATUS     current
    DESCRIPTION
            ""
    INDEX {
            lcsStatusConfigSyncLocalConfigAppliedEntryIdx
          }
    ::= { lcsStatusConfigSyncLocalConfigAppliedTable 1 }

LcsStatusConfigSyncLocalConfigAppliedEntry ::= SEQUENCE {
            lcsStatusConfigSyncLocalConfigAppliedEntryIdx Integer32,
            lcsStatusConfigSyncLocalConfigAppliedEntryAppliedAt DisplayString,
            lcsStatusConfigSyncLocalConfigAppliedEntryAppliedAtNumerical Counter32,
            lcsStatusConfigSyncLocalConfigAppliedEntryPath DisplayString,
            lcsStatusConfigSyncLocalConfigAppliedEntryType INTEGER,
            lcsStatusConfigSyncLocalConfigAppliedEntryValue DisplayString,
            lcsStatusConfigSyncLocalConfigAppliedEntryResult INTEGER
    }

-- {COLUMN} 1.3.6.1.4.1.2356.11.1.11.51.4.2.1.1
lcsStatusConfigSyncLocalConfigAppliedEntryIdx OBJECT-TYPE
    SYNTAX     Integer32 (0..2147483647)
    MAX-ACCESS read-only
    STATUS     current
    DESCRIPTION
            "-- empty --"
    ::= { lcsStatusConfigSyncLocalConfigAppliedEntry 1 }

-- {COLUMN} 1.3.6.1.4.1.2356.11.1.11.51.4.2.1.2
lcsStatusConfigSyncLocalConfigAppliedEntryAppliedAt OBJECT-TYPE
    SYNTAX     DisplayString (SIZE(0..255))
    MAX-ACCESS read-only
    STATUS     current
    DESCRIPTION
            "-- empty --"
    ::= { lcsStatusConfigSyncLocalConfigAppliedEntry 2 }

-- {COLUMN} 1.3.6.1.4.1.2356.11.1.11.51.4.2.1.3
lcsStatusConfigSyncLocalConfigAppliedEntryAppliedAtNumerical OBJECT-TYPE
    SYNTAX     Counter32
    MAX-ACCESS read-only
    STATUS     current
    DESCRIPTION
            "-- empty --"
    ::= { lcsStatusConfigSyncLocalConfigAppliedEntry 3 }

-- {COLUMN} 1.3.6.1.4.1.2356.11.1.11.51.4.2.1.4
lcsStatusConfigSyncLocalConfigAppliedEntryPath OBJECT-TYPE
    SYNTAX     DisplayString (SIZE(0..255))
    MAX-ACCESS read-only
    STATUS     current
    DESCRIPTION
            "-- empty --"
    ::= { lcsStatusConfigSyncLocalConfigAppliedEntry 4 }

-- {COLUMN} 1.3.6.1.4.1.2356.11.1.11.51.4.2.1.5
lcsStatusConfigSyncLocalConfigAppliedEntryType OBJECT-TYPE
    SYNTAX     INTEGER {
                  eSetScalar (1),
                  eSetRow (2),
                  eDeleteRow (3)
            }
    MAX-ACCESS read-only
    STATUS     current
    DESCRIPTION
            "-- empty --"
    ::= { lcsStatusConfigSyncLocalConfigAppliedEntry 5 }

-- {COLUMN} 1.3.6.1.4.1.2356.11.1.11.51.4.2.1.6
lcsStatusConfigSyncLocalConfigAppliedEntryValue OBJECT-TYPE
    SYNTAX     DisplayString (SIZE(0..255))
    MAX-ACCESS read-only
    STATUS     current
    DESCRIPTION
            "-- empty --"
    ::= { lcsStatusConfigSyncLocalConfigAppliedEntry 6 }

-- {COLUMN} 1.3.6.1.4.1.2356.11.1.11.51.4.2.1.7
lcsStatusConfigSyncLocalConfigAppliedEntryResult OBJECT-TYPE
    SYNTAX     INTEGER {
                  eOk (0),
                  eOkMsgSent (1),
                  eOkClose (2),
                  eOkAbort (3),
                  eOkMore (4),
                  eOkStarted (5),
                  eNoLogin (16),
                  eSyntaxError (32),
                  eNoPath (48),
                  ePathUnresolvable (64),
                  ePathAmbiguous (80),
                  eNoMenuStack (96),
                  eNotSettable (112),
                  eValueInvalid (128),
                  eReadOnlyConn (144),
                  eActionFailed (160),
                  eTableIsFull (176),
                  eWasIgnored (192),
                  eWrongPassword (208),
                  ePathNameEmpty (224),
                  eEndOfLine (240)
            }
    MAX-ACCESS read-only
    STATUS     current
    DESCRIPTION
            "-- empty --"
    ::= { lcsStatusConfigSyncLocalConfigAppliedEntry 7 }

-- {NODE} 1.3.6.1.4.1.2356.11.1.11.51.5
lcsStatusConfigSyncRunningCluster OBJECT IDENTIFIER ::= { lcsStatusConfigSync 5 }

-- {SCALAR} 1.3.6.1.4.1.2356.11.1.11.51.5.1
lcsStatusConfigSyncRunningClusterId OBJECT-TYPE
    SYNTAX     DisplayString (SIZE(0..8))
    MAX-ACCESS read-only
    STATUS     current
    DESCRIPTION
            "-- empty --"
    ::= { lcsStatusConfigSyncRunningCluster 1 }

-- {SCALAR} 1.3.6.1.4.1.2356.11.1.11.51.5.2
lcsStatusConfigSyncRunningClusterName OBJECT-TYPE
    SYNTAX     DisplayString (SIZE(0..254))
    MAX-ACCESS read-only
    STATUS     current
    DESCRIPTION
            "-- empty --"
    ::= { lcsStatusConfigSyncRunningCluster 2 }

-- {TABLE} 1.3.6.1.4.1.2356.11.1.11.51.5.3
lcsStatusConfigSyncRunningClusterGroupMembersTable OBJECT-TYPE
    SYNTAX     SEQUENCE OF LcsStatusConfigSyncRunningClusterGroupMembersEntry
    MAX-ACCESS not-accessible
    STATUS     current
    DESCRIPTION
            "-- empty --"
    ::= { lcsStatusConfigSyncRunningCluster 3 }

-- {ROW} 1.3.6.1.4.1.2356.11.1.11.51.5.3.1
lcsStatusConfigSyncRunningClusterGroupMembersEntry OBJECT-TYPE
    SYNTAX     LcsStatusConfigSyncRunningClusterGroupMembersEntry
    MAX-ACCESS not-accessible
    STATUS     current
    DESCRIPTION
            ""
    INDEX {
            lcsStatusConfigSyncRunningClusterGroupMembersEntryIdx
          }
    ::= { lcsStatusConfigSyncRunningClusterGroupMembersTable 1 }

LcsStatusConfigSyncRunningClusterGroupMembersEntry ::= SEQUENCE {
            lcsStatusConfigSyncRunningClusterGroupMembersEntryIdx Integer32,
            lcsStatusConfigSyncRunningClusterGroupMembersEntryId Integer32,
            lcsStatusConfigSyncRunningClusterGroupMembersEntryAddress DisplayString,
            lcsStatusConfigSyncRunningClusterGroupMembersEntryThisDevice INTEGER
    }

-- {COLUMN} 1.3.6.1.4.1.2356.11.1.11.51.5.3.1.1
lcsStatusConfigSyncRunningClusterGroupMembersEntryIdx OBJECT-TYPE
    SYNTAX     Integer32 (0..65535)
    MAX-ACCESS read-only
    STATUS     current
    DESCRIPTION
            "-- empty --"
    ::= { lcsStatusConfigSyncRunningClusterGroupMembersEntry 1 }

-- {COLUMN} 1.3.6.1.4.1.2356.11.1.11.51.5.3.1.2
lcsStatusConfigSyncRunningClusterGroupMembersEntryId OBJECT-TYPE
    SYNTAX     Integer32 (0..65535)
    MAX-ACCESS read-only
    STATUS     current
    DESCRIPTION
            "-- empty --"
    ::= { lcsStatusConfigSyncRunningClusterGroupMembersEntry 2 }

-- {COLUMN} 1.3.6.1.4.1.2356.11.1.11.51.5.3.1.3
lcsStatusConfigSyncRunningClusterGroupMembersEntryAddress OBJECT-TYPE
    SYNTAX     DisplayString (SIZE(0..63))
    MAX-ACCESS read-only
    STATUS     current
    DESCRIPTION
            "-- empty --"
    ::= { lcsStatusConfigSyncRunningClusterGroupMembersEntry 3 }

-- {COLUMN} 1.3.6.1.4.1.2356.11.1.11.51.5.3.1.4
lcsStatusConfigSyncRunningClusterGroupMembersEntryThisDevice OBJECT-TYPE
    SYNTAX     INTEGER {
                  eNo (0),
                  eYes (1)
            }
    MAX-ACCESS read-only
    STATUS     current
    DESCRIPTION
            "-- empty --"
    ::= { lcsStatusConfigSyncRunningClusterGroupMembersEntry 4 }

-- {TABLE} 1.3.6.1.4.1.2356.11.1.11.51.5.4
lcsStatusConfigSyncRunningClusterMenuNodesTable OBJECT-TYPE
    SYNTAX     SEQUENCE OF LcsStatusConfigSyncRunningClusterMenuNodesEntry
    MAX-ACCESS not-accessible
    STATUS     current
    DESCRIPTION
            "-- empty --"
    ::= { lcsStatusConfigSyncRunningCluster 4 }

-- {ROW} 1.3.6.1.4.1.2356.11.1.11.51.5.4.1
lcsStatusConfigSyncRunningClusterMenuNodesEntry OBJECT-TYPE
    SYNTAX     LcsStatusConfigSyncRunningClusterMenuNodesEntry
    MAX-ACCESS not-accessible
    STATUS     current
    DESCRIPTION
            ""
    INDEX {
            lcsStatusConfigSyncRunningClusterMenuNodesEntryIdx
          }
    ::= { lcsStatusConfigSyncRunningClusterMenuNodesTable 1 }

LcsStatusConfigSyncRunningClusterMenuNodesEntry ::= SEQUENCE {
            lcsStatusConfigSyncRunningClusterMenuNodesEntryIdx Integer32,
            lcsStatusConfigSyncRunningClusterMenuNodesEntryId Integer32,
            lcsStatusConfigSyncRunningClusterMenuNodesEntryPath DisplayString,
            lcsStatusConfigSyncRunningClusterMenuNodesEntrySnmpOid DisplayString,
            lcsStatusConfigSyncRunningClusterMenuNodesEntryIndexColumns DisplayString
    }

-- {COLUMN} 1.3.6.1.4.1.2356.11.1.11.51.5.4.1.1
lcsStatusConfigSyncRunningClusterMenuNodesEntryIdx OBJECT-TYPE
    SYNTAX     Integer32 (0..2147483647)
    MAX-ACCESS read-only
    STATUS     current
    DESCRIPTION
            "-- empty --"
    ::= { lcsStatusConfigSyncRunningClusterMenuNodesEntry 1 }

-- {COLUMN} 1.3.6.1.4.1.2356.11.1.11.51.5.4.1.2
lcsStatusConfigSyncRunningClusterMenuNodesEntryId OBJECT-TYPE
    SYNTAX     Integer32 (0..2147483647)
    MAX-ACCESS read-only
    STATUS     current
    DESCRIPTION
            "-- empty --"
    ::= { lcsStatusConfigSyncRunningClusterMenuNodesEntry 2 }

-- {COLUMN} 1.3.6.1.4.1.2356.11.1.11.51.5.4.1.3
lcsStatusConfigSyncRunningClusterMenuNodesEntryPath OBJECT-TYPE
    SYNTAX     DisplayString (SIZE(0..127))
    MAX-ACCESS read-only
    STATUS     current
    DESCRIPTION
            "-- empty --"
    ::= { lcsStatusConfigSyncRunningClusterMenuNodesEntry 3 }

-- {COLUMN} 1.3.6.1.4.1.2356.11.1.11.51.5.4.1.4
lcsStatusConfigSyncRunningClusterMenuNodesEntrySnmpOid OBJECT-TYPE
    SYNTAX     DisplayString (SIZE(0..63))
    MAX-ACCESS read-only
    STATUS     current
    DESCRIPTION
            "-- empty --"
    ::= { lcsStatusConfigSyncRunningClusterMenuNodesEntry 4 }

-- {COLUMN} 1.3.6.1.4.1.2356.11.1.11.51.5.4.1.5
lcsStatusConfigSyncRunningClusterMenuNodesEntryIndexColumns OBJECT-TYPE
    SYNTAX     DisplayString (SIZE(0..127))
    MAX-ACCESS read-only
    STATUS     current
    DESCRIPTION
            "-- empty --"
    ::= { lcsStatusConfigSyncRunningClusterMenuNodesEntry 5 }

-- {TABLE} 1.3.6.1.4.1.2356.11.1.11.51.5.5
lcsStatusConfigSyncRunningClusterIgnoredRowsTable OBJECT-TYPE
    SYNTAX     SEQUENCE OF LcsStatusConfigSyncRunningClusterIgnoredRowsEntry
    MAX-ACCESS not-accessible
    STATUS     current
    DESCRIPTION
            "-- empty --"
    ::= { lcsStatusConfigSyncRunningCluster 5 }

-- {ROW} 1.3.6.1.4.1.2356.11.1.11.51.5.5.1
lcsStatusConfigSyncRunningClusterIgnoredRowsEntry OBJECT-TYPE
    SYNTAX     LcsStatusConfigSyncRunningClusterIgnoredRowsEntry
    MAX-ACCESS not-accessible
    STATUS     current
    DESCRIPTION
            ""
    INDEX {
            lcsStatusConfigSyncRunningClusterIgnoredRowsEntryIdx
          }
    ::= { lcsStatusConfigSyncRunningClusterIgnoredRowsTable 1 }

LcsStatusConfigSyncRunningClusterIgnoredRowsEntry ::= SEQUENCE {
            lcsStatusConfigSyncRunningClusterIgnoredRowsEntryIdx Integer32,
            lcsStatusConfigSyncRunningClusterIgnoredRowsEntryId Integer32,
            lcsStatusConfigSyncRunningClusterIgnoredRowsEntryPath DisplayString,
            lcsStatusConfigSyncRunningClusterIgnoredRowsEntrySnmpOid DisplayString,
            lcsStatusConfigSyncRunningClusterIgnoredRowsEntryRowIndex DisplayString
    }

-- {COLUMN} 1.3.6.1.4.1.2356.11.1.11.51.5.5.1.1
lcsStatusConfigSyncRunningClusterIgnoredRowsEntryIdx OBJECT-TYPE
    SYNTAX     Integer32 (0..2147483647)
    MAX-ACCESS read-only
    STATUS     current
    DESCRIPTION
            "-- empty --"
    ::= { lcsStatusConfigSyncRunningClusterIgnoredRowsEntry 1 }

-- {COLUMN} 1.3.6.1.4.1.2356.11.1.11.51.5.5.1.2
lcsStatusConfigSyncRunningClusterIgnoredRowsEntryId OBJECT-TYPE
    SYNTAX     Integer32 (0..2147483647)
    MAX-ACCESS read-only
    STATUS     current
    DESCRIPTION
            "-- empty --"
    ::= { lcsStatusConfigSyncRunningClusterIgnoredRowsEntry 2 }

-- {COLUMN} 1.3.6.1.4.1.2356.11.1.11.51.5.5.1.3
lcsStatusConfigSyncRunningClusterIgnoredRowsEntryPath OBJECT-TYPE
    SYNTAX     DisplayString (SIZE(0..127))
    MAX-ACCESS read-only
    STATUS     current
    DESCRIPTION
            "-- empty --"
    ::= { lcsStatusConfigSyncRunningClusterIgnoredRowsEntry 3 }

-- {COLUMN} 1.3.6.1.4.1.2356.11.1.11.51.5.5.1.4
lcsStatusConfigSyncRunningClusterIgnoredRowsEntrySnmpOid OBJECT-TYPE
    SYNTAX     DisplayString (SIZE(0..63))
    MAX-ACCESS read-only
    STATUS     current
    DESCRIPTION
            "-- empty --"
    ::= { lcsStatusConfigSyncRunningClusterIgnoredRowsEntry 4 }

-- {COLUMN} 1.3.6.1.4.1.2356.11.1.11.51.5.5.1.5
lcsStatusConfigSyncRunningClusterIgnoredRowsEntryRowIndex OBJECT-TYPE
    SYNTAX     DisplayString (SIZE(0..127))
    MAX-ACCESS read-only
    STATUS     current
    DESCRIPTION
            "-- empty --"
    ::= { lcsStatusConfigSyncRunningClusterIgnoredRowsEntry 5 }

-- {NODE} 1.3.6.1.4.1.2356.11.1.11.51.6
lcsStatusConfigSyncConfigHistory OBJECT IDENTIFIER ::= { lcsStatusConfigSync 6 }

-- {SCALAR} 1.3.6.1.4.1.2356.11.1.11.51.6.1
lcsStatusConfigSyncConfigHistorySnapshotReceivedAt OBJECT-TYPE
    SYNTAX     Counter32
    MAX-ACCESS read-only
    STATUS     current
    DESCRIPTION
            "-- empty --"
    ::= { lcsStatusConfigSyncConfigHistory 1 }

-- {SCALAR} 1.3.6.1.4.1.2356.11.1.11.51.6.2
lcsStatusConfigSyncConfigHistorySnapshotTimestamp OBJECT-TYPE
    SYNTAX     DisplayString (SIZE(0..8))
    MAX-ACCESS read-only
    STATUS     current
    DESCRIPTION
            "-- empty --"
    ::= { lcsStatusConfigSyncConfigHistory 2 }

-- {TABLE} 1.3.6.1.4.1.2356.11.1.11.51.6.3
lcsStatusConfigSyncConfigHistorySnapshotTable OBJECT-TYPE
    SYNTAX     SEQUENCE OF LcsStatusConfigSyncConfigHistorySnapshotEntry
    MAX-ACCESS not-accessible
    STATUS     current
    DESCRIPTION
            "-- empty --"
    ::= { lcsStatusConfigSyncConfigHistory 3 }

-- {ROW} 1.3.6.1.4.1.2356.11.1.11.51.6.3.1
lcsStatusConfigSyncConfigHistorySnapshotEntry OBJECT-TYPE
    SYNTAX     LcsStatusConfigSyncConfigHistorySnapshotEntry
    MAX-ACCESS not-accessible
    STATUS     current
    DESCRIPTION
            ""
    INDEX {
            lcsStatusConfigSyncConfigHistorySnapshotEntryIdx
          }
    ::= { lcsStatusConfigSyncConfigHistorySnapshotTable 1 }

LcsStatusConfigSyncConfigHistorySnapshotEntry ::= SEQUENCE {
            lcsStatusConfigSyncConfigHistorySnapshotEntryIdx Integer32,
            lcsStatusConfigSyncConfigHistorySnapshotEntryPath DisplayString,
            lcsStatusConfigSyncConfigHistorySnapshotEntryValue DisplayString
    }

-- {COLUMN} 1.3.6.1.4.1.2356.11.1.11.51.6.3.1.1
lcsStatusConfigSyncConfigHistorySnapshotEntryIdx OBJECT-TYPE
    SYNTAX     Integer32 (0..2147483647)
    MAX-ACCESS read-only
    STATUS     current
    DESCRIPTION
            "-- empty --"
    ::= { lcsStatusConfigSyncConfigHistorySnapshotEntry 1 }

-- {COLUMN} 1.3.6.1.4.1.2356.11.1.11.51.6.3.1.2
lcsStatusConfigSyncConfigHistorySnapshotEntryPath OBJECT-TYPE
    SYNTAX     DisplayString (SIZE(0..127))
    MAX-ACCESS read-only
    STATUS     current
    DESCRIPTION
            "-- empty --"
    ::= { lcsStatusConfigSyncConfigHistorySnapshotEntry 2 }

-- {COLUMN} 1.3.6.1.4.1.2356.11.1.11.51.6.3.1.3
lcsStatusConfigSyncConfigHistorySnapshotEntryValue OBJECT-TYPE
    SYNTAX     DisplayString (SIZE(0..254))
    MAX-ACCESS read-only
    STATUS     current
    DESCRIPTION
            "-- empty --"
    ::= { lcsStatusConfigSyncConfigHistorySnapshotEntry 3 }

-- {TABLE} 1.3.6.1.4.1.2356.11.1.11.51.6.4
lcsStatusConfigSyncConfigHistoryModificationsTable OBJECT-TYPE
    SYNTAX     SEQUENCE OF LcsStatusConfigSyncConfigHistoryModificationsEntry
    MAX-ACCESS not-accessible
    STATUS     current
    DESCRIPTION
            "-- empty --"
    ::= { lcsStatusConfigSyncConfigHistory 4 }

-- {ROW} 1.3.6.1.4.1.2356.11.1.11.51.6.4.1
lcsStatusConfigSyncConfigHistoryModificationsEntry OBJECT-TYPE
    SYNTAX     LcsStatusConfigSyncConfigHistoryModificationsEntry
    MAX-ACCESS not-accessible
    STATUS     current
    DESCRIPTION
            ""
    INDEX {
            lcsStatusConfigSyncConfigHistoryModificationsEntryTimestamp,
            lcsStatusConfigSyncConfigHistoryModificationsEntryNo
          }
    ::= { lcsStatusConfigSyncConfigHistoryModificationsTable 1 }

LcsStatusConfigSyncConfigHistoryModificationsEntry ::= SEQUENCE {
            lcsStatusConfigSyncConfigHistoryModificationsEntryTimestamp OCTET STRING,
            lcsStatusConfigSyncConfigHistoryModificationsEntryNo Unsigned32,
            lcsStatusConfigSyncConfigHistoryModificationsEntryReceivedAt Gauge32,
            lcsStatusConfigSyncConfigHistoryModificationsEntryOriginator Unsigned32,
            lcsStatusConfigSyncConfigHistoryModificationsEntryPath OCTET STRING,
            lcsStatusConfigSyncConfigHistoryModificationsEntryType INTEGER,
            lcsStatusConfigSyncConfigHistoryModificationsEntryValue OCTET STRING
    }

-- {COLUMN} 1.3.6.1.4.1.2356.11.1.11.51.6.4.1.1
lcsStatusConfigSyncConfigHistoryModificationsEntryTimestamp OBJECT-TYPE
    SYNTAX     OCTET STRING (SIZE(0..17))
    MAX-ACCESS read-only
    STATUS     current
    DESCRIPTION
            "-- empty --"
    ::= { lcsStatusConfigSyncConfigHistoryModificationsEntry 1 }

-- {COLUMN} 1.3.6.1.4.1.2356.11.1.11.51.6.4.1.2
lcsStatusConfigSyncConfigHistoryModificationsEntryNo OBJECT-TYPE
    SYNTAX     Unsigned32 (0..4294967295)
    MAX-ACCESS read-only
    STATUS     current
    DESCRIPTION
            "-- empty --"
    ::= { lcsStatusConfigSyncConfigHistoryModificationsEntry 2 }

-- {COLUMN} 1.3.6.1.4.1.2356.11.1.11.51.6.4.1.3
lcsStatusConfigSyncConfigHistoryModificationsEntryReceivedAt OBJECT-TYPE
    SYNTAX     Gauge32
    MAX-ACCESS read-only
    STATUS     current
    DESCRIPTION
            "-- empty --"
    ::= { lcsStatusConfigSyncConfigHistoryModificationsEntry 3 }

-- {COLUMN} 1.3.6.1.4.1.2356.11.1.11.51.6.4.1.4
lcsStatusConfigSyncConfigHistoryModificationsEntryOriginator OBJECT-TYPE
    SYNTAX     Unsigned32 (0..65535)
    MAX-ACCESS read-only
    STATUS     current
    DESCRIPTION
            "-- empty --"
    ::= { lcsStatusConfigSyncConfigHistoryModificationsEntry 4 }

-- {COLUMN} 1.3.6.1.4.1.2356.11.1.11.51.6.4.1.5
lcsStatusConfigSyncConfigHistoryModificationsEntryPath OBJECT-TYPE
    SYNTAX     OCTET STRING (SIZE(0..128))
    MAX-ACCESS read-only
    STATUS     current
    DESCRIPTION
            "-- empty --"
    ::= { lcsStatusConfigSyncConfigHistoryModificationsEntry 5 }

-- {COLUMN} 1.3.6.1.4.1.2356.11.1.11.51.6.4.1.6
lcsStatusConfigSyncConfigHistoryModificationsEntryType OBJECT-TYPE
    SYNTAX     INTEGER {
                  eSetScalar (1),
                  eSetRow (2),
                  eDeleteRow (3)
            }
    MAX-ACCESS read-only
    STATUS     current
    DESCRIPTION
            "-- empty --"
    ::= { lcsStatusConfigSyncConfigHistoryModificationsEntry 6 }

-- {COLUMN} 1.3.6.1.4.1.2356.11.1.11.51.6.4.1.7
lcsStatusConfigSyncConfigHistoryModificationsEntryValue OBJECT-TYPE
    SYNTAX     OCTET STRING (SIZE(0..255))
    MAX-ACCESS read-only
    STATUS     current
    DESCRIPTION
            "-- empty --"
    ::= { lcsStatusConfigSyncConfigHistoryModificationsEntry 7 }

-- {SCALAR} 1.3.6.1.4.1.2356.11.1.11.51.6.5
lcsStatusConfigSyncConfigHistoryRenewSnapshot OBJECT-TYPE
    SYNTAX     DisplayString
    MAX-ACCESS read-write
    STATUS     current
    DESCRIPTION
            "-- empty --"
    ::= { lcsStatusConfigSyncConfigHistory 5 }

-- {TABLE} 1.3.6.1.4.1.2356.11.1.11.51.7
lcsStatusConfigSyncReplicasTable OBJECT-TYPE
    SYNTAX     SEQUENCE OF LcsStatusConfigSyncReplicasEntry
    MAX-ACCESS not-accessible
    STATUS     current
    DESCRIPTION
            "-- empty --"
    ::= { lcsStatusConfigSync 7 }

-- {ROW} 1.3.6.1.4.1.2356.11.1.11.51.7.1
lcsStatusConfigSyncReplicasEntry OBJECT-TYPE
    SYNTAX     LcsStatusConfigSyncReplicasEntry
    MAX-ACCESS not-accessible
    STATUS     current
    DESCRIPTION
            ""
    INDEX {
            lcsStatusConfigSyncReplicasEntryIdx
          }
    ::= { lcsStatusConfigSyncReplicasTable 1 }

LcsStatusConfigSyncReplicasEntry ::= SEQUENCE {
            lcsStatusConfigSyncReplicasEntryIdx Integer32,
            lcsStatusConfigSyncReplicasEntryId Integer32,
            lcsStatusConfigSyncReplicasEntryAddress DisplayString,
            lcsStatusConfigSyncReplicasEntryResolvedAddress DisplayString,
            lcsStatusConfigSyncReplicasEntryConnectionState INTEGER,
            lcsStatusConfigSyncReplicasEntryState INTEGER,
            lcsStatusConfigSyncReplicasEntryClusterTime Integer32,
            lcsStatusConfigSyncReplicasEntryLastMessageReceivedAt DisplayString,
            lcsStatusConfigSyncReplicasEntryLastMessageReceivedAtNumerical Counter32,
            lcsStatusConfigSyncReplicasEntryLastUpdateReceivedAt DisplayString,
            lcsStatusConfigSyncReplicasEntryLastUpdateReceivedAtNumerical Counter32,
            lcsStatusConfigSyncReplicasEntryLastMessageSentAt DisplayString,
            lcsStatusConfigSyncReplicasEntryLastMessageSentAtNumerical Counter32
    }

-- {COLUMN} 1.3.6.1.4.1.2356.11.1.11.51.7.1.1
lcsStatusConfigSyncReplicasEntryIdx OBJECT-TYPE
    SYNTAX     Integer32 (0..65535)
    MAX-ACCESS read-only
    STATUS     current
    DESCRIPTION
            "-- empty --"
    ::= { lcsStatusConfigSyncReplicasEntry 1 }

-- {COLUMN} 1.3.6.1.4.1.2356.11.1.11.51.7.1.2
lcsStatusConfigSyncReplicasEntryId OBJECT-TYPE
    SYNTAX     Integer32 (0..65535)
    MAX-ACCESS read-only
    STATUS     current
    DESCRIPTION
            "-- empty --"
    ::= { lcsStatusConfigSyncReplicasEntry 2 }

-- {COLUMN} 1.3.6.1.4.1.2356.11.1.11.51.7.1.3
lcsStatusConfigSyncReplicasEntryAddress OBJECT-TYPE
    SYNTAX     DisplayString (SIZE(0..255))
    MAX-ACCESS read-only
    STATUS     current
    DESCRIPTION
            "-- empty --"
    ::= { lcsStatusConfigSyncReplicasEntry 3 }

-- {COLUMN} 1.3.6.1.4.1.2356.11.1.11.51.7.1.4
lcsStatusConfigSyncReplicasEntryResolvedAddress OBJECT-TYPE
    SYNTAX     DisplayString (SIZE(0..255))
    MAX-ACCESS read-only
    STATUS     current
    DESCRIPTION
            "-- empty --"
    ::= { lcsStatusConfigSyncReplicasEntry 4 }

-- {COLUMN} 1.3.6.1.4.1.2356.11.1.11.51.7.1.5
lcsStatusConfigSyncReplicasEntryConnectionState OBJECT-TYPE
    SYNTAX     INTEGER {
                  eNotConnected (0),
                  eDnsLookup (1),
                  eConnecting (2),
                  eOk (3),
                  eDnsLookupFailure (4),
                  eTcpConnectFailure (5),
                  eTlsConnectFailure (6),
                  eClosedByReplica (7),
                  eIncompatibleFirmware (8),
                  eTransferError (9)
            }
    MAX-ACCESS read-only
    STATUS     current
    DESCRIPTION
            "-- empty --"
    ::= { lcsStatusConfigSyncReplicasEntry 5 }

-- {COLUMN} 1.3.6.1.4.1.2356.11.1.11.51.7.1.6
lcsStatusConfigSyncReplicasEntryState OBJECT-TYPE
    SYNTAX     INTEGER {
                  eUnknown (0),
                  eMissingMessages (1),
                  eMissingUpdates (2),
                  eOldCluster (3),
                  eNewCluster (4),
                  eNoSnapshot (5),
                  eTimeUnknown (6),
                  eOk (7)
            }
    MAX-ACCESS read-only
    STATUS     current
    DESCRIPTION
            "-- empty --"
    ::= { lcsStatusConfigSyncReplicasEntry 6 }

-- {COLUMN} 1.3.6.1.4.1.2356.11.1.11.51.7.1.7
lcsStatusConfigSyncReplicasEntryClusterTime OBJECT-TYPE
    SYNTAX     Integer32 (0..2147483647)
    MAX-ACCESS read-only
    STATUS     current
    DESCRIPTION
            "-- empty --"
    ::= { lcsStatusConfigSyncReplicasEntry 7 }

-- {COLUMN} 1.3.6.1.4.1.2356.11.1.11.51.7.1.8
lcsStatusConfigSyncReplicasEntryLastMessageReceivedAt OBJECT-TYPE
    SYNTAX     DisplayString (SIZE(0..255))
    MAX-ACCESS read-only
    STATUS     current
    DESCRIPTION
            "-- empty --"
    ::= { lcsStatusConfigSyncReplicasEntry 8 }

-- {COLUMN} 1.3.6.1.4.1.2356.11.1.11.51.7.1.9
lcsStatusConfigSyncReplicasEntryLastMessageReceivedAtNumerical OBJECT-TYPE
    SYNTAX     Counter32
    MAX-ACCESS read-only
    STATUS     current
    DESCRIPTION
            "-- empty --"
    ::= { lcsStatusConfigSyncReplicasEntry 9 }

-- {COLUMN} 1.3.6.1.4.1.2356.11.1.11.51.7.1.10
lcsStatusConfigSyncReplicasEntryLastUpdateReceivedAt OBJECT-TYPE
    SYNTAX     DisplayString (SIZE(0..255))
    MAX-ACCESS read-only
    STATUS     current
    DESCRIPTION
            "-- empty --"
    ::= { lcsStatusConfigSyncReplicasEntry 10 }

-- {COLUMN} 1.3.6.1.4.1.2356.11.1.11.51.7.1.11
lcsStatusConfigSyncReplicasEntryLastUpdateReceivedAtNumerical OBJECT-TYPE
    SYNTAX     Counter32
    MAX-ACCESS read-only
    STATUS     current
    DESCRIPTION
            "-- empty --"
    ::= { lcsStatusConfigSyncReplicasEntry 11 }

-- {COLUMN} 1.3.6.1.4.1.2356.11.1.11.51.7.1.12
lcsStatusConfigSyncReplicasEntryLastMessageSentAt OBJECT-TYPE
    SYNTAX     DisplayString (SIZE(0..255))
    MAX-ACCESS read-only
    STATUS     current
    DESCRIPTION
            "-- empty --"
    ::= { lcsStatusConfigSyncReplicasEntry 12 }

-- {COLUMN} 1.3.6.1.4.1.2356.11.1.11.51.7.1.13
lcsStatusConfigSyncReplicasEntryLastMessageSentAtNumerical OBJECT-TYPE
    SYNTAX     Counter32
    MAX-ACCESS read-only
    STATUS     current
    DESCRIPTION
            "-- empty --"
    ::= { lcsStatusConfigSyncReplicasEntry 13 }

-- {NODE} 1.3.6.1.4.1.2356.11.1.11.65
lcsStatusConfigLl2m OBJECT IDENTIFIER ::= { lcsStatusConfig 65 }

-- {SCALAR} 1.3.6.1.4.1.2356.11.1.11.65.1
lcsStatusConfigLl2mRxPackets OBJECT-TYPE
    SYNTAX     Integer32 (0..2147483647)
    MAX-ACCESS read-only
    STATUS     current
    DESCRIPTION
            ""
    ::= { lcsStatusConfigLl2m 1 }

-- {SCALAR} 1.3.6.1.4.1.2356.11.1.11.65.2
lcsStatusConfigLl2mRxBroadcastPackets OBJECT-TYPE
    SYNTAX     Integer32 (0..2147483647)
    MAX-ACCESS read-only
    STATUS     current
    DESCRIPTION
            ""
    ::= { lcsStatusConfigLl2m 2 }

-- {SCALAR} 1.3.6.1.4.1.2356.11.1.11.65.3
lcsStatusConfigLl2mRxMulticastPackets OBJECT-TYPE
    SYNTAX     Integer32 (0..2147483647)
    MAX-ACCESS read-only
    STATUS     current
    DESCRIPTION
            ""
    ::= { lcsStatusConfigLl2m 3 }

-- {SCALAR} 1.3.6.1.4.1.2356.11.1.11.65.4
lcsStatusConfigLl2mRxUnicastPackets OBJECT-TYPE
    SYNTAX     Integer32 (0..2147483647)
    MAX-ACCESS read-only
    STATUS     current
    DESCRIPTION
            ""
    ::= { lcsStatusConfigLl2m 4 }

-- {SCALAR} 1.3.6.1.4.1.2356.11.1.11.65.5
lcsStatusConfigLl2mRxDiscard OBJECT-TYPE
    SYNTAX     Integer32 (0..2147483647)
    MAX-ACCESS read-only
    STATUS     current
    DESCRIPTION
            ""
    ::= { lcsStatusConfigLl2m 5 }

-- {SCALAR} 1.3.6.1.4.1.2356.11.1.11.65.6
lcsStatusConfigLl2mRxMalformed OBJECT-TYPE
    SYNTAX     Integer32 (0..2147483647)
    MAX-ACCESS read-only
    STATUS     current
    DESCRIPTION
            ""
    ::= { lcsStatusConfigLl2m 6 }

-- {NODE} 1.3.6.1.4.1.2356.11.1.11.65.20
lcsStatusConfigLl2mServer OBJECT IDENTIFIER ::= { lcsStatusConfigLl2m 20 }

-- {SCALAR} 1.3.6.1.4.1.2356.11.1.11.65.20.1
lcsStatusConfigLl2mServerRxPackets OBJECT-TYPE
    SYNTAX     Integer32 (0..2147483647)
    MAX-ACCESS read-only
    STATUS     current
    DESCRIPTION
            ""
    ::= { lcsStatusConfigLl2mServer 1 }

-- {SCALAR} 1.3.6.1.4.1.2356.11.1.11.65.20.2
lcsStatusConfigLl2mServerRxBroadcastPackets OBJECT-TYPE
    SYNTAX     Integer32 (0..2147483647)
    MAX-ACCESS read-only
    STATUS     current
    DESCRIPTION
            ""
    ::= { lcsStatusConfigLl2mServer 2 }

-- {SCALAR} 1.3.6.1.4.1.2356.11.1.11.65.20.3
lcsStatusConfigLl2mServerRxMulticastPackets OBJECT-TYPE
    SYNTAX     Integer32 (0..2147483647)
    MAX-ACCESS read-only
    STATUS     current
    DESCRIPTION
            ""
    ::= { lcsStatusConfigLl2mServer 3 }

-- {SCALAR} 1.3.6.1.4.1.2356.11.1.11.65.20.4
lcsStatusConfigLl2mServerRxUnicastPackets OBJECT-TYPE
    SYNTAX     Integer32 (0..2147483647)
    MAX-ACCESS read-only
    STATUS     current
    DESCRIPTION
            ""
    ::= { lcsStatusConfigLl2mServer 4 }

-- {SCALAR} 1.3.6.1.4.1.2356.11.1.11.65.20.5
lcsStatusConfigLl2mServerRxDiscard OBJECT-TYPE
    SYNTAX     Integer32 (0..2147483647)
    MAX-ACCESS read-only
    STATUS     current
    DESCRIPTION
            ""
    ::= { lcsStatusConfigLl2mServer 5 }

-- {SCALAR} 1.3.6.1.4.1.2356.11.1.11.65.20.99
lcsStatusConfigLl2mServerDeleteValues OBJECT-TYPE
    SYNTAX     DisplayString
    MAX-ACCESS read-write
    STATUS     current
    DESCRIPTION
            ""
    ::= { lcsStatusConfigLl2mServer 99 }

-- {NODE} 1.3.6.1.4.1.2356.11.1.11.65.30
lcsStatusConfigLl2mClient OBJECT IDENTIFIER ::= { lcsStatusConfigLl2m 30 }

-- {SCALAR} 1.3.6.1.4.1.2356.11.1.11.65.30.1
lcsStatusConfigLl2mClientRxPackets OBJECT-TYPE
    SYNTAX     Integer32 (0..2147483647)
    MAX-ACCESS read-only
    STATUS     current
    DESCRIPTION
            ""
    ::= { lcsStatusConfigLl2mClient 1 }

-- {SCALAR} 1.3.6.1.4.1.2356.11.1.11.65.30.2
lcsStatusConfigLl2mClientRxBroadcastPackets OBJECT-TYPE
    SYNTAX     Integer32 (0..2147483647)
    MAX-ACCESS read-only
    STATUS     current
    DESCRIPTION
            ""
    ::= { lcsStatusConfigLl2mClient 2 }

-- {SCALAR} 1.3.6.1.4.1.2356.11.1.11.65.30.3
lcsStatusConfigLl2mClientRxMulticastPackets OBJECT-TYPE
    SYNTAX     Integer32 (0..2147483647)
    MAX-ACCESS read-only
    STATUS     current
    DESCRIPTION
            ""
    ::= { lcsStatusConfigLl2mClient 3 }

-- {SCALAR} 1.3.6.1.4.1.2356.11.1.11.65.30.4
lcsStatusConfigLl2mClientRxUnicastPackets OBJECT-TYPE
    SYNTAX     Integer32 (0..2147483647)
    MAX-ACCESS read-only
    STATUS     current
    DESCRIPTION
            ""
    ::= { lcsStatusConfigLl2mClient 4 }

-- {SCALAR} 1.3.6.1.4.1.2356.11.1.11.65.30.5
lcsStatusConfigLl2mClientRxDiscard OBJECT-TYPE
    SYNTAX     Integer32 (0..2147483647)
    MAX-ACCESS read-only
    STATUS     current
    DESCRIPTION
            ""
    ::= { lcsStatusConfigLl2mClient 5 }

-- {SCALAR} 1.3.6.1.4.1.2356.11.1.11.65.30.99
lcsStatusConfigLl2mClientDeleteValues OBJECT-TYPE
    SYNTAX     DisplayString
    MAX-ACCESS read-write
    STATUS     current
    DESCRIPTION
            ""
    ::= { lcsStatusConfigLl2mClient 99 }

-- {SCALAR} 1.3.6.1.4.1.2356.11.1.11.65.99
lcsStatusConfigLl2mDeleteValues OBJECT-TYPE
    SYNTAX     DisplayString
    MAX-ACCESS read-write
    STATUS     current
    DESCRIPTION
            ""
    ::= { lcsStatusConfigLl2m 99 }

-- {NODE} 1.3.6.1.4.1.2356.11.1.11.70
lcsStatusConfigDownloadStatus OBJECT IDENTIFIER ::= { lcsStatusConfig 70 }

-- {SCALAR} 1.3.6.1.4.1.2356.11.1.11.70.1
lcsStatusConfigDownloadStatusFirmwareSuccesses OBJECT-TYPE
    SYNTAX     Integer32 (0..2147483647)
    MAX-ACCESS read-only
    STATUS     current
    DESCRIPTION
            ""
    ::= { lcsStatusConfigDownloadStatus 1 }

-- {SCALAR} 1.3.6.1.4.1.2356.11.1.11.70.2
lcsStatusConfigDownloadStatusFirmwareFailures OBJECT-TYPE
    SYNTAX     Integer32 (0..2147483647)
    MAX-ACCESS read-only
    STATUS     current
    DESCRIPTION
            ""
    ::= { lcsStatusConfigDownloadStatus 2 }

-- {SCALAR} 1.3.6.1.4.1.2356.11.1.11.70.3
lcsStatusConfigDownloadStatusConfigurationSuccesses OBJECT-TYPE
    SYNTAX     Integer32 (0..2147483647)
    MAX-ACCESS read-only
    STATUS     current
    DESCRIPTION
            ""
    ::= { lcsStatusConfigDownloadStatus 3 }

-- {SCALAR} 1.3.6.1.4.1.2356.11.1.11.70.4
lcsStatusConfigDownloadStatusConfigurationFailures OBJECT-TYPE
    SYNTAX     Integer32 (0..2147483647)
    MAX-ACCESS read-only
    STATUS     current
    DESCRIPTION
            ""
    ::= { lcsStatusConfigDownloadStatus 4 }

-- {SCALAR} 1.3.6.1.4.1.2356.11.1.11.70.5
lcsStatusConfigDownloadStatusScriptSuccesses OBJECT-TYPE
    SYNTAX     Integer32 (0..2147483647)
    MAX-ACCESS read-only
    STATUS     current
    DESCRIPTION
            ""
    ::= { lcsStatusConfigDownloadStatus 5 }

-- {SCALAR} 1.3.6.1.4.1.2356.11.1.11.70.6
lcsStatusConfigDownloadStatusScriptFailures OBJECT-TYPE
    SYNTAX     Integer32 (0..2147483647)
    MAX-ACCESS read-only
    STATUS     current
    DESCRIPTION
            ""
    ::= { lcsStatusConfigDownloadStatus 6 }

-- {SCALAR} 1.3.6.1.4.1.2356.11.1.11.70.7
lcsStatusConfigDownloadStatusFileSuccesses OBJECT-TYPE
    SYNTAX     Integer32 (0..2147483647)
    MAX-ACCESS read-only
    STATUS     current
    DESCRIPTION
            ""
    ::= { lcsStatusConfigDownloadStatus 7 }

-- {SCALAR} 1.3.6.1.4.1.2356.11.1.11.70.8
lcsStatusConfigDownloadStatusFileFailures OBJECT-TYPE
    SYNTAX     Integer32 (0..2147483647)
    MAX-ACCESS read-only
    STATUS     current
    DESCRIPTION
            ""
    ::= { lcsStatusConfigDownloadStatus 8 }

-- {TABLE} 1.3.6.1.4.1.2356.11.1.11.70.20
lcsStatusConfigDownloadStatusLastOperationsTable OBJECT-TYPE
    SYNTAX     SEQUENCE OF LcsStatusConfigDownloadStatusLastOperationsEntry
    MAX-ACCESS not-accessible
    STATUS     current
    DESCRIPTION
            ""
    ::= { lcsStatusConfigDownloadStatus 20 }

-- {ROW} 1.3.6.1.4.1.2356.11.1.11.70.20.1
lcsStatusConfigDownloadStatusLastOperationsEntry OBJECT-TYPE
    SYNTAX     LcsStatusConfigDownloadStatusLastOperationsEntry
    MAX-ACCESS not-accessible
    STATUS     current
    DESCRIPTION
            ""
    INDEX {
            lcsStatusConfigDownloadStatusLastOperationsEntryIndex
          }
    ::= { lcsStatusConfigDownloadStatusLastOperationsTable 1 }

LcsStatusConfigDownloadStatusLastOperationsEntry ::= SEQUENCE {
            lcsStatusConfigDownloadStatusLastOperationsEntryIndex Integer32,
            lcsStatusConfigDownloadStatusLastOperationsEntryIdentifier Integer32,
            lcsStatusConfigDownloadStatusLastOperationsEntryType INTEGER,
            lcsStatusConfigDownloadStatusLastOperationsEntryUrl DisplayString,
            lcsStatusConfigDownloadStatusLastOperationsEntryStatus INTEGER,
            lcsStatusConfigDownloadStatusLastOperationsEntryFailureReason DisplayString
    }

-- {COLUMN} 1.3.6.1.4.1.2356.11.1.11.70.20.1.1
lcsStatusConfigDownloadStatusLastOperationsEntryIndex OBJECT-TYPE
    SYNTAX     Integer32 (0..2147483647)
    MAX-ACCESS read-only
    STATUS     current
    DESCRIPTION
            ""
    ::= { lcsStatusConfigDownloadStatusLastOperationsEntry 1 }

-- {COLUMN} 1.3.6.1.4.1.2356.11.1.11.70.20.1.2
lcsStatusConfigDownloadStatusLastOperationsEntryIdentifier OBJECT-TYPE
    SYNTAX     Integer32 (0..2147483647)
    MAX-ACCESS read-only
    STATUS     current
    DESCRIPTION
            ""
    ::= { lcsStatusConfigDownloadStatusLastOperationsEntry 2 }

-- {COLUMN} 1.3.6.1.4.1.2356.11.1.11.70.20.1.3
lcsStatusConfigDownloadStatusLastOperationsEntryType OBJECT-TYPE
    SYNTAX     INTEGER {
                  eConfiguration (0),
                  eFirmware (1),
                  eScript (2),
                  eFile (3)
            }
    MAX-ACCESS read-only
    STATUS     current
    DESCRIPTION
            ""
    ::= { lcsStatusConfigDownloadStatusLastOperationsEntry 3 }

-- {COLUMN} 1.3.6.1.4.1.2356.11.1.11.70.20.1.4
lcsStatusConfigDownloadStatusLastOperationsEntryUrl OBJECT-TYPE
    SYNTAX     DisplayString (SIZE(0..252))
    MAX-ACCESS read-only
    STATUS     current
    DESCRIPTION
            ""
    ::= { lcsStatusConfigDownloadStatusLastOperationsEntry 4 }

-- {COLUMN} 1.3.6.1.4.1.2356.11.1.11.70.20.1.5
lcsStatusConfigDownloadStatusLastOperationsEntryStatus OBJECT-TYPE
    SYNTAX     INTEGER {
                  eIdle (0),
                  ePending (1),
                  eSuccess (2),
                  eFailure (3),
                  eUnknown (4)
            }
    MAX-ACCESS read-only
    STATUS     current
    DESCRIPTION
            ""
    ::= { lcsStatusConfigDownloadStatusLastOperationsEntry 5 }

-- {COLUMN} 1.3.6.1.4.1.2356.11.1.11.70.20.1.6
lcsStatusConfigDownloadStatusLastOperationsEntryFailureReason OBJECT-TYPE
    SYNTAX     DisplayString (SIZE(0..100))
    MAX-ACCESS read-only
    STATUS     current
    DESCRIPTION
            ""
    ::= { lcsStatusConfigDownloadStatusLastOperationsEntry 6 }

-- {SCALAR} 1.3.6.1.4.1.2356.11.1.11.70.99
lcsStatusConfigDownloadStatusDeleteValues OBJECT-TYPE
    SYNTAX     DisplayString
    MAX-ACCESS read-write
    STATUS     current
    DESCRIPTION
            ""
    ::= { lcsStatusConfigDownloadStatus 99 }

-- {TABLE} 1.3.6.1.4.1.2356.11.1.11.71
lcsStatusConfigServicesTable OBJECT-TYPE
    SYNTAX     SEQUENCE OF LcsStatusConfigServicesEntry
    MAX-ACCESS not-accessible
    STATUS     current
    DESCRIPTION
            "-- empty --"
    ::= { lcsStatusConfig 71 }

-- {ROW} 1.3.6.1.4.1.2356.11.1.11.71.1
lcsStatusConfigServicesEntry OBJECT-TYPE
    SYNTAX     LcsStatusConfigServicesEntry
    MAX-ACCESS not-accessible
    STATUS     current
    DESCRIPTION
            ""
    INDEX {
            lcsStatusConfigServicesEntryService
          }
    ::= { lcsStatusConfigServicesTable 1 }

LcsStatusConfigServicesEntry ::= SEQUENCE {
            lcsStatusConfigServicesEntryService DisplayString,
            lcsStatusConfigServicesEntryPort Unsigned32,
            lcsStatusConfigServicesEntryProtocol DisplayString,
            lcsStatusConfigServicesEntryActive INTEGER,
            lcsStatusConfigServicesEntryLan INTEGER,
            lcsStatusConfigServicesEntryWan INTEGER,
            lcsStatusConfigServicesEntryVpn INTEGER,
            lcsStatusConfigServicesEntryWlan INTEGER
    }

-- {COLUMN} 1.3.6.1.4.1.2356.11.1.11.71.1.1
lcsStatusConfigServicesEntryService OBJECT-TYPE
    SYNTAX     DisplayString (SIZE(0..33))
    MAX-ACCESS read-only
    STATUS     current
    DESCRIPTION
            "-- empty --"
    ::= { lcsStatusConfigServicesEntry 1 }

-- {COLUMN} 1.3.6.1.4.1.2356.11.1.11.71.1.2
lcsStatusConfigServicesEntryPort OBJECT-TYPE
    SYNTAX     Unsigned32 (0..65535)
    MAX-ACCESS read-only
    STATUS     current
    DESCRIPTION
            "-- empty --"
    ::= { lcsStatusConfigServicesEntry 2 }

-- {COLUMN} 1.3.6.1.4.1.2356.11.1.11.71.1.3
lcsStatusConfigServicesEntryProtocol OBJECT-TYPE
    SYNTAX     DisplayString (SIZE(0..16))
    MAX-ACCESS read-only
    STATUS     current
    DESCRIPTION
            "-- empty --"
    ::= { lcsStatusConfigServicesEntry 3 }

-- {COLUMN} 1.3.6.1.4.1.2356.11.1.11.71.1.4
lcsStatusConfigServicesEntryActive OBJECT-TYPE
    SYNTAX     INTEGER {
                  eNo (0),
                  eYes (1)
            }
    MAX-ACCESS read-only
    STATUS     current
    DESCRIPTION
            "-- empty --"
    ::= { lcsStatusConfigServicesEntry 4 }

-- {COLUMN} 1.3.6.1.4.1.2356.11.1.11.71.1.5
lcsStatusConfigServicesEntryLan OBJECT-TYPE
    SYNTAX     INTEGER {
                  eNo (0),
                  eYes (1)
            }
    MAX-ACCESS read-only
    STATUS     current
    DESCRIPTION
            "-- empty --"
    ::= { lcsStatusConfigServicesEntry 5 }

-- {COLUMN} 1.3.6.1.4.1.2356.11.1.11.71.1.6
lcsStatusConfigServicesEntryWan OBJECT-TYPE
    SYNTAX     INTEGER {
                  eNo (0),
                  eYes (1)
            }
    MAX-ACCESS read-only
    STATUS     current
    DESCRIPTION
            "-- empty --"
    ::= { lcsStatusConfigServicesEntry 6 }

-- {COLUMN} 1.3.6.1.4.1.2356.11.1.11.71.1.7
lcsStatusConfigServicesEntryVpn OBJECT-TYPE
    SYNTAX     INTEGER {
                  eNo (0),
                  eYes (1)
            }
    MAX-ACCESS read-only
    STATUS     current
    DESCRIPTION
            "-- empty --"
    ::= { lcsStatusConfigServicesEntry 7 }

-- {COLUMN} 1.3.6.1.4.1.2356.11.1.11.71.1.8
lcsStatusConfigServicesEntryWlan OBJECT-TYPE
    SYNTAX     INTEGER {
                  eNo (0),
                  eYes (1)
            }
    MAX-ACCESS read-only
    STATUS     current
    DESCRIPTION
            "-- empty --"
    ::= { lcsStatusConfigServicesEntry 8 }

-- {NODE} 1.3.6.1.4.1.2356.11.1.12
lcsStatusQueue OBJECT IDENTIFIER ::= { lcsStatus 12 }

-- {SCALAR} 1.3.6.1.4.1.2356.11.1.12.1
lcsStatusQueueLanHeapPackets OBJECT-TYPE
    SYNTAX     Integer32 (0..2147483647)
    MAX-ACCESS read-only
    STATUS     current
    DESCRIPTION
            ""
    ::= { lcsStatusQueue 1 }

-- {SCALAR} 1.3.6.1.4.1.2356.11.1.12.2
lcsStatusQueueQueuePackets OBJECT-TYPE
    SYNTAX     Integer32 (0..2147483647)
    MAX-ACCESS read-only
    STATUS     current
    DESCRIPTION
            ""
    ::= { lcsStatusQueue 2 }

-- {SCALAR} 1.3.6.1.4.1.2356.11.1.12.3
lcsStatusQueueWanHeapPackets OBJECT-TYPE
    SYNTAX     Integer32 (0..2147483647)
    MAX-ACCESS read-only
    STATUS     current
    DESCRIPTION
            ""
    ::= { lcsStatusQueue 3 }

-- {SCALAR} 1.3.6.1.4.1.2356.11.1.12.4
lcsStatusQueueWanQueuePackets OBJECT-TYPE
    SYNTAX     Integer32 (0..2147483647)
    MAX-ACCESS read-only
    STATUS     current
    DESCRIPTION
            ""
    ::= { lcsStatusQueue 4 }

-- {SCALAR} 1.3.6.1.4.1.2356.11.1.12.7
lcsStatusQueueArpQueryQueuePackets OBJECT-TYPE
    SYNTAX     Integer32 (0..2147483647)
    MAX-ACCESS read-only
    STATUS     current
    DESCRIPTION
            ""
    ::= { lcsStatusQueue 7 }

-- {SCALAR} 1.3.6.1.4.1.2356.11.1.12.8
lcsStatusQueueArpQueuePackets OBJECT-TYPE
    SYNTAX     Integer32 (0..2147483647)
    MAX-ACCESS read-only
    STATUS     current
    DESCRIPTION
            ""
    ::= { lcsStatusQueue 8 }

-- {SCALAR} 1.3.6.1.4.1.2356.11.1.12.9
lcsStatusQueueIpQueuePackets OBJECT-TYPE
    SYNTAX     Integer32 (0..2147483647)
    MAX-ACCESS read-only
    STATUS     current
    DESCRIPTION
            ""
    ::= { lcsStatusQueue 9 }

-- {SCALAR} 1.3.6.1.4.1.2356.11.1.12.10
lcsStatusQueueIpUrgentQueuePackets OBJECT-TYPE
    SYNTAX     Integer32 (0..2147483647)
    MAX-ACCESS read-only
    STATUS     current
    DESCRIPTION
            ""
    ::= { lcsStatusQueue 10 }

-- {SCALAR} 1.3.6.1.4.1.2356.11.1.12.11
lcsStatusQueueIcmpQueuePackets OBJECT-TYPE
    SYNTAX     Integer32 (0..2147483647)
    MAX-ACCESS read-only
    STATUS     current
    DESCRIPTION
            ""
    ::= { lcsStatusQueue 11 }

-- {SCALAR} 1.3.6.1.4.1.2356.11.1.12.12
lcsStatusQueueTcpQueuePackets OBJECT-TYPE
    SYNTAX     Integer32 (0..2147483647)
    MAX-ACCESS read-only
    STATUS     current
    DESCRIPTION
            ""
    ::= { lcsStatusQueue 12 }

-- {SCALAR} 1.3.6.1.4.1.2356.11.1.12.13
lcsStatusQueueTftpServerQueuePackets OBJECT-TYPE
    SYNTAX     Integer32 (0..2147483647)
    MAX-ACCESS read-only
    STATUS     current
    DESCRIPTION
            ""
    ::= { lcsStatusQueue 13 }

-- {SCALAR} 1.3.6.1.4.1.2356.11.1.12.14
lcsStatusQueueSnmpQueuePackets OBJECT-TYPE
    SYNTAX     Integer32 (0..2147483647)
    MAX-ACCESS read-only
    STATUS     current
    DESCRIPTION
            ""
    ::= { lcsStatusQueue 14 }

-- {SCALAR} 1.3.6.1.4.1.2356.11.1.12.22
lcsStatusQueueProtHeapPackets OBJECT-TYPE
    SYNTAX     Integer32 (0..2147483647)
    MAX-ACCESS read-only
    STATUS     current
    DESCRIPTION
            ""
    ::= { lcsStatusQueue 22 }

-- {SCALAR} 1.3.6.1.4.1.2356.11.1.12.27
lcsStatusQueueDhcpServerQueuePackets OBJECT-TYPE
    SYNTAX     Integer32 (0..2147483647)
    MAX-ACCESS read-only
    STATUS     current
    DESCRIPTION
            ""
    ::= { lcsStatusQueue 27 }

-- {SCALAR} 1.3.6.1.4.1.2356.11.1.12.28
lcsStatusQueueDhcpClientQueuePackets OBJECT-TYPE
    SYNTAX     Integer32 (0..2147483647)
    MAX-ACCESS read-only
    STATUS     current
    DESCRIPTION
            ""
    ::= { lcsStatusQueue 28 }

-- {SCALAR} 1.3.6.1.4.1.2356.11.1.12.29
lcsStatusQueueIprRipQueuePackets OBJECT-TYPE
    SYNTAX     Integer32 (0..2147483647)
    MAX-ACCESS read-only
    STATUS     current
    DESCRIPTION
            ""
    ::= { lcsStatusQueue 29 }

-- {SCALAR} 1.3.6.1.4.1.2356.11.1.12.30
lcsStatusQueueDnsTxQueuePackets OBJECT-TYPE
    SYNTAX     Integer32 (0..2147483647)
    MAX-ACCESS read-only
    STATUS     current
    DESCRIPTION
            ""
    ::= { lcsStatusQueue 30 }

-- {SCALAR} 1.3.6.1.4.1.2356.11.1.12.31
lcsStatusQueueDnsRxQueuePackets OBJECT-TYPE
    SYNTAX     Integer32 (0..2147483647)
    MAX-ACCESS read-only
    STATUS     current
    DESCRIPTION
            ""
    ::= { lcsStatusQueue 31 }

-- {SCALAR} 1.3.6.1.4.1.2356.11.1.12.40
lcsStatusQueueWlanManagementHeapPackets OBJECT-TYPE
    SYNTAX     Integer32 (0..2147483647)
    MAX-ACCESS read-only
    STATUS     current
    DESCRIPTION
            ""
    ::= { lcsStatusQueue 40 }

-- {SCALAR} 1.3.6.1.4.1.2356.11.1.12.41
lcsStatusQueueIpHeapPackets OBJECT-TYPE
    SYNTAX     Integer32 (0..2147483647)
    MAX-ACCESS read-only
    STATUS     current
    DESCRIPTION
            "-- empty --"
    ::= { lcsStatusQueue 41 }

-- {TABLE} 1.3.6.1.4.1.2356.11.1.13
lcsStatusConnectionTable OBJECT-TYPE
    SYNTAX     SEQUENCE OF LcsStatusConnectionEntry
    MAX-ACCESS not-accessible
    STATUS     current
    DESCRIPTION
            ""
    ::= { lcsStatus 13 }

-- {ROW} 1.3.6.1.4.1.2356.11.1.13.1
lcsStatusConnectionEntry OBJECT-TYPE
    SYNTAX     LcsStatusConnectionEntry
    MAX-ACCESS not-accessible
    STATUS     current
    DESCRIPTION
            ""
    INDEX {
            lcsStatusConnectionEntryIfc
          }
    ::= { lcsStatusConnectionTable 1 }

LcsStatusConnectionEntry ::= SEQUENCE {
            lcsStatusConnectionEntryIfc INTEGER,
            lcsStatusConnectionEntryConnections Integer32,
            lcsStatusConnectionEntryActive Integer32,
            lcsStatusConnectionEntryPassive Integer32,
            lcsStatusConnectionEntryErrors Integer32,
            lcsStatusConnectionEntryConTime DisplayString,
            lcsStatusConnectionEntryCharge Integer32
    }

-- {COLUMN} 1.3.6.1.4.1.2356.11.1.13.1.1
lcsStatusConnectionEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusConnectionEntry 1 }

-- {COLUMN} 1.3.6.1.4.1.2356.11.1.13.1.2
lcsStatusConnectionEntryConnections OBJECT-TYPE
    SYNTAX     Integer32 (0..2147483647)
    MAX-ACCESS read-only
    STATUS     current
    DESCRIPTION
            ""
    ::= { lcsStatusConnectionEntry 2 }

-- {COLUMN} 1.3.6.1.4.1.2356.11.1.13.1.3
lcsStatusConnectionEntryActive OBJECT-TYPE
    SYNTAX     Integer32 (0..2147483647)
    MAX-ACCESS read-only
    STATUS     current
    DESCRIPTION
            ""
    ::= { lcsStatusConnectionEntry 3 }

-- {COLUMN} 1.3.6.1.4.1.2356.11.1.13.1.4
lcsStatusConnectionEntryPassive OBJECT-TYPE
    SYNTAX     Integer32 (0..2147483647)
    MAX-ACCESS read-only
    STATUS     current
    DESCRIPTION
            ""
    ::= { lcsStatusConnectionEntry 4 }

-- {COLUMN} 1.3.6.1.4.1.2356.11.1.13.1.5
lcsStatusConnectionEntryErrors OBJECT-TYPE
    SYNTAX     Integer32 (0..2147483647)
    MAX-ACCESS read-only
    STATUS     current
    DESCRIPTION
            ""
    ::= { lcsStatusConnectionEntry 5 }

-- {COLUMN} 1.3.6.1.4.1.2356.11.1.13.1.6
lcsStatusConnectionEntryConTime OBJECT-TYPE
    SYNTAX     DisplayString (SIZE(0..255))
    MAX-ACCESS read-only
    STATUS     current
    DESCRIPTION
            ""
    ::= { lcsStatusConnectionEntry 6 }

-- {COLUMN} 1.3.6.1.4.1.2356.11.1.13.1.7
lcsStatusConnectionEntryCharge OBJECT-TYPE
    SYNTAX     Integer32 (0..2147483647)
    MAX-ACCESS read-only
    STATUS     current
    DESCRIPTION
            ""
    ::= { lcsStatusConnectionEntry 7 }

-- {TABLE} 1.3.6.1.4.1.2356.11.1.14
lcsStatusInfoConnectionTable OBJECT-TYPE
    SYNTAX     SEQUENCE OF LcsStatusInfoConnectionEntry
    MAX-ACCESS not-accessible
    STATUS     current
    DESCRIPTION
            ""
    ::= { lcsStatus 14 }

-- {ROW} 1.3.6.1.4.1.2356.11.1.14.1
lcsStatusInfoConnectionEntry OBJECT-TYPE
    SYNTAX     LcsStatusInfoConnectionEntry
    MAX-ACCESS not-accessible
    STATUS     current
    DESCRIPTION
            ""
    INDEX {
            lcsStatusInfoConnectionEntryIfc
          }
    ::= { lcsStatusInfoConnectionTable 1 }

LcsStatusInfoConnectionEntry ::= SEQUENCE {
            lcsStatusInfoConnectionEntryIfc INTEGER,
            lcsStatusInfoConnectionEntryStatus DisplayString,
            lcsStatusInfoConnectionEntryMode INTEGER,
            lcsStatusInfoConnectionEntryDialupRemote DisplayString,
            lcsStatusInfoConnectionEntryPeer DisplayString,
            lcsStatusInfoConnectionEntryB1Dt Integer32,
            lcsStatusInfoConnectionEntryB2Dt Integer32
    }

-- {COLUMN} 1.3.6.1.4.1.2356.11.1.14.1.1
lcsStatusInfoConnectionEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusInfoConnectionEntry 1 }

-- {COLUMN} 1.3.6.1.4.1.2356.11.1.14.1.2
lcsStatusInfoConnectionEntryStatus OBJECT-TYPE
    SYNTAX     DisplayString (SIZE(0..16))
    MAX-ACCESS read-only
    STATUS     current
    DESCRIPTION
            ""
    ::= { lcsStatusInfoConnectionEntry 2 }

-- {COLUMN} 1.3.6.1.4.1.2356.11.1.14.1.3
lcsStatusInfoConnectionEntryMode OBJECT-TYPE
    SYNTAX     INTEGER {
                  eUnknown (0),
                  eActive (4),
                  ePassive (5),
                  eCallback (9)
            }
    MAX-ACCESS read-only
    STATUS     current
    DESCRIPTION
            ""
    ::= { lcsStatusInfoConnectionEntry 3 }

-- {COLUMN} 1.3.6.1.4.1.2356.11.1.14.1.4
lcsStatusInfoConnectionEntryDialupRemote OBJECT-TYPE
    SYNTAX     DisplayString (SIZE(0..20))
    MAX-ACCESS read-only
    STATUS     current
    DESCRIPTION
            ""
    ::= { lcsStatusInfoConnectionEntry 4 }

-- {COLUMN} 1.3.6.1.4.1.2356.11.1.14.1.5
lcsStatusInfoConnectionEntryPeer OBJECT-TYPE
    SYNTAX     DisplayString (SIZE(0..16))
    MAX-ACCESS read-only
    STATUS     current
    DESCRIPTION
            ""
    ::= { lcsStatusInfoConnectionEntry 5 }

-- {COLUMN} 1.3.6.1.4.1.2356.11.1.14.1.6
lcsStatusInfoConnectionEntryB1Dt OBJECT-TYPE
    SYNTAX     Integer32 (0..65535)
    MAX-ACCESS read-only
    STATUS     current
    DESCRIPTION
            ""
    ::= { lcsStatusInfoConnectionEntry 6 }

-- {COLUMN} 1.3.6.1.4.1.2356.11.1.14.1.7
lcsStatusInfoConnectionEntryB2Dt OBJECT-TYPE
    SYNTAX     Integer32 (0..65535)
    MAX-ACCESS read-only
    STATUS     current
    DESCRIPTION
            ""
    ::= { lcsStatusInfoConnectionEntry 7 }

-- {TABLE} 1.3.6.1.4.1.2356.11.1.15
lcsStatusLayerConnectionTable OBJECT-TYPE
    SYNTAX     SEQUENCE OF LcsStatusLayerConnectionEntry
    MAX-ACCESS not-accessible
    STATUS     current
    DESCRIPTION
            ""
    ::= { lcsStatus 15 }

-- {ROW} 1.3.6.1.4.1.2356.11.1.15.1
lcsStatusLayerConnectionEntry OBJECT-TYPE
    SYNTAX     LcsStatusLayerConnectionEntry
    MAX-ACCESS not-accessible
    STATUS     current
    DESCRIPTION
            ""
    INDEX {
            lcsStatusLayerConnectionEntryIfc
          }
    ::= { lcsStatusLayerConnectionTable 1 }

LcsStatusLayerConnectionEntry ::= SEQUENCE {
            lcsStatusLayerConnectionEntryIfc INTEGER,
            lcsStatusLayerConnectionEntryWanLayer DisplayString,
            lcsStatusLayerConnectionEntryEncaps INTEGER,
            lcsStatusLayerConnectionEntryLay3 INTEGER,
            lcsStatusLayerConnectionEntryLay2 INTEGER,
            lcsStatusLayerConnectionEntryL2Opt INTEGER,
            lcsStatusLayerConnectionEntryLay1 INTEGER,
            lcsStatusLayerConnectionEntryL1Parameter INTEGER
    }

-- {COLUMN} 1.3.6.1.4.1.2356.11.1.15.1.1
lcsStatusLayerConnectionEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusLayerConnectionEntry 1 }

-- {COLUMN} 1.3.6.1.4.1.2356.11.1.15.1.2
lcsStatusLayerConnectionEntryWanLayer OBJECT-TYPE
    SYNTAX     DisplayString (SIZE(0..9))
    MAX-ACCESS read-only
    STATUS     current
    DESCRIPTION
            ""
    ::= { lcsStatusLayerConnectionEntry 2 }

-- {COLUMN} 1.3.6.1.4.1.2356.11.1.15.1.3
lcsStatusLayerConnectionEntryEncaps OBJECT-TYPE
    SYNTAX     INTEGER {
                  eEther (0),
                  eLlcMux (1),
                  eLlcEth (3),
                  eVcMux (4),
                  eTrans (255)
            }
    MAX-ACCESS read-only
    STATUS     current
    DESCRIPTION
            ""
    ::= { lcsStatusLayerConnectionEntry 3 }

-- {COLUMN} 1.3.6.1.4.1.2356.11.1.15.1.4
lcsStatusLayerConnectionEntryLay3 OBJECT-TYPE
    SYNTAX     INTEGER {
                  eNONE (0),
                  ePpp (4),
                  eAppp (5),
                  eScppp (6),
                  eScappp (7),
                  eSctrans (8),
                  eDhcp (9),
                  eTRANS (255)
            }
    MAX-ACCESS read-only
    STATUS     current
    DESCRIPTION
            ""
    ::= { lcsStatusLayerConnectionEntry 4 }

-- {COLUMN} 1.3.6.1.4.1.2356.11.1.15.1.5
lcsStatusLayerConnectionEntryLay2 OBJECT-TYPE
    SYNTAX     INTEGER {
                  eX75lapb (0),
                  eTrans (1),
                  ePppoe (5),
                  eSscop (6)
            }
    MAX-ACCESS read-only
    STATUS     current
    DESCRIPTION
            ""
    ::= { lcsStatusLayerConnectionEntry 5 }

-- {COLUMN} 1.3.6.1.4.1.2356.11.1.15.1.6
lcsStatusLayerConnectionEntryL2Opt OBJECT-TYPE
    SYNTAX     INTEGER {
                  eCompr (0),
                  eBundle (1),
                  eBndPlusCmpr (2),
                  eNone (255)
            }
    MAX-ACCESS read-only
    STATUS     current
    DESCRIPTION
            ""
    ::= { lcsStatusLayerConnectionEntry 6 }

-- {COLUMN} 1.3.6.1.4.1.2356.11.1.15.1.7
lcsStatusLayerConnectionEntryLay1 OBJECT-TYPE
    SYNTAX     INTEGER {
                  eHdlc64k (0),
                  eHdlc56k (1),
                  eAdsl (2),
                  eV1109k6 (3),
                  eEth (4),
                  eModem (5),
                  eSerial (6),
                  eVdsl (9),
                  eV11019k2 (67),
                  eV11038k4 (131)
            }
    MAX-ACCESS read-only
    STATUS     current
    DESCRIPTION
            ""
    ::= { lcsStatusLayerConnectionEntry 7 }

-- {COLUMN} 1.3.6.1.4.1.2356.11.1.15.1.8
lcsStatusLayerConnectionEntryL1Parameter OBJECT-TYPE
    SYNTAX     INTEGER {
                  eNone (0),
                  eV21300 (1),
                  eV23600 (2),
                  eV231200 (3),
                  eV221200 (4),
                  eV22bis2400 (5),
                  eV32qam4800 (6),
                  eV32qam9600 (7),
                  eV32bis7200 (8),
                  eV32tcm9600 (9),
                  eV32bis12000 (10),
                  eV32bis14400 (11),
                  eV342400 (12),
                  eV344800 (13),
                  eV347200 (14),
                  eV349600 (15),
                  eV3412000 (16),
                  eV3414400 (17),
                  eV3416800 (18),
                  eV3419200 (19),
                  eV3421600 (20),
                  eV3424000 (21),
                  eV3426400 (22),
                  eV3428800 (23),
                  eV3431200 (24),
                  eV3433600 (25),
                  eV9028000 (26),
                  eV9029333 (27),
                  eV9030667 (28),
                  eV9032000 (29),
                  eV9033333 (30),
                  eV9034667 (31),
                  eV9036000 (32),
                  eV9037333 (33),
                  eV9038667 (34),
                  eV9040000 (35),
                  eV9041333 (36),
                  eV9042667 (37),
                  eV9044000 (38),
                  eV9045333 (39),
                  eV9046667 (40),
                  eV9048000 (41),
                  eV9049333 (42),
                  eV9050667 (43),
                  eV9052000 (44),
                  eV9053333 (45),
                  eV9054667 (46),
                  eV9056000 (47)
            }
    MAX-ACCESS read-only
    STATUS     current
    DESCRIPTION
            ""
    ::= { lcsStatusLayerConnectionEntry 8 }

-- {TABLE} 1.3.6.1.4.1.2356.11.1.16
lcsStatusCallInformationTable OBJECT-TYPE
    SYNTAX     SEQUENCE OF LcsStatusCallInformationEntry
    MAX-ACCESS not-accessible
    STATUS     current
    DESCRIPTION
            ""
    ::= { lcsStatus 16 }

-- {ROW} 1.3.6.1.4.1.2356.11.1.16.1
lcsStatusCallInformationEntry OBJECT-TYPE
    SYNTAX     LcsStatusCallInformationEntry
    MAX-ACCESS not-accessible
    STATUS     current
    DESCRIPTION
            ""
    INDEX {
            lcsStatusCallInformationEntrySystemTime,
            lcsStatusCallInformationEntryCounter
          }
    ::= { lcsStatusCallInformationTable 1 }

LcsStatusCallInformationEntry ::= SEQUENCE {
            lcsStatusCallInformationEntrySystemTime Gauge32,
            lcsStatusCallInformationEntryIfc INTEGER,
            lcsStatusCallInformationEntryClipCaller DisplayString,
            lcsStatusCallInformationEntryDialCaller DisplayString,
            lcsStatusCallInformationEntryCapab INTEGER,
            lcsStatusCallInformationEntryBChan Integer32,
            lcsStatusCallInformationEntryCounter Integer32
    }

-- {COLUMN} 1.3.6.1.4.1.2356.11.1.16.1.1
lcsStatusCallInformationEntrySystemTime OBJECT-TYPE
    SYNTAX     Gauge32
    MAX-ACCESS read-only
    STATUS     current
    DESCRIPTION
            ""
    ::= { lcsStatusCallInformationEntry 1 }

-- {COLUMN} 1.3.6.1.4.1.2356.11.1.16.1.2
lcsStatusCallInformationEntryIfc OBJECT-TYPE
    SYNTAX     INTEGER {
                  eS01 (257),
                  eS02 (258),
                  eModem (513),
                  eDsl1 (2049),
                  eDsl2 (2050),
                  eDsl3 (2051),
                  eDsl4 (2052),
                  eDsl5 (2053),
                  eAdsl (8193),
                  eVdsl (16385),
                  eVdsl2 (16386)
            }
    MAX-ACCESS read-only
    STATUS     current
    DESCRIPTION
            ""
    ::= { lcsStatusCallInformationEntry 2 }

-- {COLUMN} 1.3.6.1.4.1.2356.11.1.16.1.3
lcsStatusCallInformationEntryClipCaller OBJECT-TYPE
    SYNTAX     DisplayString (SIZE(0..20))
    MAX-ACCESS read-only
    STATUS     current
    DESCRIPTION
            ""
    ::= { lcsStatusCallInformationEntry 3 }

-- {COLUMN} 1.3.6.1.4.1.2356.11.1.16.1.4
lcsStatusCallInformationEntryDialCaller OBJECT-TYPE
    SYNTAX     DisplayString (SIZE(0..20))
    MAX-ACCESS read-only
    STATUS     current
    DESCRIPTION
            ""
    ::= { lcsStatusCallInformationEntry 4 }

-- {COLUMN} 1.3.6.1.4.1.2356.11.1.16.1.5
lcsStatusCallInformationEntryCapab OBJECT-TYPE
    SYNTAX     INTEGER {
                  eHdlc64k (0),
                  eHdlc56k (1),
                  eV1109k6 (3),
                  eModem (5),
                  eA31khz (13),
                  eSpeech (14),
                  eFaxG23 (15),
                  eV11019k2 (67),
                  eV11038k4 (131),
                  eUnknown (255)
            }
    MAX-ACCESS read-only
    STATUS     current
    DESCRIPTION
            ""
    ::= { lcsStatusCallInformationEntry 5 }

-- {COLUMN} 1.3.6.1.4.1.2356.11.1.16.1.6
lcsStatusCallInformationEntryBChan OBJECT-TYPE
    SYNTAX     Integer32 (0..65535)
    MAX-ACCESS read-only
    STATUS     current
    DESCRIPTION
            ""
    ::= { lcsStatusCallInformationEntry 6 }

-- {COLUMN} 1.3.6.1.4.1.2356.11.1.16.1.7
lcsStatusCallInformationEntryCounter OBJECT-TYPE
    SYNTAX     Integer32 (0..2147483647)
    MAX-ACCESS read-only
    STATUS     current
    DESCRIPTION
            ""
    ::= { lcsStatusCallInformationEntry 7 }

-- {TABLE} 1.3.6.1.4.1.2356.11.1.17
lcsStatusRemoteConnectionsTable OBJECT-TYPE
    SYNTAX     SEQUENCE OF LcsStatusRemoteConnectionsEntry
    MAX-ACCESS not-accessible
    STATUS     current
    DESCRIPTION
            ""
    ::= { lcsStatus 17 }

-- {ROW} 1.3.6.1.4.1.2356.11.1.17.1
lcsStatusRemoteConnectionsEntry OBJECT-TYPE
    SYNTAX     LcsStatusRemoteConnectionsEntry
    MAX-ACCESS not-accessible
    STATUS     current
    DESCRIPTION
            ""
    INDEX {
            lcsStatusRemoteConnectionsEntryConnStart,
            lcsStatusRemoteConnectionsEntryCounter
          }
    ::= { lcsStatusRemoteConnectionsTable 1 }

LcsStatusRemoteConnectionsEntry ::= SEQUENCE {
            lcsStatusRemoteConnectionsEntryConnStart DisplayString,
            lcsStatusRemoteConnectionsEntryRemoteId DisplayString,
            lcsStatusRemoteConnectionsEntryMode INTEGER,
            lcsStatusRemoteConnectionsEntryIfc INTEGER,
            lcsStatusRemoteConnectionsEntryConnTime DisplayString,
            lcsStatusRemoteConnectionsEntryCharge Integer32,
            lcsStatusRemoteConnectionsEntryCounter Integer32
    }

-- {COLUMN} 1.3.6.1.4.1.2356.11.1.17.1.1
lcsStatusRemoteConnectionsEntryConnStart OBJECT-TYPE
    SYNTAX     DisplayString (SIZE(0..19))
    MAX-ACCESS read-only
    STATUS     current
    DESCRIPTION
            ""
    ::= { lcsStatusRemoteConnectionsEntry 1 }

-- {COLUMN} 1.3.6.1.4.1.2356.11.1.17.1.2
lcsStatusRemoteConnectionsEntryRemoteId OBJECT-TYPE
    SYNTAX     DisplayString (SIZE(0..16))
    MAX-ACCESS read-only
    STATUS     current
    DESCRIPTION
            ""
    ::= { lcsStatusRemoteConnectionsEntry 2 }

-- {COLUMN} 1.3.6.1.4.1.2356.11.1.17.1.3
lcsStatusRemoteConnectionsEntryMode OBJECT-TYPE
    SYNTAX     INTEGER {
                  eUnknown (0),
                  eActive (4),
                  ePassive (5),
                  eCallback (9)
            }
    MAX-ACCESS read-only
    STATUS     current
    DESCRIPTION
            ""
    ::= { lcsStatusRemoteConnectionsEntry 3 }

-- {COLUMN} 1.3.6.1.4.1.2356.11.1.17.1.4
lcsStatusRemoteConnectionsEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusRemoteConnectionsEntry 4 }

-- {COLUMN} 1.3.6.1.4.1.2356.11.1.17.1.5
lcsStatusRemoteConnectionsEntryConnTime OBJECT-TYPE
    SYNTAX     DisplayString (SIZE(0..255))
    MAX-ACCESS read-only
    STATUS     current
    DESCRIPTION
            ""
    ::= { lcsStatusRemoteConnectionsEntry 5 }

-- {COLUMN} 1.3.6.1.4.1.2356.11.1.17.1.6
lcsStatusRemoteConnectionsEntryCharge OBJECT-TYPE
    SYNTAX     Integer32 (0..2147483647)
    MAX-ACCESS read-only
    STATUS     current
    DESCRIPTION
            ""
    ::= { lcsStatusRemoteConnectionsEntry 6 }

-- {COLUMN} 1.3.6.1.4.1.2356.11.1.17.1.8
lcsStatusRemoteConnectionsEntryCounter OBJECT-TYPE
    SYNTAX     Integer32 (0..2147483647)
    MAX-ACCESS read-only
    STATUS     current
    DESCRIPTION
            ""
    ::= { lcsStatusRemoteConnectionsEntry 8 }

-- {SCALAR} 1.3.6.1.4.1.2356.11.1.18
lcsStatusCurrentTime OBJECT-TYPE
    SYNTAX     DisplayString
    MAX-ACCESS read-only
    STATUS     current
    DESCRIPTION
            ""
    ::= { lcsStatus 18 }

-- {NODE} 1.3.6.1.4.1.2356.11.1.21
lcsStatusTime OBJECT IDENTIFIER ::= { lcsStatus 21 }

-- {SCALAR} 1.3.6.1.4.1.2356.11.1.21.1
lcsStatusTimeCurrentTime OBJECT-TYPE
    SYNTAX     DisplayString
    MAX-ACCESS read-only
    STATUS     current
    DESCRIPTION
            ""
    ::= { lcsStatusTime 1 }

-- {SCALAR} 1.3.6.1.4.1.2356.11.1.21.2
lcsStatusTimeSource OBJECT-TYPE
    SYNTAX     INTEGER {
                  eNo (0),
                  eManual (1),
                  eIsdn (2),
                  eLan (3),
                  eRam (4),
                  eLanconfig (8),
                  eNtp (9),
                  eCapwap (10),
                  eRtc (11),
                  eGps (12),
                  eLmc (13)
            }
    MAX-ACCESS read-only
    STATUS     current
    DESCRIPTION
            ""
    ::= { lcsStatusTime 2 }

-- {SCALAR} 1.3.6.1.4.1.2356.11.1.21.3
lcsStatusTimeSetCount OBJECT-TYPE
    SYNTAX     Counter32
    MAX-ACCESS read-only
    STATUS     current
    DESCRIPTION
            ""
    ::= { lcsStatusTime 3 }

-- {NODE} 1.3.6.1.4.1.2356.11.1.21.4
lcsStatusTimeIsdn OBJECT IDENTIFIER ::= { lcsStatusTime 4 }

-- {SCALAR} 1.3.6.1.4.1.2356.11.1.21.4.1
lcsStatusTimeIsdnConnection OBJECT-TYPE
    SYNTAX     Integer32 (0..255)
    MAX-ACCESS read-only
    STATUS     current
    DESCRIPTION
            ""
    ::= { lcsStatusTimeIsdn 1 }

-- {SCALAR} 1.3.6.1.4.1.2356.11.1.21.4.2
lcsStatusTimeIsdnInformation OBJECT-TYPE
    SYNTAX     Integer32 (0..255)
    MAX-ACCESS read-only
    STATUS     current
    DESCRIPTION
            ""
    ::= { lcsStatusTimeIsdn 2 }

-- {SCALAR} 1.3.6.1.4.1.2356.11.1.21.4.3
lcsStatusTimeIsdnInfoError OBJECT-TYPE
    SYNTAX     Integer32 (0..255)
    MAX-ACCESS read-only
    STATUS     current
    DESCRIPTION
            ""
    ::= { lcsStatusTimeIsdn 3 }

-- {SCALAR} 1.3.6.1.4.1.2356.11.1.21.4.4
lcsStatusTimeIsdnUnits OBJECT-TYPE
    SYNTAX     Integer32 (0..65535)
    MAX-ACCESS read-only
    STATUS     current
    DESCRIPTION
            ""
    ::= { lcsStatusTimeIsdn 4 }

-- {SCALAR} 1.3.6.1.4.1.2356.11.1.21.4.5
lcsStatusTimeIsdnDeleteValues OBJECT-TYPE
    SYNTAX     DisplayString
    MAX-ACCESS read-write
    STATUS     current
    DESCRIPTION
            ""
    ::= { lcsStatusTimeIsdn 5 }

-- {SCALAR} 1.3.6.1.4.1.2356.11.1.21.7
lcsStatusTimeUtcInSeconds OBJECT-TYPE
    SYNTAX     Counter32
    MAX-ACCESS read-only
    STATUS     current
    DESCRIPTION
            ""
    ::= { lcsStatusTime 7 }

-- {SCALAR} 1.3.6.1.4.1.2356.11.1.21.10
lcsStatusTimeTimezone OBJECT-TYPE
    SYNTAX     INTEGER {
                  e0 (0),
                  eplus1 (1),
                  eplus2 (2),
                  eplus3 (3),
                  eplus4 (4),
                  eplus5 (5),
                  eplus6 (6),
                  eplus7 (7),
                  eplus8 (8),
                  eplus9 (9),
                  eplus10 (10),
                  eplus11 (11),
                  eplus12 (12),
                  eplus13 (13),
                  eplus14 (14),
                  eminus12 (244),
                  eminus11 (245),
                  eminus10 (246),
                  eminus9 (247),
                  eminus8 (248),
                  eminus7 (249),
                  eminus6 (250),
                  eminus5 (251),
                  eminus4 (252),
                  eminus3 (253),
                  eminus2 (254),
                  eminus1 (255)
            }
    MAX-ACCESS read-only
    STATUS     current
    DESCRIPTION
            ""
    ::= { lcsStatusTime 10 }

-- {SCALAR} 1.3.6.1.4.1.2356.11.1.21.11
lcsStatusTimeDaylightSavingTime OBJECT-TYPE
    SYNTAX     INTEGER {
                  eNo (0),
                  eYes (1),
                  eEuropeEu (2),
                  eRussia (3),
                  eUsa (4),
                  eUserDefined (255)
            }
    MAX-ACCESS read-only
    STATUS     current
    DESCRIPTION
            ""
    ::= { lcsStatusTime 11 }

-- {TABLE} 1.3.6.1.4.1.2356.11.1.21.12
lcsStatusTimeDstClockChangesTable OBJECT-TYPE
    SYNTAX     SEQUENCE OF LcsStatusTimeDstClockChangesEntry
    MAX-ACCESS not-accessible
    STATUS     current
    DESCRIPTION
            ""
    ::= { lcsStatusTime 12 }

-- {ROW} 1.3.6.1.4.1.2356.11.1.21.12.1
lcsStatusTimeDstClockChangesEntry OBJECT-TYPE
    SYNTAX     LcsStatusTimeDstClockChangesEntry
    MAX-ACCESS not-accessible
    STATUS     current
    DESCRIPTION
            ""
    INDEX {
            lcsStatusTimeDstClockChangesEntryEvent
          }
    ::= { lcsStatusTimeDstClockChangesTable 1 }

LcsStatusTimeDstClockChangesEntry ::= SEQUENCE {
            lcsStatusTimeDstClockChangesEntryEvent INTEGER,
            lcsStatusTimeDstClockChangesEntryIndex INTEGER,
            lcsStatusTimeDstClockChangesEntryDay INTEGER,
            lcsStatusTimeDstClockChangesEntryMonth INTEGER,
            lcsStatusTimeDstClockChangesEntryHour Integer32,
            lcsStatusTimeDstClockChangesEntryMinute Integer32,
            lcsStatusTimeDstClockChangesEntryTimeType INTEGER
    }

-- {COLUMN} 1.3.6.1.4.1.2356.11.1.21.12.1.1
lcsStatusTimeDstClockChangesEntryEvent OBJECT-TYPE
    SYNTAX     INTEGER {
                  eStart (1),
                  eEnd (2)
            }
    MAX-ACCESS read-only
    STATUS     current
    DESCRIPTION
            ""
    ::= { lcsStatusTimeDstClockChangesEntry 1 }

-- {COLUMN} 1.3.6.1.4.1.2356.11.1.21.12.1.2
lcsStatusTimeDstClockChangesEntryIndex OBJECT-TYPE
    SYNTAX     INTEGER {
                  eFirst (1),
                  eSecond (2),
                  eThird (3),
                  eFourth (4),
                  e4Last (252),
                  e3Last (253),
                  e2Last (254),
                  eLast (255)
            }
    MAX-ACCESS read-only
    STATUS     current
    DESCRIPTION
            ""
    ::= { lcsStatusTimeDstClockChangesEntry 2 }

-- {COLUMN} 1.3.6.1.4.1.2356.11.1.21.12.1.3
lcsStatusTimeDstClockChangesEntryDay OBJECT-TYPE
    SYNTAX     INTEGER {
                  eSunday (0),
                  eMonday (1),
                  eTuesday (2),
                  eWednesday (3),
                  eThursday (4),
                  eFriday (5),
                  eSaturday (6)
            }
    MAX-ACCESS read-only
    STATUS     current
    DESCRIPTION
            ""
    ::= { lcsStatusTimeDstClockChangesEntry 3 }

-- {COLUMN} 1.3.6.1.4.1.2356.11.1.21.12.1.4
lcsStatusTimeDstClockChangesEntryMonth OBJECT-TYPE
    SYNTAX     INTEGER {
                  eJanuary (1),
                  eFebruary (2),
                  eMarch (3),
                  eApril (4),
                  eMay (5),
                  eJune (6),
                  eJuly (7),
                  eAugust (8),
                  eSeptember (9),
                  eOctober (10),
                  eNovember (11),
                  eDecember (12)
            }
    MAX-ACCESS read-only
    STATUS     current
    DESCRIPTION
            ""
    ::= { lcsStatusTimeDstClockChangesEntry 4 }

-- {COLUMN} 1.3.6.1.4.1.2356.11.1.21.12.1.5
lcsStatusTimeDstClockChangesEntryHour OBJECT-TYPE
    SYNTAX     Integer32 (0..255)
    MAX-ACCESS read-only
    STATUS     current
    DESCRIPTION
            ""
    ::= { lcsStatusTimeDstClockChangesEntry 5 }

-- {COLUMN} 1.3.6.1.4.1.2356.11.1.21.12.1.6
lcsStatusTimeDstClockChangesEntryMinute OBJECT-TYPE
    SYNTAX     Integer32 (0..255)
    MAX-ACCESS read-only
    STATUS     current
    DESCRIPTION
            ""
    ::= { lcsStatusTimeDstClockChangesEntry 6 }

-- {COLUMN} 1.3.6.1.4.1.2356.11.1.21.12.1.7
lcsStatusTimeDstClockChangesEntryTimeType OBJECT-TYPE
    SYNTAX     INTEGER {
                  eLst (0),
                  eUtc (1)
            }
    MAX-ACCESS read-only
    STATUS     current
    DESCRIPTION
            ""
    ::= { lcsStatusTimeDstClockChangesEntry 7 }

-- {NODE} 1.3.6.1.4.1.2356.11.1.22
lcsStatusLcr OBJECT IDENTIFIER ::= { lcsStatus 22 }

-- {SCALAR} 1.3.6.1.4.1.2356.11.1.22.1
lcsStatusLcrTotalCalls OBJECT-TYPE
    SYNTAX     Counter32
    MAX-ACCESS read-only
    STATUS     current
    DESCRIPTION
            ""
    ::= { lcsStatusLcr 1 }

-- {SCALAR} 1.3.6.1.4.1.2356.11.1.22.2
lcsStatusLcrFoundEvents OBJECT-TYPE
    SYNTAX     Counter32
    MAX-ACCESS read-only
    STATUS     current
    DESCRIPTION
            ""
    ::= { lcsStatusLcr 2 }

-- {SCALAR} 1.3.6.1.4.1.2356.11.1.22.3
lcsStatusLcrNotfoundErrors OBJECT-TYPE
    SYNTAX     Counter32
    MAX-ACCESS read-only
    STATUS     current
    DESCRIPTION
            ""
    ::= { lcsStatusLcr 3 }

-- {SCALAR} 1.3.6.1.4.1.2356.11.1.22.4
lcsStatusLcrMissingtimeErrors OBJECT-TYPE
    SYNTAX     Counter32
    MAX-ACCESS read-only
    STATUS     current
    DESCRIPTION
            ""
    ::= { lcsStatusLcr 4 }

-- {TABLE} 1.3.6.1.4.1.2356.11.1.22.6
lcsStatusLcrProviderTable OBJECT-TYPE
    SYNTAX     SEQUENCE OF LcsStatusLcrProviderEntry
    MAX-ACCESS not-accessible
    STATUS     current
    DESCRIPTION
            ""
    ::= { lcsStatusLcr 6 }

-- {ROW} 1.3.6.1.4.1.2356.11.1.22.6.1
lcsStatusLcrProviderEntry OBJECT-TYPE
    SYNTAX     LcsStatusLcrProviderEntry
    MAX-ACCESS not-accessible
    STATUS     current
    DESCRIPTION
            ""
    INDEX {
            lcsStatusLcrProviderEntryProvider
          }
    ::= { lcsStatusLcrProviderTable 1 }

LcsStatusLcrProviderEntry ::= SEQUENCE {
            lcsStatusLcrProviderEntryProvider DisplayString,
            lcsStatusLcrProviderEntryFailures Integer32,
            lcsStatusLcrProviderEntrySuccesses Integer32
    }

-- {COLUMN} 1.3.6.1.4.1.2356.11.1.22.6.1.1
lcsStatusLcrProviderEntryProvider OBJECT-TYPE
    SYNTAX     DisplayString (SIZE(0..10))
    MAX-ACCESS read-only
    STATUS     current
    DESCRIPTION
            ""
    ::= { lcsStatusLcrProviderEntry 1 }

-- {COLUMN} 1.3.6.1.4.1.2356.11.1.22.6.1.2
lcsStatusLcrProviderEntryFailures OBJECT-TYPE
    SYNTAX     Integer32 (0..2147483647)
    MAX-ACCESS read-only
    STATUS     current
    DESCRIPTION
            ""
    ::= { lcsStatusLcrProviderEntry 2 }

-- {COLUMN} 1.3.6.1.4.1.2356.11.1.22.6.1.3
lcsStatusLcrProviderEntrySuccesses OBJECT-TYPE
    SYNTAX     Integer32 (0..2147483647)
    MAX-ACCESS read-only
    STATUS     current
    DESCRIPTION
            ""
    ::= { lcsStatusLcrProviderEntry 3 }

-- {SCALAR} 1.3.6.1.4.1.2356.11.1.22.7
lcsStatusLcrDeleteValues OBJECT-TYPE
    SYNTAX     DisplayString
    MAX-ACCESS read-write
    STATUS     current
    DESCRIPTION
            ""
    ::= { lcsStatusLcr 7 }

-- {NODE} 1.3.6.1.4.1.2356.11.1.22.31
lcsStatusLcrPppoe OBJECT IDENTIFIER ::= { lcsStatusLcr 31 }

-- {SCALAR} 1.3.6.1.4.1.2356.11.1.22.31.1
lcsStatusLcrPppoeTxPadi OBJECT-TYPE
    SYNTAX     Integer32 (0..2147483647)
    MAX-ACCESS read-only
    STATUS     current
    DESCRIPTION
            ""
    ::= { lcsStatusLcrPppoe 1 }

-- {SCALAR} 1.3.6.1.4.1.2356.11.1.22.31.2
lcsStatusLcrPppoeRxPado OBJECT-TYPE
    SYNTAX     Integer32 (0..2147483647)
    MAX-ACCESS read-only
    STATUS     current
    DESCRIPTION
            ""
    ::= { lcsStatusLcrPppoe 2 }

-- {SCALAR} 1.3.6.1.4.1.2356.11.1.22.31.3
lcsStatusLcrPppoeTxPadr OBJECT-TYPE
    SYNTAX     Integer32 (0..2147483647)
    MAX-ACCESS read-only
    STATUS     current
    DESCRIPTION
            ""
    ::= { lcsStatusLcrPppoe 3 }

-- {SCALAR} 1.3.6.1.4.1.2356.11.1.22.31.4
lcsStatusLcrPppoeRxPads OBJECT-TYPE
    SYNTAX     Integer32 (0..2147483647)
    MAX-ACCESS read-only
    STATUS     current
    DESCRIPTION
            ""
    ::= { lcsStatusLcrPppoe 4 }

-- {SCALAR} 1.3.6.1.4.1.2356.11.1.22.31.5
lcsStatusLcrPppoeTxPadt OBJECT-TYPE
    SYNTAX     Integer32 (0..2147483647)
    MAX-ACCESS read-only
    STATUS     current
    DESCRIPTION
            ""
    ::= { lcsStatusLcrPppoe 5 }

-- {SCALAR} 1.3.6.1.4.1.2356.11.1.22.31.6
lcsStatusLcrPppoeRxPadt OBJECT-TYPE
    SYNTAX     Integer32 (0..2147483647)
    MAX-ACCESS read-only
    STATUS     current
    DESCRIPTION
            ""
    ::= { lcsStatusLcrPppoe 6 }

-- {SCALAR} 1.3.6.1.4.1.2356.11.1.22.31.7
lcsStatusLcrPppoeTxProtocol OBJECT-TYPE
    SYNTAX     Integer32 (0..2147483647)
    MAX-ACCESS read-only
    STATUS     current
    DESCRIPTION
            ""
    ::= { lcsStatusLcrPppoe 7 }

-- {SCALAR} 1.3.6.1.4.1.2356.11.1.22.31.8
lcsStatusLcrPppoeRxProtocol OBJECT-TYPE
    SYNTAX     Integer32 (0..2147483647)
    MAX-ACCESS read-only
    STATUS     current
    DESCRIPTION
            ""
    ::= { lcsStatusLcrPppoe 8 }

-- {SCALAR} 1.3.6.1.4.1.2356.11.1.22.31.9
lcsStatusLcrPppoeTxData OBJECT-TYPE
    SYNTAX     Integer32 (0..2147483647)
    MAX-ACCESS read-only
    STATUS     current
    DESCRIPTION
            ""
    ::= { lcsStatusLcrPppoe 9 }

-- {SCALAR} 1.3.6.1.4.1.2356.11.1.22.31.10
lcsStatusLcrPppoeRxData OBJECT-TYPE
    SYNTAX     Integer32 (0..2147483647)
    MAX-ACCESS read-only
    STATUS     current
    DESCRIPTION
            ""
    ::= { lcsStatusLcrPppoe 10 }

-- {SCALAR} 1.3.6.1.4.1.2356.11.1.22.31.11
lcsStatusLcrPppoeRxBad OBJECT-TYPE
    SYNTAX     Integer32 (0..2147483647)
    MAX-ACCESS read-only
    STATUS     current
    DESCRIPTION
            ""
    ::= { lcsStatusLcrPppoe 11 }

-- {SCALAR} 1.3.6.1.4.1.2356.11.1.22.31.12
lcsStatusLcrPppoeAcName OBJECT-TYPE
    SYNTAX     DisplayString (SIZE(0..63))
    MAX-ACCESS read-only
    STATUS     current
    DESCRIPTION
            ""
    ::= { lcsStatusLcrPppoe 12 }

-- {SCALAR} 1.3.6.1.4.1.2356.11.1.22.31.13
lcsStatusLcrPppoeService OBJECT-TYPE
    SYNTAX     DisplayString (SIZE(0..63))
    MAX-ACCESS read-only
    STATUS     current
    DESCRIPTION
            ""
    ::= { lcsStatusLcrPppoe 13 }

-- {SCALAR} 1.3.6.1.4.1.2356.11.1.22.31.30
lcsStatusLcrPppoeDeleteValues OBJECT-TYPE
    SYNTAX     DisplayString
    MAX-ACCESS read-write
    STATUS     current
    DESCRIPTION
            ""
    ::= { lcsStatusLcrPppoe 30 }

-- {NODE} 1.3.6.1.4.1.2356.11.1.24
lcsStatusCharging OBJECT IDENTIFIER ::= { lcsStatus 24 }

-- {SCALAR} 1.3.6.1.4.1.2356.11.1.24.1
lcsStatusChargingSpareDslBroadbandMinutes OBJECT-TYPE
    SYNTAX     Integer32 (0..2147483647)
    MAX-ACCESS read-only
    STATUS     current
    DESCRIPTION
            ""
    ::= { lcsStatusCharging 1 }

-- {TABLE} 1.3.6.1.4.1.2356.11.1.24.2
lcsStatusChargingTimeTableTable OBJECT-TYPE
    SYNTAX     SEQUENCE OF LcsStatusChargingTimeTableEntry
    MAX-ACCESS not-accessible
    STATUS     current
    DESCRIPTION
            ""
    ::= { lcsStatusCharging 2 }

-- {ROW} 1.3.6.1.4.1.2356.11.1.24.2.1
lcsStatusChargingTimeTableEntry OBJECT-TYPE
    SYNTAX     LcsStatusChargingTimeTableEntry
    MAX-ACCESS not-accessible
    STATUS     current
    DESCRIPTION
            ""
    INDEX {
            lcsStatusChargingTimeTableEntryIfc
          }
    ::= { lcsStatusChargingTimeTableTable 1 }

LcsStatusChargingTimeTableEntry ::= SEQUENCE {
            lcsStatusChargingTimeTableEntryIfc INTEGER,
            lcsStatusChargingTimeTableEntryBudgetMinutes Integer32,
            lcsStatusChargingTimeTableEntrySpareMinutes Integer32,
            lcsStatusChargingTimeTableEntryMinutesActive Integer32,
            lcsStatusChargingTimeTableEntryMinutesPassive Integer32
    }

-- {COLUMN} 1.3.6.1.4.1.2356.11.1.24.2.1.1
lcsStatusChargingTimeTableEntryIfc OBJECT-TYPE
    SYNTAX     INTEGER {
                  eRouterDslBroadband (1),
                  eRouterSerial (2),
                  eLancapi (3),
                  eAb1 (4),
                  eAb2 (5),
                  eAb3 (6),
                  eAb4 (7),
                  eTimeModul (255)
            }
    MAX-ACCESS read-only
    STATUS     current
    DESCRIPTION
            ""
    ::= { lcsStatusChargingTimeTableEntry 1 }

-- {COLUMN} 1.3.6.1.4.1.2356.11.1.24.2.1.2
lcsStatusChargingTimeTableEntryBudgetMinutes OBJECT-TYPE
    SYNTAX     Integer32 (0..2147483647)
    MAX-ACCESS read-only
    STATUS     current
    DESCRIPTION
            ""
    ::= { lcsStatusChargingTimeTableEntry 2 }

-- {COLUMN} 1.3.6.1.4.1.2356.11.1.24.2.1.3
lcsStatusChargingTimeTableEntrySpareMinutes OBJECT-TYPE
    SYNTAX     Integer32 (0..2147483647)
    MAX-ACCESS read-only
    STATUS     current
    DESCRIPTION
            ""
    ::= { lcsStatusChargingTimeTableEntry 3 }

-- {COLUMN} 1.3.6.1.4.1.2356.11.1.24.2.1.4
lcsStatusChargingTimeTableEntryMinutesActive OBJECT-TYPE
    SYNTAX     Integer32 (0..2147483647)
    MAX-ACCESS read-only
    STATUS     current
    DESCRIPTION
            ""
    ::= { lcsStatusChargingTimeTableEntry 4 }

-- {COLUMN} 1.3.6.1.4.1.2356.11.1.24.2.1.5
lcsStatusChargingTimeTableEntryMinutesPassive OBJECT-TYPE
    SYNTAX     Integer32 (0..2147483647)
    MAX-ACCESS read-only
    STATUS     current
    DESCRIPTION
            ""
    ::= { lcsStatusChargingTimeTableEntry 5 }

-- {SCALAR} 1.3.6.1.4.1.2356.11.1.24.3
lcsStatusChargingDeleteValues OBJECT-TYPE
    SYNTAX     DisplayString
    MAX-ACCESS read-write
    STATUS     current
    DESCRIPTION
            ""
    ::= { lcsStatusCharging 3 }

-- {SCALAR} 1.3.6.1.4.1.2356.11.1.24.4
lcsStatusChargingSpareUnits OBJECT-TYPE
    SYNTAX     Integer32 (0..65535)
    MAX-ACCESS read-only
    STATUS     current
    DESCRIPTION
            ""
    ::= { lcsStatusCharging 4 }

-- {TABLE} 1.3.6.1.4.1.2356.11.1.24.5
lcsStatusChargingTableBudgetTable OBJECT-TYPE
    SYNTAX     SEQUENCE OF LcsStatusChargingTableBudgetEntry
    MAX-ACCESS not-accessible
    STATUS     current
    DESCRIPTION
            ""
    ::= { lcsStatusCharging 5 }

-- {ROW} 1.3.6.1.4.1.2356.11.1.24.5.1
lcsStatusChargingTableBudgetEntry OBJECT-TYPE
    SYNTAX     LcsStatusChargingTableBudgetEntry
    MAX-ACCESS not-accessible
    STATUS     current
    DESCRIPTION
            ""
    INDEX {
            lcsStatusChargingTableBudgetEntryIfc
          }
    ::= { lcsStatusChargingTableBudgetTable 1 }

LcsStatusChargingTableBudgetEntry ::= SEQUENCE {
            lcsStatusChargingTableBudgetEntryIfc INTEGER,
            lcsStatusChargingTableBudgetEntryBudgetUnits Integer32,
            lcsStatusChargingTableBudgetEntrySpareBudget Integer32,
            lcsStatusChargingTableBudgetEntryTotalUnits Integer32
    }

-- {COLUMN} 1.3.6.1.4.1.2356.11.1.24.5.1.1
lcsStatusChargingTableBudgetEntryIfc OBJECT-TYPE
    SYNTAX     INTEGER {
                  eRouterSerial (1),
                  eLancapi (2),
                  eAb1 (3),
                  eAb2 (4),
                  eAb3 (5),
                  eAb4 (6),
                  eTimeModul (255)
            }
    MAX-ACCESS read-only
    STATUS     current
    DESCRIPTION
            ""
    ::= { lcsStatusChargingTableBudgetEntry 1 }

-- {COLUMN} 1.3.6.1.4.1.2356.11.1.24.5.1.2
lcsStatusChargingTableBudgetEntryBudgetUnits OBJECT-TYPE
    SYNTAX     Integer32 (0..65535)
    MAX-ACCESS read-only
    STATUS     current
    DESCRIPTION
            ""
    ::= { lcsStatusChargingTableBudgetEntry 2 }

-- {COLUMN} 1.3.6.1.4.1.2356.11.1.24.5.1.3
lcsStatusChargingTableBudgetEntrySpareBudget OBJECT-TYPE
    SYNTAX     Integer32 (0..65535)
    MAX-ACCESS read-only
    STATUS     current
    DESCRIPTION
            ""
    ::= { lcsStatusChargingTableBudgetEntry 3 }

-- {COLUMN} 1.3.6.1.4.1.2356.11.1.24.5.1.4
lcsStatusChargingTableBudgetEntryTotalUnits OBJECT-TYPE
    SYNTAX     Integer32 (0..2147483647)
    MAX-ACCESS read-only
    STATUS     current
    DESCRIPTION
            ""
    ::= { lcsStatusChargingTableBudgetEntry 4 }

-- {SCALAR} 1.3.6.1.4.1.2356.11.1.24.6
lcsStatusChargingSpareDaysPerPeriod OBJECT-TYPE
    SYNTAX     Integer32 (0..65535)
    MAX-ACCESS read-only
    STATUS     current
    DESCRIPTION
            ""
    ::= { lcsStatusCharging 6 }

-- {SCALAR} 1.3.6.1.4.1.2356.11.1.24.7
lcsStatusChargingRouterUnits OBJECT-TYPE
    SYNTAX     Integer32 (0..2147483647)
    MAX-ACCESS read-only
    STATUS     current
    DESCRIPTION
            ""
    ::= { lcsStatusCharging 7 }

-- {SCALAR} 1.3.6.1.4.1.2356.11.1.24.8
lcsStatusChargingTotalUnits OBJECT-TYPE
    SYNTAX     Integer32 (0..2147483647)
    MAX-ACCESS read-only
    STATUS     current
    DESCRIPTION
            ""
    ::= { lcsStatusCharging 8 }

-- {SCALAR} 1.3.6.1.4.1.2356.11.1.24.9
lcsStatusChargingRouterDslBroadbandMinutesActive OBJECT-TYPE
    SYNTAX     Integer32 (0..2147483647)
    MAX-ACCESS read-only
    STATUS     current
    DESCRIPTION
            ""
    ::= { lcsStatusCharging 9 }

-- {SCALAR} 1.3.6.1.4.1.2356.11.1.24.10
lcsStatusChargingSpareDialupMinutes OBJECT-TYPE
    SYNTAX     Integer32 (0..2147483647)
    MAX-ACCESS read-only
    STATUS     current
    DESCRIPTION
            ""
    ::= { lcsStatusCharging 10 }

-- {SCALAR} 1.3.6.1.4.1.2356.11.1.24.11
lcsStatusChargingDialupMinutesActive OBJECT-TYPE
    SYNTAX     Integer32 (0..2147483647)
    MAX-ACCESS read-only
    STATUS     current
    DESCRIPTION
            ""
    ::= { lcsStatusCharging 11 }

-- {TABLE} 1.3.6.1.4.1.2356.11.1.24.12
lcsStatusChargingVolumeBudgetsTable OBJECT-TYPE
    SYNTAX     SEQUENCE OF LcsStatusChargingVolumeBudgetsEntry
    MAX-ACCESS not-accessible
    STATUS     current
    DESCRIPTION
            "-- empty --"
    ::= { lcsStatusCharging 12 }

-- {ROW} 1.3.6.1.4.1.2356.11.1.24.12.1
lcsStatusChargingVolumeBudgetsEntry OBJECT-TYPE
    SYNTAX     LcsStatusChargingVolumeBudgetsEntry
    MAX-ACCESS not-accessible
    STATUS     current
    DESCRIPTION
            ""
    INDEX {
            lcsStatusChargingVolumeBudgetsEntryPeer
          }
    ::= { lcsStatusChargingVolumeBudgetsTable 1 }

LcsStatusChargingVolumeBudgetsEntry ::= SEQUENCE {
            lcsStatusChargingVolumeBudgetsEntryPeer DisplayString,
            lcsStatusChargingVolumeBudgetsEntryDataMb Integer32,
            lcsStatusChargingVolumeBudgetsEntryDataKb Integer32,
            lcsStatusChargingVolumeBudgetsEntryLimitMb Integer32,
            lcsStatusChargingVolumeBudgetsEntryPercent Integer32,
            lcsStatusChargingVolumeBudgetsEntryFlags BITS,
            lcsStatusChargingVolumeBudgetsEntryMonth Integer32,
            lcsStatusChargingVolumeBudgetsEntryYear Integer32
    }

-- {COLUMN} 1.3.6.1.4.1.2356.11.1.24.12.1.1
lcsStatusChargingVolumeBudgetsEntryPeer OBJECT-TYPE
    SYNTAX     DisplayString (SIZE(0..16))
    MAX-ACCESS read-only
    STATUS     current
    DESCRIPTION
            "-- empty --"
    ::= { lcsStatusChargingVolumeBudgetsEntry 1 }

-- {COLUMN} 1.3.6.1.4.1.2356.11.1.24.12.1.2
lcsStatusChargingVolumeBudgetsEntryDataMb OBJECT-TYPE
    SYNTAX     Integer32 (0..2147483647)
    MAX-ACCESS read-only
    STATUS     current
    DESCRIPTION
            "-- empty --"
    ::= { lcsStatusChargingVolumeBudgetsEntry 2 }

-- {COLUMN} 1.3.6.1.4.1.2356.11.1.24.12.1.3
lcsStatusChargingVolumeBudgetsEntryDataKb OBJECT-TYPE
    SYNTAX     Integer32 (0..2147483647)
    MAX-ACCESS read-only
    STATUS     current
    DESCRIPTION
            "-- empty --"
    ::= { lcsStatusChargingVolumeBudgetsEntry 3 }

-- {COLUMN} 1.3.6.1.4.1.2356.11.1.24.12.1.4
lcsStatusChargingVolumeBudgetsEntryLimitMb OBJECT-TYPE
    SYNTAX     Integer32 (0..2147483647)
    MAX-ACCESS read-only
    STATUS     current
    DESCRIPTION
            "-- empty --"
    ::= { lcsStatusChargingVolumeBudgetsEntry 4 }

-- {COLUMN} 1.3.6.1.4.1.2356.11.1.24.12.1.5
lcsStatusChargingVolumeBudgetsEntryPercent OBJECT-TYPE
    SYNTAX     Integer32 (0..2147483647)
    MAX-ACCESS read-only
    STATUS     current
    DESCRIPTION
            "-- empty --"
    ::= { lcsStatusChargingVolumeBudgetsEntry 5 }

-- {COLUMN} 1.3.6.1.4.1.2356.11.1.24.12.1.6
lcsStatusChargingVolumeBudgetsEntryFlags OBJECT-TYPE
    SYNTAX     BITS {
                  eChargeLocked (5),
                  eExhausted (6),
                  eAlert (7)
            }
    MAX-ACCESS read-write
    STATUS     current
    DESCRIPTION
            "-- empty --"
    ::= { lcsStatusChargingVolumeBudgetsEntry 6 }

-- {COLUMN} 1.3.6.1.4.1.2356.11.1.24.12.1.7
lcsStatusChargingVolumeBudgetsEntryMonth OBJECT-TYPE
    SYNTAX     Integer32 (0..255)
    MAX-ACCESS read-only
    STATUS     current
    DESCRIPTION
            "-- empty --"
    ::= { lcsStatusChargingVolumeBudgetsEntry 7 }

-- {COLUMN} 1.3.6.1.4.1.2356.11.1.24.12.1.8
lcsStatusChargingVolumeBudgetsEntryYear OBJECT-TYPE
    SYNTAX     Integer32 (0..2147483647)
    MAX-ACCESS read-only
    STATUS     current
    DESCRIPTION
            "-- empty --"
    ::= { lcsStatusChargingVolumeBudgetsEntry 8 }

-- {TABLE} 1.3.6.1.4.1.2356.11.1.24.13
lcsStatusChargingArchiveTable OBJECT-TYPE
    SYNTAX     SEQUENCE OF LcsStatusChargingArchiveEntry
    MAX-ACCESS not-accessible
    STATUS     current
    DESCRIPTION
            "-- empty --"
    ::= { lcsStatusCharging 13 }

-- {ROW} 1.3.6.1.4.1.2356.11.1.24.13.1
lcsStatusChargingArchiveEntry OBJECT-TYPE
    SYNTAX     LcsStatusChargingArchiveEntry
    MAX-ACCESS not-accessible
    STATUS     current
    DESCRIPTION
            ""
    INDEX {
            lcsStatusChargingArchiveEntryPeer
          }
    ::= { lcsStatusChargingArchiveTable 1 }

LcsStatusChargingArchiveEntry ::= SEQUENCE {
            lcsStatusChargingArchiveEntryPeer DisplayString,
            lcsStatusChargingArchiveEntryCurrMonth Integer32,
            lcsStatusChargingArchiveEntryCurrYear Integer32,
            lcsStatusChargingArchiveEntryCurrLimit Integer32,
            lcsStatusChargingArchiveEntryCurrFlags Integer32,
            lcsStatusChargingArchiveEntryMbJan Integer32,
            lcsStatusChargingArchiveEntryKbJan Integer32,
            lcsStatusChargingArchiveEntryMbFeb Integer32,
            lcsStatusChargingArchiveEntryKbFeb Integer32,
            lcsStatusChargingArchiveEntryMbMar Integer32,
            lcsStatusChargingArchiveEntryKbMar Integer32,
            lcsStatusChargingArchiveEntryMbApr Integer32,
            lcsStatusChargingArchiveEntryKbApr Integer32,
            lcsStatusChargingArchiveEntryMbMay Integer32,
            lcsStatusChargingArchiveEntryKbMay Integer32,
            lcsStatusChargingArchiveEntryMbJun Integer32,
            lcsStatusChargingArchiveEntryKbJun Integer32,
            lcsStatusChargingArchiveEntryMbJul Integer32,
            lcsStatusChargingArchiveEntryKbJul Integer32,
            lcsStatusChargingArchiveEntryMbAug Integer32,
            lcsStatusChargingArchiveEntryKbAug Integer32,
            lcsStatusChargingArchiveEntryMbSep Integer32,
            lcsStatusChargingArchiveEntryKbSep Integer32,
            lcsStatusChargingArchiveEntryMbOct Integer32,
            lcsStatusChargingArchiveEntryKbOct Integer32,
            lcsStatusChargingArchiveEntryMbNov Integer32,
            lcsStatusChargingArchiveEntryKbNov Integer32,
            lcsStatusChargingArchiveEntryMbDec Integer32,
            lcsStatusChargingArchiveEntryKbDec Integer32
    }

-- {COLUMN} 1.3.6.1.4.1.2356.11.1.24.13.1.1
lcsStatusChargingArchiveEntryPeer OBJECT-TYPE
    SYNTAX     DisplayString (SIZE(0..16))
    MAX-ACCESS read-only
    STATUS     current
    DESCRIPTION
            "-- empty --"
    ::= { lcsStatusChargingArchiveEntry 1 }

-- {COLUMN} 1.3.6.1.4.1.2356.11.1.24.13.1.2
lcsStatusChargingArchiveEntryCurrMonth OBJECT-TYPE
    SYNTAX     Integer32 (0..65535)
    MAX-ACCESS read-only
    STATUS     current
    DESCRIPTION
            "-- empty --"
    ::= { lcsStatusChargingArchiveEntry 2 }

-- {COLUMN} 1.3.6.1.4.1.2356.11.1.24.13.1.3
lcsStatusChargingArchiveEntryCurrYear OBJECT-TYPE
    SYNTAX     Integer32 (0..65535)
    MAX-ACCESS read-only
    STATUS     current
    DESCRIPTION
            "-- empty --"
    ::= { lcsStatusChargingArchiveEntry 3 }

-- {COLUMN} 1.3.6.1.4.1.2356.11.1.24.13.1.4
lcsStatusChargingArchiveEntryCurrLimit OBJECT-TYPE
    SYNTAX     Integer32 (0..2147483647)
    MAX-ACCESS read-only
    STATUS     current
    DESCRIPTION
            "-- empty --"
    ::= { lcsStatusChargingArchiveEntry 4 }

-- {COLUMN} 1.3.6.1.4.1.2356.11.1.24.13.1.5
lcsStatusChargingArchiveEntryCurrFlags OBJECT-TYPE
    SYNTAX     Integer32 (0..255)
    MAX-ACCESS read-only
    STATUS     current
    DESCRIPTION
            "-- empty --"
    ::= { lcsStatusChargingArchiveEntry 5 }

-- {COLUMN} 1.3.6.1.4.1.2356.11.1.24.13.1.6
lcsStatusChargingArchiveEntryMbJan OBJECT-TYPE
    SYNTAX     Integer32 (0..2147483647)
    MAX-ACCESS read-only
    STATUS     current
    DESCRIPTION
            "-- empty --"
    ::= { lcsStatusChargingArchiveEntry 6 }

-- {COLUMN} 1.3.6.1.4.1.2356.11.1.24.13.1.7
lcsStatusChargingArchiveEntryKbJan OBJECT-TYPE
    SYNTAX     Integer32 (0..2147483647)
    MAX-ACCESS read-only
    STATUS     current
    DESCRIPTION
            "-- empty --"
    ::= { lcsStatusChargingArchiveEntry 7 }

-- {COLUMN} 1.3.6.1.4.1.2356.11.1.24.13.1.8
lcsStatusChargingArchiveEntryMbFeb OBJECT-TYPE
    SYNTAX     Integer32 (0..2147483647)
    MAX-ACCESS read-only
    STATUS     current
    DESCRIPTION
            "-- empty --"
    ::= { lcsStatusChargingArchiveEntry 8 }

-- {COLUMN} 1.3.6.1.4.1.2356.11.1.24.13.1.9
lcsStatusChargingArchiveEntryKbFeb OBJECT-TYPE
    SYNTAX     Integer32 (0..2147483647)
    MAX-ACCESS read-only
    STATUS     current
    DESCRIPTION
            "-- empty --"
    ::= { lcsStatusChargingArchiveEntry 9 }

-- {COLUMN} 1.3.6.1.4.1.2356.11.1.24.13.1.10
lcsStatusChargingArchiveEntryMbMar OBJECT-TYPE
    SYNTAX     Integer32 (0..2147483647)
    MAX-ACCESS read-only
    STATUS     current
    DESCRIPTION
            "-- empty --"
    ::= { lcsStatusChargingArchiveEntry 10 }

-- {COLUMN} 1.3.6.1.4.1.2356.11.1.24.13.1.11
lcsStatusChargingArchiveEntryKbMar OBJECT-TYPE
    SYNTAX     Integer32 (0..2147483647)
    MAX-ACCESS read-only
    STATUS     current
    DESCRIPTION
            "-- empty --"
    ::= { lcsStatusChargingArchiveEntry 11 }

-- {COLUMN} 1.3.6.1.4.1.2356.11.1.24.13.1.12
lcsStatusChargingArchiveEntryMbApr OBJECT-TYPE
    SYNTAX     Integer32 (0..2147483647)
    MAX-ACCESS read-only
    STATUS     current
    DESCRIPTION
            "-- empty --"
    ::= { lcsStatusChargingArchiveEntry 12 }

-- {COLUMN} 1.3.6.1.4.1.2356.11.1.24.13.1.13
lcsStatusChargingArchiveEntryKbApr OBJECT-TYPE
    SYNTAX     Integer32 (0..2147483647)
    MAX-ACCESS read-only
    STATUS     current
    DESCRIPTION
            "-- empty --"
    ::= { lcsStatusChargingArchiveEntry 13 }

-- {COLUMN} 1.3.6.1.4.1.2356.11.1.24.13.1.14
lcsStatusChargingArchiveEntryMbMay OBJECT-TYPE
    SYNTAX     Integer32 (0..2147483647)
    MAX-ACCESS read-only
    STATUS     current
    DESCRIPTION
            "-- empty --"
    ::= { lcsStatusChargingArchiveEntry 14 }

-- {COLUMN} 1.3.6.1.4.1.2356.11.1.24.13.1.15
lcsStatusChargingArchiveEntryKbMay OBJECT-TYPE
    SYNTAX     Integer32 (0..2147483647)
    MAX-ACCESS read-only
    STATUS     current
    DESCRIPTION
            "-- empty --"
    ::= { lcsStatusChargingArchiveEntry 15 }

-- {COLUMN} 1.3.6.1.4.1.2356.11.1.24.13.1.16
lcsStatusChargingArchiveEntryMbJun OBJECT-TYPE
    SYNTAX     Integer32 (0..2147483647)
    MAX-ACCESS read-only
    STATUS     current
    DESCRIPTION
            "-- empty --"
    ::= { lcsStatusChargingArchiveEntry 16 }

-- {COLUMN} 1.3.6.1.4.1.2356.11.1.24.13.1.17
lcsStatusChargingArchiveEntryKbJun OBJECT-TYPE
    SYNTAX     Integer32 (0..2147483647)
    MAX-ACCESS read-only
    STATUS     current
    DESCRIPTION
            "-- empty --"
    ::= { lcsStatusChargingArchiveEntry 17 }

-- {COLUMN} 1.3.6.1.4.1.2356.11.1.24.13.1.18
lcsStatusChargingArchiveEntryMbJul OBJECT-TYPE
    SYNTAX     Integer32 (0..2147483647)
    MAX-ACCESS read-only
    STATUS     current
    DESCRIPTION
            "-- empty --"
    ::= { lcsStatusChargingArchiveEntry 18 }

-- {COLUMN} 1.3.6.1.4.1.2356.11.1.24.13.1.19
lcsStatusChargingArchiveEntryKbJul OBJECT-TYPE
    SYNTAX     Integer32 (0..2147483647)
    MAX-ACCESS read-only
    STATUS     current
    DESCRIPTION
            "-- empty --"
    ::= { lcsStatusChargingArchiveEntry 19 }

-- {COLUMN} 1.3.6.1.4.1.2356.11.1.24.13.1.20
lcsStatusChargingArchiveEntryMbAug OBJECT-TYPE
    SYNTAX     Integer32 (0..2147483647)
    MAX-ACCESS read-only
    STATUS     current
    DESCRIPTION
            "-- empty --"
    ::= { lcsStatusChargingArchiveEntry 20 }

-- {COLUMN} 1.3.6.1.4.1.2356.11.1.24.13.1.21
lcsStatusChargingArchiveEntryKbAug OBJECT-TYPE
    SYNTAX     Integer32 (0..2147483647)
    MAX-ACCESS read-only
    STATUS     current
    DESCRIPTION
            "-- empty --"
    ::= { lcsStatusChargingArchiveEntry 21 }

-- {COLUMN} 1.3.6.1.4.1.2356.11.1.24.13.1.22
lcsStatusChargingArchiveEntryMbSep OBJECT-TYPE
    SYNTAX     Integer32 (0..2147483647)
    MAX-ACCESS read-only
    STATUS     current
    DESCRIPTION
            "-- empty --"
    ::= { lcsStatusChargingArchiveEntry 22 }

-- {COLUMN} 1.3.6.1.4.1.2356.11.1.24.13.1.23
lcsStatusChargingArchiveEntryKbSep OBJECT-TYPE
    SYNTAX     Integer32 (0..2147483647)
    MAX-ACCESS read-only
    STATUS     current
    DESCRIPTION
            "-- empty --"
    ::= { lcsStatusChargingArchiveEntry 23 }

-- {COLUMN} 1.3.6.1.4.1.2356.11.1.24.13.1.24
lcsStatusChargingArchiveEntryMbOct OBJECT-TYPE
    SYNTAX     Integer32 (0..2147483647)
    MAX-ACCESS read-only
    STATUS     current
    DESCRIPTION
            "-- empty --"
    ::= { lcsStatusChargingArchiveEntry 24 }

-- {COLUMN} 1.3.6.1.4.1.2356.11.1.24.13.1.25
lcsStatusChargingArchiveEntryKbOct OBJECT-TYPE
    SYNTAX     Integer32 (0..2147483647)
    MAX-ACCESS read-only
    STATUS     current
    DESCRIPTION
            "-- empty --"
    ::= { lcsStatusChargingArchiveEntry 25 }

-- {COLUMN} 1.3.6.1.4.1.2356.11.1.24.13.1.26
lcsStatusChargingArchiveEntryMbNov OBJECT-TYPE
    SYNTAX     Integer32 (0..2147483647)
    MAX-ACCESS read-only
    STATUS     current
    DESCRIPTION
            "-- empty --"
    ::= { lcsStatusChargingArchiveEntry 26 }

-- {COLUMN} 1.3.6.1.4.1.2356.11.1.24.13.1.27
lcsStatusChargingArchiveEntryKbNov OBJECT-TYPE
    SYNTAX     Integer32 (0..2147483647)
    MAX-ACCESS read-only
    STATUS     current
    DESCRIPTION
            "-- empty --"
    ::= { lcsStatusChargingArchiveEntry 27 }

-- {COLUMN} 1.3.6.1.4.1.2356.11.1.24.13.1.28
lcsStatusChargingArchiveEntryMbDec OBJECT-TYPE
    SYNTAX     Integer32 (0..2147483647)
    MAX-ACCESS read-only
    STATUS     current
    DESCRIPTION
            "-- empty --"
    ::= { lcsStatusChargingArchiveEntry 28 }

-- {COLUMN} 1.3.6.1.4.1.2356.11.1.24.13.1.29
lcsStatusChargingArchiveEntryKbDec OBJECT-TYPE
    SYNTAX     Integer32 (0..2147483647)
    MAX-ACCESS read-only
    STATUS     current
    DESCRIPTION
            "-- empty --"
    ::= { lcsStatusChargingArchiveEntry 29 }

-- {SCALAR} 1.3.6.1.4.1.2356.11.1.24.14
lcsStatusChargingClearArchive OBJECT-TYPE
    SYNTAX     DisplayString
    MAX-ACCESS read-write
    STATUS     current
    DESCRIPTION
            "-- empty --"
    ::= { lcsStatusCharging 14 }

-- {SCALAR} 1.3.6.1.4.1.2356.11.1.24.15
lcsStatusChargingActivateAdditionalBudget OBJECT-TYPE
    SYNTAX     DisplayString
    MAX-ACCESS read-write
    STATUS     current
    DESCRIPTION
            "-- empty --"
    ::= { lcsStatusCharging 15 }

-- {NODE} 1.3.6.1.4.1.2356.11.1.24.31
lcsStatusChargingPppoe OBJECT IDENTIFIER ::= { lcsStatusCharging 31 }

-- {SCALAR} 1.3.6.1.4.1.2356.11.1.24.31.1
lcsStatusChargingPppoeTxPadi OBJECT-TYPE
    SYNTAX     Integer32 (0..2147483647)
    MAX-ACCESS read-only
    STATUS     current
    DESCRIPTION
            ""
    ::= { lcsStatusChargingPppoe 1 }

-- {SCALAR} 1.3.6.1.4.1.2356.11.1.24.31.2
lcsStatusChargingPppoeRxPado OBJECT-TYPE
    SYNTAX     Integer32 (0..2147483647)
    MAX-ACCESS read-only
    STATUS     current
    DESCRIPTION
            ""
    ::= { lcsStatusChargingPppoe 2 }

-- {SCALAR} 1.3.6.1.4.1.2356.11.1.24.31.3
lcsStatusChargingPppoeTxPadr OBJECT-TYPE
    SYNTAX     Integer32 (0..2147483647)
    MAX-ACCESS read-only
    STATUS     current
    DESCRIPTION
            ""
    ::= { lcsStatusChargingPppoe 3 }

-- {SCALAR} 1.3.6.1.4.1.2356.11.1.24.31.4
lcsStatusChargingPppoeRxPads OBJECT-TYPE
    SYNTAX     Integer32 (0..2147483647)
    MAX-ACCESS read-only
    STATUS     current
    DESCRIPTION
            ""
    ::= { lcsStatusChargingPppoe 4 }

-- {SCALAR} 1.3.6.1.4.1.2356.11.1.24.31.5
lcsStatusChargingPppoeTxPadt OBJECT-TYPE
    SYNTAX     Integer32 (0..2147483647)
    MAX-ACCESS read-only
    STATUS     current
    DESCRIPTION
            ""
    ::= { lcsStatusChargingPppoe 5 }

-- {SCALAR} 1.3.6.1.4.1.2356.11.1.24.31.6
lcsStatusChargingPppoeRxPadt OBJECT-TYPE
    SYNTAX     Integer32 (0..2147483647)
    MAX-ACCESS read-only
    STATUS     current
    DESCRIPTION
            ""
    ::= { lcsStatusChargingPppoe 6 }

-- {SCALAR} 1.3.6.1.4.1.2356.11.1.24.31.7
lcsStatusChargingPppoeTxProtocol OBJECT-TYPE
    SYNTAX     Integer32 (0..2147483647)
    MAX-ACCESS read-only
    STATUS     current
    DESCRIPTION
            ""
    ::= { lcsStatusChargingPppoe 7 }

-- {SCALAR} 1.3.6.1.4.1.2356.11.1.24.31.8
lcsStatusChargingPppoeRxProtocol OBJECT-TYPE
    SYNTAX     Integer32 (0..2147483647)
    MAX-ACCESS read-only
    STATUS     current
    DESCRIPTION
            ""
    ::= { lcsStatusChargingPppoe 8 }

-- {SCALAR} 1.3.6.1.4.1.2356.11.1.24.31.9
lcsStatusChargingPppoeTxData OBJECT-TYPE
    SYNTAX     Integer32 (0..2147483647)
    MAX-ACCESS read-only
    STATUS     current
    DESCRIPTION
            ""
    ::= { lcsStatusChargingPppoe 9 }

-- {SCALAR} 1.3.6.1.4.1.2356.11.1.24.31.10
lcsStatusChargingPppoeRxData OBJECT-TYPE
    SYNTAX     Integer32 (0..2147483647)
    MAX-ACCESS read-only
    STATUS     current
    DESCRIPTION
            ""
    ::= { lcsStatusChargingPppoe 10 }

-- {SCALAR} 1.3.6.1.4.1.2356.11.1.24.31.11
lcsStatusChargingPppoeRxBad OBJECT-TYPE
    SYNTAX     Integer32 (0..2147483647)
    MAX-ACCESS read-only
    STATUS     current
    DESCRIPTION
            ""
    ::= { lcsStatusChargingPppoe 11 }

-- {SCALAR} 1.3.6.1.4.1.2356.11.1.24.31.12
lcsStatusChargingPppoeAcName OBJECT-TYPE
    SYNTAX     DisplayString (SIZE(0..63))
    MAX-ACCESS read-only
    STATUS     current
    DESCRIPTION
            ""
    ::= { lcsStatusChargingPppoe 12 }

-- {SCALAR} 1.3.6.1.4.1.2356.11.1.24.31.13
lcsStatusChargingPppoeService OBJECT-TYPE
    SYNTAX     DisplayString (SIZE(0..63))
    MAX-ACCESS read-only
    STATUS     current
    DESCRIPTION
            ""
    ::= { lcsStatusChargingPppoe 13 }

-- {SCALAR} 1.3.6.1.4.1.2356.11.1.24.31.30
lcsStatusChargingPppoeDeleteValues OBJECT-TYPE
    SYNTAX     DisplayString
    MAX-ACCESS read-write
    STATUS     current
    DESCRIPTION
            ""
    ::= { lcsStatusChargingPppoe 30 }

-- {NODE} 1.3.6.1.4.1.2356.11.1.25
lcsStatusDslol OBJECT IDENTIFIER ::= { lcsStatus 25 }

-- {SCALAR} 1.3.6.1.4.1.2356.11.1.25.1
lcsStatusDslolRxPackets OBJECT-TYPE
    SYNTAX     Counter32
    MAX-ACCESS read-only
    STATUS     current
    DESCRIPTION
            ""
    ::= { lcsStatusDslol 1 }

-- {SCALAR} 1.3.6.1.4.1.2356.11.1.25.2
lcsStatusDslolTxPackets OBJECT-TYPE
    SYNTAX     Counter32
    MAX-ACCESS read-only
    STATUS     current
    DESCRIPTION
            ""
    ::= { lcsStatusDslol 2 }

-- {SCALAR} 1.3.6.1.4.1.2356.11.1.25.3
lcsStatusDslolRxErrors OBJECT-TYPE
    SYNTAX     Counter32
    MAX-ACCESS read-only
    STATUS     current
    DESCRIPTION
            ""
    ::= { lcsStatusDslol 3 }

-- {SCALAR} 1.3.6.1.4.1.2356.11.1.25.4
lcsStatusDslolTxErrors OBJECT-TYPE
    SYNTAX     Counter32
    MAX-ACCESS read-only
    STATUS     current
    DESCRIPTION
            ""
    ::= { lcsStatusDslol 4 }

-- {SCALAR} 1.3.6.1.4.1.2356.11.1.25.5
lcsStatusDslolRxNoConnection OBJECT-TYPE
    SYNTAX     Counter32
    MAX-ACCESS read-only
    STATUS     current
    DESCRIPTION
            ""
    ::= { lcsStatusDslol 5 }

-- {SCALAR} 1.3.6.1.4.1.2356.11.1.25.6
lcsStatusDslolNicErrors OBJECT-TYPE
    SYNTAX     Counter32
    MAX-ACCESS read-only
    STATUS     current
    DESCRIPTION
            ""
    ::= { lcsStatusDslol 6 }

-- {SCALAR} 1.3.6.1.4.1.2356.11.1.25.7
lcsStatusDslolQueuePackets OBJECT-TYPE
    SYNTAX     Integer32 (0..2147483647)
    MAX-ACCESS read-only
    STATUS     current
    DESCRIPTION
            ""
    ::= { lcsStatusDslol 7 }

-- {SCALAR} 1.3.6.1.4.1.2356.11.1.25.8
lcsStatusDslolQueueErrors OBJECT-TYPE
    SYNTAX     Counter32
    MAX-ACCESS read-only
    STATUS     current
    DESCRIPTION
            ""
    ::= { lcsStatusDslol 8 }

-- {SCALAR} 1.3.6.1.4.1.2356.11.1.25.9
lcsStatusDslolRxBytes OBJECT-TYPE
    SYNTAX     Counter64
    MAX-ACCESS read-only
    STATUS     current
    DESCRIPTION
            ""
    ::= { lcsStatusDslol 9 }

-- {SCALAR} 1.3.6.1.4.1.2356.11.1.25.10
lcsStatusDslolTxBytes OBJECT-TYPE
    SYNTAX     Counter64
    MAX-ACCESS read-only
    STATUS     current
    DESCRIPTION
            ""
    ::= { lcsStatusDslol 10 }

-- {SCALAR} 1.3.6.1.4.1.2356.11.1.25.11
lcsStatusDslolRxUnicasts OBJECT-TYPE
    SYNTAX     Counter32
    MAX-ACCESS read-only
    STATUS     current
    DESCRIPTION
            ""
    ::= { lcsStatusDslol 11 }

-- {SCALAR} 1.3.6.1.4.1.2356.11.1.25.12
lcsStatusDslolTxBroadcasts OBJECT-TYPE
    SYNTAX     Counter32
    MAX-ACCESS read-only
    STATUS     current
    DESCRIPTION
            ""
    ::= { lcsStatusDslol 12 }

-- {SCALAR} 1.3.6.1.4.1.2356.11.1.25.13
lcsStatusDslolTxUnicasts OBJECT-TYPE
    SYNTAX     Counter32
    MAX-ACCESS read-only
    STATUS     current
    DESCRIPTION
            ""
    ::= { lcsStatusDslol 13 }

-- {SCALAR} 1.3.6.1.4.1.2356.11.1.25.14
lcsStatusDslolLinkActive OBJECT-TYPE
    SYNTAX     INTEGER {
                  eNo (0),
                  eYes (1)
            }
    MAX-ACCESS read-only
    STATUS     current
    DESCRIPTION
            ""
    ::= { lcsStatusDslol 14 }

-- {SCALAR} 1.3.6.1.4.1.2356.11.1.25.17
lcsStatusDslolRxCrcErrors OBJECT-TYPE
    SYNTAX     Counter32
    MAX-ACCESS read-only
    STATUS     current
    DESCRIPTION
            ""
    ::= { lcsStatusDslol 17 }

-- {SCALAR} 1.3.6.1.4.1.2356.11.1.25.18
lcsStatusDslolRxAlignErrors OBJECT-TYPE
    SYNTAX     Counter32
    MAX-ACCESS read-only
    STATUS     current
    DESCRIPTION
            ""
    ::= { lcsStatusDslol 18 }

-- {SCALAR} 1.3.6.1.4.1.2356.11.1.25.19
lcsStatusDslolCollisions OBJECT-TYPE
    SYNTAX     Counter32
    MAX-ACCESS read-only
    STATUS     current
    DESCRIPTION
            ""
    ::= { lcsStatusDslol 19 }

-- {SCALAR} 1.3.6.1.4.1.2356.11.1.25.20
lcsStatusDslolSingleCollisions OBJECT-TYPE
    SYNTAX     Counter32
    MAX-ACCESS read-only
    STATUS     current
    DESCRIPTION
            ""
    ::= { lcsStatusDslol 20 }

-- {SCALAR} 1.3.6.1.4.1.2356.11.1.25.21
lcsStatusDslolMultipleCollisions OBJECT-TYPE
    SYNTAX     Counter32
    MAX-ACCESS read-only
    STATUS     current
    DESCRIPTION
            ""
    ::= { lcsStatusDslol 21 }

-- {SCALAR} 1.3.6.1.4.1.2356.11.1.25.22
lcsStatusDslolLateCollisions OBJECT-TYPE
    SYNTAX     Counter32
    MAX-ACCESS read-only
    STATUS     current
    DESCRIPTION
            ""
    ::= { lcsStatusDslol 22 }

-- {SCALAR} 1.3.6.1.4.1.2356.11.1.25.23
lcsStatusDslolExcessiveCollisions OBJECT-TYPE
    SYNTAX     Counter32
    MAX-ACCESS read-only
    STATUS     current
    DESCRIPTION
            ""
    ::= { lcsStatusDslol 23 }

-- {NODE} 1.3.6.1.4.1.2356.11.1.25.24
lcsStatusDslolDslol OBJECT IDENTIFIER ::= { lcsStatusDslol 24 }

-- {SCALAR} 1.3.6.1.4.1.2356.11.1.25.24.1
lcsStatusDslolDslolIpConfiguration OBJECT-TYPE
    SYNTAX     INTEGER {
                  eInvalid (0),
                  eValid (1)
            }
    MAX-ACCESS read-only
    STATUS     current
    DESCRIPTION
            ""
    ::= { lcsStatusDslolDslol 1 }

-- {SCALAR} 1.3.6.1.4.1.2356.11.1.25.24.2
lcsStatusDslolDslolIpNetwork OBJECT-TYPE
    SYNTAX     IpAddress
    MAX-ACCESS read-only
    STATUS     current
    DESCRIPTION
            ""
    ::= { lcsStatusDslolDslol 2 }

-- {SCALAR} 1.3.6.1.4.1.2356.11.1.25.24.3
lcsStatusDslolDslolIpNetmask OBJECT-TYPE
    SYNTAX     IpAddress
    MAX-ACCESS read-only
    STATUS     current
    DESCRIPTION
            ""
    ::= { lcsStatusDslolDslol 3 }

-- {SCALAR} 1.3.6.1.4.1.2356.11.1.25.24.4
lcsStatusDslolDslolGatewayIp OBJECT-TYPE
    SYNTAX     IpAddress
    MAX-ACCESS read-only
    STATUS     current
    DESCRIPTION
            ""
    ::= { lcsStatusDslolDslol 4 }

-- {SCALAR} 1.3.6.1.4.1.2356.11.1.25.24.5
lcsStatusDslolDslolGatewayMac OBJECT-TYPE
    SYNTAX     DisplayString (SIZE(0..12))
    MAX-ACCESS read-only
    STATUS     current
    DESCRIPTION
            ""
    ::= { lcsStatusDslolDslol 5 }

-- {SCALAR} 1.3.6.1.4.1.2356.11.1.25.24.6
lcsStatusDslolDslolCatchDhcp OBJECT-TYPE
    SYNTAX     INTEGER {
                  eNo (0),
                  eYes (1)
            }
    MAX-ACCESS read-only
    STATUS     current
    DESCRIPTION
            ""
    ::= { lcsStatusDslolDslol 6 }

-- {SCALAR} 1.3.6.1.4.1.2356.11.1.25.24.7
lcsStatusDslolDslolExclusiveMode OBJECT-TYPE
    SYNTAX     INTEGER {
                  eNo (0),
                  eYes (1)
            }
    MAX-ACCESS read-only
    STATUS     current
    DESCRIPTION
            ""
    ::= { lcsStatusDslolDslol 7 }

-- {SCALAR} 1.3.6.1.4.1.2356.11.1.25.25
lcsStatusDslolRxTooShort OBJECT-TYPE
    SYNTAX     Counter32
    MAX-ACCESS read-only
    STATUS     current
    DESCRIPTION
            ""
    ::= { lcsStatusDslol 25 }

-- {SCALAR} 1.3.6.1.4.1.2356.11.1.25.26
lcsStatusDslolRxTooLong OBJECT-TYPE
    SYNTAX     Counter32
    MAX-ACCESS read-only
    STATUS     current
    DESCRIPTION
            ""
    ::= { lcsStatusDslol 26 }

-- {SCALAR} 1.3.6.1.4.1.2356.11.1.25.27
lcsStatusDslolTxCarrier OBJECT-TYPE
    SYNTAX     Counter32
    MAX-ACCESS read-only
    STATUS     current
    DESCRIPTION
            ""
    ::= { lcsStatusDslol 27 }

-- {SCALAR} 1.3.6.1.4.1.2356.11.1.25.28
lcsStatusDslolTxDeferred OBJECT-TYPE
    SYNTAX     Counter32
    MAX-ACCESS read-only
    STATUS     current
    DESCRIPTION
            ""
    ::= { lcsStatusDslol 28 }

-- {SCALAR} 1.3.6.1.4.1.2356.11.1.25.30
lcsStatusDslolDeleteValues OBJECT-TYPE
    SYNTAX     DisplayString
    MAX-ACCESS read-write
    STATUS     current
    DESCRIPTION
            ""
    ::= { lcsStatusDslol 30 }

-- {NODE} 1.3.6.1.4.1.2356.11.1.25.31
lcsStatusDslolPppoe OBJECT IDENTIFIER ::= { lcsStatusDslol 31 }

-- {SCALAR} 1.3.6.1.4.1.2356.11.1.25.31.1
lcsStatusDslolPppoeTxPadi OBJECT-TYPE
    SYNTAX     Integer32 (0..2147483647)
    MAX-ACCESS read-only
    STATUS     current
    DESCRIPTION
            ""
    ::= { lcsStatusDslolPppoe 1 }

-- {SCALAR} 1.3.6.1.4.1.2356.11.1.25.31.2
lcsStatusDslolPppoeRxPado OBJECT-TYPE
    SYNTAX     Integer32 (0..2147483647)
    MAX-ACCESS read-only
    STATUS     current
    DESCRIPTION
            ""
    ::= { lcsStatusDslolPppoe 2 }

-- {SCALAR} 1.3.6.1.4.1.2356.11.1.25.31.3
lcsStatusDslolPppoeTxPadr OBJECT-TYPE
    SYNTAX     Integer32 (0..2147483647)
    MAX-ACCESS read-only
    STATUS     current
    DESCRIPTION
            ""
    ::= { lcsStatusDslolPppoe 3 }

-- {SCALAR} 1.3.6.1.4.1.2356.11.1.25.31.4
lcsStatusDslolPppoeRxPads OBJECT-TYPE
    SYNTAX     Integer32 (0..2147483647)
    MAX-ACCESS read-only
    STATUS     current
    DESCRIPTION
            ""
    ::= { lcsStatusDslolPppoe 4 }

-- {SCALAR} 1.3.6.1.4.1.2356.11.1.25.31.5
lcsStatusDslolPppoeTxPadt OBJECT-TYPE
    SYNTAX     Integer32 (0..2147483647)
    MAX-ACCESS read-only
    STATUS     current
    DESCRIPTION
            ""
    ::= { lcsStatusDslolPppoe 5 }

-- {SCALAR} 1.3.6.1.4.1.2356.11.1.25.31.6
lcsStatusDslolPppoeRxPadt OBJECT-TYPE
    SYNTAX     Integer32 (0..2147483647)
    MAX-ACCESS read-only
    STATUS     current
    DESCRIPTION
            ""
    ::= { lcsStatusDslolPppoe 6 }

-- {SCALAR} 1.3.6.1.4.1.2356.11.1.25.31.7
lcsStatusDslolPppoeTxProtocol OBJECT-TYPE
    SYNTAX     Integer32 (0..2147483647)
    MAX-ACCESS read-only
    STATUS     current
    DESCRIPTION
            ""
    ::= { lcsStatusDslolPppoe 7 }

-- {SCALAR} 1.3.6.1.4.1.2356.11.1.25.31.8
lcsStatusDslolPppoeRxProtocol OBJECT-TYPE
    SYNTAX     Integer32 (0..2147483647)
    MAX-ACCESS read-only
    STATUS     current
    DESCRIPTION
            ""
    ::= { lcsStatusDslolPppoe 8 }

-- {SCALAR} 1.3.6.1.4.1.2356.11.1.25.31.9
lcsStatusDslolPppoeTxData OBJECT-TYPE
    SYNTAX     Integer32 (0..2147483647)
    MAX-ACCESS read-only
    STATUS     current
    DESCRIPTION
            ""
    ::= { lcsStatusDslolPppoe 9 }

-- {SCALAR} 1.3.6.1.4.1.2356.11.1.25.31.10
lcsStatusDslolPppoeRxData OBJECT-TYPE
    SYNTAX     Integer32 (0..2147483647)
    MAX-ACCESS read-only
    STATUS     current
    DESCRIPTION
            ""
    ::= { lcsStatusDslolPppoe 10 }

-- {SCALAR} 1.3.6.1.4.1.2356.11.1.25.31.11
lcsStatusDslolPppoeRxBad OBJECT-TYPE
    SYNTAX     Integer32 (0..2147483647)
    MAX-ACCESS read-only
    STATUS     current
    DESCRIPTION
            ""
    ::= { lcsStatusDslolPppoe 11 }

-- {SCALAR} 1.3.6.1.4.1.2356.11.1.25.31.12
lcsStatusDslolPppoeAcName OBJECT-TYPE
    SYNTAX     DisplayString (SIZE(0..63))
    MAX-ACCESS read-only
    STATUS     current
    DESCRIPTION
            ""
    ::= { lcsStatusDslolPppoe 12 }

-- {SCALAR} 1.3.6.1.4.1.2356.11.1.25.31.13
lcsStatusDslolPppoeService OBJECT-TYPE
    SYNTAX     DisplayString (SIZE(0..63))
    MAX-ACCESS read-only
    STATUS     current
    DESCRIPTION
            ""
    ::= { lcsStatusDslolPppoe 13 }

-- {SCALAR} 1.3.6.1.4.1.2356.11.1.25.31.30
lcsStatusDslolPppoeDeleteValues OBJECT-TYPE
    SYNTAX     DisplayString
    MAX-ACCESS read-write
    STATUS     current
    DESCRIPTION
            ""
    ::= { lcsStatusDslolPppoe 30 }

-- {NODE} 1.3.6.1.4.1.2356.11.1.26
lcsStatusVpn OBJECT IDENTIFIER ::= { lcsStatus 26 }

-- {SCALAR} 1.3.6.1.4.1.2356.11.1.26.1
lcsStatusVpnPeers OBJECT-TYPE
    SYNTAX     Integer32 (0..2147483647)
    MAX-ACCESS read-only
    STATUS     current
    DESCRIPTION
            ""
    ::= { lcsStatusVpn 1 }

-- {SCALAR} 1.3.6.1.4.1.2356.11.1.26.2
lcsStatusVpnRules OBJECT-TYPE
    SYNTAX     Integer32 (0..2147483647)
    MAX-ACCESS read-only
    STATUS     current
    DESCRIPTION
            ""
    ::= { lcsStatusVpn 2 }

-- {SCALAR} 1.3.6.1.4.1.2356.11.1.26.4
lcsStatusVpnTunnel OBJECT-TYPE
    SYNTAX     Integer32 (0..2147483647)
    MAX-ACCESS read-only
    STATUS     current
    DESCRIPTION
            ""
    ::= { lcsStatusVpn 4 }

-- {SCALAR} 1.3.6.1.4.1.2356.11.1.26.5
lcsStatusVpnIkeSas OBJECT-TYPE
    SYNTAX     Integer32 (0..2147483647)
    MAX-ACCESS read-only
    STATUS     current
    DESCRIPTION
            ""
    ::= { lcsStatusVpn 5 }

-- {SCALAR} 1.3.6.1.4.1.2356.11.1.26.6
lcsStatusVpnEspSas OBJECT-TYPE
    SYNTAX     Integer32 (0..2147483647)
    MAX-ACCESS read-only
    STATUS     current
    DESCRIPTION
            ""
    ::= { lcsStatusVpn 6 }

-- {SCALAR} 1.3.6.1.4.1.2356.11.1.26.7
lcsStatusVpnAhSas OBJECT-TYPE
    SYNTAX     Integer32 (0..2147483647)
    MAX-ACCESS read-only
    STATUS     current
    DESCRIPTION
            ""
    ::= { lcsStatusVpn 7 }

-- {TABLE} 1.3.6.1.4.1.2356.11.1.26.8
lcsStatusVpnIkeTable OBJECT-TYPE
    SYNTAX     SEQUENCE OF LcsStatusVpnIkeEntry
    MAX-ACCESS not-accessible
    STATUS     current
    DESCRIPTION
            ""
    ::= { lcsStatusVpn 8 }

-- {ROW} 1.3.6.1.4.1.2356.11.1.26.8.1
lcsStatusVpnIkeEntry OBJECT-TYPE
    SYNTAX     LcsStatusVpnIkeEntry
    MAX-ACCESS not-accessible
    STATUS     current
    DESCRIPTION
            ""
    INDEX {
            lcsStatusVpnIkeEntryIdx
          }
    ::= { lcsStatusVpnIkeTable 1 }

LcsStatusVpnIkeEntry ::= SEQUENCE {
            lcsStatusVpnIkeEntryIdx DisplayString,
            lcsStatusVpnIkeEntryPeer DisplayString,
            lcsStatusVpnIkeEntryDestAddress IpAddress,
            lcsStatusVpnIkeEntrySrcAddress IpAddress,
            lcsStatusVpnIkeEntryCryptAlg DisplayString,
            lcsStatusVpnIkeEntryHashAlg DisplayString,
            lcsStatusVpnIkeEntryAge Integer32,
            lcsStatusVpnIkeEntryInitiator DisplayString,
            lcsStatusVpnIkeEntrySoftSec Integer32,
            lcsStatusVpnIkeEntryMaxSec Integer32,
            lcsStatusVpnIkeEntryKbyte Integer32,
            lcsStatusVpnIkeEntrySoftKbyte Integer32,
            lcsStatusVpnIkeEntryMaxKbyte Integer32,
            lcsStatusVpnIkeEntryIkeAuthMode INTEGER,
            lcsStatusVpnIkeEntryDstPort Integer32,
            lcsStatusVpnIkeEntrySrcPort Integer32,
            lcsStatusVpnIkeEntryDestAddressNew DisplayString,
            lcsStatusVpnIkeEntrySrcAddressNew DisplayString
    }

-- {COLUMN} 1.3.6.1.4.1.2356.11.1.26.8.1.1
lcsStatusVpnIkeEntryIdx OBJECT-TYPE
    SYNTAX     DisplayString (SIZE(0..255))
    MAX-ACCESS read-only
    STATUS     current
    DESCRIPTION
            ""
    ::= { lcsStatusVpnIkeEntry 1 }

-- {COLUMN} 1.3.6.1.4.1.2356.11.1.26.8.1.2
lcsStatusVpnIkeEntryPeer OBJECT-TYPE
    SYNTAX     DisplayString (SIZE(0..15))
    MAX-ACCESS read-only
    STATUS     current
    DESCRIPTION
            ""
    ::= { lcsStatusVpnIkeEntry 2 }

-- {COLUMN} 1.3.6.1.4.1.2356.11.1.26.8.1.3
lcsStatusVpnIkeEntryDestAddress OBJECT-TYPE
    SYNTAX     IpAddress
    MAX-ACCESS read-only
    STATUS     obsolete
    DESCRIPTION
            ""
    ::= { lcsStatusVpnIkeEntry 3 }

-- {COLUMN} 1.3.6.1.4.1.2356.11.1.26.8.1.4
lcsStatusVpnIkeEntrySrcAddress OBJECT-TYPE
    SYNTAX     IpAddress
    MAX-ACCESS read-only
    STATUS     obsolete
    DESCRIPTION
            ""
    ::= { lcsStatusVpnIkeEntry 4 }

-- {COLUMN} 1.3.6.1.4.1.2356.11.1.26.8.1.5
lcsStatusVpnIkeEntryCryptAlg OBJECT-TYPE
    SYNTAX     DisplayString (SIZE(0..12))
    MAX-ACCESS read-only
    STATUS     current
    DESCRIPTION
            ""
    ::= { lcsStatusVpnIkeEntry 5 }

-- {COLUMN} 1.3.6.1.4.1.2356.11.1.26.8.1.6
lcsStatusVpnIkeEntryHashAlg OBJECT-TYPE
    SYNTAX     DisplayString (SIZE(0..12))
    MAX-ACCESS read-only
    STATUS     current
    DESCRIPTION
            ""
    ::= { lcsStatusVpnIkeEntry 6 }

-- {COLUMN} 1.3.6.1.4.1.2356.11.1.26.8.1.8
lcsStatusVpnIkeEntryAge OBJECT-TYPE
    SYNTAX     Integer32 (0..2147483647)
    MAX-ACCESS read-only
    STATUS     current
    DESCRIPTION
            ""
    ::= { lcsStatusVpnIkeEntry 8 }

-- {COLUMN} 1.3.6.1.4.1.2356.11.1.26.8.1.9
lcsStatusVpnIkeEntryInitiator OBJECT-TYPE
    SYNTAX     DisplayString (SIZE(0..3))
    MAX-ACCESS read-only
    STATUS     current
    DESCRIPTION
            ""
    ::= { lcsStatusVpnIkeEntry 9 }

-- {COLUMN} 1.3.6.1.4.1.2356.11.1.26.8.1.10
lcsStatusVpnIkeEntrySoftSec OBJECT-TYPE
    SYNTAX     Integer32 (0..2147483647)
    MAX-ACCESS read-only
    STATUS     current
    DESCRIPTION
            ""
    ::= { lcsStatusVpnIkeEntry 10 }

-- {COLUMN} 1.3.6.1.4.1.2356.11.1.26.8.1.11
lcsStatusVpnIkeEntryMaxSec OBJECT-TYPE
    SYNTAX     Integer32 (0..2147483647)
    MAX-ACCESS read-only
    STATUS     current
    DESCRIPTION
            ""
    ::= { lcsStatusVpnIkeEntry 11 }

-- {COLUMN} 1.3.6.1.4.1.2356.11.1.26.8.1.12
lcsStatusVpnIkeEntryKbyte OBJECT-TYPE
    SYNTAX     Integer32 (0..2147483647)
    MAX-ACCESS read-only
    STATUS     current
    DESCRIPTION
            ""
    ::= { lcsStatusVpnIkeEntry 12 }

-- {COLUMN} 1.3.6.1.4.1.2356.11.1.26.8.1.13
lcsStatusVpnIkeEntrySoftKbyte OBJECT-TYPE
    SYNTAX     Integer32 (0..2147483647)
    MAX-ACCESS read-only
    STATUS     current
    DESCRIPTION
            ""
    ::= { lcsStatusVpnIkeEntry 13 }

-- {COLUMN} 1.3.6.1.4.1.2356.11.1.26.8.1.14
lcsStatusVpnIkeEntryMaxKbyte OBJECT-TYPE
    SYNTAX     Integer32 (0..2147483647)
    MAX-ACCESS read-only
    STATUS     current
    DESCRIPTION
            ""
    ::= { lcsStatusVpnIkeEntry 14 }

-- {COLUMN} 1.3.6.1.4.1.2356.11.1.26.8.1.15
lcsStatusVpnIkeEntryIkeAuthMode OBJECT-TYPE
    SYNTAX     INTEGER {
                  eNo (0),
                  ePreShared (1),
                  eDss (2),
                  eRsaSig (3),
                  eRsaEnc (4),
                  eRsaEncRev (5),
                  eElGamalEnc (6),
                  eElGamalEncRev (7),
                  eEcdsaSig (8),
                  eEcdsa256 (9),
                  eEcdsa384 (10),
                  eEcdsa521 (11),
                  eDigitalSignature (14),
                  eEap (201),
                  ePreSharedInitXauth (65001),
                  ePreSharedRespXauth (65002),
                  eDssInitXauth (65003),
                  eDssRespXauth (65004),
                  eRsaInitXauth (65005),
                  eRsaRespXauth (65006)
            }
    MAX-ACCESS read-only
    STATUS     current
    DESCRIPTION
            ""
    ::= { lcsStatusVpnIkeEntry 15 }

-- {COLUMN} 1.3.6.1.4.1.2356.11.1.26.8.1.16
lcsStatusVpnIkeEntryDstPort OBJECT-TYPE
    SYNTAX     Integer32 (0..65535)
    MAX-ACCESS read-only
    STATUS     current
    DESCRIPTION
            ""
    ::= { lcsStatusVpnIkeEntry 16 }

-- {COLUMN} 1.3.6.1.4.1.2356.11.1.26.8.1.17
lcsStatusVpnIkeEntrySrcPort OBJECT-TYPE
    SYNTAX     Integer32 (0..65535)
    MAX-ACCESS read-only
    STATUS     current
    DESCRIPTION
            ""
    ::= { lcsStatusVpnIkeEntry 17 }

-- {COLUMN} 1.3.6.1.4.1.2356.11.1.26.8.1.18
lcsStatusVpnIkeEntryDestAddressNew OBJECT-TYPE
    SYNTAX     DisplayString (SIZE(0..39))
    MAX-ACCESS read-only
    STATUS     current
    DESCRIPTION
            ""
    ::= { lcsStatusVpnIkeEntry 18 }

-- {COLUMN} 1.3.6.1.4.1.2356.11.1.26.8.1.19
lcsStatusVpnIkeEntrySrcAddressNew OBJECT-TYPE
    SYNTAX     DisplayString (SIZE(0..39))
    MAX-ACCESS read-only
    STATUS     current
    DESCRIPTION
            ""
    ::= { lcsStatusVpnIkeEntry 19 }

-- {TABLE} 1.3.6.1.4.1.2356.11.1.26.9
lcsStatusVpnEspTable OBJECT-TYPE
    SYNTAX     SEQUENCE OF LcsStatusVpnEspEntry
    MAX-ACCESS not-accessible
    STATUS     current
    DESCRIPTION
            ""
    ::= { lcsStatusVpn 9 }

-- {ROW} 1.3.6.1.4.1.2356.11.1.26.9.1
lcsStatusVpnEspEntry OBJECT-TYPE
    SYNTAX     LcsStatusVpnEspEntry
    MAX-ACCESS not-accessible
    STATUS     current
    DESCRIPTION
            ""
    INDEX {
            lcsStatusVpnEspEntryIdx
          }
    ::= { lcsStatusVpnEspTable 1 }

LcsStatusVpnEspEntry ::= SEQUENCE {
            lcsStatusVpnEspEntryIdx DisplayString,
            lcsStatusVpnEspEntryPeer DisplayString,
            lcsStatusVpnEspEntryDestAddress IpAddress,
            lcsStatusVpnEspEntrySrcAddress IpAddress,
            lcsStatusVpnEspEntryMode DisplayString,
            lcsStatusVpnEspEntryCryptAlg DisplayString,
            lcsStatusVpnEspEntryHashAlg DisplayString,
            lcsStatusVpnEspEntrySpi DisplayString,
            lcsStatusVpnEspEntryAge Integer32,
            lcsStatusVpnEspEntrySoftSec Integer32,
            lcsStatusVpnEspEntryMaxSec Integer32,
            lcsStatusVpnEspEntryKbyte Integer32,
            lcsStatusVpnEspEntrySoftKbyte Integer32,
            lcsStatusVpnEspEntryMaxKbyte Integer32,
            lcsStatusVpnEspEntryDestAddressNew DisplayString,
            lcsStatusVpnEspEntrySrcAddressNew DisplayString
    }

-- {COLUMN} 1.3.6.1.4.1.2356.11.1.26.9.1.1
lcsStatusVpnEspEntryIdx OBJECT-TYPE
    SYNTAX     DisplayString (SIZE(0..255))
    MAX-ACCESS read-only
    STATUS     current
    DESCRIPTION
            ""
    ::= { lcsStatusVpnEspEntry 1 }

-- {COLUMN} 1.3.6.1.4.1.2356.11.1.26.9.1.2
lcsStatusVpnEspEntryPeer OBJECT-TYPE
    SYNTAX     DisplayString (SIZE(0..15))
    MAX-ACCESS read-only
    STATUS     current
    DESCRIPTION
            ""
    ::= { lcsStatusVpnEspEntry 2 }

-- {COLUMN} 1.3.6.1.4.1.2356.11.1.26.9.1.3
lcsStatusVpnEspEntryDestAddress OBJECT-TYPE
    SYNTAX     IpAddress
    MAX-ACCESS read-only
    STATUS     obsolete
    DESCRIPTION
            ""
    ::= { lcsStatusVpnEspEntry 3 }

-- {COLUMN} 1.3.6.1.4.1.2356.11.1.26.9.1.4
lcsStatusVpnEspEntrySrcAddress OBJECT-TYPE
    SYNTAX     IpAddress
    MAX-ACCESS read-only
    STATUS     obsolete
    DESCRIPTION
            ""
    ::= { lcsStatusVpnEspEntry 4 }

-- {COLUMN} 1.3.6.1.4.1.2356.11.1.26.9.1.5
lcsStatusVpnEspEntryMode OBJECT-TYPE
    SYNTAX     DisplayString (SIZE(0..2))
    MAX-ACCESS read-only
    STATUS     current
    DESCRIPTION
            ""
    ::= { lcsStatusVpnEspEntry 5 }

-- {COLUMN} 1.3.6.1.4.1.2356.11.1.26.9.1.6
lcsStatusVpnEspEntryCryptAlg OBJECT-TYPE
    SYNTAX     DisplayString (SIZE(0..12))
    MAX-ACCESS read-only
    STATUS     current
    DESCRIPTION
            ""
    ::= { lcsStatusVpnEspEntry 6 }

-- {COLUMN} 1.3.6.1.4.1.2356.11.1.26.9.1.7
lcsStatusVpnEspEntryHashAlg OBJECT-TYPE
    SYNTAX     DisplayString (SIZE(0..12))
    MAX-ACCESS read-only
    STATUS     current
    DESCRIPTION
            ""
    ::= { lcsStatusVpnEspEntry 7 }

-- {COLUMN} 1.3.6.1.4.1.2356.11.1.26.9.1.9
lcsStatusVpnEspEntrySpi OBJECT-TYPE
    SYNTAX     DisplayString (SIZE(0..15))
    MAX-ACCESS read-only
    STATUS     current
    DESCRIPTION
            ""
    ::= { lcsStatusVpnEspEntry 9 }

-- {COLUMN} 1.3.6.1.4.1.2356.11.1.26.9.1.10
lcsStatusVpnEspEntryAge OBJECT-TYPE
    SYNTAX     Integer32 (0..2147483647)
    MAX-ACCESS read-only
    STATUS     current
    DESCRIPTION
            ""
    ::= { lcsStatusVpnEspEntry 10 }

-- {COLUMN} 1.3.6.1.4.1.2356.11.1.26.9.1.11
lcsStatusVpnEspEntrySoftSec OBJECT-TYPE
    SYNTAX     Integer32 (0..2147483647)
    MAX-ACCESS read-only
    STATUS     current
    DESCRIPTION
            ""
    ::= { lcsStatusVpnEspEntry 11 }

-- {COLUMN} 1.3.6.1.4.1.2356.11.1.26.9.1.12
lcsStatusVpnEspEntryMaxSec OBJECT-TYPE
    SYNTAX     Integer32 (0..2147483647)
    MAX-ACCESS read-only
    STATUS     current
    DESCRIPTION
            ""
    ::= { lcsStatusVpnEspEntry 12 }

-- {COLUMN} 1.3.6.1.4.1.2356.11.1.26.9.1.13
lcsStatusVpnEspEntryKbyte OBJECT-TYPE
    SYNTAX     Integer32 (0..2147483647)
    MAX-ACCESS read-only
    STATUS     current
    DESCRIPTION
            ""
    ::= { lcsStatusVpnEspEntry 13 }

-- {COLUMN} 1.3.6.1.4.1.2356.11.1.26.9.1.14
lcsStatusVpnEspEntrySoftKbyte OBJECT-TYPE
    SYNTAX     Integer32 (0..2147483647)
    MAX-ACCESS read-only
    STATUS     current
    DESCRIPTION
            ""
    ::= { lcsStatusVpnEspEntry 14 }

-- {COLUMN} 1.3.6.1.4.1.2356.11.1.26.9.1.15
lcsStatusVpnEspEntryMaxKbyte OBJECT-TYPE
    SYNTAX     Integer32 (0..2147483647)
    MAX-ACCESS read-only
    STATUS     current
    DESCRIPTION
            ""
    ::= { lcsStatusVpnEspEntry 15 }

-- {COLUMN} 1.3.6.1.4.1.2356.11.1.26.9.1.16
lcsStatusVpnEspEntryDestAddressNew OBJECT-TYPE
    SYNTAX     DisplayString (SIZE(0..39))
    MAX-ACCESS read-only
    STATUS     current
    DESCRIPTION
            ""
    ::= { lcsStatusVpnEspEntry 16 }

-- {COLUMN} 1.3.6.1.4.1.2356.11.1.26.9.1.17
lcsStatusVpnEspEntrySrcAddressNew OBJECT-TYPE
    SYNTAX     DisplayString (SIZE(0..39))
    MAX-ACCESS read-only
    STATUS     current
    DESCRIPTION
            ""
    ::= { lcsStatusVpnEspEntry 17 }

-- {TABLE} 1.3.6.1.4.1.2356.11.1.26.10
lcsStatusVpnAhTable OBJECT-TYPE
    SYNTAX     SEQUENCE OF LcsStatusVpnAhEntry
    MAX-ACCESS not-accessible
    STATUS     current
    DESCRIPTION
            ""
    ::= { lcsStatusVpn 10 }

-- {ROW} 1.3.6.1.4.1.2356.11.1.26.10.1
lcsStatusVpnAhEntry OBJECT-TYPE
    SYNTAX     LcsStatusVpnAhEntry
    MAX-ACCESS not-accessible
    STATUS     current
    DESCRIPTION
            ""
    INDEX {
            lcsStatusVpnAhEntryIdx
          }
    ::= { lcsStatusVpnAhTable 1 }

LcsStatusVpnAhEntry ::= SEQUENCE {
            lcsStatusVpnAhEntryIdx DisplayString,
            lcsStatusVpnAhEntryPeer DisplayString,
            lcsStatusVpnAhEntryDestAddress IpAddress,
            lcsStatusVpnAhEntrySrcAddress IpAddress,
            lcsStatusVpnAhEntryMode DisplayString,
            lcsStatusVpnAhEntryCryptAlg DisplayString,
            lcsStatusVpnAhEntryHashAlg DisplayString,
            lcsStatusVpnAhEntrySpi DisplayString,
            lcsStatusVpnAhEntryAge Integer32,
            lcsStatusVpnAhEntrySoftSec Integer32,
            lcsStatusVpnAhEntryMaxSec Integer32,
            lcsStatusVpnAhEntryKbyte Integer32,
            lcsStatusVpnAhEntrySoftKbyte Integer32,
            lcsStatusVpnAhEntryMaxKbyte Integer32,
            lcsStatusVpnAhEntryDestAddressNew DisplayString,
            lcsStatusVpnAhEntrySrcAddressNew DisplayString
    }

-- {COLUMN} 1.3.6.1.4.1.2356.11.1.26.10.1.1
lcsStatusVpnAhEntryIdx OBJECT-TYPE
    SYNTAX     DisplayString (SIZE(0..255))
    MAX-ACCESS read-only
    STATUS     current
    DESCRIPTION
            ""
    ::= { lcsStatusVpnAhEntry 1 }

-- {COLUMN} 1.3.6.1.4.1.2356.11.1.26.10.1.2
lcsStatusVpnAhEntryPeer OBJECT-TYPE
    SYNTAX     DisplayString (SIZE(0..15))
    MAX-ACCESS read-only
    STATUS     current
    DESCRIPTION
            ""
    ::= { lcsStatusVpnAhEntry 2 }

-- {COLUMN} 1.3.6.1.4.1.2356.11.1.26.10.1.3
lcsStatusVpnAhEntryDestAddress OBJECT-TYPE
    SYNTAX     IpAddress
    MAX-ACCESS read-only
    STATUS     obsolete
    DESCRIPTION
            ""
    ::= { lcsStatusVpnAhEntry 3 }

-- {COLUMN} 1.3.6.1.4.1.2356.11.1.26.10.1.4
lcsStatusVpnAhEntrySrcAddress OBJECT-TYPE
    SYNTAX     IpAddress
    MAX-ACCESS read-only
    STATUS     obsolete
    DESCRIPTION
            ""
    ::= { lcsStatusVpnAhEntry 4 }

-- {COLUMN} 1.3.6.1.4.1.2356.11.1.26.10.1.5
lcsStatusVpnAhEntryMode OBJECT-TYPE
    SYNTAX     DisplayString (SIZE(0..2))
    MAX-ACCESS read-only
    STATUS     current
    DESCRIPTION
            ""
    ::= { lcsStatusVpnAhEntry 5 }

-- {COLUMN} 1.3.6.1.4.1.2356.11.1.26.10.1.6
lcsStatusVpnAhEntryCryptAlg OBJECT-TYPE
    SYNTAX     DisplayString (SIZE(0..12))
    MAX-ACCESS read-only
    STATUS     current
    DESCRIPTION
            ""
    ::= { lcsStatusVpnAhEntry 6 }

-- {COLUMN} 1.3.6.1.4.1.2356.11.1.26.10.1.7
lcsStatusVpnAhEntryHashAlg OBJECT-TYPE
    SYNTAX     DisplayString (SIZE(0..12))
    MAX-ACCESS read-only
    STATUS     current
    DESCRIPTION
            ""
    ::= { lcsStatusVpnAhEntry 7 }

-- {COLUMN} 1.3.6.1.4.1.2356.11.1.26.10.1.9
lcsStatusVpnAhEntrySpi OBJECT-TYPE
    SYNTAX     DisplayString (SIZE(0..15))
    MAX-ACCESS read-only
    STATUS     current
    DESCRIPTION
            ""
    ::= { lcsStatusVpnAhEntry 9 }

-- {COLUMN} 1.3.6.1.4.1.2356.11.1.26.10.1.10
lcsStatusVpnAhEntryAge OBJECT-TYPE
    SYNTAX     Integer32 (0..2147483647)
    MAX-ACCESS read-only
    STATUS     current
    DESCRIPTION
            ""
    ::= { lcsStatusVpnAhEntry 10 }

-- {COLUMN} 1.3.6.1.4.1.2356.11.1.26.10.1.11
lcsStatusVpnAhEntrySoftSec OBJECT-TYPE
    SYNTAX     Integer32 (0..2147483647)
    MAX-ACCESS read-only
    STATUS     current
    DESCRIPTION
            ""
    ::= { lcsStatusVpnAhEntry 11 }

-- {COLUMN} 1.3.6.1.4.1.2356.11.1.26.10.1.12
lcsStatusVpnAhEntryMaxSec OBJECT-TYPE
    SYNTAX     Integer32 (0..2147483647)
    MAX-ACCESS read-only
    STATUS     current
    DESCRIPTION
            ""
    ::= { lcsStatusVpnAhEntry 12 }

-- {COLUMN} 1.3.6.1.4.1.2356.11.1.26.10.1.13
lcsStatusVpnAhEntryKbyte OBJECT-TYPE
    SYNTAX     Integer32 (0..2147483647)
    MAX-ACCESS read-only
    STATUS     current
    DESCRIPTION
            ""
    ::= { lcsStatusVpnAhEntry 13 }

-- {COLUMN} 1.3.6.1.4.1.2356.11.1.26.10.1.14
lcsStatusVpnAhEntrySoftKbyte OBJECT-TYPE
    SYNTAX     Integer32 (0..2147483647)
    MAX-ACCESS read-only
    STATUS     current
    DESCRIPTION
            ""
    ::= { lcsStatusVpnAhEntry 14 }

-- {COLUMN} 1.3.6.1.4.1.2356.11.1.26.10.1.15
lcsStatusVpnAhEntryMaxKbyte OBJECT-TYPE
    SYNTAX     Integer32 (0..2147483647)
    MAX-ACCESS read-only
    STATUS     current
    DESCRIPTION
            ""
    ::= { lcsStatusVpnAhEntry 15 }

-- {COLUMN} 1.3.6.1.4.1.2356.11.1.26.10.1.16
lcsStatusVpnAhEntryDestAddressNew OBJECT-TYPE
    SYNTAX     DisplayString (SIZE(0..39))
    MAX-ACCESS read-only
    STATUS     current
    DESCRIPTION
            ""
    ::= { lcsStatusVpnAhEntry 16 }

-- {COLUMN} 1.3.6.1.4.1.2356.11.1.26.10.1.17
lcsStatusVpnAhEntrySrcAddressNew OBJECT-TYPE
    SYNTAX     DisplayString (SIZE(0..39))
    MAX-ACCESS read-only
    STATUS     current
    DESCRIPTION
            ""
    ::= { lcsStatusVpnAhEntry 17 }

-- {SCALAR} 1.3.6.1.4.1.2356.11.1.26.12
lcsStatusVpnDeleteValues OBJECT-TYPE
    SYNTAX     DisplayString
    MAX-ACCESS read-write
    STATUS     current
    DESCRIPTION
            ""
    ::= { lcsStatusVpn 12 }

-- {SCALAR} 1.3.6.1.4.1.2356.11.1.26.13
lcsStatusVpnIpcompSas OBJECT-TYPE
    SYNTAX     Integer32 (0..2147483647)
    MAX-ACCESS read-only
    STATUS     current
    DESCRIPTION
            ""
    ::= { lcsStatusVpn 13 }

-- {TABLE} 1.3.6.1.4.1.2356.11.1.26.14
lcsStatusVpnIpcompTable OBJECT-TYPE
    SYNTAX     SEQUENCE OF LcsStatusVpnIpcompEntry
    MAX-ACCESS not-accessible
    STATUS     current
    DESCRIPTION
            ""
    ::= { lcsStatusVpn 14 }

-- {ROW} 1.3.6.1.4.1.2356.11.1.26.14.1
lcsStatusVpnIpcompEntry OBJECT-TYPE
    SYNTAX     LcsStatusVpnIpcompEntry
    MAX-ACCESS not-accessible
    STATUS     current
    DESCRIPTION
            ""
    INDEX {
            lcsStatusVpnIpcompEntryIdx
          }
    ::= { lcsStatusVpnIpcompTable 1 }

LcsStatusVpnIpcompEntry ::= SEQUENCE {
            lcsStatusVpnIpcompEntryIdx DisplayString,
            lcsStatusVpnIpcompEntryPeer DisplayString,
            lcsStatusVpnIpcompEntryDestAddress IpAddress,
            lcsStatusVpnIpcompEntrySrcAddress IpAddress,
            lcsStatusVpnIpcompEntryMode DisplayString,
            lcsStatusVpnIpcompEntryCryptAlg DisplayString,
            lcsStatusVpnIpcompEntryHashAlg DisplayString,
            lcsStatusVpnIpcompEntrySpi DisplayString,
            lcsStatusVpnIpcompEntryAge Integer32,
            lcsStatusVpnIpcompEntrySoftSec Integer32,
            lcsStatusVpnIpcompEntryMaxSec Integer32,
            lcsStatusVpnIpcompEntryKbyte Integer32,
            lcsStatusVpnIpcompEntrySoftKbyte Integer32,
            lcsStatusVpnIpcompEntryMaxKbyte Integer32,
            lcsStatusVpnIpcompEntryDestAddressNew DisplayString,
            lcsStatusVpnIpcompEntrySrcAddressNew DisplayString
    }

-- {COLUMN} 1.3.6.1.4.1.2356.11.1.26.14.1.1
lcsStatusVpnIpcompEntryIdx OBJECT-TYPE
    SYNTAX     DisplayString (SIZE(0..255))
    MAX-ACCESS read-only
    STATUS     current
    DESCRIPTION
            ""
    ::= { lcsStatusVpnIpcompEntry 1 }

-- {COLUMN} 1.3.6.1.4.1.2356.11.1.26.14.1.2
lcsStatusVpnIpcompEntryPeer OBJECT-TYPE
    SYNTAX     DisplayString (SIZE(0..15))
    MAX-ACCESS read-only
    STATUS     current
    DESCRIPTION
            ""
    ::= { lcsStatusVpnIpcompEntry 2 }

-- {COLUMN} 1.3.6.1.4.1.2356.11.1.26.14.1.3
lcsStatusVpnIpcompEntryDestAddress OBJECT-TYPE
    SYNTAX     IpAddress
    MAX-ACCESS read-only
    STATUS     obsolete
    DESCRIPTION
            ""
    ::= { lcsStatusVpnIpcompEntry 3 }

-- {COLUMN} 1.3.6.1.4.1.2356.11.1.26.14.1.4
lcsStatusVpnIpcompEntrySrcAddress OBJECT-TYPE
    SYNTAX     IpAddress
    MAX-ACCESS read-only
    STATUS     obsolete
    DESCRIPTION
            ""
    ::= { lcsStatusVpnIpcompEntry 4 }

-- {COLUMN} 1.3.6.1.4.1.2356.11.1.26.14.1.5
lcsStatusVpnIpcompEntryMode OBJECT-TYPE
    SYNTAX     DisplayString (SIZE(0..2))
    MAX-ACCESS read-only
    STATUS     current
    DESCRIPTION
            ""
    ::= { lcsStatusVpnIpcompEntry 5 }

-- {COLUMN} 1.3.6.1.4.1.2356.11.1.26.14.1.6
lcsStatusVpnIpcompEntryCryptAlg OBJECT-TYPE
    SYNTAX     DisplayString (SIZE(0..12))
    MAX-ACCESS read-only
    STATUS     current
    DESCRIPTION
            ""
    ::= { lcsStatusVpnIpcompEntry 6 }

-- {COLUMN} 1.3.6.1.4.1.2356.11.1.26.14.1.7
lcsStatusVpnIpcompEntryHashAlg OBJECT-TYPE
    SYNTAX     DisplayString (SIZE(0..12))
    MAX-ACCESS read-only
    STATUS     current
    DESCRIPTION
            ""
    ::= { lcsStatusVpnIpcompEntry 7 }

-- {COLUMN} 1.3.6.1.4.1.2356.11.1.26.14.1.9
lcsStatusVpnIpcompEntrySpi OBJECT-TYPE
    SYNTAX     DisplayString (SIZE(0..15))
    MAX-ACCESS read-only
    STATUS     current
    DESCRIPTION
            ""
    ::= { lcsStatusVpnIpcompEntry 9 }

-- {COLUMN} 1.3.6.1.4.1.2356.11.1.26.14.1.10
lcsStatusVpnIpcompEntryAge OBJECT-TYPE
    SYNTAX     Integer32 (0..2147483647)
    MAX-ACCESS read-only
    STATUS     current
    DESCRIPTION
            ""
    ::= { lcsStatusVpnIpcompEntry 10 }

-- {COLUMN} 1.3.6.1.4.1.2356.11.1.26.14.1.11
lcsStatusVpnIpcompEntrySoftSec OBJECT-TYPE
    SYNTAX     Integer32 (0..2147483647)
    MAX-ACCESS read-only
    STATUS     current
    DESCRIPTION
            ""
    ::= { lcsStatusVpnIpcompEntry 11 }

-- {COLUMN} 1.3.6.1.4.1.2356.11.1.26.14.1.12
lcsStatusVpnIpcompEntryMaxSec OBJECT-TYPE
    SYNTAX     Integer32 (0..2147483647)
    MAX-ACCESS read-only
    STATUS     current
    DESCRIPTION
            ""
    ::= { lcsStatusVpnIpcompEntry 12 }

-- {COLUMN} 1.3.6.1.4.1.2356.11.1.26.14.1.13
lcsStatusVpnIpcompEntryKbyte OBJECT-TYPE
    SYNTAX     Integer32 (0..2147483647)
    MAX-ACCESS read-only
    STATUS     current
    DESCRIPTION
            ""
    ::= { lcsStatusVpnIpcompEntry 13 }

-- {COLUMN} 1.3.6.1.4.1.2356.11.1.26.14.1.14
lcsStatusVpnIpcompEntrySoftKbyte OBJECT-TYPE
    SYNTAX     Integer32 (0..2147483647)
    MAX-ACCESS read-only
    STATUS     current
    DESCRIPTION
            ""
    ::= { lcsStatusVpnIpcompEntry 14 }

-- {COLUMN} 1.3.6.1.4.1.2356.11.1.26.14.1.15
lcsStatusVpnIpcompEntryMaxKbyte OBJECT-TYPE
    SYNTAX     Integer32 (0..2147483647)
    MAX-ACCESS read-only
    STATUS     current
    DESCRIPTION
            ""
    ::= { lcsStatusVpnIpcompEntry 15 }

-- {COLUMN} 1.3.6.1.4.1.2356.11.1.26.14.1.16
lcsStatusVpnIpcompEntryDestAddressNew OBJECT-TYPE
    SYNTAX     DisplayString (SIZE(0..39))
    MAX-ACCESS read-only
    STATUS     current
    DESCRIPTION
            ""
    ::= { lcsStatusVpnIpcompEntry 16 }

-- {COLUMN} 1.3.6.1.4.1.2356.11.1.26.14.1.17
lcsStatusVpnIpcompEntrySrcAddressNew OBJECT-TYPE
    SYNTAX     DisplayString (SIZE(0..39))
    MAX-ACCESS read-only
    STATUS     current
    DESCRIPTION
            ""
    ::= { lcsStatusVpnIpcompEntry 17 }

-- {TABLE} 1.3.6.1.4.1.2356.11.1.26.17
lcsStatusVpnConnectionsTable OBJECT-TYPE
    SYNTAX     SEQUENCE OF LcsStatusVpnConnectionsEntry
    MAX-ACCESS not-accessible
    STATUS     current
    DESCRIPTION
            ""
    ::= { lcsStatusVpn 17 }

-- {ROW} 1.3.6.1.4.1.2356.11.1.26.17.1
lcsStatusVpnConnectionsEntry OBJECT-TYPE
    SYNTAX     LcsStatusVpnConnectionsEntry
    MAX-ACCESS not-accessible
    STATUS     current
    DESCRIPTION
            ""
    INDEX {
            lcsStatusVpnConnectionsEntryPeer
          }
    ::= { lcsStatusVpnConnectionsTable 1 }

LcsStatusVpnConnectionsEntry ::= SEQUENCE {
            lcsStatusVpnConnectionsEntryPeer DisplayString,
            lcsStatusVpnConnectionsEntryPhysConn DisplayString,
            lcsStatusVpnConnectionsEntryRemoteGw IpAddress,
            lcsStatusVpnConnectionsEntryCryptAlg DisplayString,
            lcsStatusVpnConnectionsEntryCryptLength Integer32,
            lcsStatusVpnConnectionsEntryHashAlg DisplayString,
            lcsStatusVpnConnectionsEntryHashLength Integer32,
            lcsStatusVpnConnectionsEntryHmacAlg DisplayString,
            lcsStatusVpnConnectionsEntryHmacLength Integer32,
            lcsStatusVpnConnectionsEntryComprAlg DisplayString,
            lcsStatusVpnConnectionsEntryState INTEGER,
            lcsStatusVpnConnectionsEntryMode INTEGER,
            lcsStatusVpnConnectionsEntryShTime Integer32,
            lcsStatusVpnConnectionsEntryB1Dt Integer32,
            lcsStatusVpnConnectionsEntryLastError INTEGER,
            lcsStatusVpnConnectionsEntryClientSn INTEGER,
            lcsStatusVpnConnectionsEntryNatDetection INTEGER,
            lcsStatusVpnConnectionsEntryConnTime Gauge32,
            lcsStatusVpnConnectionsEntrySslEncaps INTEGER,
            lcsStatusVpnConnectionsEntryRemoteGwNew DisplayString,
            lcsStatusVpnConnectionsEntryIkeType DisplayString,
            lcsStatusVpnConnectionsEntryEncapsulation INTEGER,
            lcsStatusVpnConnectionsEntryHRxBytes Integer32,
            lcsStatusVpnConnectionsEntryHTxBytes Integer32
    }

-- {COLUMN} 1.3.6.1.4.1.2356.11.1.26.17.1.1
lcsStatusVpnConnectionsEntryPeer OBJECT-TYPE
    SYNTAX     DisplayString (SIZE(0..16))
    MAX-ACCESS read-only
    STATUS     current
    DESCRIPTION
            ""
    ::= { lcsStatusVpnConnectionsEntry 1 }

-- {COLUMN} 1.3.6.1.4.1.2356.11.1.26.17.1.2
lcsStatusVpnConnectionsEntryPhysConn OBJECT-TYPE
    SYNTAX     DisplayString (SIZE(0..16))
    MAX-ACCESS read-only
    STATUS     current
    DESCRIPTION
            ""
    ::= { lcsStatusVpnConnectionsEntry 2 }

-- {COLUMN} 1.3.6.1.4.1.2356.11.1.26.17.1.3
lcsStatusVpnConnectionsEntryRemoteGw OBJECT-TYPE
    SYNTAX     IpAddress
    MAX-ACCESS read-only
    STATUS     obsolete
    DESCRIPTION
            ""
    ::= { lcsStatusVpnConnectionsEntry 3 }

-- {COLUMN} 1.3.6.1.4.1.2356.11.1.26.17.1.4
lcsStatusVpnConnectionsEntryCryptAlg OBJECT-TYPE
    SYNTAX     DisplayString (SIZE(0..14))
    MAX-ACCESS read-only
    STATUS     current
    DESCRIPTION
            ""
    ::= { lcsStatusVpnConnectionsEntry 4 }

-- {COLUMN} 1.3.6.1.4.1.2356.11.1.26.17.1.5
lcsStatusVpnConnectionsEntryCryptLength OBJECT-TYPE
    SYNTAX     Integer32 (0..65535)
    MAX-ACCESS read-only
    STATUS     current
    DESCRIPTION
            ""
    ::= { lcsStatusVpnConnectionsEntry 5 }

-- {COLUMN} 1.3.6.1.4.1.2356.11.1.26.17.1.6
lcsStatusVpnConnectionsEntryHashAlg OBJECT-TYPE
    SYNTAX     DisplayString (SIZE(0..14))
    MAX-ACCESS read-only
    STATUS     current
    DESCRIPTION
            ""
    ::= { lcsStatusVpnConnectionsEntry 6 }

-- {COLUMN} 1.3.6.1.4.1.2356.11.1.26.17.1.7
lcsStatusVpnConnectionsEntryHashLength OBJECT-TYPE
    SYNTAX     Integer32 (0..65535)
    MAX-ACCESS read-only
    STATUS     current
    DESCRIPTION
            ""
    ::= { lcsStatusVpnConnectionsEntry 7 }

-- {COLUMN} 1.3.6.1.4.1.2356.11.1.26.17.1.8
lcsStatusVpnConnectionsEntryHmacAlg OBJECT-TYPE
    SYNTAX     DisplayString (SIZE(0..14))
    MAX-ACCESS read-only
    STATUS     current
    DESCRIPTION
            ""
    ::= { lcsStatusVpnConnectionsEntry 8 }

-- {COLUMN} 1.3.6.1.4.1.2356.11.1.26.17.1.9
lcsStatusVpnConnectionsEntryHmacLength OBJECT-TYPE
    SYNTAX     Integer32 (0..65535)
    MAX-ACCESS read-only
    STATUS     current
    DESCRIPTION
            ""
    ::= { lcsStatusVpnConnectionsEntry 9 }

-- {COLUMN} 1.3.6.1.4.1.2356.11.1.26.17.1.10
lcsStatusVpnConnectionsEntryComprAlg OBJECT-TYPE
    SYNTAX     DisplayString (SIZE(0..14))
    MAX-ACCESS read-only
    STATUS     current
    DESCRIPTION
            ""
    ::= { lcsStatusVpnConnectionsEntry 10 }

-- {COLUMN} 1.3.6.1.4.1.2356.11.1.26.17.1.11
lcsStatusVpnConnectionsEntryState OBJECT-TYPE
    SYNTAX     INTEGER {
                  eInit (0),
                  eSetupWan (1),
                  eReady (2),
                  eWaitForCb (3),
                  eDial (4),
                  eIncomingCall (5),
                  eProtocol (6),
                  eConnection (7),
                  eDisconnecting (8),
                  eCallBack (9),
                  eBundleConnect (10),
                  eProtocol2 (11),
                  eReserved (12),
                  eBundle (13)
            }
    MAX-ACCESS read-only
    STATUS     current
    DESCRIPTION
            ""
    ::= { lcsStatusVpnConnectionsEntry 11 }

-- {COLUMN} 1.3.6.1.4.1.2356.11.1.26.17.1.12
lcsStatusVpnConnectionsEntryMode OBJECT-TYPE
    SYNTAX     INTEGER {
                  ePassive (0),
                  eActive (128)
            }
    MAX-ACCESS read-only
    STATUS     current
    DESCRIPTION
            ""
    ::= { lcsStatusVpnConnectionsEntry 12 }

-- {COLUMN} 1.3.6.1.4.1.2356.11.1.26.17.1.13
lcsStatusVpnConnectionsEntryShTime OBJECT-TYPE
    SYNTAX     Integer32 (0..65535)
    MAX-ACCESS read-only
    STATUS     current
    DESCRIPTION
            ""
    ::= { lcsStatusVpnConnectionsEntry 13 }

-- {COLUMN} 1.3.6.1.4.1.2356.11.1.26.17.1.14
lcsStatusVpnConnectionsEntryB1Dt OBJECT-TYPE
    SYNTAX     Integer32 (0..65535)
    MAX-ACCESS read-only
    STATUS     current
    DESCRIPTION
            ""
    ::= { lcsStatusVpnConnectionsEntry 14 }

-- {COLUMN} 1.3.6.1.4.1.2356.11.1.26.17.1.16
lcsStatusVpnConnectionsEntryLastError OBJECT-TYPE
    SYNTAX     INTEGER {
                  eNone (0),
                  eIcmpConnError (275),
                  eIfcILicenseExceeded (4353),
                  eIfcINoChannelAvailable (4354),
                  eIfcINoRouteToRemoteGateway (4355),
                  eIfcINoPppTableEntryMatched (4356),
                  eIfcIConnectionTimeoutDynamic (4357),
                  eIfcIConnectionTimeoutIkeIpsec (4358),
                  eIfcINoPollTableEntryMatched (4360),
                  eIfcINameResolutionFailed (4361),
                  eIfcINegotiatorChargeLocked (4369),
                  eIfcINegotiatorTimeLocked (4370),
                  eIfcINegotiatorNoDialNumber (4371),
                  eIfcINegotiatorNoRemote (4372),
                  eIfcINegotiatorRemoteBlocked (4373),
                  eIfcINegotiatorNoMulticonnect (4374),
                  eIfcINegotiatorLineError (4375),
                  eIfcIPhysicalChargeLocked (4385),
                  eIfcIPhysicalTimeLocked (4386),
                  eIfcIPhysicalNoDialNumber (4387),
                  eIfcIPhysicalNoRemote (4388),
                  eIfcIPhysicalNoServerAddress (4389),
                  eIfcIPhysicalRemoteLocked (4390),
                  eIfcIPhysicalNoMulticonnect (4391),
                  eIfcIConnectionLimitReached (4393),
                  eIfcRLicenseExceeded (4609),
                  eIfcRNoChannelAvailable (4610),
                  eIfcRNoRouteToRemoteGateway (4611),
                  eIfcRNoPppTableEntryMatched (4612),
                  eIfcRConnectionTimeoutDynamic (4613),
                  eIfcRConnectionTimeoutIkeIpsec (4614),
                  eIfcRConnectionLimitReached (4649),
                  eIfcXLinePollingFailed (4871),
                  eIfcXGwInsideRemoteNetwork (4874),
                  eIfcXPhysicalLineError (4904),
                  eIkeINoProposalMatched (8451),
                  eIkeIIkeKeyMismatch (8458),
                  eIkeIDpdTimeout (8461),
                  eIkeIUnableToGetIssuerCert (8462),
                  eIkeIUnableToGetCrl (8463),
                  eIkeIUnableToDecryptCertSignature (8464),
                  eIkeIUnableToDecryptCrlSignature (8465),
                  eIkeIUnableToDecodeIssuerPublicKey (8466),
                  eIkeICertSignatureFailure (8467),
                  eIkeICrlSignatureFailure (8468),
                  eIkeICertNotYetValid (8469),
                  eIkeICertHasExpired (8470),
                  eIkeICrlNotYetValid (8471),
                  eIkeICrlHasExpired (8472),
                  eIkeIErrorInCertNotBeforeField (8473),
                  eIkeIErrorInCertNotAfterField (8474),
                  eIkeIErrorInCrlLastUpdateField (8475),
                  eIkeIErrorInCrlNextUpdateField (8476),
                  eIkeIOutOfMem (8477),
                  eIkeIDepthZeroSelfSignedCert (8478),
                  eIkeISelfSignedCertInChain (8479),
                  eIkeIUnableToGetIssuerCertLocally (8480),
                  eIkeIUnableToVerifyLeafSignature (8481),
                  eIkeICertChainTooLong (8482),
                  eIkeICertRevoked (8483),
                  eIkeIInvalidCa (8484),
                  eIkeIPathLengthExceeded (8485),
                  eIkeIInvalidPurpose (8486),
                  eIkeICertUntrusted (8487),
                  eIkeICertRejected (8488),
                  eIkeISubjectIssuerMismatch (8489),
                  eIkeIAkidSkidMismatch (8490),
                  eIkeIAkidIssuerSerialMismatch (8491),
                  eIkeIKeyusageNoCertsign (8492),
                  eIkeIUnableToGetCrlIssuer (8493),
                  eIkeIUnhandledCriticalExtension (8494),
                  eIkeIKeyusageNoCrlSign (8495),
                  eIkeIUnhandledCriticalCrlExtension (8496),
                  eIkeICrlHasExceededExceedance (8497),
                  eIkeIApplicationVerification (8498),
                  eIkeICertRevokedUnspecified (8499),
                  eIkeICertRevokedKeyCompromise (8500),
                  eIkeICertRevokedCaCompromise (8501),
                  eIkeICertRevokedAffiliationChanged (8502),
                  eIkeICertRevokedSuperseded (8503),
                  eIkeICertRevokedCessationOfOperation (8504),
                  eIkeICertRevokedCertificateHold (8505),
                  eIkeICertRevokedRemoveFromCrl (8506),
                  eIkeICertRevokedPrivilegeWithdrawn (8507),
                  eIkeICertRevokedAACompromise (8508),
                  eIkeICertRevokedUnknownReason (8509),
                  eIkeIOutOfMemory (8702),
                  eIkeIGeneralFailure (8703),
                  eIkeRLicenseExceeded (8705),
                  eIkeRExchangeTypeMismatch (8706),
                  eIkeRNoProposalMatched (8707),
                  eIkeRIkeGroupMismatch (8708),
                  eIkeRLifeTypeUnsupported (8709),
                  eIkeRLifeDurationMismatch (8710),
                  eIkeRIdTypeUnsupported (8711),
                  eIkeRIdTypeMismatch (8712),
                  eIkeRNoRuleMatchedId (8713),
                  eIkeRIkeKeyMismatch (8714),
                  eIkeRLicenseDemosnExceeded (8715),
                  eIkeRLicenseSnExceeded (8716),
                  eIkeRDpdTimeout (8717),
                  eIkeRUnableToGetIssuerCert (8718),
                  eIkeRUnableToGetCrl (8719),
                  eIkeRUnableToDecryptCertSignature (8720),
                  eIkeRUnableToDecryptCrlSignature (8721),
                  eIkeRUnableToDecodeIssuerPublicKey (8722),
                  eIkeRCertSignatureFailure (8723),
                  eIkeRCrlSignatureFailure (8724),
                  eIkeRCertNotYetValid (8725),
                  eIkeRCertHasExpired (8726),
                  eIkeRCrlNotYetValid (8727),
                  eIkeRCrlHasExpired (8728),
                  eIkeRErrorInCertNotBeforeField (8729),
                  eIkeRErrorInCertNotAfterField (8730),
                  eIkeRErrorInCrlLastUpdateField (8731),
                  eIkeRErrorInCrlNextUpdateField (8732),
                  eIkeROutOfMem (8733),
                  eIkeRDepthZeroSelfSignedCert (8734),
                  eIkeRSelfSignedCertInChain (8735),
                  eIkeRUnableToGetIssuerCertLocally (8736),
                  eIkeRUnableToVerifyLeafSignature (8737),
                  eIkeRCertChainTooLong (8738),
                  eIkeRCertRevoked (8739),
                  eIkeRInvalidCa (8740),
                  eIkeRPathLengthExceeded (8741),
                  eIkeRInvalidPurpose (8742),
                  eIkeRCertUntrusted (8743),
                  eIkeRCertRejected (8744),
                  eIkeRSubjectIssuerMismatch (8745),
                  eIkeRAkidSkidMismatch (8746),
                  eIkeRAkidIssuerSerialMismatch (8747),
                  eIkeRKeyusageNoCertsign (8748),
                  eIkeRUnableToGetCrlIssuer (8749),
                  eIkeRUnhandledCriticalExtension (8750),
                  eIkeRKeyusageNoCrlSign (8751),
                  eIkeRUnhandledCriticalCrlExtension (8752),
                  eIkeRCrlHasExceededExceedance (8753),
                  eIkeRApplicationVerification (8754),
                  eIkeRCertRevokedUnspecified (8755),
                  eIkeRCertRevokedKeyCompromise (8756),
                  eIkeRCertRevokedCaCompromise (8757),
                  eIkeRCertRevokedAffiliationChanged (8758),
                  eIkeRCertRevokedSuperseded (8759),
                  eIkeRCertRevokedCessationOfOperation (8760),
                  eIkeRCertRevokedCertificateHold (8761),
                  eIkeRCertRevokedRemoveFromCrl (8762),
                  eIkeRCertRevokedPrivilegeWithdrawn (8763),
                  eIkeRCertRevokedAACompromise (8764),
                  eIkeRCertRevokedUnknownReason (8765),
                  eIkeRConnLimitReached (8784),
                  eIkeROutOfMemory (8958),
                  eIkeRGeneralFailure (8959),
                  eIpsecINoProposalMatched (12546),
                  eIpsecRNoRuleMatchedIds (12801),
                  eIpsecRNoProposalMatched (12802),
                  eIpsecRPfsGroupMismatch (12803),
                  eRemoteDisconnected (17153),
                  eManualDisconnect (17154),
                  eShortholdExpired (17155),
                  ePhysicalDisconnected (17156),
                  eInvalidPhysicalChannel (17157),
                  eDynamicVpnReconnect (17158),
                  eConfigurationChanged (17159),
                  eRemovedFromConfig (17160),
                  eBackupEstablished (17161),
                  eBackupEnd (17162)
            }
    MAX-ACCESS read-write
    STATUS     current
    DESCRIPTION
            ""
    ::= { lcsStatusVpnConnectionsEntry 16 }

-- {COLUMN} 1.3.6.1.4.1.2356.11.1.26.17.1.17
lcsStatusVpnConnectionsEntryClientSn OBJECT-TYPE
    SYNTAX     INTEGER {
                  eNotAvailable (-1),
                  eDemoVersion (0)
            }
    MAX-ACCESS read-only
    STATUS     current
    DESCRIPTION
            ""
    ::= { lcsStatusVpnConnectionsEntry 17 }

-- {COLUMN} 1.3.6.1.4.1.2356.11.1.26.17.1.18
lcsStatusVpnConnectionsEntryNatDetection OBJECT-TYPE
    SYNTAX     INTEGER {
                  eNoNat (0),
                  eNatLocal (1),
                  eNatRemote (2),
                  eNatBoth (3)
            }
    MAX-ACCESS read-only
    STATUS     current
    DESCRIPTION
            ""
    ::= { lcsStatusVpnConnectionsEntry 18 }

-- {COLUMN} 1.3.6.1.4.1.2356.11.1.26.17.1.19
lcsStatusVpnConnectionsEntryConnTime OBJECT-TYPE
    SYNTAX     Gauge32
    MAX-ACCESS read-only
    STATUS     current
    DESCRIPTION
            ""
    ::= { lcsStatusVpnConnectionsEntry 19 }

-- {COLUMN} 1.3.6.1.4.1.2356.11.1.26.17.1.20
lcsStatusVpnConnectionsEntrySslEncaps OBJECT-TYPE
    SYNTAX     INTEGER {
                  eNo (0),
                  eYes (1)
            }
    MAX-ACCESS read-only
    STATUS     current
    DESCRIPTION
            ""
    ::= { lcsStatusVpnConnectionsEntry 20 }

-- {COLUMN} 1.3.6.1.4.1.2356.11.1.26.17.1.21
lcsStatusVpnConnectionsEntryRemoteGwNew OBJECT-TYPE
    SYNTAX     DisplayString (SIZE(0..39))
    MAX-ACCESS read-only
    STATUS     current
    DESCRIPTION
            ""
    ::= { lcsStatusVpnConnectionsEntry 21 }

-- {COLUMN} 1.3.6.1.4.1.2356.11.1.26.17.1.22
lcsStatusVpnConnectionsEntryIkeType OBJECT-TYPE
    SYNTAX     DisplayString (SIZE(0..6))
    MAX-ACCESS read-only
    STATUS     current
    DESCRIPTION
            "-- empty --"
    ::= { lcsStatusVpnConnectionsEntry 22 }

-- {COLUMN} 1.3.6.1.4.1.2356.11.1.26.17.1.23
lcsStatusVpnConnectionsEntryEncapsulation OBJECT-TYPE
    SYNTAX     INTEGER {
                  eNone (0),
                  eUdp (1),
                  eSsl (2)
            }
    MAX-ACCESS read-only
    STATUS     current
    DESCRIPTION
            "-- empty --"
    ::= { lcsStatusVpnConnectionsEntry 23 }

-- {COLUMN} 1.3.6.1.4.1.2356.11.1.26.17.1.24
lcsStatusVpnConnectionsEntryHRxBytes OBJECT-TYPE
    SYNTAX     Integer32 (0..2147483647)
    MAX-ACCESS read-only
    STATUS     current
    DESCRIPTION
            "-- empty --"
    ::= { lcsStatusVpnConnectionsEntry 24 }

-- {COLUMN} 1.3.6.1.4.1.2356.11.1.26.17.1.25
lcsStatusVpnConnectionsEntryHTxBytes OBJECT-TYPE
    SYNTAX     Integer32 (0..2147483647)
    MAX-ACCESS read-only
    STATUS     current
    DESCRIPTION
            "-- empty --"
    ::= { lcsStatusVpnConnectionsEntry 25 }

-- {SCALAR} 1.3.6.1.4.1.2356.11.1.26.20
lcsStatusVpnRxPackets OBJECT-TYPE
    SYNTAX     Counter32
    MAX-ACCESS read-only
    STATUS     current
    DESCRIPTION
            ""
    ::= { lcsStatusVpn 20 }

-- {SCALAR} 1.3.6.1.4.1.2356.11.1.26.21
lcsStatusVpnTxPackets OBJECT-TYPE
    SYNTAX     Counter32
    MAX-ACCESS read-only
    STATUS     current
    DESCRIPTION
            ""
    ::= { lcsStatusVpn 21 }

-- {SCALAR} 1.3.6.1.4.1.2356.11.1.26.22
lcsStatusVpnTxDropped OBJECT-TYPE
    SYNTAX     Counter32
    MAX-ACCESS read-only
    STATUS     current
    DESCRIPTION
            ""
    ::= { lcsStatusVpn 22 }

-- {SCALAR} 1.3.6.1.4.1.2356.11.1.26.23
lcsStatusVpnRxErrors OBJECT-TYPE
    SYNTAX     Counter32
    MAX-ACCESS read-only
    STATUS     current
    DESCRIPTION
            ""
    ::= { lcsStatusVpn 23 }

-- {SCALAR} 1.3.6.1.4.1.2356.11.1.26.25
lcsStatusVpnTxInvalid OBJECT-TYPE
    SYNTAX     Counter64
    MAX-ACCESS read-only
    STATUS     current
    DESCRIPTION
            ""
    ::= { lcsStatusVpn 25 }

-- {SCALAR} 1.3.6.1.4.1.2356.11.1.26.26
lcsStatusVpnTxNoSa OBJECT-TYPE
    SYNTAX     Counter64
    MAX-ACCESS read-only
    STATUS     current
    DESCRIPTION
            ""
    ::= { lcsStatusVpn 26 }

-- {SCALAR} 1.3.6.1.4.1.2356.11.1.26.27
lcsStatusVpnTxNoPolicy OBJECT-TYPE
    SYNTAX     Counter64
    MAX-ACCESS read-only
    STATUS     current
    DESCRIPTION
            ""
    ::= { lcsStatusVpn 27 }

-- {SCALAR} 1.3.6.1.4.1.2356.11.1.26.28
lcsStatusVpnRxEspAuthFail OBJECT-TYPE
    SYNTAX     Counter64
    MAX-ACCESS read-only
    STATUS     current
    DESCRIPTION
            ""
    ::= { lcsStatusVpn 28 }

-- {SCALAR} 1.3.6.1.4.1.2356.11.1.26.29
lcsStatusVpnRxAhAuthFail OBJECT-TYPE
    SYNTAX     Counter64
    MAX-ACCESS read-only
    STATUS     current
    DESCRIPTION
            ""
    ::= { lcsStatusVpn 29 }

-- {SCALAR} 1.3.6.1.4.1.2356.11.1.26.30
lcsStatusVpnRxIpcompFail OBJECT-TYPE
    SYNTAX     Counter64
    MAX-ACCESS read-only
    STATUS     current
    DESCRIPTION
            ""
    ::= { lcsStatusVpn 30 }

-- {SCALAR} 1.3.6.1.4.1.2356.11.1.26.31
lcsStatusVpnRxEspReplay OBJECT-TYPE
    SYNTAX     Counter64
    MAX-ACCESS read-only
    STATUS     current
    DESCRIPTION
            ""
    ::= { lcsStatusVpn 31 }

-- {SCALAR} 1.3.6.1.4.1.2356.11.1.26.32
lcsStatusVpnRxAhReplay OBJECT-TYPE
    SYNTAX     Counter64
    MAX-ACCESS read-only
    STATUS     current
    DESCRIPTION
            ""
    ::= { lcsStatusVpn 32 }

-- {SCALAR} 1.3.6.1.4.1.2356.11.1.26.33
lcsStatusVpnRxBadSpi OBJECT-TYPE
    SYNTAX     Counter64
    MAX-ACCESS read-only
    STATUS     current
    DESCRIPTION
            ""
    ::= { lcsStatusVpn 33 }

-- {SCALAR} 1.3.6.1.4.1.2356.11.1.26.34
lcsStatusVpnRxInvalid OBJECT-TYPE
    SYNTAX     Counter64
    MAX-ACCESS read-only
    STATUS     current
    DESCRIPTION
            ""
    ::= { lcsStatusVpn 34 }

-- {SCALAR} 1.3.6.1.4.1.2356.11.1.26.35
lcsStatusVpnRxNoSa OBJECT-TYPE
    SYNTAX     Counter64
    MAX-ACCESS read-only
    STATUS     current
    DESCRIPTION
            ""
    ::= { lcsStatusVpn 35 }

-- {SCALAR} 1.3.6.1.4.1.2356.11.1.26.36
lcsStatusVpnQueueError OBJECT-TYPE
    SYNTAX     Counter64
    MAX-ACCESS read-only
    STATUS     current
    DESCRIPTION
            ""
    ::= { lcsStatusVpn 36 }

-- {NODE} 1.3.6.1.4.1.2356.11.1.26.37
lcsStatusVpnDhGroups OBJECT IDENTIFIER ::= { lcsStatusVpn 37 }

-- {TABLE} 1.3.6.1.4.1.2356.11.1.26.37.5
lcsStatusVpnDhGroupsPrecalculationTable OBJECT-TYPE
    SYNTAX     SEQUENCE OF LcsStatusVpnDhGroupsPrecalculationEntry
    MAX-ACCESS not-accessible
    STATUS     current
    DESCRIPTION
            "-- empty --"
    ::= { lcsStatusVpnDhGroups 5 }

-- {ROW} 1.3.6.1.4.1.2356.11.1.26.37.5.1
lcsStatusVpnDhGroupsPrecalculationEntry OBJECT-TYPE
    SYNTAX     LcsStatusVpnDhGroupsPrecalculationEntry
    MAX-ACCESS not-accessible
    STATUS     current
    DESCRIPTION
            ""
    INDEX {
            lcsStatusVpnDhGroupsPrecalculationEntryDhGroup
          }
    ::= { lcsStatusVpnDhGroupsPrecalculationTable 1 }

LcsStatusVpnDhGroupsPrecalculationEntry ::= SEQUENCE {
            lcsStatusVpnDhGroupsPrecalculationEntryDhGroup Integer32,
            lcsStatusVpnDhGroupsPrecalculationEntryRuleDependentTarget Integer32,
            lcsStatusVpnDhGroupsPrecalculationEntryConfiguredTarget Integer32,
            lcsStatusVpnDhGroupsPrecalculationEntryActualTarget Integer32,
            lcsStatusVpnDhGroupsPrecalculationEntryCurrentStock Integer32
    }

-- {COLUMN} 1.3.6.1.4.1.2356.11.1.26.37.5.1.1
lcsStatusVpnDhGroupsPrecalculationEntryDhGroup OBJECT-TYPE
    SYNTAX     Integer32 (0..2147483647)
    MAX-ACCESS read-only
    STATUS     current
    DESCRIPTION
            "-- empty --"
    ::= { lcsStatusVpnDhGroupsPrecalculationEntry 1 }

-- {COLUMN} 1.3.6.1.4.1.2356.11.1.26.37.5.1.2
lcsStatusVpnDhGroupsPrecalculationEntryRuleDependentTarget OBJECT-TYPE
    SYNTAX     Integer32 (0..2147483647)
    MAX-ACCESS read-only
    STATUS     current
    DESCRIPTION
            "-- empty --"
    ::= { lcsStatusVpnDhGroupsPrecalculationEntry 2 }

-- {COLUMN} 1.3.6.1.4.1.2356.11.1.26.37.5.1.3
lcsStatusVpnDhGroupsPrecalculationEntryConfiguredTarget OBJECT-TYPE
    SYNTAX     Integer32 (0..2147483647)
    MAX-ACCESS read-only
    STATUS     current
    DESCRIPTION
            "-- empty --"
    ::= { lcsStatusVpnDhGroupsPrecalculationEntry 3 }

-- {COLUMN} 1.3.6.1.4.1.2356.11.1.26.37.5.1.4
lcsStatusVpnDhGroupsPrecalculationEntryActualTarget OBJECT-TYPE
    SYNTAX     Integer32 (0..2147483647)
    MAX-ACCESS read-only
    STATUS     current
    DESCRIPTION
            "-- empty --"
    ::= { lcsStatusVpnDhGroupsPrecalculationEntry 4 }

-- {COLUMN} 1.3.6.1.4.1.2356.11.1.26.37.5.1.5
lcsStatusVpnDhGroupsPrecalculationEntryCurrentStock OBJECT-TYPE
    SYNTAX     Integer32 (0..2147483647)
    MAX-ACCESS read-only
    STATUS     current
    DESCRIPTION
            "-- empty --"
    ::= { lcsStatusVpnDhGroupsPrecalculationEntry 5 }

-- {SCALAR} 1.3.6.1.4.1.2356.11.1.26.38
lcsStatusVpnDeleteConnErrors OBJECT-TYPE
    SYNTAX     DisplayString
    MAX-ACCESS read-write
    STATUS     current
    DESCRIPTION
            "-- empty --"
    ::= { lcsStatusVpn 38 }

-- {NODE} 1.3.6.1.4.1.2356.11.1.26.39
lcsStatusVpnRadius OBJECT IDENTIFIER ::= { lcsStatusVpn 39 }

-- {TABLE} 1.3.6.1.4.1.2356.11.1.26.39.1
lcsStatusVpnRadiusAuthorizationTable OBJECT-TYPE
    SYNTAX     SEQUENCE OF LcsStatusVpnRadiusAuthorizationEntry
    MAX-ACCESS not-accessible
    STATUS     current
    DESCRIPTION
            "-- empty --"
    ::= { lcsStatusVpnRadius 1 }

-- {ROW} 1.3.6.1.4.1.2356.11.1.26.39.1.1
lcsStatusVpnRadiusAuthorizationEntry OBJECT-TYPE
    SYNTAX     LcsStatusVpnRadiusAuthorizationEntry
    MAX-ACCESS not-accessible
    STATUS     current
    DESCRIPTION
            ""
    INDEX {
            lcsStatusVpnRadiusAuthorizationEntryPeer
          }
    ::= { lcsStatusVpnRadiusAuthorizationTable 1 }

LcsStatusVpnRadiusAuthorizationEntry ::= SEQUENCE {
            lcsStatusVpnRadiusAuthorizationEntryPeer OCTET STRING,
            lcsStatusVpnRadiusAuthorizationEntryRemoteId OCTET STRING,
            lcsStatusVpnRadiusAuthorizationEntryLocalGateway OCTET STRING,
            lcsStatusVpnRadiusAuthorizationEntryRemoteGateway OCTET STRING,
            lcsStatusVpnRadiusAuthorizationEntryState INTEGER,
            lcsStatusVpnRadiusAuthorizationEntryServerHostname OCTET STRING,
            lcsStatusVpnRadiusAuthorizationEntryCfgIpv4Address OCTET STRING,
            lcsStatusVpnRadiusAuthorizationEntryCfgIpv4DnsServers OCTET STRING,
            lcsStatusVpnRadiusAuthorizationEntryCfgIpv4Pool OCTET STRING,
            lcsStatusVpnRadiusAuthorizationEntryCfgIpv6Address OCTET STRING,
            lcsStatusVpnRadiusAuthorizationEntryCfgIpv6DnsServers OCTET STRING,
            lcsStatusVpnRadiusAuthorizationEntryCfgIpv6Pool OCTET STRING,
            lcsStatusVpnRadiusAuthorizationEntryRtgTag OCTET STRING,
            lcsStatusVpnRadiusAuthorizationEntryFramedIpv4Routes OCTET STRING,
            lcsStatusVpnRadiusAuthorizationEntryFramedIpv6Routes OCTET STRING,
            lcsStatusVpnRadiusAuthorizationEntryIkeIpv4Routes OCTET STRING,
            lcsStatusVpnRadiusAuthorizationEntryIkeIpv6Routes OCTET STRING,
            lcsStatusVpnRadiusAuthorizationEntryOtherAttributes OCTET STRING,
            lcsStatusVpnRadiusAuthorizationEntryCoaActive INTEGER,
            lcsStatusVpnRadiusAuthorizationEntryLoadBalancer OCTET STRING,
            lcsStatusVpnRadiusAuthorizationEntryClientBinding INTEGER
    }

-- {COLUMN} 1.3.6.1.4.1.2356.11.1.26.39.1.1.1
lcsStatusVpnRadiusAuthorizationEntryPeer OBJECT-TYPE
    SYNTAX     OCTET STRING (SIZE(0..17))
    MAX-ACCESS read-only
    STATUS     current
    DESCRIPTION
            "-- empty --"
    ::= { lcsStatusVpnRadiusAuthorizationEntry 1 }

-- {COLUMN} 1.3.6.1.4.1.2356.11.1.26.39.1.1.2
lcsStatusVpnRadiusAuthorizationEntryRemoteId OBJECT-TYPE
    SYNTAX     OCTET STRING (SIZE(0..255))
    MAX-ACCESS read-only
    STATUS     current
    DESCRIPTION
            "-- empty --"
    ::= { lcsStatusVpnRadiusAuthorizationEntry 2 }

-- {COLUMN} 1.3.6.1.4.1.2356.11.1.26.39.1.1.3
lcsStatusVpnRadiusAuthorizationEntryLocalGateway OBJECT-TYPE
    SYNTAX     OCTET STRING (SIZE(0..40))
    MAX-ACCESS read-only
    STATUS     current
    DESCRIPTION
            "-- empty --"
    ::= { lcsStatusVpnRadiusAuthorizationEntry 3 }

-- {COLUMN} 1.3.6.1.4.1.2356.11.1.26.39.1.1.4
lcsStatusVpnRadiusAuthorizationEntryRemoteGateway OBJECT-TYPE
    SYNTAX     OCTET STRING (SIZE(0..40))
    MAX-ACCESS read-only
    STATUS     current
    DESCRIPTION
            "-- empty --"
    ::= { lcsStatusVpnRadiusAuthorizationEntry 4 }

-- {COLUMN} 1.3.6.1.4.1.2356.11.1.26.39.1.1.5
lcsStatusVpnRadiusAuthorizationEntryState OBJECT-TYPE
    SYNTAX     INTEGER {
                  eRunning (0),
                  eSucceeded (1),
                  eFailed (2)
            }
    MAX-ACCESS read-only
    STATUS     current
    DESCRIPTION
            "-- empty --"
    ::= { lcsStatusVpnRadiusAuthorizationEntry 5 }

-- {COLUMN} 1.3.6.1.4.1.2356.11.1.26.39.1.1.6
lcsStatusVpnRadiusAuthorizationEntryServerHostname OBJECT-TYPE
    SYNTAX     OCTET STRING (SIZE(0..65))
    MAX-ACCESS read-only
    STATUS     current
    DESCRIPTION
            "-- empty --"
    ::= { lcsStatusVpnRadiusAuthorizationEntry 6 }

-- {COLUMN} 1.3.6.1.4.1.2356.11.1.26.39.1.1.7
lcsStatusVpnRadiusAuthorizationEntryCfgIpv4Address OBJECT-TYPE
    SYNTAX     OCTET STRING (SIZE(0..16))
    MAX-ACCESS read-only
    STATUS     current
    DESCRIPTION
            "-- empty --"
    ::= { lcsStatusVpnRadiusAuthorizationEntry 7 }

-- {COLUMN} 1.3.6.1.4.1.2356.11.1.26.39.1.1.8
lcsStatusVpnRadiusAuthorizationEntryCfgIpv4DnsServers OBJECT-TYPE
    SYNTAX     OCTET STRING (SIZE(0..64))
    MAX-ACCESS read-only
    STATUS     current
    DESCRIPTION
            "-- empty --"
    ::= { lcsStatusVpnRadiusAuthorizationEntry 8 }

-- {COLUMN} 1.3.6.1.4.1.2356.11.1.26.39.1.1.9
lcsStatusVpnRadiusAuthorizationEntryCfgIpv4Pool OBJECT-TYPE
    SYNTAX     OCTET STRING (SIZE(0..17))
    MAX-ACCESS read-only
    STATUS     current
    DESCRIPTION
            "-- empty --"
    ::= { lcsStatusVpnRadiusAuthorizationEntry 9 }

-- {COLUMN} 1.3.6.1.4.1.2356.11.1.26.39.1.1.10
lcsStatusVpnRadiusAuthorizationEntryCfgIpv6Address OBJECT-TYPE
    SYNTAX     OCTET STRING (SIZE(0..40))
    MAX-ACCESS read-only
    STATUS     current
    DESCRIPTION
            "-- empty --"
    ::= { lcsStatusVpnRadiusAuthorizationEntry 10 }

-- {COLUMN} 1.3.6.1.4.1.2356.11.1.26.39.1.1.11
lcsStatusVpnRadiusAuthorizationEntryCfgIpv6DnsServers OBJECT-TYPE
    SYNTAX     OCTET STRING (SIZE(0..128))
    MAX-ACCESS read-only
    STATUS     current
    DESCRIPTION
            "-- empty --"
    ::= { lcsStatusVpnRadiusAuthorizationEntry 11 }

-- {COLUMN} 1.3.6.1.4.1.2356.11.1.26.39.1.1.12
lcsStatusVpnRadiusAuthorizationEntryCfgIpv6Pool OBJECT-TYPE
    SYNTAX     OCTET STRING (SIZE(0..17))
    MAX-ACCESS read-only
    STATUS     current
    DESCRIPTION
            "-- empty --"
    ::= { lcsStatusVpnRadiusAuthorizationEntry 12 }

-- {COLUMN} 1.3.6.1.4.1.2356.11.1.26.39.1.1.13
lcsStatusVpnRadiusAuthorizationEntryRtgTag OBJECT-TYPE
    SYNTAX     OCTET STRING (SIZE(0..6))
    MAX-ACCESS read-only
    STATUS     current
    DESCRIPTION
            "-- empty --"
    ::= { lcsStatusVpnRadiusAuthorizationEntry 13 }

-- {COLUMN} 1.3.6.1.4.1.2356.11.1.26.39.1.1.14
lcsStatusVpnRadiusAuthorizationEntryFramedIpv4Routes OBJECT-TYPE
    SYNTAX     OCTET STRING (SIZE(0..255))
    MAX-ACCESS read-only
    STATUS     current
    DESCRIPTION
            "-- empty --"
    ::= { lcsStatusVpnRadiusAuthorizationEntry 14 }

-- {COLUMN} 1.3.6.1.4.1.2356.11.1.26.39.1.1.15
lcsStatusVpnRadiusAuthorizationEntryFramedIpv6Routes OBJECT-TYPE
    SYNTAX     OCTET STRING (SIZE(0..255))
    MAX-ACCESS read-only
    STATUS     current
    DESCRIPTION
            "-- empty --"
    ::= { lcsStatusVpnRadiusAuthorizationEntry 15 }

-- {COLUMN} 1.3.6.1.4.1.2356.11.1.26.39.1.1.16
lcsStatusVpnRadiusAuthorizationEntryIkeIpv4Routes OBJECT-TYPE
    SYNTAX     OCTET STRING (SIZE(0..255))
    MAX-ACCESS read-only
    STATUS     current
    DESCRIPTION
            "-- empty --"
    ::= { lcsStatusVpnRadiusAuthorizationEntry 16 }

-- {COLUMN} 1.3.6.1.4.1.2356.11.1.26.39.1.1.17
lcsStatusVpnRadiusAuthorizationEntryIkeIpv6Routes OBJECT-TYPE
    SYNTAX     OCTET STRING (SIZE(0..255))
    MAX-ACCESS read-only
    STATUS     current
    DESCRIPTION
            "-- empty --"
    ::= { lcsStatusVpnRadiusAuthorizationEntry 17 }

-- {COLUMN} 1.3.6.1.4.1.2356.11.1.26.39.1.1.18
lcsStatusVpnRadiusAuthorizationEntryOtherAttributes OBJECT-TYPE
    SYNTAX     OCTET STRING (SIZE(0..255))
    MAX-ACCESS read-only
    STATUS     current
    DESCRIPTION
            "-- empty --"
    ::= { lcsStatusVpnRadiusAuthorizationEntry 18 }

-- {COLUMN} 1.3.6.1.4.1.2356.11.1.26.39.1.1.19
lcsStatusVpnRadiusAuthorizationEntryCoaActive OBJECT-TYPE
    SYNTAX     INTEGER {
                  eNo (0),
                  eYes (1)
            }
    MAX-ACCESS read-only
    STATUS     current
    DESCRIPTION
            "-- empty --"
    ::= { lcsStatusVpnRadiusAuthorizationEntry 19 }

-- {COLUMN} 1.3.6.1.4.1.2356.11.1.26.39.1.1.20
lcsStatusVpnRadiusAuthorizationEntryLoadBalancer OBJECT-TYPE
    SYNTAX     OCTET STRING (SIZE(0..17))
    MAX-ACCESS read-only
    STATUS     current
    DESCRIPTION
            "-- empty --"
    ::= { lcsStatusVpnRadiusAuthorizationEntry 20 }

-- {COLUMN} 1.3.6.1.4.1.2356.11.1.26.39.1.1.21
lcsStatusVpnRadiusAuthorizationEntryClientBinding OBJECT-TYPE
    SYNTAX     INTEGER {
                  eNo (0),
                  eYes (1)
            }
    MAX-ACCESS read-only
    STATUS     current
    DESCRIPTION
            "-- empty --"
    ::= { lcsStatusVpnRadiusAuthorizationEntry 21 }

-- {TABLE} 1.3.6.1.4.1.2356.11.1.26.39.2
lcsStatusVpnRadiusAccountingTable OBJECT-TYPE
    SYNTAX     SEQUENCE OF LcsStatusVpnRadiusAccountingEntry
    MAX-ACCESS not-accessible
    STATUS     current
    DESCRIPTION
            "-- empty --"
    ::= { lcsStatusVpnRadius 2 }

-- {ROW} 1.3.6.1.4.1.2356.11.1.26.39.2.1
lcsStatusVpnRadiusAccountingEntry OBJECT-TYPE
    SYNTAX     LcsStatusVpnRadiusAccountingEntry
    MAX-ACCESS not-accessible
    STATUS     current
    DESCRIPTION
            ""
    INDEX {
            lcsStatusVpnRadiusAccountingEntryPeer
          }
    ::= { lcsStatusVpnRadiusAccountingTable 1 }

LcsStatusVpnRadiusAccountingEntry ::= SEQUENCE {
            lcsStatusVpnRadiusAccountingEntryPeer OCTET STRING,
            lcsStatusVpnRadiusAccountingEntrySessionId OCTET STRING,
            lcsStatusVpnRadiusAccountingEntryRemoteId OCTET STRING,
            lcsStatusVpnRadiusAccountingEntryLocalGateway OCTET STRING,
            lcsStatusVpnRadiusAccountingEntryRemoteGateway OCTET STRING,
            lcsStatusVpnRadiusAccountingEntryCfgIpv4Address OCTET STRING,
            lcsStatusVpnRadiusAccountingEntryCfgIpv6Address OCTET STRING,
            lcsStatusVpnRadiusAccountingEntryState INTEGER,
            lcsStatusVpnRadiusAccountingEntryServerHostname OCTET STRING,
            lcsStatusVpnRadiusAccountingEntrySessionTime Unsigned32,
            lcsStatusVpnRadiusAccountingEntryInputOctets Counter64,
            lcsStatusVpnRadiusAccountingEntryOutputOctets Counter64,
            lcsStatusVpnRadiusAccountingEntryInputPackets Unsigned32,
            lcsStatusVpnRadiusAccountingEntryOutputPackets Unsigned32
    }

-- {COLUMN} 1.3.6.1.4.1.2356.11.1.26.39.2.1.1
lcsStatusVpnRadiusAccountingEntryPeer OBJECT-TYPE
    SYNTAX     OCTET STRING (SIZE(0..17))
    MAX-ACCESS read-only
    STATUS     current
    DESCRIPTION
            "-- empty --"
    ::= { lcsStatusVpnRadiusAccountingEntry 1 }

-- {COLUMN} 1.3.6.1.4.1.2356.11.1.26.39.2.1.2
lcsStatusVpnRadiusAccountingEntrySessionId OBJECT-TYPE
    SYNTAX     OCTET STRING (SIZE(0..37))
    MAX-ACCESS read-only
    STATUS     current
    DESCRIPTION
            "-- empty --"
    ::= { lcsStatusVpnRadiusAccountingEntry 2 }

-- {COLUMN} 1.3.6.1.4.1.2356.11.1.26.39.2.1.3
lcsStatusVpnRadiusAccountingEntryRemoteId OBJECT-TYPE
    SYNTAX     OCTET STRING (SIZE(0..255))
    MAX-ACCESS read-only
    STATUS     current
    DESCRIPTION
            "-- empty --"
    ::= { lcsStatusVpnRadiusAccountingEntry 3 }

-- {COLUMN} 1.3.6.1.4.1.2356.11.1.26.39.2.1.4
lcsStatusVpnRadiusAccountingEntryLocalGateway OBJECT-TYPE
    SYNTAX     OCTET STRING (SIZE(0..40))
    MAX-ACCESS read-only
    STATUS     current
    DESCRIPTION
            "-- empty --"
    ::= { lcsStatusVpnRadiusAccountingEntry 4 }

-- {COLUMN} 1.3.6.1.4.1.2356.11.1.26.39.2.1.5
lcsStatusVpnRadiusAccountingEntryRemoteGateway OBJECT-TYPE
    SYNTAX     OCTET STRING (SIZE(0..40))
    MAX-ACCESS read-only
    STATUS     current
    DESCRIPTION
            "-- empty --"
    ::= { lcsStatusVpnRadiusAccountingEntry 5 }

-- {COLUMN} 1.3.6.1.4.1.2356.11.1.26.39.2.1.6
lcsStatusVpnRadiusAccountingEntryCfgIpv4Address OBJECT-TYPE
    SYNTAX     OCTET STRING (SIZE(0..16))
    MAX-ACCESS read-only
    STATUS     current
    DESCRIPTION
            "-- empty --"
    ::= { lcsStatusVpnRadiusAccountingEntry 6 }

-- {COLUMN} 1.3.6.1.4.1.2356.11.1.26.39.2.1.7
lcsStatusVpnRadiusAccountingEntryCfgIpv6Address OBJECT-TYPE
    SYNTAX     OCTET STRING (SIZE(0..40))
    MAX-ACCESS read-only
    STATUS     current
    DESCRIPTION
            "-- empty --"
    ::= { lcsStatusVpnRadiusAccountingEntry 7 }

-- {COLUMN} 1.3.6.1.4.1.2356.11.1.26.39.2.1.8
lcsStatusVpnRadiusAccountingEntryState OBJECT-TYPE
    SYNTAX     INTEGER {
                  eStarting (0),
                  eStartFailed (1),
                  eRunning (2),
                  eUpdateFailed (3)
            }
    MAX-ACCESS read-only
    STATUS     current
    DESCRIPTION
            "-- empty --"
    ::= { lcsStatusVpnRadiusAccountingEntry 8 }

-- {COLUMN} 1.3.6.1.4.1.2356.11.1.26.39.2.1.9
lcsStatusVpnRadiusAccountingEntryServerHostname OBJECT-TYPE
    SYNTAX     OCTET STRING (SIZE(0..65))
    MAX-ACCESS read-only
    STATUS     current
    DESCRIPTION
            "-- empty --"
    ::= { lcsStatusVpnRadiusAccountingEntry 9 }

-- {COLUMN} 1.3.6.1.4.1.2356.11.1.26.39.2.1.10
lcsStatusVpnRadiusAccountingEntrySessionTime OBJECT-TYPE
    SYNTAX     Unsigned32 (0..4294967295)
    MAX-ACCESS read-only
    STATUS     current
    DESCRIPTION
            "-- empty --"
    ::= { lcsStatusVpnRadiusAccountingEntry 10 }

-- {COLUMN} 1.3.6.1.4.1.2356.11.1.26.39.2.1.11
lcsStatusVpnRadiusAccountingEntryInputOctets OBJECT-TYPE
    SYNTAX     Counter64
    MAX-ACCESS read-only
    STATUS     current
    DESCRIPTION
            "-- empty --"
    ::= { lcsStatusVpnRadiusAccountingEntry 11 }

-- {COLUMN} 1.3.6.1.4.1.2356.11.1.26.39.2.1.12
lcsStatusVpnRadiusAccountingEntryOutputOctets OBJECT-TYPE
    SYNTAX     Counter64
    MAX-ACCESS read-only
    STATUS     current
    DESCRIPTION
            "-- empty --"
    ::= { lcsStatusVpnRadiusAccountingEntry 12 }

-- {COLUMN} 1.3.6.1.4.1.2356.11.1.26.39.2.1.13
lcsStatusVpnRadiusAccountingEntryInputPackets OBJECT-TYPE
    SYNTAX     Unsigned32 (0..4294967295)
    MAX-ACCESS read-only
    STATUS     current
    DESCRIPTION
            "-- empty --"
    ::= { lcsStatusVpnRadiusAccountingEntry 13 }

-- {COLUMN} 1.3.6.1.4.1.2356.11.1.26.39.2.1.14
lcsStatusVpnRadiusAccountingEntryOutputPackets OBJECT-TYPE
    SYNTAX     Unsigned32 (0..4294967295)
    MAX-ACCESS read-only
    STATUS     current
    DESCRIPTION
            "-- empty --"
    ::= { lcsStatusVpnRadiusAccountingEntry 14 }

-- {SCALAR} 1.3.6.1.4.1.2356.11.1.26.40
lcsStatusVpnLicenses OBJECT-TYPE
    SYNTAX     Integer32 (0..2147483647)
    MAX-ACCESS read-only
    STATUS     current
    DESCRIPTION
            "-- empty --"
    ::= { lcsStatusVpn 40 }

-- {TABLE} 1.3.6.1.4.1.2356.11.1.26.41
lcsStatusVpnLmcTable OBJECT-TYPE
    SYNTAX     SEQUENCE OF LcsStatusVpnLmcEntry
    MAX-ACCESS not-accessible
    STATUS     current
    DESCRIPTION
            "-- empty --"
    ::= { lcsStatusVpn 41 }

-- {ROW} 1.3.6.1.4.1.2356.11.1.26.41.1
lcsStatusVpnLmcEntry OBJECT-TYPE
    SYNTAX     LcsStatusVpnLmcEntry
    MAX-ACCESS not-accessible
    STATUS     current
    DESCRIPTION
            ""
    INDEX {
            lcsStatusVpnLmcEntryPeer
          }
    ::= { lcsStatusVpnLmcTable 1 }

LcsStatusVpnLmcEntry ::= SEQUENCE {
            lcsStatusVpnLmcEntryPeer DisplayString,
            lcsStatusVpnLmcEntryLmcId DisplayString
    }

-- {COLUMN} 1.3.6.1.4.1.2356.11.1.26.41.1.1
lcsStatusVpnLmcEntryPeer OBJECT-TYPE
    SYNTAX     DisplayString (SIZE(0..255))
    MAX-ACCESS read-only
    STATUS     current
    DESCRIPTION
            "-- empty --"
    ::= { lcsStatusVpnLmcEntry 1 }

-- {COLUMN} 1.3.6.1.4.1.2356.11.1.26.41.1.2
lcsStatusVpnLmcEntryLmcId OBJECT-TYPE
    SYNTAX     DisplayString (SIZE(0..100))
    MAX-ACCESS read-only
    STATUS     current
    DESCRIPTION
            "-- empty --"
    ::= { lcsStatusVpnLmcEntry 2 }

-- {SCALAR} 1.3.6.1.4.1.2356.11.1.26.44
lcsStatusVpnLicensesInUse OBJECT-TYPE
    SYNTAX     Integer32 (0..2147483647)
    MAX-ACCESS read-only
    STATUS     current
    DESCRIPTION
            "-- empty --"
    ::= { lcsStatusVpn 44 }

-- {NODE} 1.3.6.1.4.1.2356.11.1.26.50
lcsStatusVpnLoadBalancer OBJECT IDENTIFIER ::= { lcsStatusVpn 50 }

-- {SCALAR} 1.3.6.1.4.1.2356.11.1.26.50.1
lcsStatusVpnLoadBalancerOperating OBJECT-TYPE
    SYNTAX     INTEGER {
                  eNo (0),
                  eYes (1)
            }
    MAX-ACCESS read-only
    STATUS     current
    DESCRIPTION
            "-- empty --"
    ::= { lcsStatusVpnLoadBalancer 1 }

-- {TABLE} 1.3.6.1.4.1.2356.11.1.26.50.3
lcsStatusVpnLoadBalancerPeerStatusTable OBJECT-TYPE
    SYNTAX     SEQUENCE OF LcsStatusVpnLoadBalancerPeerStatusEntry
    MAX-ACCESS not-accessible
    STATUS     current
    DESCRIPTION
            "-- empty --"
    ::= { lcsStatusVpnLoadBalancer 3 }

-- {ROW} 1.3.6.1.4.1.2356.11.1.26.50.3.1
lcsStatusVpnLoadBalancerPeerStatusEntry OBJECT-TYPE
    SYNTAX     LcsStatusVpnLoadBalancerPeerStatusEntry
    MAX-ACCESS not-accessible
    STATUS     current
    DESCRIPTION
            ""
    INDEX {
            lcsStatusVpnLoadBalancerPeerStatusEntryPeerAddress,
            lcsStatusVpnLoadBalancerPeerStatusEntryVlbInstanceId
          }
    ::= { lcsStatusVpnLoadBalancerPeerStatusTable 1 }

LcsStatusVpnLoadBalancerPeerStatusEntry ::= SEQUENCE {
            lcsStatusVpnLoadBalancerPeerStatusEntryPeerAddress OCTET STRING,
            lcsStatusVpnLoadBalancerPeerStatusEntryVlbInstanceId Unsigned32,
            lcsStatusVpnLoadBalancerPeerStatusEntryVrrpMaster INTEGER,
            lcsStatusVpnLoadBalancerPeerStatusEntryBestTarget INTEGER,
            lcsStatusVpnLoadBalancerPeerStatusEntrySystemName OCTET STRING,
            lcsStatusVpnLoadBalancerPeerStatusEntryIpv4Target OCTET STRING,
            lcsStatusVpnLoadBalancerPeerStatusEntryCpuLoad OCTET STRING,
            lcsStatusVpnLoadBalancerPeerStatusEntryTotalVpn OCTET STRING,
            lcsStatusVpnLoadBalancerPeerStatusEntryUsedVpn OCTET STRING
    }

-- {COLUMN} 1.3.6.1.4.1.2356.11.1.26.50.3.1.1
lcsStatusVpnLoadBalancerPeerStatusEntryPeerAddress OBJECT-TYPE
    SYNTAX     OCTET STRING (SIZE(0..39))
    MAX-ACCESS read-only
    STATUS     current
    DESCRIPTION
            "-- empty --"
    ::= { lcsStatusVpnLoadBalancerPeerStatusEntry 1 }

-- {COLUMN} 1.3.6.1.4.1.2356.11.1.26.50.3.1.2
lcsStatusVpnLoadBalancerPeerStatusEntryVlbInstanceId OBJECT-TYPE
    SYNTAX     Unsigned32 (0..255)
    MAX-ACCESS read-only
    STATUS     current
    DESCRIPTION
            "-- empty --"
    ::= { lcsStatusVpnLoadBalancerPeerStatusEntry 2 }

-- {COLUMN} 1.3.6.1.4.1.2356.11.1.26.50.3.1.3
lcsStatusVpnLoadBalancerPeerStatusEntryVrrpMaster OBJECT-TYPE
    SYNTAX     INTEGER {
                  eNo (0),
                  eYes (1)
            }
    MAX-ACCESS read-only
    STATUS     current
    DESCRIPTION
            "-- empty --"
    ::= { lcsStatusVpnLoadBalancerPeerStatusEntry 3 }

-- {COLUMN} 1.3.6.1.4.1.2356.11.1.26.50.3.1.4
lcsStatusVpnLoadBalancerPeerStatusEntryBestTarget OBJECT-TYPE
    SYNTAX     INTEGER {
                  eNo (0),
                  eYes (1)
            }
    MAX-ACCESS read-only
    STATUS     current
    DESCRIPTION
            "-- empty --"
    ::= { lcsStatusVpnLoadBalancerPeerStatusEntry 4 }

-- {COLUMN} 1.3.6.1.4.1.2356.11.1.26.50.3.1.5
lcsStatusVpnLoadBalancerPeerStatusEntrySystemName OBJECT-TYPE
    SYNTAX     OCTET STRING (SIZE(0..20))
    MAX-ACCESS read-only
    STATUS     current
    DESCRIPTION
            "-- empty --"
    ::= { lcsStatusVpnLoadBalancerPeerStatusEntry 5 }

-- {COLUMN} 1.3.6.1.4.1.2356.11.1.26.50.3.1.6
lcsStatusVpnLoadBalancerPeerStatusEntryIpv4Target OBJECT-TYPE
    SYNTAX     OCTET STRING (SIZE(0..15))
    MAX-ACCESS read-only
    STATUS     current
    DESCRIPTION
            "-- empty --"
    ::= { lcsStatusVpnLoadBalancerPeerStatusEntry 6 }

-- {COLUMN} 1.3.6.1.4.1.2356.11.1.26.50.3.1.7
lcsStatusVpnLoadBalancerPeerStatusEntryCpuLoad OBJECT-TYPE
    SYNTAX     OCTET STRING (SIZE(0..4))
    MAX-ACCESS read-only
    STATUS     current
    DESCRIPTION
            "-- empty --"
    ::= { lcsStatusVpnLoadBalancerPeerStatusEntry 7 }

-- {COLUMN} 1.3.6.1.4.1.2356.11.1.26.50.3.1.8
lcsStatusVpnLoadBalancerPeerStatusEntryTotalVpn OBJECT-TYPE
    SYNTAX     OCTET STRING (SIZE(0..10))
    MAX-ACCESS read-only
    STATUS     current
    DESCRIPTION
            "-- empty --"
    ::= { lcsStatusVpnLoadBalancerPeerStatusEntry 8 }

-- {COLUMN} 1.3.6.1.4.1.2356.11.1.26.50.3.1.9
lcsStatusVpnLoadBalancerPeerStatusEntryUsedVpn OBJECT-TYPE
    SYNTAX     OCTET STRING (SIZE(0..10))
    MAX-ACCESS read-only
    STATUS     current
    DESCRIPTION
            "-- empty --"
    ::= { lcsStatusVpnLoadBalancerPeerStatusEntry 9 }

-- {NODE} 1.3.6.1.4.1.2356.11.1.27
lcsStatusPptp OBJECT IDENTIFIER ::= { lcsStatus 27 }

-- {SCALAR} 1.3.6.1.4.1.2356.11.1.27.1
lcsStatusPptpRxPackets OBJECT-TYPE
    SYNTAX     Counter32
    MAX-ACCESS read-only
    STATUS     current
    DESCRIPTION
            ""
    ::= { lcsStatusPptp 1 }

-- {SCALAR} 1.3.6.1.4.1.2356.11.1.27.2
lcsStatusPptpTxPackets OBJECT-TYPE
    SYNTAX     Counter32
    MAX-ACCESS read-only
    STATUS     current
    DESCRIPTION
            ""
    ::= { lcsStatusPptp 2 }

-- {SCALAR} 1.3.6.1.4.1.2356.11.1.27.3
lcsStatusPptpEchoRetries OBJECT-TYPE
    SYNTAX     Counter32
    MAX-ACCESS read-only
    STATUS     current
    DESCRIPTION
            ""
    ::= { lcsStatusPptp 3 }

-- {SCALAR} 1.3.6.1.4.1.2356.11.1.27.4
lcsStatusPptpAckTimeouts OBJECT-TYPE
    SYNTAX     Counter32
    MAX-ACCESS read-only
    STATUS     current
    DESCRIPTION
            ""
    ::= { lcsStatusPptp 4 }

-- {SCALAR} 1.3.6.1.4.1.2356.11.1.27.5
lcsStatusPptpDroppedPackets OBJECT-TYPE
    SYNTAX     Counter32
    MAX-ACCESS read-only
    STATUS     current
    DESCRIPTION
            ""
    ::= { lcsStatusPptp 5 }

-- {SCALAR} 1.3.6.1.4.1.2356.11.1.27.6
lcsStatusPptpRxErrors OBJECT-TYPE
    SYNTAX     Counter32
    MAX-ACCESS read-only
    STATUS     current
    DESCRIPTION
            ""
    ::= { lcsStatusPptp 6 }

-- {SCALAR} 1.3.6.1.4.1.2356.11.1.27.7
lcsStatusPptpTcpErrors OBJECT-TYPE
    SYNTAX     Counter32
    MAX-ACCESS read-only
    STATUS     current
    DESCRIPTION
            ""
    ::= { lcsStatusPptp 7 }

-- {SCALAR} 1.3.6.1.4.1.2356.11.1.27.8
lcsStatusPptpCallErrors OBJECT-TYPE
    SYNTAX     Counter32
    MAX-ACCESS read-only
    STATUS     current
    DESCRIPTION
            ""
    ::= { lcsStatusPptp 8 }

-- {TABLE} 1.3.6.1.4.1.2356.11.1.27.9
lcsStatusPptpConnectionsTable OBJECT-TYPE
    SYNTAX     SEQUENCE OF LcsStatusPptpConnectionsEntry
    MAX-ACCESS not-accessible
    STATUS     current
    DESCRIPTION
            ""
    ::= { lcsStatusPptp 9 }

-- {ROW} 1.3.6.1.4.1.2356.11.1.27.9.1
lcsStatusPptpConnectionsEntry OBJECT-TYPE
    SYNTAX     LcsStatusPptpConnectionsEntry
    MAX-ACCESS not-accessible
    STATUS     current
    DESCRIPTION
            ""
    INDEX {
            lcsStatusPptpConnectionsEntryChannel
          }
    ::= { lcsStatusPptpConnectionsTable 1 }

LcsStatusPptpConnectionsEntry ::= SEQUENCE {
            lcsStatusPptpConnectionsEntryChannel DisplayString,
            lcsStatusPptpConnectionsEntryState INTEGER,
            lcsStatusPptpConnectionsEntryMode INTEGER,
            lcsStatusPptpConnectionsEntryShTime Integer32,
            lcsStatusPptpConnectionsEntryPhysConnection DisplayString,
            lcsStatusPptpConnectionsEntryPeerAddress IpAddress,
            lcsStatusPptpConnectionsEntryIpAddress IpAddress,
            lcsStatusPptpConnectionsEntryDnsDefault IpAddress,
            lcsStatusPptpConnectionsEntryNbnsDefault IpAddress,
            lcsStatusPptpConnectionsEntryLastError INTEGER,
            lcsStatusPptpConnectionsEntryDnsBackup IpAddress,
            lcsStatusPptpConnectionsEntryNbnsBackup IpAddress,
            lcsStatusPptpConnectionsEntryConnTime Gauge32,
            lcsStatusPptpConnectionsEntryGateway IpAddress,
            lcsStatusPptpConnectionsEntryEncryption INTEGER
    }

-- {COLUMN} 1.3.6.1.4.1.2356.11.1.27.9.1.1
lcsStatusPptpConnectionsEntryChannel OBJECT-TYPE
    SYNTAX     DisplayString (SIZE(0..16))
    MAX-ACCESS read-only
    STATUS     current
    DESCRIPTION
            ""
    ::= { lcsStatusPptpConnectionsEntry 1 }

-- {COLUMN} 1.3.6.1.4.1.2356.11.1.27.9.1.3
lcsStatusPptpConnectionsEntryState OBJECT-TYPE
    SYNTAX     INTEGER {
                  eInit (0),
                  eSetupWan (1),
                  eReady (2),
                  eWaitForCb (3),
                  eDial (4),
                  eIncomingCall (5),
                  eProtocol (6),
                  eConnection (7),
                  eDisconnecting (8),
                  eCallBack (9),
                  eBundleConnect (10),
                  eProtocol2 (11),
                  eReserved (12),
                  eBundle (13)
            }
    MAX-ACCESS read-only
    STATUS     current
    DESCRIPTION
            ""
    ::= { lcsStatusPptpConnectionsEntry 3 }

-- {COLUMN} 1.3.6.1.4.1.2356.11.1.27.9.1.4
lcsStatusPptpConnectionsEntryMode OBJECT-TYPE
    SYNTAX     INTEGER {
                  ePassive (0),
                  eActive (128)
            }
    MAX-ACCESS read-only
    STATUS     current
    DESCRIPTION
            ""
    ::= { lcsStatusPptpConnectionsEntry 4 }

-- {COLUMN} 1.3.6.1.4.1.2356.11.1.27.9.1.5
lcsStatusPptpConnectionsEntryShTime OBJECT-TYPE
    SYNTAX     Integer32 (0..65535)
    MAX-ACCESS read-only
    STATUS     current
    DESCRIPTION
            ""
    ::= { lcsStatusPptpConnectionsEntry 5 }

-- {COLUMN} 1.3.6.1.4.1.2356.11.1.27.9.1.6
lcsStatusPptpConnectionsEntryPhysConnection OBJECT-TYPE
    SYNTAX     DisplayString (SIZE(0..16))
    MAX-ACCESS read-only
    STATUS     current
    DESCRIPTION
            ""
    ::= { lcsStatusPptpConnectionsEntry 6 }

-- {COLUMN} 1.3.6.1.4.1.2356.11.1.27.9.1.7
lcsStatusPptpConnectionsEntryPeerAddress OBJECT-TYPE
    SYNTAX     IpAddress
    MAX-ACCESS read-only
    STATUS     current
    DESCRIPTION
            ""
    ::= { lcsStatusPptpConnectionsEntry 7 }

-- {COLUMN} 1.3.6.1.4.1.2356.11.1.27.9.1.8
lcsStatusPptpConnectionsEntryIpAddress OBJECT-TYPE
    SYNTAX     IpAddress
    MAX-ACCESS read-only
    STATUS     current
    DESCRIPTION
            ""
    ::= { lcsStatusPptpConnectionsEntry 8 }

-- {COLUMN} 1.3.6.1.4.1.2356.11.1.27.9.1.9
lcsStatusPptpConnectionsEntryDnsDefault OBJECT-TYPE
    SYNTAX     IpAddress
    MAX-ACCESS read-only
    STATUS     current
    DESCRIPTION
            ""
    ::= { lcsStatusPptpConnectionsEntry 9 }

-- {COLUMN} 1.3.6.1.4.1.2356.11.1.27.9.1.10
lcsStatusPptpConnectionsEntryNbnsDefault OBJECT-TYPE
    SYNTAX     IpAddress
    MAX-ACCESS read-only
    STATUS     current
    DESCRIPTION
            ""
    ::= { lcsStatusPptpConnectionsEntry 10 }

-- {COLUMN} 1.3.6.1.4.1.2356.11.1.27.9.1.11
lcsStatusPptpConnectionsEntryLastError OBJECT-TYPE
    SYNTAX     INTEGER {
                  eNone (0),
                  eRemoteDoubled (267),
                  eIcmpConnError (275),
                  eDhcpTimeout (277),
                  ePptpNoResponse (278),
                  eVpnNoResponse (279),
                  eArpNoResponse (280),
                  ePptpNoChannel (513),
                  ePptpBadFormat (514),
                  ePptpBadValue (515),
                  ePptpNoRessource (516),
                  ePptpBadCallId (517),
                  ePptpGenError (518),
                  ePptpNoAddress (519),
                  ePptpDnsResolvError (520),
                  ePptpTcpConnError (521),
                  eRemoteDisconnected (17153),
                  eManualDisconnect (17154),
                  eShortholdExpired (17155),
                  ePhysicalDisconnected (17156),
                  eInvalidPhysicalChannel (17157),
                  eDynamicVpnReconnect (17158),
                  eConfigurationChanged (17159),
                  eRemovedFromConfig (17160),
                  eLcpRejected (32768),
                  eAuthError (32769),
                  eAuthRejected (32770),
                  eLcpConnError (32771),
                  ePapRejected (32784),
                  ePapRxTimeout (32785),
                  ePapTxTimeout (32786),
                  eWrongPapReq (32787),
                  ePapNakReceived (32788),
                  eUnknPapPeer (32789),
                  eChapRejected (32800),
                  eChapRxTimeout (32801),
                  eChapTxTimeout (32802),
                  eWrongChapResp (32803),
                  eChapFailRecvd (32804),
                  eUnknChapPeer (32805),
                  eIpxcpRejected (32816),
                  eWrongIpxcpNet (32817),
                  eIpxcpNetReject (32818),
                  eIpxcpRouteUnkn (32819),
                  eIpcpRejected (32832),
                  eCcpRejected (32848),
                  eNoNcpAvailable (33008)
            }
    MAX-ACCESS read-write
    STATUS     current
    DESCRIPTION
            ""
    ::= { lcsStatusPptpConnectionsEntry 11 }

-- {COLUMN} 1.3.6.1.4.1.2356.11.1.27.9.1.12
lcsStatusPptpConnectionsEntryDnsBackup OBJECT-TYPE
    SYNTAX     IpAddress
    MAX-ACCESS read-only
    STATUS     current
    DESCRIPTION
            ""
    ::= { lcsStatusPptpConnectionsEntry 12 }

-- {COLUMN} 1.3.6.1.4.1.2356.11.1.27.9.1.13
lcsStatusPptpConnectionsEntryNbnsBackup OBJECT-TYPE
    SYNTAX     IpAddress
    MAX-ACCESS read-only
    STATUS     current
    DESCRIPTION
            ""
    ::= { lcsStatusPptpConnectionsEntry 13 }

-- {COLUMN} 1.3.6.1.4.1.2356.11.1.27.9.1.14
lcsStatusPptpConnectionsEntryConnTime OBJECT-TYPE
    SYNTAX     Gauge32
    MAX-ACCESS read-only
    STATUS     current
    DESCRIPTION
            ""
    ::= { lcsStatusPptpConnectionsEntry 14 }

-- {COLUMN} 1.3.6.1.4.1.2356.11.1.27.9.1.15
lcsStatusPptpConnectionsEntryGateway OBJECT-TYPE
    SYNTAX     IpAddress
    MAX-ACCESS read-only
    STATUS     current
    DESCRIPTION
            ""
    ::= { lcsStatusPptpConnectionsEntry 15 }

-- {COLUMN} 1.3.6.1.4.1.2356.11.1.27.9.1.16
lcsStatusPptpConnectionsEntryEncryption OBJECT-TYPE
    SYNTAX     INTEGER {
                  eOff (0),
                  e128Bits (64),
                  e56Bits (192),
                  e40Bits (224)
            }
    MAX-ACCESS read-only
    STATUS     current
    DESCRIPTION
            "-- empty --"
    ::= { lcsStatusPptpConnectionsEntry 16 }

-- {SCALAR} 1.3.6.1.4.1.2356.11.1.27.10
lcsStatusPptpTunnel OBJECT-TYPE
    SYNTAX     Integer32 (0..2147483647)
    MAX-ACCESS read-only
    STATUS     current
    DESCRIPTION
            ""
    ::= { lcsStatusPptp 10 }

-- {SCALAR} 1.3.6.1.4.1.2356.11.1.27.11
lcsStatusPptpDeleteValues OBJECT-TYPE
    SYNTAX     DisplayString
    MAX-ACCESS read-write
    STATUS     current
    DESCRIPTION
            ""
    ::= { lcsStatusPptp 11 }

-- {SCALAR} 1.3.6.1.4.1.2356.11.1.27.12
lcsStatusPptpFlowControlQueue OBJECT-TYPE
    SYNTAX     Integer32 (0..2147483647)
    MAX-ACCESS read-only
    STATUS     current
    DESCRIPTION
            ""
    ::= { lcsStatusPptp 12 }

-- {SCALAR} 1.3.6.1.4.1.2356.11.1.27.13
lcsStatusPptpEncryptedTunnel OBJECT-TYPE
    SYNTAX     Integer32 (0..2147483647)
    MAX-ACCESS read-only
    STATUS     current
    DESCRIPTION
            "-- empty --"
    ::= { lcsStatusPptp 13 }

-- {NODE} 1.3.6.1.4.1.2356.11.1.28
lcsStatusPppoe OBJECT IDENTIFIER ::= { lcsStatus 28 }

-- {SCALAR} 1.3.6.1.4.1.2356.11.1.28.1
lcsStatusPppoeTxPadi OBJECT-TYPE
    SYNTAX     Integer32 (0..2147483647)
    MAX-ACCESS read-only
    STATUS     current
    DESCRIPTION
            "-- empty --"
    ::= { lcsStatusPppoe 1 }

-- {SCALAR} 1.3.6.1.4.1.2356.11.1.28.2
lcsStatusPppoeRxPado OBJECT-TYPE
    SYNTAX     Integer32 (0..2147483647)
    MAX-ACCESS read-only
    STATUS     current
    DESCRIPTION
            "-- empty --"
    ::= { lcsStatusPppoe 2 }

-- {SCALAR} 1.3.6.1.4.1.2356.11.1.28.3
lcsStatusPppoeTxPadr OBJECT-TYPE
    SYNTAX     Integer32 (0..2147483647)
    MAX-ACCESS read-only
    STATUS     current
    DESCRIPTION
            "-- empty --"
    ::= { lcsStatusPppoe 3 }

-- {SCALAR} 1.3.6.1.4.1.2356.11.1.28.4
lcsStatusPppoeRxPads OBJECT-TYPE
    SYNTAX     Integer32 (0..2147483647)
    MAX-ACCESS read-only
    STATUS     current
    DESCRIPTION
            "-- empty --"
    ::= { lcsStatusPppoe 4 }

-- {SCALAR} 1.3.6.1.4.1.2356.11.1.28.5
lcsStatusPppoeTxPadt OBJECT-TYPE
    SYNTAX     Integer32 (0..2147483647)
    MAX-ACCESS read-only
    STATUS     current
    DESCRIPTION
            "-- empty --"
    ::= { lcsStatusPppoe 5 }

-- {SCALAR} 1.3.6.1.4.1.2356.11.1.28.6
lcsStatusPppoeRxPadt OBJECT-TYPE
    SYNTAX     Integer32 (0..2147483647)
    MAX-ACCESS read-only
    STATUS     current
    DESCRIPTION
            "-- empty --"
    ::= { lcsStatusPppoe 6 }

-- {SCALAR} 1.3.6.1.4.1.2356.11.1.28.7
lcsStatusPppoeTxProtocol OBJECT-TYPE
    SYNTAX     Integer32 (0..2147483647)
    MAX-ACCESS read-only
    STATUS     current
    DESCRIPTION
            "-- empty --"
    ::= { lcsStatusPppoe 7 }

-- {SCALAR} 1.3.6.1.4.1.2356.11.1.28.8
lcsStatusPppoeRxProtocol OBJECT-TYPE
    SYNTAX     Integer32 (0..2147483647)
    MAX-ACCESS read-only
    STATUS     current
    DESCRIPTION
            "-- empty --"
    ::= { lcsStatusPppoe 8 }

-- {SCALAR} 1.3.6.1.4.1.2356.11.1.28.9
lcsStatusPppoeTxData OBJECT-TYPE
    SYNTAX     Integer32 (0..2147483647)
    MAX-ACCESS read-only
    STATUS     current
    DESCRIPTION
            "-- empty --"
    ::= { lcsStatusPppoe 9 }

-- {SCALAR} 1.3.6.1.4.1.2356.11.1.28.10
lcsStatusPppoeRxData OBJECT-TYPE
    SYNTAX     Integer32 (0..2147483647)
    MAX-ACCESS read-only
    STATUS     current
    DESCRIPTION
            "-- empty --"
    ::= { lcsStatusPppoe 10 }

-- {SCALAR} 1.3.6.1.4.1.2356.11.1.28.11
lcsStatusPppoeRxBad OBJECT-TYPE
    SYNTAX     Integer32 (0..2147483647)
    MAX-ACCESS read-only
    STATUS     current
    DESCRIPTION
            "-- empty --"
    ::= { lcsStatusPppoe 11 }

-- {SCALAR} 1.3.6.1.4.1.2356.11.1.28.12
lcsStatusPppoeAcName OBJECT-TYPE
    SYNTAX     DisplayString (SIZE(0..63))
    MAX-ACCESS read-only
    STATUS     current
    DESCRIPTION
            "-- empty --"
    ::= { lcsStatusPppoe 12 }

-- {SCALAR} 1.3.6.1.4.1.2356.11.1.28.13
lcsStatusPppoeService OBJECT-TYPE
    SYNTAX     DisplayString (SIZE(0..63))
    MAX-ACCESS read-only
    STATUS     current
    DESCRIPTION
            "-- empty --"
    ::= { lcsStatusPppoe 13 }

-- {SCALAR} 1.3.6.1.4.1.2356.11.1.28.30
lcsStatusPppoeDeleteValues OBJECT-TYPE
    SYNTAX     DisplayString
    MAX-ACCESS read-write
    STATUS     current
    DESCRIPTION
            "-- empty --"
    ::= { lcsStatusPppoe 30 }

-- {NODE} 1.3.6.1.4.1.2356.11.1.31
lcsStatusLanBridge OBJECT IDENTIFIER ::= { lcsStatus 31 }

-- {TABLE} 1.3.6.1.4.1.2356.11.1.31.1
lcsStatusLanBridgeAddressTableTable OBJECT-TYPE
    SYNTAX     SEQUENCE OF LcsStatusLanBridgeAddressTableEntry
    MAX-ACCESS not-accessible
    STATUS     current
    DESCRIPTION
            ""
    ::= { lcsStatusLanBridge 1 }

-- {ROW} 1.3.6.1.4.1.2356.11.1.31.1.1
lcsStatusLanBridgeAddressTableEntry OBJECT-TYPE
    SYNTAX     LcsStatusLanBridgeAddressTableEntry
    MAX-ACCESS not-accessible
    STATUS     current
    DESCRIPTION
            ""
    INDEX {
            lcsStatusLanBridgeAddressTableEntryIndex
          }
    ::= { lcsStatusLanBridgeAddressTableTable 1 }

LcsStatusLanBridgeAddressTableEntry ::= SEQUENCE {
            lcsStatusLanBridgeAddressTableEntryIndex Integer32,
            lcsStatusLanBridgeAddressTableEntryAge Integer32,
            lcsStatusLanBridgeAddressTableEntryMacAddress MacAddress,
            lcsStatusLanBridgeAddressTableEntryEthernetPort INTEGER,
            lcsStatusLanBridgeAddressTableEntryBrgAddr MacAddress,
            lcsStatusLanBridgeAddressTableEntryVlanId Integer32,
            lcsStatusLanBridgeAddressTableEntryBridgeGroup INTEGER,
            lcsStatusLanBridgeAddressTableEntryPort DisplayString
    }

-- {COLUMN} 1.3.6.1.4.1.2356.11.1.31.1.1.1
lcsStatusLanBridgeAddressTableEntryIndex OBJECT-TYPE
    SYNTAX     Integer32 (0..2147483647)
    MAX-ACCESS read-only
    STATUS     current
    DESCRIPTION
            ""
    ::= { lcsStatusLanBridgeAddressTableEntry 1 }

-- {COLUMN} 1.3.6.1.4.1.2356.11.1.31.1.1.2
lcsStatusLanBridgeAddressTableEntryAge OBJECT-TYPE
    SYNTAX     Integer32 (0..65535)
    MAX-ACCESS read-only
    STATUS     current
    DESCRIPTION
            ""
    ::= { lcsStatusLanBridgeAddressTableEntry 2 }

-- {COLUMN} 1.3.6.1.4.1.2356.11.1.31.1.1.3
lcsStatusLanBridgeAddressTableEntryMacAddress OBJECT-TYPE
    SYNTAX     MacAddress
    MAX-ACCESS read-only
    STATUS     current
    DESCRIPTION
            ""
    ::= { lcsStatusLanBridgeAddressTableEntry 3 }

-- {COLUMN} 1.3.6.1.4.1.2356.11.1.31.1.1.5
lcsStatusLanBridgeAddressTableEntryEthernetPort OBJECT-TYPE
    SYNTAX     INTEGER {
                  eUnknown (0),
                  eUplink (1),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            ""
    ::= { lcsStatusLanBridgeAddressTableEntry 5 }

-- {COLUMN} 1.3.6.1.4.1.2356.11.1.31.1.1.6
lcsStatusLanBridgeAddressTableEntryBrgAddr OBJECT-TYPE
    SYNTAX     MacAddress
    MAX-ACCESS read-only
    STATUS     current
    DESCRIPTION
            ""
    ::= { lcsStatusLanBridgeAddressTableEntry 6 }

-- {COLUMN} 1.3.6.1.4.1.2356.11.1.31.1.1.7
lcsStatusLanBridgeAddressTableEntryVlanId OBJECT-TYPE
    SYNTAX     Integer32 (0..65535)
    MAX-ACCESS read-only
    STATUS     current
    DESCRIPTION
            ""
    ::= { lcsStatusLanBridgeAddressTableEntry 7 }

-- {COLUMN} 1.3.6.1.4.1.2356.11.1.31.1.1.8
lcsStatusLanBridgeAddressTableEntryBridgeGroup OBJECT-TYPE
    SYNTAX     INTEGER {
                  eBrg1 (0),
                  eBrg2 (1),
                  eBrg3 (2),
                  eBrg4 (3),
                  eBrg5 (4),
                  eBrg6 (5),
                  eBrg7 (6),
                  eBrg8 (7),
                  eNone (255)
            }
    MAX-ACCESS read-only
    STATUS     current
    DESCRIPTION
            ""
    ::= { lcsStatusLanBridgeAddressTableEntry 8 }

-- {COLUMN} 1.3.6.1.4.1.2356.11.1.31.1.1.9
lcsStatusLanBridgeAddressTableEntryPort OBJECT-TYPE
    SYNTAX     DisplayString (SIZE(0..255))
    MAX-ACCESS read-only
    STATUS     current
    DESCRIPTION
            ""
    ::= { lcsStatusLanBridgeAddressTableEntry 9 }

-- {SCALAR} 1.3.6.1.4.1.2356.11.1.31.8
lcsStatusLanBridgeIsolatedMode OBJECT-TYPE
    SYNTAX     INTEGER {
                  eNo (0),
                  eYes (1)
            }
    MAX-ACCESS read-only
    STATUS     current
    DESCRIPTION
            ""
    ::= { lcsStatusLanBridge 8 }

-- {TABLE} 1.3.6.1.4.1.2356.11.1.31.9
lcsStatusLanBridgeConnectionTableTable OBJECT-TYPE
    SYNTAX     SEQUENCE OF LcsStatusLanBridgeConnectionTableEntry
    MAX-ACCESS not-accessible
    STATUS     current
    DESCRIPTION
            ""
    ::= { lcsStatusLanBridge 9 }

-- {ROW} 1.3.6.1.4.1.2356.11.1.31.9.1
lcsStatusLanBridgeConnectionTableEntry OBJECT-TYPE
    SYNTAX     LcsStatusLanBridgeConnectionTableEntry
    MAX-ACCESS not-accessible
    STATUS     current
    DESCRIPTION
            ""
    INDEX {
            lcsStatusLanBridgeConnectionTableEntryIndex
          }
    ::= { lcsStatusLanBridgeConnectionTableTable 1 }

LcsStatusLanBridgeConnectionTableEntry ::= SEQUENCE {
            lcsStatusLanBridgeConnectionTableEntryIndex Integer32,
            lcsStatusLanBridgeConnectionTableEntryProtocol DisplayString,
            lcsStatusLanBridgeConnectionTableEntrySubProtocol Integer32,
            lcsStatusLanBridgeConnectionTableEntrySourceAddress IpAddress,
            lcsStatusLanBridgeConnectionTableEntrySourcePort Integer32,
            lcsStatusLanBridgeConnectionTableEntryDestPort Integer32,
            lcsStatusLanBridgeConnectionTableEntryDestAddress IpAddress,
            lcsStatusLanBridgeConnectionTableEntryDestMac DisplayString,
            lcsStatusLanBridgeConnectionTableEntryAge Integer32,
            lcsStatusLanBridgeConnectionTableEntryInterface INTEGER,
            lcsStatusLanBridgeConnectionTableEntryName DisplayString
    }

-- {COLUMN} 1.3.6.1.4.1.2356.11.1.31.9.1.1
lcsStatusLanBridgeConnectionTableEntryIndex OBJECT-TYPE
    SYNTAX     Integer32 (0..2147483647)
    MAX-ACCESS read-only
    STATUS     current
    DESCRIPTION
            ""
    ::= { lcsStatusLanBridgeConnectionTableEntry 1 }

-- {COLUMN} 1.3.6.1.4.1.2356.11.1.31.9.1.3
lcsStatusLanBridgeConnectionTableEntryProtocol OBJECT-TYPE
    SYNTAX     DisplayString (SIZE(0..4))
    MAX-ACCESS read-only
    STATUS     current
    DESCRIPTION
            ""
    ::= { lcsStatusLanBridgeConnectionTableEntry 3 }

-- {COLUMN} 1.3.6.1.4.1.2356.11.1.31.9.1.4
lcsStatusLanBridgeConnectionTableEntrySubProtocol OBJECT-TYPE
    SYNTAX     Integer32 (0..65535)
    MAX-ACCESS read-only
    STATUS     current
    DESCRIPTION
            ""
    ::= { lcsStatusLanBridgeConnectionTableEntry 4 }

-- {COLUMN} 1.3.6.1.4.1.2356.11.1.31.9.1.5
lcsStatusLanBridgeConnectionTableEntrySourceAddress OBJECT-TYPE
    SYNTAX     IpAddress
    MAX-ACCESS read-only
    STATUS     current
    DESCRIPTION
            ""
    ::= { lcsStatusLanBridgeConnectionTableEntry 5 }

-- {COLUMN} 1.3.6.1.4.1.2356.11.1.31.9.1.6
lcsStatusLanBridgeConnectionTableEntrySourcePort OBJECT-TYPE
    SYNTAX     Integer32 (0..65535)
    MAX-ACCESS read-only
    STATUS     current
    DESCRIPTION
            ""
    ::= { lcsStatusLanBridgeConnectionTableEntry 6 }

-- {COLUMN} 1.3.6.1.4.1.2356.11.1.31.9.1.7
lcsStatusLanBridgeConnectionTableEntryDestPort OBJECT-TYPE
    SYNTAX     Integer32 (0..65535)
    MAX-ACCESS read-only
    STATUS     current
    DESCRIPTION
            ""
    ::= { lcsStatusLanBridgeConnectionTableEntry 7 }

-- {COLUMN} 1.3.6.1.4.1.2356.11.1.31.9.1.8
lcsStatusLanBridgeConnectionTableEntryDestAddress OBJECT-TYPE
    SYNTAX     IpAddress
    MAX-ACCESS read-only
    STATUS     current
    DESCRIPTION
            ""
    ::= { lcsStatusLanBridgeConnectionTableEntry 8 }

-- {COLUMN} 1.3.6.1.4.1.2356.11.1.31.9.1.9
lcsStatusLanBridgeConnectionTableEntryDestMac OBJECT-TYPE
    SYNTAX     DisplayString (SIZE(0..12))
    MAX-ACCESS read-only
    STATUS     current
    DESCRIPTION
            ""
    ::= { lcsStatusLanBridgeConnectionTableEntry 9 }

-- {COLUMN} 1.3.6.1.4.1.2356.11.1.31.9.1.10
lcsStatusLanBridgeConnectionTableEntryAge OBJECT-TYPE
    SYNTAX     Integer32 (0..2147483647)
    MAX-ACCESS read-only
    STATUS     current
    DESCRIPTION
            ""
    ::= { lcsStatusLanBridgeConnectionTableEntry 10 }

-- {COLUMN} 1.3.6.1.4.1.2356.11.1.31.9.1.11
lcsStatusLanBridgeConnectionTableEntryInterface OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsStatusLanBridgeConnectionTableEntry 11 }

-- {COLUMN} 1.3.6.1.4.1.2356.11.1.31.9.1.12
lcsStatusLanBridgeConnectionTableEntryName OBJECT-TYPE
    SYNTAX     DisplayString (SIZE(0..24))
    MAX-ACCESS read-only
    STATUS     current
    DESCRIPTION
            "-- empty --"
    ::= { lcsStatusLanBridgeConnectionTableEntry 12 }

-- {TABLE} 1.3.6.1.4.1.2356.11.1.31.10
lcsStatusLanBridgeDhcpTableTable OBJECT-TYPE
    SYNTAX     SEQUENCE OF LcsStatusLanBridgeDhcpTableEntry
    MAX-ACCESS not-accessible
    STATUS     current
    DESCRIPTION
            ""
    ::= { lcsStatusLanBridge 10 }

-- {ROW} 1.3.6.1.4.1.2356.11.1.31.10.1
lcsStatusLanBridgeDhcpTableEntry OBJECT-TYPE
    SYNTAX     LcsStatusLanBridgeDhcpTableEntry
    MAX-ACCESS not-accessible
    STATUS     current
    DESCRIPTION
            ""
    INDEX {
            lcsStatusLanBridgeDhcpTableEntryMacAddress
          }
    ::= { lcsStatusLanBridgeDhcpTableTable 1 }

LcsStatusLanBridgeDhcpTableEntry ::= SEQUENCE {
            lcsStatusLanBridgeDhcpTableEntryMacAddress MacAddress,
            lcsStatusLanBridgeDhcpTableEntryIpAddress IpAddress,
            lcsStatusLanBridgeDhcpTableEntryLastUpdate Integer32,
            lcsStatusLanBridgeDhcpTableEntryPort DisplayString,
            lcsStatusLanBridgeDhcpTableEntrySrcPort DisplayString
    }

-- {COLUMN} 1.3.6.1.4.1.2356.11.1.31.10.1.1
lcsStatusLanBridgeDhcpTableEntryMacAddress OBJECT-TYPE
    SYNTAX     MacAddress
    MAX-ACCESS read-only
    STATUS     current
    DESCRIPTION
            ""
    ::= { lcsStatusLanBridgeDhcpTableEntry 1 }

-- {COLUMN} 1.3.6.1.4.1.2356.11.1.31.10.1.4
lcsStatusLanBridgeDhcpTableEntryIpAddress OBJECT-TYPE
    SYNTAX     IpAddress
    MAX-ACCESS read-only
    STATUS     current
    DESCRIPTION
            ""
    ::= { lcsStatusLanBridgeDhcpTableEntry 4 }

-- {COLUMN} 1.3.6.1.4.1.2356.11.1.31.10.1.5
lcsStatusLanBridgeDhcpTableEntryLastUpdate OBJECT-TYPE
    SYNTAX     Integer32 (0..2147483647)
    MAX-ACCESS read-only
    STATUS     current
    DESCRIPTION
            ""
    ::= { lcsStatusLanBridgeDhcpTableEntry 5 }

-- {COLUMN} 1.3.6.1.4.1.2356.11.1.31.10.1.6
lcsStatusLanBridgeDhcpTableEntryPort OBJECT-TYPE
    SYNTAX     DisplayString (SIZE(0..255))
    MAX-ACCESS read-only
    STATUS     current
    DESCRIPTION
            ""
    ::= { lcsStatusLanBridgeDhcpTableEntry 6 }

-- {COLUMN} 1.3.6.1.4.1.2356.11.1.31.10.1.7
lcsStatusLanBridgeDhcpTableEntrySrcPort OBJECT-TYPE
    SYNTAX     DisplayString (SIZE(0..255))
    MAX-ACCESS read-only
    STATUS     current
    DESCRIPTION
            ""
    ::= { lcsStatusLanBridgeDhcpTableEntry 7 }

-- {TABLE} 1.3.6.1.4.1.2356.11.1.31.11
lcsStatusLanBridgePortDataTable OBJECT-TYPE
    SYNTAX     SEQUENCE OF LcsStatusLanBridgePortDataEntry
    MAX-ACCESS not-accessible
    STATUS     current
    DESCRIPTION
            ""
    ::= { lcsStatusLanBridge 11 }

-- {ROW} 1.3.6.1.4.1.2356.11.1.31.11.1
lcsStatusLanBridgePortDataEntry OBJECT-TYPE
    SYNTAX     LcsStatusLanBridgePortDataEntry
    MAX-ACCESS not-accessible
    STATUS     current
    DESCRIPTION
            ""
    INDEX {
            lcsStatusLanBridgePortDataEntryPort
          }
    ::= { lcsStatusLanBridgePortDataTable 1 }

LcsStatusLanBridgePortDataEntry ::= SEQUENCE {
            lcsStatusLanBridgePortDataEntryPort DisplayString,
            lcsStatusLanBridgePortDataEntryPointToPointPort INTEGER,
            lcsStatusLanBridgePortDataEntryOperatingState INTEGER,
            lcsStatusLanBridgePortDataEntryBridgeGroup INTEGER,
            lcsStatusLanBridgePortDataEntryInPackets Integer32,
            lcsStatusLanBridgePortDataEntryOutPackets Integer32,
            lcsStatusLanBridgePortDataEntryInDiscards Integer32,
            lcsStatusLanBridgePortDataEntryPrivateMode INTEGER
    }

-- {COLUMN} 1.3.6.1.4.1.2356.11.1.31.11.1.1
lcsStatusLanBridgePortDataEntryPort OBJECT-TYPE
    SYNTAX     DisplayString (SIZE(0..255))
    MAX-ACCESS read-only
    STATUS     current
    DESCRIPTION
            ""
    ::= { lcsStatusLanBridgePortDataEntry 1 }

-- {COLUMN} 1.3.6.1.4.1.2356.11.1.31.11.1.2
lcsStatusLanBridgePortDataEntryPointToPointPort OBJECT-TYPE
    SYNTAX     INTEGER {
                  eNo (0),
                  eYes (1)
            }
    MAX-ACCESS read-only
    STATUS     current
    DESCRIPTION
            ""
    ::= { lcsStatusLanBridgePortDataEntry 2 }

-- {COLUMN} 1.3.6.1.4.1.2356.11.1.31.11.1.3
lcsStatusLanBridgePortDataEntryOperatingState OBJECT-TYPE
    SYNTAX     INTEGER {
                  eUp (1),
                  eDown (2),
                  eTesting (3),
                  eUnknown (4),
                  eDormant (5),
                  eNotPresent (6),
                  eLowerLayerDown (7)
            }
    MAX-ACCESS read-only
    STATUS     current
    DESCRIPTION
            ""
    ::= { lcsStatusLanBridgePortDataEntry 3 }

-- {COLUMN} 1.3.6.1.4.1.2356.11.1.31.11.1.5
lcsStatusLanBridgePortDataEntryBridgeGroup OBJECT-TYPE
    SYNTAX     INTEGER {
                  eBrg1 (0),
                  eBrg2 (1),
                  eBrg3 (2),
                  eBrg4 (3),
                  eBrg5 (4),
                  eBrg6 (5),
                  eBrg7 (6),
                  eBrg8 (7),
                  eNone (255)
            }
    MAX-ACCESS read-only
    STATUS     current
    DESCRIPTION
            ""
    ::= { lcsStatusLanBridgePortDataEntry 5 }

-- {COLUMN} 1.3.6.1.4.1.2356.11.1.31.11.1.6
lcsStatusLanBridgePortDataEntryInPackets OBJECT-TYPE
    SYNTAX     Integer32 (0..2147483647)
    MAX-ACCESS read-only
    STATUS     current
    DESCRIPTION
            ""
    ::= { lcsStatusLanBridgePortDataEntry 6 }

-- {COLUMN} 1.3.6.1.4.1.2356.11.1.31.11.1.7
lcsStatusLanBridgePortDataEntryOutPackets OBJECT-TYPE
    SYNTAX     Integer32 (0..2147483647)
    MAX-ACCESS read-only
    STATUS     current
    DESCRIPTION
            ""
    ::= { lcsStatusLanBridgePortDataEntry 7 }

-- {COLUMN} 1.3.6.1.4.1.2356.11.1.31.11.1.8
lcsStatusLanBridgePortDataEntryInDiscards OBJECT-TYPE
    SYNTAX     Integer32 (0..2147483647)
    MAX-ACCESS read-only
    STATUS     current
    DESCRIPTION
            ""
    ::= { lcsStatusLanBridgePortDataEntry 8 }

-- {COLUMN} 1.3.6.1.4.1.2356.11.1.31.11.1.9
lcsStatusLanBridgePortDataEntryPrivateMode OBJECT-TYPE
    SYNTAX     INTEGER {
                  eNo (0),
                  eYes (1)
            }
    MAX-ACCESS read-only
    STATUS     current
    DESCRIPTION
            "-- empty --"
    ::= { lcsStatusLanBridgePortDataEntry 9 }

-- {TABLE} 1.3.6.1.4.1.2356.11.1.31.12
lcsStatusLanBridgeProtocolTableTable OBJECT-TYPE
    SYNTAX     SEQUENCE OF LcsStatusLanBridgeProtocolTableEntry
    MAX-ACCESS not-accessible
    STATUS     current
    DESCRIPTION
            "-- empty --"
    ::= { lcsStatusLanBridge 12 }

-- {ROW} 1.3.6.1.4.1.2356.11.1.31.12.1
lcsStatusLanBridgeProtocolTableEntry OBJECT-TYPE
    SYNTAX     LcsStatusLanBridgeProtocolTableEntry
    MAX-ACCESS not-accessible
    STATUS     current
    DESCRIPTION
            ""
    INDEX {
            lcsStatusLanBridgeProtocolTableEntryName,
            lcsStatusLanBridgeProtocolTableEntrySource
          }
    ::= { lcsStatusLanBridgeProtocolTableTable 1 }

LcsStatusLanBridgeProtocolTableEntry ::= SEQUENCE {
            lcsStatusLanBridgeProtocolTableEntryName DisplayString,
            lcsStatusLanBridgeProtocolTableEntryProtocol DisplayString,
            lcsStatusLanBridgeProtocolTableEntrySubProtocol Integer32,
            lcsStatusLanBridgeProtocolTableEntryPort Integer32,
            lcsStatusLanBridgeProtocolTableEntryPortEnd Integer32,
            lcsStatusLanBridgeProtocolTableEntryIfcList DisplayString,
            lcsStatusLanBridgeProtocolTableEntryAction INTEGER,
            lcsStatusLanBridgeProtocolTableEntryRedirectIpAddress IpAddress,
            lcsStatusLanBridgeProtocolTableEntryDestMacAddr MacAddress,
            lcsStatusLanBridgeProtocolTableEntryIpNetwork IpAddress,
            lcsStatusLanBridgeProtocolTableEntryIpNetmask IpAddress,
            lcsStatusLanBridgeProtocolTableEntryDhcpSrcMac INTEGER,
            lcsStatusLanBridgeProtocolTableEntrySource DisplayString
    }

-- {COLUMN} 1.3.6.1.4.1.2356.11.1.31.12.1.1
lcsStatusLanBridgeProtocolTableEntryName OBJECT-TYPE
    SYNTAX     DisplayString (SIZE(0..255))
    MAX-ACCESS read-only
    STATUS     current
    DESCRIPTION
            "-- empty --"
    ::= { lcsStatusLanBridgeProtocolTableEntry 1 }

-- {COLUMN} 1.3.6.1.4.1.2356.11.1.31.12.1.2
lcsStatusLanBridgeProtocolTableEntryProtocol OBJECT-TYPE
    SYNTAX     DisplayString (SIZE(0..255))
    MAX-ACCESS read-only
    STATUS     current
    DESCRIPTION
            "-- empty --"
    ::= { lcsStatusLanBridgeProtocolTableEntry 2 }

-- {COLUMN} 1.3.6.1.4.1.2356.11.1.31.12.1.3
lcsStatusLanBridgeProtocolTableEntrySubProtocol OBJECT-TYPE
    SYNTAX     Integer32 (0..65535)
    MAX-ACCESS read-only
    STATUS     current
    DESCRIPTION
            "-- empty --"
    ::= { lcsStatusLanBridgeProtocolTableEntry 3 }

-- {COLUMN} 1.3.6.1.4.1.2356.11.1.31.12.1.4
lcsStatusLanBridgeProtocolTableEntryPort OBJECT-TYPE
    SYNTAX     Integer32 (0..65535)
    MAX-ACCESS read-only
    STATUS     current
    DESCRIPTION
            "-- empty --"
    ::= { lcsStatusLanBridgeProtocolTableEntry 4 }

-- {COLUMN} 1.3.6.1.4.1.2356.11.1.31.12.1.5
lcsStatusLanBridgeProtocolTableEntryPortEnd OBJECT-TYPE
    SYNTAX     Integer32 (0..65535)
    MAX-ACCESS read-only
    STATUS     current
    DESCRIPTION
            "-- empty --"
    ::= { lcsStatusLanBridgeProtocolTableEntry 5 }

-- {COLUMN} 1.3.6.1.4.1.2356.11.1.31.12.1.6
lcsStatusLanBridgeProtocolTableEntryIfcList OBJECT-TYPE
    SYNTAX     DisplayString (SIZE(0..255))
    MAX-ACCESS read-only
    STATUS     current
    DESCRIPTION
            "-- empty --"
    ::= { lcsStatusLanBridgeProtocolTableEntry 6 }

-- {COLUMN} 1.3.6.1.4.1.2356.11.1.31.12.1.7
lcsStatusLanBridgeProtocolTableEntryAction OBJECT-TYPE
    SYNTAX     INTEGER {
                  eDrop (0),
                  ePass (1),
                  eRedirect (2)
            }
    MAX-ACCESS read-only
    STATUS     current
    DESCRIPTION
            "-- empty --"
    ::= { lcsStatusLanBridgeProtocolTableEntry 7 }

-- {COLUMN} 1.3.6.1.4.1.2356.11.1.31.12.1.8
lcsStatusLanBridgeProtocolTableEntryRedirectIpAddress OBJECT-TYPE
    SYNTAX     IpAddress
    MAX-ACCESS read-only
    STATUS     current
    DESCRIPTION
            "-- empty --"
    ::= { lcsStatusLanBridgeProtocolTableEntry 8 }

-- {COLUMN} 1.3.6.1.4.1.2356.11.1.31.12.1.9
lcsStatusLanBridgeProtocolTableEntryDestMacAddr OBJECT-TYPE
    SYNTAX     MacAddress
    MAX-ACCESS read-only
    STATUS     current
    DESCRIPTION
            "-- empty --"
    ::= { lcsStatusLanBridgeProtocolTableEntry 9 }

-- {COLUMN} 1.3.6.1.4.1.2356.11.1.31.12.1.10
lcsStatusLanBridgeProtocolTableEntryIpNetwork OBJECT-TYPE
    SYNTAX     IpAddress
    MAX-ACCESS read-only
    STATUS     current
    DESCRIPTION
            "-- empty --"
    ::= { lcsStatusLanBridgeProtocolTableEntry 10 }

-- {COLUMN} 1.3.6.1.4.1.2356.11.1.31.12.1.11
lcsStatusLanBridgeProtocolTableEntryIpNetmask OBJECT-TYPE
    SYNTAX     IpAddress
    MAX-ACCESS read-only
    STATUS     current
    DESCRIPTION
            "-- empty --"
    ::= { lcsStatusLanBridgeProtocolTableEntry 11 }

-- {COLUMN} 1.3.6.1.4.1.2356.11.1.31.12.1.12
lcsStatusLanBridgeProtocolTableEntryDhcpSrcMac OBJECT-TYPE
    SYNTAX     INTEGER {
                  eIrrelevant (0),
                  eNo (1),
                  eYes (2)
            }
    MAX-ACCESS read-only
    STATUS     current
    DESCRIPTION
            "-- empty --"
    ::= { lcsStatusLanBridgeProtocolTableEntry 12 }

-- {COLUMN} 1.3.6.1.4.1.2356.11.1.31.12.1.13
lcsStatusLanBridgeProtocolTableEntrySource OBJECT-TYPE
    SYNTAX     DisplayString (SIZE(0..255))
    MAX-ACCESS read-only
    STATUS     current
    DESCRIPTION
            "-- empty --"
    ::= { lcsStatusLanBridgeProtocolTableEntry 13 }

-- {NODE} 1.3.6.1.4.1.2356.11.1.31.20
lcsStatusLanBridgeSpanningTree OBJECT IDENTIFIER ::= { lcsStatusLanBridge 20 }

-- {SCALAR} 1.3.6.1.4.1.2356.11.1.31.20.1
lcsStatusLanBridgeSpanningTreeOperating OBJECT-TYPE
    SYNTAX     INTEGER {
                  eNo (0),
                  eYes (1)
            }
    MAX-ACCESS read-only
    STATUS     current
    DESCRIPTION
            ""
    ::= { lcsStatusLanBridgeSpanningTree 1 }

-- {SCALAR} 1.3.6.1.4.1.2356.11.1.31.20.2
lcsStatusLanBridgeSpanningTreeBridgeId OBJECT-TYPE
    SYNTAX     DisplayString (SIZE(0..20))
    MAX-ACCESS read-only
    STATUS     current
    DESCRIPTION
            ""
    ::= { lcsStatusLanBridgeSpanningTree 2 }

-- {SCALAR} 1.3.6.1.4.1.2356.11.1.31.20.3
lcsStatusLanBridgeSpanningTreeRootBridge OBJECT-TYPE
    SYNTAX     DisplayString (SIZE(0..20))
    MAX-ACCESS read-only
    STATUS     current
    DESCRIPTION
            ""
    ::= { lcsStatusLanBridgeSpanningTree 3 }

-- {SCALAR} 1.3.6.1.4.1.2356.11.1.31.20.5
lcsStatusLanBridgeSpanningTreeRootPathCost OBJECT-TYPE
    SYNTAX     Integer32 (0..2147483647)
    MAX-ACCESS read-only
    STATUS     current
    DESCRIPTION
            ""
    ::= { lcsStatusLanBridgeSpanningTree 5 }

-- {TABLE} 1.3.6.1.4.1.2356.11.1.31.20.6
lcsStatusLanBridgeSpanningTreePortTableTable OBJECT-TYPE
    SYNTAX     SEQUENCE OF LcsStatusLanBridgeSpanningTreePortTableEntry
    MAX-ACCESS not-accessible
    STATUS     current
    DESCRIPTION
            ""
    ::= { lcsStatusLanBridgeSpanningTree 6 }

-- {ROW} 1.3.6.1.4.1.2356.11.1.31.20.6.1
lcsStatusLanBridgeSpanningTreePortTableEntry OBJECT-TYPE
    SYNTAX     LcsStatusLanBridgeSpanningTreePortTableEntry
    MAX-ACCESS not-accessible
    STATUS     current
    DESCRIPTION
            ""
    INDEX {
            lcsStatusLanBridgeSpanningTreePortTableEntryDescription
          }
    ::= { lcsStatusLanBridgeSpanningTreePortTableTable 1 }

LcsStatusLanBridgeSpanningTreePortTableEntry ::= SEQUENCE {
            lcsStatusLanBridgeSpanningTreePortTableEntryDescription DisplayString,
            lcsStatusLanBridgeSpanningTreePortTableEntryPriority Integer32,
            lcsStatusLanBridgeSpanningTreePortTableEntryState INTEGER,
            lcsStatusLanBridgeSpanningTreePortTableEntryRoot DisplayString,
            lcsStatusLanBridgeSpanningTreePortTableEntryBridge DisplayString,
            lcsStatusLanBridgeSpanningTreePortTableEntryPathCost Integer32
    }

-- {COLUMN} 1.3.6.1.4.1.2356.11.1.31.20.6.1.1
lcsStatusLanBridgeSpanningTreePortTableEntryDescription OBJECT-TYPE
    SYNTAX     DisplayString (SIZE(0..18))
    MAX-ACCESS read-only
    STATUS     current
    DESCRIPTION
            ""
    ::= { lcsStatusLanBridgeSpanningTreePortTableEntry 1 }

-- {COLUMN} 1.3.6.1.4.1.2356.11.1.31.20.6.1.2
lcsStatusLanBridgeSpanningTreePortTableEntryPriority OBJECT-TYPE
    SYNTAX     Integer32 (0..255)
    MAX-ACCESS read-only
    STATUS     current
    DESCRIPTION
            ""
    ::= { lcsStatusLanBridgeSpanningTreePortTableEntry 2 }

-- {COLUMN} 1.3.6.1.4.1.2356.11.1.31.20.6.1.3
lcsStatusLanBridgeSpanningTreePortTableEntryState OBJECT-TYPE
    SYNTAX     INTEGER {
                  eDisabled (0),
                  eListening (1),
                  eLearning (2),
                  eForwarding (3),
                  eBlocking (4)
            }
    MAX-ACCESS read-only
    STATUS     current
    DESCRIPTION
            ""
    ::= { lcsStatusLanBridgeSpanningTreePortTableEntry 3 }

-- {COLUMN} 1.3.6.1.4.1.2356.11.1.31.20.6.1.4
lcsStatusLanBridgeSpanningTreePortTableEntryRoot OBJECT-TYPE
    SYNTAX     DisplayString (SIZE(0..16))
    MAX-ACCESS read-only
    STATUS     current
    DESCRIPTION
            ""
    ::= { lcsStatusLanBridgeSpanningTreePortTableEntry 4 }

-- {COLUMN} 1.3.6.1.4.1.2356.11.1.31.20.6.1.5
lcsStatusLanBridgeSpanningTreePortTableEntryBridge OBJECT-TYPE
    SYNTAX     DisplayString (SIZE(0..16))
    MAX-ACCESS read-only
    STATUS     current
    DESCRIPTION
            ""
    ::= { lcsStatusLanBridgeSpanningTreePortTableEntry 5 }

-- {COLUMN} 1.3.6.1.4.1.2356.11.1.31.20.6.1.6
lcsStatusLanBridgeSpanningTreePortTableEntryPathCost OBJECT-TYPE
    SYNTAX     Integer32 (0..2147483647)
    MAX-ACCESS read-only
    STATUS     current
    DESCRIPTION
            ""
    ::= { lcsStatusLanBridgeSpanningTreePortTableEntry 6 }

-- {SCALAR} 1.3.6.1.4.1.2356.11.1.31.20.7
lcsStatusLanBridgeSpanningTreeProtocolVersion OBJECT-TYPE
    SYNTAX     INTEGER {
                  eClassic (0),
                  eRapid (1)
            }
    MAX-ACCESS read-only
    STATUS     current
    DESCRIPTION
            ""
    ::= { lcsStatusLanBridgeSpanningTree 7 }

-- {SCALAR} 1.3.6.1.4.1.2356.11.1.31.20.8
lcsStatusLanBridgeSpanningTreePathCostComputation OBJECT-TYPE
    SYNTAX     INTEGER {
                  eClassic (0),
                  eRapid (1)
            }
    MAX-ACCESS read-only
    STATUS     current
    DESCRIPTION
            ""
    ::= { lcsStatusLanBridgeSpanningTree 8 }

-- {SCALAR} 1.3.6.1.4.1.2356.11.1.31.20.9
lcsStatusLanBridgeSpanningTreeBridgePriority OBJECT-TYPE
    SYNTAX     Integer32 (0..65535)
    MAX-ACCESS read-only
    STATUS     current
    DESCRIPTION
            ""
    ::= { lcsStatusLanBridgeSpanningTree 9 }

-- {TABLE} 1.3.6.1.4.1.2356.11.1.31.20.10
lcsStatusLanBridgeSpanningTreeRstpPortTableTable OBJECT-TYPE
    SYNTAX     SEQUENCE OF LcsStatusLanBridgeSpanningTreeRstpPortTableEntry
    MAX-ACCESS not-accessible
    STATUS     current
    DESCRIPTION
            ""
    ::= { lcsStatusLanBridgeSpanningTree 10 }

-- {ROW} 1.3.6.1.4.1.2356.11.1.31.20.10.1
lcsStatusLanBridgeSpanningTreeRstpPortTableEntry OBJECT-TYPE
    SYNTAX     LcsStatusLanBridgeSpanningTreeRstpPortTableEntry
    MAX-ACCESS not-accessible
    STATUS     current
    DESCRIPTION
            ""
    INDEX {
            lcsStatusLanBridgeSpanningTreeRstpPortTableEntryDescription
          }
    ::= { lcsStatusLanBridgeSpanningTreeRstpPortTableTable 1 }

LcsStatusLanBridgeSpanningTreeRstpPortTableEntry ::= SEQUENCE {
            lcsStatusLanBridgeSpanningTreeRstpPortTableEntryDescription DisplayString,
            lcsStatusLanBridgeSpanningTreeRstpPortTableEntryRole INTEGER,
            lcsStatusLanBridgeSpanningTreeRstpPortTableEntryLearning INTEGER,
            lcsStatusLanBridgeSpanningTreeRstpPortTableEntryForwarding INTEGER,
            lcsStatusLanBridgeSpanningTreeRstpPortTableEntryEdgePort INTEGER,
            lcsStatusLanBridgeSpanningTreeRstpPortTableEntryProtocolVersion INTEGER,
            lcsStatusLanBridgeSpanningTreeRstpPortTableEntryPathCost Integer32
    }

-- {COLUMN} 1.3.6.1.4.1.2356.11.1.31.20.10.1.1
lcsStatusLanBridgeSpanningTreeRstpPortTableEntryDescription OBJECT-TYPE
    SYNTAX     DisplayString (SIZE(0..255))
    MAX-ACCESS read-only
    STATUS     current
    DESCRIPTION
            ""
    ::= { lcsStatusLanBridgeSpanningTreeRstpPortTableEntry 1 }

-- {COLUMN} 1.3.6.1.4.1.2356.11.1.31.20.10.1.2
lcsStatusLanBridgeSpanningTreeRstpPortTableEntryRole OBJECT-TYPE
    SYNTAX     INTEGER {
                  eRoot (0),
                  eDesignated (1),
                  eAlternate (2),
                  eBackup (3),
                  eDisabled (4)
            }
    MAX-ACCESS read-only
    STATUS     current
    DESCRIPTION
            ""
    ::= { lcsStatusLanBridgeSpanningTreeRstpPortTableEntry 2 }

-- {COLUMN} 1.3.6.1.4.1.2356.11.1.31.20.10.1.3
lcsStatusLanBridgeSpanningTreeRstpPortTableEntryLearning OBJECT-TYPE
    SYNTAX     INTEGER {
                  eNo (0),
                  eYes (1)
            }
    MAX-ACCESS read-only
    STATUS     current
    DESCRIPTION
            ""
    ::= { lcsStatusLanBridgeSpanningTreeRstpPortTableEntry 3 }

-- {COLUMN} 1.3.6.1.4.1.2356.11.1.31.20.10.1.4
lcsStatusLanBridgeSpanningTreeRstpPortTableEntryForwarding OBJECT-TYPE
    SYNTAX     INTEGER {
                  eNo (0),
                  eYes (1)
            }
    MAX-ACCESS read-only
    STATUS     current
    DESCRIPTION
            ""
    ::= { lcsStatusLanBridgeSpanningTreeRstpPortTableEntry 4 }

-- {COLUMN} 1.3.6.1.4.1.2356.11.1.31.20.10.1.5
lcsStatusLanBridgeSpanningTreeRstpPortTableEntryEdgePort OBJECT-TYPE
    SYNTAX     INTEGER {
                  eNo (0),
                  eYes (1)
            }
    MAX-ACCESS read-only
    STATUS     current
    DESCRIPTION
            ""
    ::= { lcsStatusLanBridgeSpanningTreeRstpPortTableEntry 5 }

-- {COLUMN} 1.3.6.1.4.1.2356.11.1.31.20.10.1.6
lcsStatusLanBridgeSpanningTreeRstpPortTableEntryProtocolVersion OBJECT-TYPE
    SYNTAX     INTEGER {
                  eClassic (0),
                  eRapid (1)
            }
    MAX-ACCESS read-only
    STATUS     current
    DESCRIPTION
            ""
    ::= { lcsStatusLanBridgeSpanningTreeRstpPortTableEntry 6 }

-- {COLUMN} 1.3.6.1.4.1.2356.11.1.31.20.10.1.7
lcsStatusLanBridgeSpanningTreeRstpPortTableEntryPathCost OBJECT-TYPE
    SYNTAX     Integer32 (0..2147483647)
    MAX-ACCESS read-only
    STATUS     current
    DESCRIPTION
            ""
    ::= { lcsStatusLanBridgeSpanningTreeRstpPortTableEntry 7 }

-- {SCALAR} 1.3.6.1.4.1.2356.11.1.31.20.11
lcsStatusLanBridgeSpanningTreeRootPort OBJECT-TYPE
    SYNTAX     DisplayString
    MAX-ACCESS read-only
    STATUS     current
    DESCRIPTION
            ""
    ::= { lcsStatusLanBridgeSpanningTree 11 }

-- {TABLE} 1.3.6.1.4.1.2356.11.1.31.20.12
lcsStatusLanBridgeSpanningTreeLogTableTable OBJECT-TYPE
    SYNTAX     SEQUENCE OF LcsStatusLanBridgeSpanningTreeLogTableEntry
    MAX-ACCESS not-accessible
    STATUS     current
    DESCRIPTION
            "-- empty --"
    ::= { lcsStatusLanBridgeSpanningTree 12 }

-- {ROW} 1.3.6.1.4.1.2356.11.1.31.20.12.1
lcsStatusLanBridgeSpanningTreeLogTableEntry OBJECT-TYPE
    SYNTAX     LcsStatusLanBridgeSpanningTreeLogTableEntry
    MAX-ACCESS not-accessible
    STATUS     current
    DESCRIPTION
            ""
    INDEX {
            lcsStatusLanBridgeSpanningTreeLogTableEntryIndex
          }
    ::= { lcsStatusLanBridgeSpanningTreeLogTableTable 1 }

LcsStatusLanBridgeSpanningTreeLogTableEntry ::= SEQUENCE {
            lcsStatusLanBridgeSpanningTreeLogTableEntryIndex Integer32,
            lcsStatusLanBridgeSpanningTreeLogTableEntryTime DisplayString,
            lcsStatusLanBridgeSpanningTreeLogTableEntryEvent DisplayString
    }

-- {COLUMN} 1.3.6.1.4.1.2356.11.1.31.20.12.1.1
lcsStatusLanBridgeSpanningTreeLogTableEntryIndex OBJECT-TYPE
    SYNTAX     Integer32 (0..2147483647)
    MAX-ACCESS read-only
    STATUS     current
    DESCRIPTION
            "-- empty --"
    ::= { lcsStatusLanBridgeSpanningTreeLogTableEntry 1 }

-- {COLUMN} 1.3.6.1.4.1.2356.11.1.31.20.12.1.2
lcsStatusLanBridgeSpanningTreeLogTableEntryTime OBJECT-TYPE
    SYNTAX     DisplayString (SIZE(0..255))
    MAX-ACCESS read-only
    STATUS     current
    DESCRIPTION
            "-- empty --"
    ::= { lcsStatusLanBridgeSpanningTreeLogTableEntry 2 }

-- {COLUMN} 1.3.6.1.4.1.2356.11.1.31.20.12.1.3
lcsStatusLanBridgeSpanningTreeLogTableEntryEvent OBJECT-TYPE
    SYNTAX     DisplayString (SIZE(0..255))
    MAX-ACCESS read-only
    STATUS     current
    DESCRIPTION
            "-- empty --"
    ::= { lcsStatusLanBridgeSpanningTreeLogTableEntry 3 }

-- {NODE} 1.3.6.1.4.1.2356.11.1.31.30
lcsStatusLanBridgeIgmpSnooping OBJECT IDENTIFIER ::= { lcsStatusLanBridge 30 }

-- {SCALAR} 1.3.6.1.4.1.2356.11.1.31.30.1
lcsStatusLanBridgeIgmpSnoopingOperating OBJECT-TYPE
    SYNTAX     INTEGER {
                  eNo (0),
                  eYes (1),
                  eAuto (2)
            }
    MAX-ACCESS read-only
    STATUS     current
    DESCRIPTION
            ""
    ::= { lcsStatusLanBridgeIgmpSnooping 1 }

-- {TABLE} 1.3.6.1.4.1.2356.11.1.31.30.2
lcsStatusLanBridgeIgmpSnoopingPortStatusTable OBJECT-TYPE
    SYNTAX     SEQUENCE OF LcsStatusLanBridgeIgmpSnoopingPortStatusEntry
    MAX-ACCESS not-accessible
    STATUS     current
    DESCRIPTION
            ""
    ::= { lcsStatusLanBridgeIgmpSnooping 2 }

-- {ROW} 1.3.6.1.4.1.2356.11.1.31.30.2.1
lcsStatusLanBridgeIgmpSnoopingPortStatusEntry OBJECT-TYPE
    SYNTAX     LcsStatusLanBridgeIgmpSnoopingPortStatusEntry
    MAX-ACCESS not-accessible
    STATUS     current
    DESCRIPTION
            ""
    INDEX {
            lcsStatusLanBridgeIgmpSnoopingPortStatusEntryPort
          }
    ::= { lcsStatusLanBridgeIgmpSnoopingPortStatusTable 1 }

LcsStatusLanBridgeIgmpSnoopingPortStatusEntry ::= SEQUENCE {
            lcsStatusLanBridgeIgmpSnoopingPortStatusEntryPort DisplayString,
            lcsStatusLanBridgeIgmpSnoopingPortStatusEntryRouterPort INTEGER,
            lcsStatusLanBridgeIgmpSnoopingPortStatusEntryIpv4Packets Counter32,
            lcsStatusLanBridgeIgmpSnoopingPortStatusEntryDataPackets Counter32,
            lcsStatusLanBridgeIgmpSnoopingPortStatusEntryControlPackets Counter32,
            lcsStatusLanBridgeIgmpSnoopingPortStatusEntryBadPackets Counter32
    }

-- {COLUMN} 1.3.6.1.4.1.2356.11.1.31.30.2.1.1
lcsStatusLanBridgeIgmpSnoopingPortStatusEntryPort OBJECT-TYPE
    SYNTAX     DisplayString (SIZE(0..18))
    MAX-ACCESS read-only
    STATUS     current
    DESCRIPTION
            ""
    ::= { lcsStatusLanBridgeIgmpSnoopingPortStatusEntry 1 }

-- {COLUMN} 1.3.6.1.4.1.2356.11.1.31.30.2.1.2
lcsStatusLanBridgeIgmpSnoopingPortStatusEntryRouterPort OBJECT-TYPE
    SYNTAX     INTEGER {
                  eNo (0),
                  eAuto (1),
                  eYes (2)
            }
    MAX-ACCESS read-only
    STATUS     current
    DESCRIPTION
            ""
    ::= { lcsStatusLanBridgeIgmpSnoopingPortStatusEntry 2 }

-- {COLUMN} 1.3.6.1.4.1.2356.11.1.31.30.2.1.10
lcsStatusLanBridgeIgmpSnoopingPortStatusEntryIpv4Packets OBJECT-TYPE
    SYNTAX     Counter32
    MAX-ACCESS read-only
    STATUS     current
    DESCRIPTION
            ""
    ::= { lcsStatusLanBridgeIgmpSnoopingPortStatusEntry 10 }

-- {COLUMN} 1.3.6.1.4.1.2356.11.1.31.30.2.1.12
lcsStatusLanBridgeIgmpSnoopingPortStatusEntryDataPackets OBJECT-TYPE
    SYNTAX     Counter32
    MAX-ACCESS read-only
    STATUS     current
    DESCRIPTION
            ""
    ::= { lcsStatusLanBridgeIgmpSnoopingPortStatusEntry 12 }

-- {COLUMN} 1.3.6.1.4.1.2356.11.1.31.30.2.1.13
lcsStatusLanBridgeIgmpSnoopingPortStatusEntryControlPackets OBJECT-TYPE
    SYNTAX     Counter32
    MAX-ACCESS read-only
    STATUS     current
    DESCRIPTION
            ""
    ::= { lcsStatusLanBridgeIgmpSnoopingPortStatusEntry 13 }

-- {COLUMN} 1.3.6.1.4.1.2356.11.1.31.30.2.1.14
lcsStatusLanBridgeIgmpSnoopingPortStatusEntryBadPackets OBJECT-TYPE
    SYNTAX     Counter32
    MAX-ACCESS read-only
    STATUS     current
    DESCRIPTION
            ""
    ::= { lcsStatusLanBridgeIgmpSnoopingPortStatusEntry 14 }

-- {TABLE} 1.3.6.1.4.1.2356.11.1.31.30.3
lcsStatusLanBridgeIgmpSnoopingGroupsTable OBJECT-TYPE
    SYNTAX     SEQUENCE OF LcsStatusLanBridgeIgmpSnoopingGroupsEntry
    MAX-ACCESS not-accessible
    STATUS     current
    DESCRIPTION
            ""
    ::= { lcsStatusLanBridgeIgmpSnooping 3 }

-- {ROW} 1.3.6.1.4.1.2356.11.1.31.30.3.1
lcsStatusLanBridgeIgmpSnoopingGroupsEntry OBJECT-TYPE
    SYNTAX     LcsStatusLanBridgeIgmpSnoopingGroupsEntry
    MAX-ACCESS not-accessible
    STATUS     current
    DESCRIPTION
            ""
    INDEX {
            lcsStatusLanBridgeIgmpSnoopingGroupsEntryAddress,
            lcsStatusLanBridgeIgmpSnoopingGroupsEntryVlanId
          }
    ::= { lcsStatusLanBridgeIgmpSnoopingGroupsTable 1 }

LcsStatusLanBridgeIgmpSnoopingGroupsEntry ::= SEQUENCE {
            lcsStatusLanBridgeIgmpSnoopingGroupsEntryAddress IpAddress,
            lcsStatusLanBridgeIgmpSnoopingGroupsEntryDynamicMembers DisplayString,
            lcsStatusLanBridgeIgmpSnoopingGroupsEntryStaticMembers DisplayString,
            lcsStatusLanBridgeIgmpSnoopingGroupsEntryVlanId Integer32,
            lcsStatusLanBridgeIgmpSnoopingGroupsEntryAllowLearning INTEGER
    }

-- {COLUMN} 1.3.6.1.4.1.2356.11.1.31.30.3.1.1
lcsStatusLanBridgeIgmpSnoopingGroupsEntryAddress OBJECT-TYPE
    SYNTAX     IpAddress
    MAX-ACCESS read-only
    STATUS     current
    DESCRIPTION
            ""
    ::= { lcsStatusLanBridgeIgmpSnoopingGroupsEntry 1 }

-- {COLUMN} 1.3.6.1.4.1.2356.11.1.31.30.3.1.2
lcsStatusLanBridgeIgmpSnoopingGroupsEntryDynamicMembers OBJECT-TYPE
    SYNTAX     DisplayString (SIZE(0..255))
    MAX-ACCESS read-only
    STATUS     current
    DESCRIPTION
            ""
    ::= { lcsStatusLanBridgeIgmpSnoopingGroupsEntry 2 }

-- {COLUMN} 1.3.6.1.4.1.2356.11.1.31.30.3.1.3
lcsStatusLanBridgeIgmpSnoopingGroupsEntryStaticMembers OBJECT-TYPE
    SYNTAX     DisplayString (SIZE(0..255))
    MAX-ACCESS read-only
    STATUS     current
    DESCRIPTION
            ""
    ::= { lcsStatusLanBridgeIgmpSnoopingGroupsEntry 3 }

-- {COLUMN} 1.3.6.1.4.1.2356.11.1.31.30.3.1.4
lcsStatusLanBridgeIgmpSnoopingGroupsEntryVlanId OBJECT-TYPE
    SYNTAX     Integer32 (0..65535)
    MAX-ACCESS read-only
    STATUS     current
    DESCRIPTION
            ""
    ::= { lcsStatusLanBridgeIgmpSnoopingGroupsEntry 4 }

-- {COLUMN} 1.3.6.1.4.1.2356.11.1.31.30.3.1.5
lcsStatusLanBridgeIgmpSnoopingGroupsEntryAllowLearning OBJECT-TYPE
    SYNTAX     INTEGER {
                  eYes (0),
                  eNo (1)
            }
    MAX-ACCESS read-only
    STATUS     current
    DESCRIPTION
            ""
    ::= { lcsStatusLanBridgeIgmpSnoopingGroupsEntry 5 }

-- {TABLE} 1.3.6.1.4.1.2356.11.1.31.30.4
lcsStatusLanBridgeIgmpSnoopingSimulatedQueriersTable OBJECT-TYPE
    SYNTAX     SEQUENCE OF LcsStatusLanBridgeIgmpSnoopingSimulatedQueriersEntry
    MAX-ACCESS not-accessible
    STATUS     current
    DESCRIPTION
            ""
    ::= { lcsStatusLanBridgeIgmpSnooping 4 }

-- {ROW} 1.3.6.1.4.1.2356.11.1.31.30.4.1
lcsStatusLanBridgeIgmpSnoopingSimulatedQueriersEntry OBJECT-TYPE
    SYNTAX     LcsStatusLanBridgeIgmpSnoopingSimulatedQueriersEntry
    MAX-ACCESS not-accessible
    STATUS     current
    DESCRIPTION
            ""
    INDEX {
            lcsStatusLanBridgeIgmpSnoopingSimulatedQueriersEntryName
          }
    ::= { lcsStatusLanBridgeIgmpSnoopingSimulatedQueriersTable 1 }

LcsStatusLanBridgeIgmpSnoopingSimulatedQueriersEntry ::= SEQUENCE {
            lcsStatusLanBridgeIgmpSnoopingSimulatedQueriersEntryName DisplayString,
            lcsStatusLanBridgeIgmpSnoopingSimulatedQueriersEntryBridgeGroup INTEGER,
            lcsStatusLanBridgeIgmpSnoopingSimulatedQueriersEntryVlanId Integer32,
            lcsStatusLanBridgeIgmpSnoopingSimulatedQueriersEntryStatus INTEGER
    }

-- {COLUMN} 1.3.6.1.4.1.2356.11.1.31.30.4.1.1
lcsStatusLanBridgeIgmpSnoopingSimulatedQueriersEntryName OBJECT-TYPE
    SYNTAX     DisplayString (SIZE(0..255))
    MAX-ACCESS read-only
    STATUS     current
    DESCRIPTION
            ""
    ::= { lcsStatusLanBridgeIgmpSnoopingSimulatedQueriersEntry 1 }

-- {COLUMN} 1.3.6.1.4.1.2356.11.1.31.30.4.1.3
lcsStatusLanBridgeIgmpSnoopingSimulatedQueriersEntryBridgeGroup OBJECT-TYPE
    SYNTAX     INTEGER {
                  eBrg1 (0),
                  eBrg2 (1),
                  eBrg3 (2),
                  eBrg4 (3),
                  eBrg5 (4),
                  eBrg6 (5),
                  eBrg7 (6),
                  eBrg8 (7),
                  eNone (255)
            }
    MAX-ACCESS read-only
    STATUS     current
    DESCRIPTION
            ""
    ::= { lcsStatusLanBridgeIgmpSnoopingSimulatedQueriersEntry 3 }

-- {COLUMN} 1.3.6.1.4.1.2356.11.1.31.30.4.1.4
lcsStatusLanBridgeIgmpSnoopingSimulatedQueriersEntryVlanId OBJECT-TYPE
    SYNTAX     Integer32 (0..65535)
    MAX-ACCESS read-only
    STATUS     current
    DESCRIPTION
            ""
    ::= { lcsStatusLanBridgeIgmpSnoopingSimulatedQueriersEntry 4 }

-- {COLUMN} 1.3.6.1.4.1.2356.11.1.31.30.4.1.5
lcsStatusLanBridgeIgmpSnoopingSimulatedQueriersEntryStatus OBJECT-TYPE
    SYNTAX     INTEGER {
                  eInitial (0),
                  eQuerier (1),
                  eNonQuerier (2)
            }
    MAX-ACCESS read-only
    STATUS     current
    DESCRIPTION
            ""
    ::= { lcsStatusLanBridgeIgmpSnoopingSimulatedQueriersEntry 5 }

-- {SCALAR} 1.3.6.1.4.1.2356.11.1.31.30.5
lcsStatusLanBridgeIgmpSnoopingFilterActive OBJECT-TYPE
    SYNTAX     INTEGER {
                  eNo (0),
                  eYes (1)
            }
    MAX-ACCESS read-only
    STATUS     current
    DESCRIPTION
            "-- empty --"
    ::= { lcsStatusLanBridgeIgmpSnooping 5 }

-- {SCALAR} 1.3.6.1.4.1.2356.11.1.31.30.10
lcsStatusLanBridgeIgmpSnoopingIpv4Packets OBJECT-TYPE
    SYNTAX     Counter32
    MAX-ACCESS read-only
    STATUS     current
    DESCRIPTION
            ""
    ::= { lcsStatusLanBridgeIgmpSnooping 10 }

-- {SCALAR} 1.3.6.1.4.1.2356.11.1.31.30.12
lcsStatusLanBridgeIgmpSnoopingDataPackets OBJECT-TYPE
    SYNTAX     Counter32
    MAX-ACCESS read-only
    STATUS     current
    DESCRIPTION
            ""
    ::= { lcsStatusLanBridgeIgmpSnooping 12 }

-- {SCALAR} 1.3.6.1.4.1.2356.11.1.31.30.13
lcsStatusLanBridgeIgmpSnoopingControlPackets OBJECT-TYPE
    SYNTAX     Counter32
    MAX-ACCESS read-only
    STATUS     current
    DESCRIPTION
            ""
    ::= { lcsStatusLanBridgeIgmpSnooping 13 }

-- {SCALAR} 1.3.6.1.4.1.2356.11.1.31.30.14
lcsStatusLanBridgeIgmpSnoopingBadPackets OBJECT-TYPE
    SYNTAX     Counter32
    MAX-ACCESS read-only
    STATUS     current
    DESCRIPTION
            ""
    ::= { lcsStatusLanBridgeIgmpSnooping 14 }

-- {SCALAR} 1.3.6.1.4.1.2356.11.1.31.30.99
lcsStatusLanBridgeIgmpSnoopingDeleteValues OBJECT-TYPE
    SYNTAX     DisplayString
    MAX-ACCESS read-write
    STATUS     current
    DESCRIPTION
            ""
    ::= { lcsStatusLanBridgeIgmpSnooping 99 }

-- {SCALAR} 1.3.6.1.4.1.2356.11.1.31.99
lcsStatusLanBridgeDeleteValues OBJECT-TYPE
    SYNTAX     DisplayString
    MAX-ACCESS read-write
    STATUS     current
    DESCRIPTION
            ""
    ::= { lcsStatusLanBridge 99 }

-- {NODE} 1.3.6.1.4.1.2356.11.1.32
lcsStatusDhcpClient OBJECT IDENTIFIER ::= { lcsStatus 32 }

-- {TABLE} 1.3.6.1.4.1.2356.11.1.32.20
lcsStatusDhcpClientWanIpListTable OBJECT-TYPE
    SYNTAX     SEQUENCE OF LcsStatusDhcpClientWanIpListEntry
    MAX-ACCESS not-accessible
    STATUS     current
    DESCRIPTION
            ""
    ::= { lcsStatusDhcpClient 20 }

-- {ROW} 1.3.6.1.4.1.2356.11.1.32.20.1
lcsStatusDhcpClientWanIpListEntry OBJECT-TYPE
    SYNTAX     LcsStatusDhcpClientWanIpListEntry
    MAX-ACCESS not-accessible
    STATUS     current
    DESCRIPTION
            ""
    INDEX {
            lcsStatusDhcpClientWanIpListEntryIfc
          }
    ::= { lcsStatusDhcpClientWanIpListTable 1 }

LcsStatusDhcpClientWanIpListEntry ::= SEQUENCE {
            lcsStatusDhcpClientWanIpListEntryIfc INTEGER,
            lcsStatusDhcpClientWanIpListEntryIpAddress IpAddress,
            lcsStatusDhcpClientWanIpListEntryIpNetmask IpAddress,
            lcsStatusDhcpClientWanIpListEntryGateway IpAddress,
            lcsStatusDhcpClientWanIpListEntryDnsDefault IpAddress,
            lcsStatusDhcpClientWanIpListEntryDnsBackup IpAddress,
            lcsStatusDhcpClientWanIpListEntryNbnsDefault IpAddress,
            lcsStatusDhcpClientWanIpListEntryNbnsBackup IpAddress,
            lcsStatusDhcpClientWanIpListEntryDhcpServer IpAddress,
            lcsStatusDhcpClientWanIpListEntryDomain DisplayString
    }

-- {COLUMN} 1.3.6.1.4.1.2356.11.1.32.20.1.1
lcsStatusDhcpClientWanIpListEntryIfc OBJECT-TYPE
    SYNTAX     INTEGER {
                  eCh01 (257),
                  eCh02 (258),
                  eCh03 (259),
                  eCh04 (260),
                  eModem (513),
                  eExt2 (514),
                  eDslCh1 (2049),
                  eDslCh2 (2050),
                  eDslCh3 (2051),
                  eDslCh4 (2052),
                  eDslCh5 (2053),
                  eDslCh6 (2054),
                  eDslCh7 (2055),
                  eDslCh8 (2056),
                  eAdsl1 (8193),
                  eAdsl2 (8194),
                  eAdsl3 (8195),
                  eAdsl4 (8196),
                  eAdsl5 (8197),
                  eAdsl6 (8198),
                  eAdsl7 (8199),
                  eAdsl8 (8200),
                  eVdsl1 (16385),
                  eVdsl2 (16386),
                  eVdsl3 (16387),
                  eVdsl4 (16388),
                  eVdsl5 (16389),
                  eVdsl6 (16390),
                  eVdsl7 (16391),
                  eVdsl8 (16392),
                  eVdsl21 (16393),
                  eVdsl22 (16394),
                  eVdsl23 (16395),
                  eVdsl24 (16396),
                  eVdsl25 (16397),
                  eVdsl26 (16398),
                  eVdsl27 (16399),
                  eVdsl28 (16400)
            }
    MAX-ACCESS read-only
    STATUS     current
    DESCRIPTION
            ""
    ::= { lcsStatusDhcpClientWanIpListEntry 1 }

-- {COLUMN} 1.3.6.1.4.1.2356.11.1.32.20.1.2
lcsStatusDhcpClientWanIpListEntryIpAddress OBJECT-TYPE
    SYNTAX     IpAddress
    MAX-ACCESS read-only
    STATUS     current
    DESCRIPTION
            ""
    ::= { lcsStatusDhcpClientWanIpListEntry 2 }

-- {COLUMN} 1.3.6.1.4.1.2356.11.1.32.20.1.3
lcsStatusDhcpClientWanIpListEntryIpNetmask OBJECT-TYPE
    SYNTAX     IpAddress
    MAX-ACCESS read-only
    STATUS     current
    DESCRIPTION
            ""
    ::= { lcsStatusDhcpClientWanIpListEntry 3 }

-- {COLUMN} 1.3.6.1.4.1.2356.11.1.32.20.1.4
lcsStatusDhcpClientWanIpListEntryGateway OBJECT-TYPE
    SYNTAX     IpAddress
    MAX-ACCESS read-only
    STATUS     current
    DESCRIPTION
            ""
    ::= { lcsStatusDhcpClientWanIpListEntry 4 }

-- {COLUMN} 1.3.6.1.4.1.2356.11.1.32.20.1.5
lcsStatusDhcpClientWanIpListEntryDnsDefault OBJECT-TYPE
    SYNTAX     IpAddress
    MAX-ACCESS read-only
    STATUS     current
    DESCRIPTION
            ""
    ::= { lcsStatusDhcpClientWanIpListEntry 5 }

-- {COLUMN} 1.3.6.1.4.1.2356.11.1.32.20.1.6
lcsStatusDhcpClientWanIpListEntryDnsBackup OBJECT-TYPE
    SYNTAX     IpAddress
    MAX-ACCESS read-only
    STATUS     current
    DESCRIPTION
            ""
    ::= { lcsStatusDhcpClientWanIpListEntry 6 }

-- {COLUMN} 1.3.6.1.4.1.2356.11.1.32.20.1.7
lcsStatusDhcpClientWanIpListEntryNbnsDefault OBJECT-TYPE
    SYNTAX     IpAddress
    MAX-ACCESS read-only
    STATUS     current
    DESCRIPTION
            ""
    ::= { lcsStatusDhcpClientWanIpListEntry 7 }

-- {COLUMN} 1.3.6.1.4.1.2356.11.1.32.20.1.8
lcsStatusDhcpClientWanIpListEntryNbnsBackup OBJECT-TYPE
    SYNTAX     IpAddress
    MAX-ACCESS read-only
    STATUS     current
    DESCRIPTION
            ""
    ::= { lcsStatusDhcpClientWanIpListEntry 8 }

-- {COLUMN} 1.3.6.1.4.1.2356.11.1.32.20.1.9
lcsStatusDhcpClientWanIpListEntryDhcpServer OBJECT-TYPE
    SYNTAX     IpAddress
    MAX-ACCESS read-only
    STATUS     current
    DESCRIPTION
            ""
    ::= { lcsStatusDhcpClientWanIpListEntry 9 }

-- {COLUMN} 1.3.6.1.4.1.2356.11.1.32.20.1.10
lcsStatusDhcpClientWanIpListEntryDomain OBJECT-TYPE
    SYNTAX     DisplayString (SIZE(0..64))
    MAX-ACCESS read-only
    STATUS     current
    DESCRIPTION
            ""
    ::= { lcsStatusDhcpClientWanIpListEntry 10 }

-- {TABLE} 1.3.6.1.4.1.2356.11.1.32.21
lcsStatusDhcpClientLanIpListTable OBJECT-TYPE
    SYNTAX     SEQUENCE OF LcsStatusDhcpClientLanIpListEntry
    MAX-ACCESS not-accessible
    STATUS     current
    DESCRIPTION
            ""
    ::= { lcsStatusDhcpClient 21 }

-- {ROW} 1.3.6.1.4.1.2356.11.1.32.21.1
lcsStatusDhcpClientLanIpListEntry OBJECT-TYPE
    SYNTAX     LcsStatusDhcpClientLanIpListEntry
    MAX-ACCESS not-accessible
    STATUS     current
    DESCRIPTION
            ""
    INDEX {
            lcsStatusDhcpClientLanIpListEntryIfc
          }
    ::= { lcsStatusDhcpClientLanIpListTable 1 }

LcsStatusDhcpClientLanIpListEntry ::= SEQUENCE {
            lcsStatusDhcpClientLanIpListEntryIfc DisplayString,
            lcsStatusDhcpClientLanIpListEntryIpAddress IpAddress,
            lcsStatusDhcpClientLanIpListEntryIpNetmask IpAddress,
            lcsStatusDhcpClientLanIpListEntryGateway IpAddress,
            lcsStatusDhcpClientLanIpListEntryDnsDefault IpAddress,
            lcsStatusDhcpClientLanIpListEntryDnsBackup IpAddress,
            lcsStatusDhcpClientLanIpListEntryNbnsDefault IpAddress,
            lcsStatusDhcpClientLanIpListEntryNbnsBackup IpAddress,
            lcsStatusDhcpClientLanIpListEntryDhcpServer IpAddress,
            lcsStatusDhcpClientLanIpListEntryDomain DisplayString
    }

-- {COLUMN} 1.3.6.1.4.1.2356.11.1.32.21.1.1
lcsStatusDhcpClientLanIpListEntryIfc OBJECT-TYPE
    SYNTAX     DisplayString (SIZE(0..16))
    MAX-ACCESS read-only
    STATUS     current
    DESCRIPTION
            ""
    ::= { lcsStatusDhcpClientLanIpListEntry 1 }

-- {COLUMN} 1.3.6.1.4.1.2356.11.1.32.21.1.2
lcsStatusDhcpClientLanIpListEntryIpAddress OBJECT-TYPE
    SYNTAX     IpAddress
    MAX-ACCESS read-only
    STATUS     current
    DESCRIPTION
            ""
    ::= { lcsStatusDhcpClientLanIpListEntry 2 }

-- {COLUMN} 1.3.6.1.4.1.2356.11.1.32.21.1.3
lcsStatusDhcpClientLanIpListEntryIpNetmask OBJECT-TYPE
    SYNTAX     IpAddress
    MAX-ACCESS read-only
    STATUS     current
    DESCRIPTION
            ""
    ::= { lcsStatusDhcpClientLanIpListEntry 3 }

-- {COLUMN} 1.3.6.1.4.1.2356.11.1.32.21.1.4
lcsStatusDhcpClientLanIpListEntryGateway OBJECT-TYPE
    SYNTAX     IpAddress
    MAX-ACCESS read-only
    STATUS     current
    DESCRIPTION
            ""
    ::= { lcsStatusDhcpClientLanIpListEntry 4 }

-- {COLUMN} 1.3.6.1.4.1.2356.11.1.32.21.1.5
lcsStatusDhcpClientLanIpListEntryDnsDefault OBJECT-TYPE
    SYNTAX     IpAddress
    MAX-ACCESS read-only
    STATUS     current
    DESCRIPTION
            ""
    ::= { lcsStatusDhcpClientLanIpListEntry 5 }

-- {COLUMN} 1.3.6.1.4.1.2356.11.1.32.21.1.6
lcsStatusDhcpClientLanIpListEntryDnsBackup OBJECT-TYPE
    SYNTAX     IpAddress
    MAX-ACCESS read-only
    STATUS     current
    DESCRIPTION
            ""
    ::= { lcsStatusDhcpClientLanIpListEntry 6 }

-- {COLUMN} 1.3.6.1.4.1.2356.11.1.32.21.1.7
lcsStatusDhcpClientLanIpListEntryNbnsDefault OBJECT-TYPE
    SYNTAX     IpAddress
    MAX-ACCESS read-only
    STATUS     current
    DESCRIPTION
            ""
    ::= { lcsStatusDhcpClientLanIpListEntry 7 }

-- {COLUMN} 1.3.6.1.4.1.2356.11.1.32.21.1.8
lcsStatusDhcpClientLanIpListEntryNbnsBackup OBJECT-TYPE
    SYNTAX     IpAddress
    MAX-ACCESS read-only
    STATUS     current
    DESCRIPTION
            ""
    ::= { lcsStatusDhcpClientLanIpListEntry 8 }

-- {COLUMN} 1.3.6.1.4.1.2356.11.1.32.21.1.9
lcsStatusDhcpClientLanIpListEntryDhcpServer OBJECT-TYPE
    SYNTAX     IpAddress
    MAX-ACCESS read-only
    STATUS     current
    DESCRIPTION
            ""
    ::= { lcsStatusDhcpClientLanIpListEntry 9 }

-- {COLUMN} 1.3.6.1.4.1.2356.11.1.32.21.1.10
lcsStatusDhcpClientLanIpListEntryDomain OBJECT-TYPE
    SYNTAX     DisplayString (SIZE(0..64))
    MAX-ACCESS read-only
    STATUS     current
    DESCRIPTION
            ""
    ::= { lcsStatusDhcpClientLanIpListEntry 10 }

-- {NODE} 1.3.6.1.4.1.2356.11.1.33
lcsStatusIsdn OBJECT IDENTIFIER ::= { lcsStatus 33 }

-- {NODE} 1.3.6.1.4.1.2356.11.1.33.1
lcsStatusIsdnLine OBJECT IDENTIFIER ::= { lcsStatusIsdn 1 }

-- {TABLE} 1.3.6.1.4.1.2356.11.1.33.1.1
lcsStatusIsdnLineS0Table OBJECT-TYPE
    SYNTAX     SEQUENCE OF LcsStatusIsdnLineS0Entry
    MAX-ACCESS not-accessible
    STATUS     current
    DESCRIPTION
            ""
    ::= { lcsStatusIsdnLine 1 }

-- {ROW} 1.3.6.1.4.1.2356.11.1.33.1.1.1
lcsStatusIsdnLineS0Entry OBJECT-TYPE
    SYNTAX     LcsStatusIsdnLineS0Entry
    MAX-ACCESS not-accessible
    STATUS     current
    DESCRIPTION
            ""
    INDEX {
            lcsStatusIsdnLineS0EntryIfc
          }
    ::= { lcsStatusIsdnLineS0Table 1 }

LcsStatusIsdnLineS0Entry ::= SEQUENCE {
            lcsStatusIsdnLineS0EntryIfc INTEGER,
            lcsStatusIsdnLineS0EntryOperating INTEGER
    }

-- {COLUMN} 1.3.6.1.4.1.2356.11.1.33.1.1.1.1
lcsStatusIsdnLineS0EntryIfc OBJECT-TYPE
    SYNTAX     INTEGER {
                  eS01 (257),
                  eS02 (258),
                  eModem (513),
                  eDsl1 (2049),
                  eDsl2 (2050),
                  eDsl3 (2051),
                  eDsl4 (2052),
                  eDsl5 (2053),
                  eAdsl (8193),
                  eVdsl (16385),
                  eVdsl2 (16386)
            }
    MAX-ACCESS read-only
    STATUS     current
    DESCRIPTION
            ""
    ::= { lcsStatusIsdnLineS0Entry 1 }

-- {COLUMN} 1.3.6.1.4.1.2356.11.1.33.1.1.1.2
lcsStatusIsdnLineS0EntryOperating OBJECT-TYPE
    SYNTAX     INTEGER {
                  eNo (0),
                  eYes (1)
            }
    MAX-ACCESS read-only
    STATUS     current
    DESCRIPTION
            ""
    ::= { lcsStatusIsdnLineS0Entry 2 }

-- {NODE} 1.3.6.1.4.1.2356.11.1.33.2
lcsStatusIsdnFraming OBJECT IDENTIFIER ::= { lcsStatusIsdn 2 }

-- {TABLE} 1.3.6.1.4.1.2356.11.1.33.2.1
lcsStatusIsdnFramingS0Table OBJECT-TYPE
    SYNTAX     SEQUENCE OF LcsStatusIsdnFramingS0Entry
    MAX-ACCESS not-accessible
    STATUS     current
    DESCRIPTION
            ""
    ::= { lcsStatusIsdnFraming 1 }

-- {ROW} 1.3.6.1.4.1.2356.11.1.33.2.1.1
lcsStatusIsdnFramingS0Entry OBJECT-TYPE
    SYNTAX     LcsStatusIsdnFramingS0Entry
    MAX-ACCESS not-accessible
    STATUS     current
    DESCRIPTION
            ""
    INDEX {
            lcsStatusIsdnFramingS0EntryIfc
          }
    ::= { lcsStatusIsdnFramingS0Table 1 }

LcsStatusIsdnFramingS0Entry ::= SEQUENCE {
            lcsStatusIsdnFramingS0EntryIfc INTEGER,
            lcsStatusIsdnFramingS0EntryState DisplayString,
            lcsStatusIsdnFramingS0EntryB1Frame BITS,
            lcsStatusIsdnFramingS0EntryB2Frame BITS
    }

-- {COLUMN} 1.3.6.1.4.1.2356.11.1.33.2.1.1.1
lcsStatusIsdnFramingS0EntryIfc OBJECT-TYPE
    SYNTAX     INTEGER {
                  eS01 (257),
                  eS02 (258),
                  eModem (513),
                  eDsl1 (2049),
                  eDsl2 (2050),
                  eDsl3 (2051),
                  eDsl4 (2052),
                  eDsl5 (2053),
                  eAdsl (8193),
                  eVdsl (16385),
                  eVdsl2 (16386)
            }
    MAX-ACCESS read-only
    STATUS     current
    DESCRIPTION
            ""
    ::= { lcsStatusIsdnFramingS0Entry 1 }

-- {COLUMN} 1.3.6.1.4.1.2356.11.1.33.2.1.1.2
lcsStatusIsdnFramingS0EntryState OBJECT-TYPE
    SYNTAX     DisplayString (SIZE(0..255))
    MAX-ACCESS read-only
    STATUS     current
    DESCRIPTION
            ""
    ::= { lcsStatusIsdnFramingS0Entry 2 }

-- {COLUMN} 1.3.6.1.4.1.2356.11.1.33.2.1.1.3
lcsStatusIsdnFramingS0EntryB1Frame OBJECT-TYPE
    SYNTAX     BITS {
                  eNone (0),
                  eTxData (5),
                  eRxData (6),
                  eLoop (7)
            }
    MAX-ACCESS read-only
    STATUS     current
    DESCRIPTION
            ""
    ::= { lcsStatusIsdnFramingS0Entry 3 }

-- {COLUMN} 1.3.6.1.4.1.2356.11.1.33.2.1.1.4
lcsStatusIsdnFramingS0EntryB2Frame OBJECT-TYPE
    SYNTAX     BITS {
                  eNone (0),
                  eTxData (5),
                  eRxData (6),
                  eLoop (7)
            }
    MAX-ACCESS read-only
    STATUS     current
    DESCRIPTION
            ""
    ::= { lcsStatusIsdnFramingS0Entry 4 }

-- {SCALAR} 1.3.6.1.4.1.2356.11.1.33.2.2
lcsStatusIsdnFramingPcmSyncSource OBJECT-TYPE
    SYNTAX     DisplayString
    MAX-ACCESS read-only
    STATUS     current
    DESCRIPTION
            ""
    ::= { lcsStatusIsdnFraming 2 }

-- {NODE} 1.3.6.1.4.1.2356.11.1.33.3
lcsStatusIsdnSignaling OBJECT IDENTIFIER ::= { lcsStatusIsdn 3 }

-- {NODE} 1.3.6.1.4.1.2356.11.1.33.3.1
lcsStatusIsdnSignalingLayer2 OBJECT IDENTIFIER ::= { lcsStatusIsdnSignaling 1 }

-- {TABLE} 1.3.6.1.4.1.2356.11.1.33.3.1.1
lcsStatusIsdnSignalingLayer2LapdTable OBJECT-TYPE
    SYNTAX     SEQUENCE OF LcsStatusIsdnSignalingLayer2LapdEntry
    MAX-ACCESS not-accessible
    STATUS     current
    DESCRIPTION
            ""
    ::= { lcsStatusIsdnSignalingLayer2 1 }

-- {ROW} 1.3.6.1.4.1.2356.11.1.33.3.1.1.1
lcsStatusIsdnSignalingLayer2LapdEntry OBJECT-TYPE
    SYNTAX     LcsStatusIsdnSignalingLayer2LapdEntry
    MAX-ACCESS not-accessible
    STATUS     current
    DESCRIPTION
            ""
    INDEX {
            lcsStatusIsdnSignalingLayer2LapdEntryChannel
          }
    ::= { lcsStatusIsdnSignalingLayer2LapdTable 1 }

LcsStatusIsdnSignalingLayer2LapdEntry ::= SEQUENCE {
            lcsStatusIsdnSignalingLayer2LapdEntryChannel INTEGER,
            lcsStatusIsdnSignalingLayer2LapdEntryTei INTEGER,
            lcsStatusIsdnSignalingLayer2LapdEntryL2Activation INTEGER,
            lcsStatusIsdnSignalingLayer2LapdEntryConnections Integer32
    }

-- {COLUMN} 1.3.6.1.4.1.2356.11.1.33.3.1.1.1.1
lcsStatusIsdnSignalingLayer2LapdEntryChannel OBJECT-TYPE
    SYNTAX     INTEGER {
                  e11 (1),
                  e12 (2),
                  e13 (3),
                  e14 (4),
                  e15 (5),
                  e16 (6),
                  e17 (7),
                  e18 (8),
                  e19 (9),
                  e110 (10),
                  e111 (11),
                  e112 (12),
                  e113 (13),
                  e114 (14),
                  e115 (15),
                  e116 (16),
                  e21 (17),
                  e22 (18),
                  e23 (19),
                  e24 (20),
                  e25 (21),
                  e26 (22),
                  e27 (23),
                  e28 (24),
                  e29 (25),
                  e210 (26),
                  e211 (27),
                  e212 (28),
                  e213 (29),
                  e214 (30),
                  e215 (31),
                  e216 (32)
            }
    MAX-ACCESS read-only
    STATUS     current
    DESCRIPTION
            ""
    ::= { lcsStatusIsdnSignalingLayer2LapdEntry 1 }

-- {COLUMN} 1.3.6.1.4.1.2356.11.1.33.3.1.1.1.2
lcsStatusIsdnSignalingLayer2LapdEntryTei OBJECT-TYPE
    SYNTAX     INTEGER {
                  eNone (128)
            }
    MAX-ACCESS read-only
    STATUS     current
    DESCRIPTION
            ""
    ::= { lcsStatusIsdnSignalingLayer2LapdEntry 2 }

-- {COLUMN} 1.3.6.1.4.1.2356.11.1.33.3.1.1.1.3
lcsStatusIsdnSignalingLayer2LapdEntryL2Activation OBJECT-TYPE
    SYNTAX     INTEGER {
                  eNo (0),
                  eYes (1)
            }
    MAX-ACCESS read-only
    STATUS     current
    DESCRIPTION
            ""
    ::= { lcsStatusIsdnSignalingLayer2LapdEntry 3 }

-- {COLUMN} 1.3.6.1.4.1.2356.11.1.33.3.1.1.1.4
lcsStatusIsdnSignalingLayer2LapdEntryConnections OBJECT-TYPE
    SYNTAX     Integer32 (0..255)
    MAX-ACCESS read-only
    STATUS     current
    DESCRIPTION
            ""
    ::= { lcsStatusIsdnSignalingLayer2LapdEntry 4 }

-- {NODE} 1.3.6.1.4.1.2356.11.1.33.3.3
lcsStatusIsdnSignalingManagement OBJECT IDENTIFIER ::= { lcsStatusIsdnSignaling 3 }

-- {TABLE} 1.3.6.1.4.1.2356.11.1.33.3.3.1
lcsStatusIsdnSignalingManagementDInfoTable OBJECT-TYPE
    SYNTAX     SEQUENCE OF LcsStatusIsdnSignalingManagementDInfoEntry
    MAX-ACCESS not-accessible
    STATUS     current
    DESCRIPTION
            ""
    ::= { lcsStatusIsdnSignalingManagement 1 }

-- {ROW} 1.3.6.1.4.1.2356.11.1.33.3.3.1.1
lcsStatusIsdnSignalingManagementDInfoEntry OBJECT-TYPE
    SYNTAX     LcsStatusIsdnSignalingManagementDInfoEntry
    MAX-ACCESS not-accessible
    STATUS     current
    DESCRIPTION
            ""
    INDEX {
            lcsStatusIsdnSignalingManagementDInfoEntryChannel
          }
    ::= { lcsStatusIsdnSignalingManagementDInfoTable 1 }

LcsStatusIsdnSignalingManagementDInfoEntry ::= SEQUENCE {
            lcsStatusIsdnSignalingManagementDInfoEntryChannel INTEGER,
            lcsStatusIsdnSignalingManagementDInfoEntryProtocol INTEGER,
            lcsStatusIsdnSignalingManagementDInfoEntryLayer2 INTEGER,
            lcsStatusIsdnSignalingManagementDInfoEntryTei INTEGER,
            lcsStatusIsdnSignalingManagementDInfoEntryS0Activation INTEGER
    }

-- {COLUMN} 1.3.6.1.4.1.2356.11.1.33.3.3.1.1.1
lcsStatusIsdnSignalingManagementDInfoEntryChannel OBJECT-TYPE
    SYNTAX     INTEGER {
                  eS01 (257),
                  eS02 (258),
                  eModem (513),
                  eDsl1 (2049),
                  eDsl2 (2050),
                  eDsl3 (2051),
                  eDsl4 (2052),
                  eDsl5 (2053),
                  eAdsl (8193),
                  eVdsl (16385),
                  eVdsl2 (16386)
            }
    MAX-ACCESS read-only
    STATUS     current
    DESCRIPTION
            ""
    ::= { lcsStatusIsdnSignalingManagementDInfoEntry 1 }

-- {COLUMN} 1.3.6.1.4.1.2356.11.1.33.3.3.1.1.2
lcsStatusIsdnSignalingManagementDInfoEntryProtocol OBJECT-TYPE
    SYNTAX     INTEGER {
                  eNo (0),
                  eDss1 (1),
                  e1tr6 (2),
                  eP2pDss1 (4),
                  eAuto (255),
                  eNtP2pDss1 (16384),
                  eNtDss1 (32768),
                  eRevNtP2pDss1 (65536),
                  eRevNtDss1 (131072),
                  eClock (262144)
            }
    MAX-ACCESS read-only
    STATUS     current
    DESCRIPTION
            ""
    ::= { lcsStatusIsdnSignalingManagementDInfoEntry 2 }

-- {COLUMN} 1.3.6.1.4.1.2356.11.1.33.3.3.1.1.3
lcsStatusIsdnSignalingManagementDInfoEntryLayer2 OBJECT-TYPE
    SYNTAX     INTEGER {
                  eNo (0),
                  eYes (1)
            }
    MAX-ACCESS read-only
    STATUS     current
    DESCRIPTION
            ""
    ::= { lcsStatusIsdnSignalingManagementDInfoEntry 3 }

-- {COLUMN} 1.3.6.1.4.1.2356.11.1.33.3.3.1.1.4
lcsStatusIsdnSignalingManagementDInfoEntryTei OBJECT-TYPE
    SYNTAX     INTEGER {
                  eNo (0),
                  eYes (1)
            }
    MAX-ACCESS read-only
    STATUS     current
    DESCRIPTION
            ""
    ::= { lcsStatusIsdnSignalingManagementDInfoEntry 4 }

-- {COLUMN} 1.3.6.1.4.1.2356.11.1.33.3.3.1.1.5
lcsStatusIsdnSignalingManagementDInfoEntryS0Activation OBJECT-TYPE
    SYNTAX     INTEGER {
                  eNo (0),
                  eYes (1)
            }
    MAX-ACCESS read-only
    STATUS     current
    DESCRIPTION
            ""
    ::= { lcsStatusIsdnSignalingManagementDInfoEntry 5 }

-- {TABLE} 1.3.6.1.4.1.2356.11.1.33.3.3.2
lcsStatusIsdnSignalingManagementErrorStatisticTable OBJECT-TYPE
    SYNTAX     SEQUENCE OF LcsStatusIsdnSignalingManagementErrorStatisticEntry
    MAX-ACCESS not-accessible
    STATUS     current
    DESCRIPTION
            ""
    ::= { lcsStatusIsdnSignalingManagement 2 }

-- {ROW} 1.3.6.1.4.1.2356.11.1.33.3.3.2.1
lcsStatusIsdnSignalingManagementErrorStatisticEntry OBJECT-TYPE
    SYNTAX     LcsStatusIsdnSignalingManagementErrorStatisticEntry
    MAX-ACCESS not-accessible
    STATUS     current
    DESCRIPTION
            ""
    INDEX {
            lcsStatusIsdnSignalingManagementErrorStatisticEntryIfc
          }
    ::= { lcsStatusIsdnSignalingManagementErrorStatisticTable 1 }

LcsStatusIsdnSignalingManagementErrorStatisticEntry ::= SEQUENCE {
            lcsStatusIsdnSignalingManagementErrorStatisticEntryIfc INTEGER,
            lcsStatusIsdnSignalingManagementErrorStatisticEntryA Integer32,
            lcsStatusIsdnSignalingManagementErrorStatisticEntryB Integer32,
            lcsStatusIsdnSignalingManagementErrorStatisticEntryC Integer32,
            lcsStatusIsdnSignalingManagementErrorStatisticEntryD Integer32,
            lcsStatusIsdnSignalingManagementErrorStatisticEntryE Integer32,
            lcsStatusIsdnSignalingManagementErrorStatisticEntryF Integer32,
            lcsStatusIsdnSignalingManagementErrorStatisticEntryG Integer32,
            lcsStatusIsdnSignalingManagementErrorStatisticEntryH Integer32,
            lcsStatusIsdnSignalingManagementErrorStatisticEntryI Integer32,
            lcsStatusIsdnSignalingManagementErrorStatisticEntryJ Integer32,
            lcsStatusIsdnSignalingManagementErrorStatisticEntryK Integer32,
            lcsStatusIsdnSignalingManagementErrorStatisticEntryL Integer32,
            lcsStatusIsdnSignalingManagementErrorStatisticEntryM Integer32,
            lcsStatusIsdnSignalingManagementErrorStatisticEntryN Integer32,
            lcsStatusIsdnSignalingManagementErrorStatisticEntryO Integer32
    }

-- {COLUMN} 1.3.6.1.4.1.2356.11.1.33.3.3.2.1.1
lcsStatusIsdnSignalingManagementErrorStatisticEntryIfc OBJECT-TYPE
    SYNTAX     INTEGER {
                  eS01 (257),
                  eS02 (258),
                  eModem (513),
                  eDsl1 (2049),
                  eDsl2 (2050),
                  eDsl3 (2051),
                  eDsl4 (2052),
                  eDsl5 (2053),
                  eAdsl (8193),
                  eVdsl (16385),
                  eVdsl2 (16386)
            }
    MAX-ACCESS read-only
    STATUS     current
    DESCRIPTION
            ""
    ::= { lcsStatusIsdnSignalingManagementErrorStatisticEntry 1 }

-- {COLUMN} 1.3.6.1.4.1.2356.11.1.33.3.3.2.1.2
lcsStatusIsdnSignalingManagementErrorStatisticEntryA OBJECT-TYPE
    SYNTAX     Integer32 (0..65535)
    MAX-ACCESS read-only
    STATUS     current
    DESCRIPTION
            ""
    ::= { lcsStatusIsdnSignalingManagementErrorStatisticEntry 2 }

-- {COLUMN} 1.3.6.1.4.1.2356.11.1.33.3.3.2.1.3
lcsStatusIsdnSignalingManagementErrorStatisticEntryB OBJECT-TYPE
    SYNTAX     Integer32 (0..65535)
    MAX-ACCESS read-only
    STATUS     current
    DESCRIPTION
            ""
    ::= { lcsStatusIsdnSignalingManagementErrorStatisticEntry 3 }

-- {COLUMN} 1.3.6.1.4.1.2356.11.1.33.3.3.2.1.4
lcsStatusIsdnSignalingManagementErrorStatisticEntryC OBJECT-TYPE
    SYNTAX     Integer32 (0..65535)
    MAX-ACCESS read-only
    STATUS     current
    DESCRIPTION
            ""
    ::= { lcsStatusIsdnSignalingManagementErrorStatisticEntry 4 }

-- {COLUMN} 1.3.6.1.4.1.2356.11.1.33.3.3.2.1.5
lcsStatusIsdnSignalingManagementErrorStatisticEntryD OBJECT-TYPE
    SYNTAX     Integer32 (0..65535)
    MAX-ACCESS read-only
    STATUS     current
    DESCRIPTION
            ""
    ::= { lcsStatusIsdnSignalingManagementErrorStatisticEntry 5 }

-- {COLUMN} 1.3.6.1.4.1.2356.11.1.33.3.3.2.1.6
lcsStatusIsdnSignalingManagementErrorStatisticEntryE OBJECT-TYPE
    SYNTAX     Integer32 (0..65535)
    MAX-ACCESS read-only
    STATUS     current
    DESCRIPTION
            ""
    ::= { lcsStatusIsdnSignalingManagementErrorStatisticEntry 6 }

-- {COLUMN} 1.3.6.1.4.1.2356.11.1.33.3.3.2.1.7
lcsStatusIsdnSignalingManagementErrorStatisticEntryF OBJECT-TYPE
    SYNTAX     Integer32 (0..65535)
    MAX-ACCESS read-only
    STATUS     current
    DESCRIPTION
            ""
    ::= { lcsStatusIsdnSignalingManagementErrorStatisticEntry 7 }

-- {COLUMN} 1.3.6.1.4.1.2356.11.1.33.3.3.2.1.8
lcsStatusIsdnSignalingManagementErrorStatisticEntryG OBJECT-TYPE
    SYNTAX     Integer32 (0..65535)
    MAX-ACCESS read-only
    STATUS     current
    DESCRIPTION
            ""
    ::= { lcsStatusIsdnSignalingManagementErrorStatisticEntry 8 }

-- {COLUMN} 1.3.6.1.4.1.2356.11.1.33.3.3.2.1.9
lcsStatusIsdnSignalingManagementErrorStatisticEntryH OBJECT-TYPE
    SYNTAX     Integer32 (0..65535)
    MAX-ACCESS read-only
    STATUS     current
    DESCRIPTION
            ""
    ::= { lcsStatusIsdnSignalingManagementErrorStatisticEntry 9 }

-- {COLUMN} 1.3.6.1.4.1.2356.11.1.33.3.3.2.1.10
lcsStatusIsdnSignalingManagementErrorStatisticEntryI OBJECT-TYPE
    SYNTAX     Integer32 (0..65535)
    MAX-ACCESS read-only
    STATUS     current
    DESCRIPTION
            ""
    ::= { lcsStatusIsdnSignalingManagementErrorStatisticEntry 10 }

-- {COLUMN} 1.3.6.1.4.1.2356.11.1.33.3.3.2.1.11
lcsStatusIsdnSignalingManagementErrorStatisticEntryJ OBJECT-TYPE
    SYNTAX     Integer32 (0..65535)
    MAX-ACCESS read-only
    STATUS     current
    DESCRIPTION
            ""
    ::= { lcsStatusIsdnSignalingManagementErrorStatisticEntry 11 }

-- {COLUMN} 1.3.6.1.4.1.2356.11.1.33.3.3.2.1.12
lcsStatusIsdnSignalingManagementErrorStatisticEntryK OBJECT-TYPE
    SYNTAX     Integer32 (0..65535)
    MAX-ACCESS read-only
    STATUS     current
    DESCRIPTION
            ""
    ::= { lcsStatusIsdnSignalingManagementErrorStatisticEntry 12 }

-- {COLUMN} 1.3.6.1.4.1.2356.11.1.33.3.3.2.1.13
lcsStatusIsdnSignalingManagementErrorStatisticEntryL OBJECT-TYPE
    SYNTAX     Integer32 (0..65535)
    MAX-ACCESS read-only
    STATUS     current
    DESCRIPTION
            ""
    ::= { lcsStatusIsdnSignalingManagementErrorStatisticEntry 13 }

-- {COLUMN} 1.3.6.1.4.1.2356.11.1.33.3.3.2.1.14
lcsStatusIsdnSignalingManagementErrorStatisticEntryM OBJECT-TYPE
    SYNTAX     Integer32 (0..65535)
    MAX-ACCESS read-only
    STATUS     current
    DESCRIPTION
            ""
    ::= { lcsStatusIsdnSignalingManagementErrorStatisticEntry 14 }

-- {COLUMN} 1.3.6.1.4.1.2356.11.1.33.3.3.2.1.15
lcsStatusIsdnSignalingManagementErrorStatisticEntryN OBJECT-TYPE
    SYNTAX     Integer32 (0..65535)
    MAX-ACCESS read-only
    STATUS     current
    DESCRIPTION
            ""
    ::= { lcsStatusIsdnSignalingManagementErrorStatisticEntry 15 }

-- {COLUMN} 1.3.6.1.4.1.2356.11.1.33.3.3.2.1.16
lcsStatusIsdnSignalingManagementErrorStatisticEntryO OBJECT-TYPE
    SYNTAX     Integer32 (0..65535)
    MAX-ACCESS read-only
    STATUS     current
    DESCRIPTION
            ""
    ::= { lcsStatusIsdnSignalingManagementErrorStatisticEntry 16 }

-- {NODE} 1.3.6.1.4.1.2356.11.1.33.20
lcsStatusIsdnPcmSwitch OBJECT IDENTIFIER ::= { lcsStatusIsdn 20 }

-- {TABLE} 1.3.6.1.4.1.2356.11.1.33.20.1
lcsStatusIsdnPcmSwitchPcmConnectionTable OBJECT-TYPE
    SYNTAX     SEQUENCE OF LcsStatusIsdnPcmSwitchPcmConnectionEntry
    MAX-ACCESS not-accessible
    STATUS     current
    DESCRIPTION
            ""
    ::= { lcsStatusIsdnPcmSwitch 1 }

-- {ROW} 1.3.6.1.4.1.2356.11.1.33.20.1.1
lcsStatusIsdnPcmSwitchPcmConnectionEntry OBJECT-TYPE
    SYNTAX     LcsStatusIsdnPcmSwitchPcmConnectionEntry
    MAX-ACCESS not-accessible
    STATUS     current
    DESCRIPTION
            ""
    INDEX {
            lcsStatusIsdnPcmSwitchPcmConnectionEntryDevice,
            lcsStatusIsdnPcmSwitchPcmConnectionEntryType,
            lcsStatusIsdnPcmSwitchPcmConnectionEntryNumber
          }
    ::= { lcsStatusIsdnPcmSwitchPcmConnectionTable 1 }

LcsStatusIsdnPcmSwitchPcmConnectionEntry ::= SEQUENCE {
            lcsStatusIsdnPcmSwitchPcmConnectionEntryDevice Integer32,
            lcsStatusIsdnPcmSwitchPcmConnectionEntryType INTEGER,
            lcsStatusIsdnPcmSwitchPcmConnectionEntryNumber Integer32,
            lcsStatusIsdnPcmSwitchPcmConnectionEntryFifo DisplayString,
            lcsStatusIsdnPcmSwitchPcmConnectionEntryFlow DisplayString,
            lcsStatusIsdnPcmSwitchPcmConnectionEntryChannel DisplayString,
            lcsStatusIsdnPcmSwitchPcmConnectionEntryTimeslot DisplayString
    }

-- {COLUMN} 1.3.6.1.4.1.2356.11.1.33.20.1.1.1
lcsStatusIsdnPcmSwitchPcmConnectionEntryDevice OBJECT-TYPE
    SYNTAX     Integer32 (0..255)
    MAX-ACCESS read-only
    STATUS     current
    DESCRIPTION
            ""
    ::= { lcsStatusIsdnPcmSwitchPcmConnectionEntry 1 }

-- {COLUMN} 1.3.6.1.4.1.2356.11.1.33.20.1.1.2
lcsStatusIsdnPcmSwitchPcmConnectionEntryType OBJECT-TYPE
    SYNTAX     INTEGER {
                  eFifo (0),
                  ePcmTs (1)
            }
    MAX-ACCESS read-only
    STATUS     current
    DESCRIPTION
            ""
    ::= { lcsStatusIsdnPcmSwitchPcmConnectionEntry 2 }

-- {COLUMN} 1.3.6.1.4.1.2356.11.1.33.20.1.1.3
lcsStatusIsdnPcmSwitchPcmConnectionEntryNumber OBJECT-TYPE
    SYNTAX     Integer32 (0..255)
    MAX-ACCESS read-only
    STATUS     current
    DESCRIPTION
            ""
    ::= { lcsStatusIsdnPcmSwitchPcmConnectionEntry 3 }

-- {COLUMN} 1.3.6.1.4.1.2356.11.1.33.20.1.1.4
lcsStatusIsdnPcmSwitchPcmConnectionEntryFifo OBJECT-TYPE
    SYNTAX     DisplayString (SIZE(0..7))
    MAX-ACCESS read-only
    STATUS     current
    DESCRIPTION
            ""
    ::= { lcsStatusIsdnPcmSwitchPcmConnectionEntry 4 }

-- {COLUMN} 1.3.6.1.4.1.2356.11.1.33.20.1.1.5
lcsStatusIsdnPcmSwitchPcmConnectionEntryFlow OBJECT-TYPE
    SYNTAX     DisplayString (SIZE(0..29))
    MAX-ACCESS read-only
    STATUS     current
    DESCRIPTION
            ""
    ::= { lcsStatusIsdnPcmSwitchPcmConnectionEntry 5 }

-- {COLUMN} 1.3.6.1.4.1.2356.11.1.33.20.1.1.6
lcsStatusIsdnPcmSwitchPcmConnectionEntryChannel OBJECT-TYPE
    SYNTAX     DisplayString (SIZE(0..4))
    MAX-ACCESS read-only
    STATUS     current
    DESCRIPTION
            ""
    ::= { lcsStatusIsdnPcmSwitchPcmConnectionEntry 6 }

-- {COLUMN} 1.3.6.1.4.1.2356.11.1.33.20.1.1.7
lcsStatusIsdnPcmSwitchPcmConnectionEntryTimeslot OBJECT-TYPE
    SYNTAX     DisplayString (SIZE(0..17))
    MAX-ACCESS read-only
    STATUS     current
    DESCRIPTION
            ""
    ::= { lcsStatusIsdnPcmSwitchPcmConnectionEntry 7 }

-- {SCALAR} 1.3.6.1.4.1.2356.11.1.33.99
lcsStatusIsdnDeleteValues OBJECT-TYPE
    SYNTAX     DisplayString
    MAX-ACCESS read-write
    STATUS     current
    DESCRIPTION
            ""
    ::= { lcsStatusIsdn 99 }

-- {NODE} 1.3.6.1.4.1.2356.11.1.35
lcsStatusSnmp OBJECT IDENTIFIER ::= { lcsStatus 35 }

-- {TABLE} 1.3.6.1.4.1.2356.11.1.35.1
lcsStatusSnmpEventTable OBJECT-TYPE
    SYNTAX     SEQUENCE OF LcsStatusSnmpEventEntry
    MAX-ACCESS not-accessible
    STATUS     current
    DESCRIPTION
            ""
    ::= { lcsStatusSnmp 1 }

-- {ROW} 1.3.6.1.4.1.2356.11.1.35.1.1
lcsStatusSnmpEventEntry OBJECT-TYPE
    SYNTAX     LcsStatusSnmpEventEntry
    MAX-ACCESS not-accessible
    STATUS     current
    DESCRIPTION
            ""
    INDEX {
            lcsStatusSnmpEventEntryTrapName,
            lcsStatusSnmpEventEntryVendorName
          }
    ::= { lcsStatusSnmpEventTable 1 }

LcsStatusSnmpEventEntry ::= SEQUENCE {
            lcsStatusSnmpEventEntryTrapName INTEGER,
            lcsStatusSnmpEventEntryVendorName INTEGER,
            lcsStatusSnmpEventEntryCount Integer32
    }

-- {COLUMN} 1.3.6.1.4.1.2356.11.1.35.1.1.1
lcsStatusSnmpEventEntryTrapName OBJECT-TYPE
    SYNTAX     INTEGER {
                  eWarmstart (1),
                  eLinkdown (2),
                  eLinkup (3),
                  eAuthfail (4),
                  eEpgnloss (5),
                  eEnterprise (6),
                  eColdstart (255)
            }
    MAX-ACCESS read-only
    STATUS     current
    DESCRIPTION
            ""
    ::= { lcsStatusSnmpEventEntry 1 }

-- {COLUMN} 1.3.6.1.4.1.2356.11.1.35.1.1.2
lcsStatusSnmpEventEntryVendorName OBJECT-TYPE
    SYNTAX     INTEGER {
                  eNone (0),
                  eStatChan (1),
                  eFwUplStart (4),
                  eUplsucc (5),
                  eUplfailto (6),
                  eUplfailincl (7),
                  eUplfailbaddev (8),
                  eLogin (9),
                  eLogout (10),
                  eCnfuplstart (11),
                  eCnfdnlstart (12),
                  eCnfdnlsucc (13),
                  eBssscan (14),
                  eBssstart (15),
                  eBssjoin (16),
                  eAuthstation (17),
                  eDeauthstation (18),
                  eAssstation (19),
                  eReassstation (20),
                  eDisassstation (21),
                  eAssrej (22),
                  eCardhung (25),
                  eIpfwflt (26),
                  eVpnconn (27),
                  ePptpconn (28),
                  eErrlogin (29),
                  eKeyhandshakeTimeout (33),
                  eSupervision (35),
                  eLdblconn (38),
                  ePppoesconn (39),
                  eVrrp (41),
                  eExceirp (42),
                  eVcmCallStatChan (43),
                  eVcmUserStatChan (44),
                  eVcmLineStatChan (45),
                  eIdleTimeout (46),
                  eAdminDeassoc (47),
                  eWlanovertemp (48),
                  eWlanovertempend (49),
                  eWlanundertemp (50),
                  eWlanundertempend (51),
                  eMacchkfail (52),
                  eRoamed (53),
                  eConnected (54),
                  eClLostconn (55),
                  eClAuthfail (56),
                  eClAssocfail (57),
                  eClConnected (58),
                  eCl8021xFail (59),
                  eAdslstate (60),
                  eCastatchg (61),
                  eNewpendreq (62),
                  eMissingAp (63),
                  eActiveAp (64),
                  eNewAp (65),
                  eStations (66),
                  eNetworks (67),
                  eNetworkcounts (68),
                  eApCounter (69),
                  eUtmcontentfilter (72),
                  eCerttabmod (73),
                  ePendlistmod (74),
                  eNextdoorAp (75),
                  eWlcTunnels (76),
                  eLicensemgtexpire (77),
                  eVdslstate (78),
                  eScrptuplstart (79),
                  eScrptdnlstart (80),
                  eIpv6fwflt (81),
                  eWwanStates (82),
                  eDS-Lite (83),
                  eVolumebudget (84),
                  eL2TP-Endpoints (85),
                  eL2TP-Connections (86),
                  eLoginBlocked (87),
                  eWidsAlarm (88),
                  eVdslstate2 (89),
                  eL2TP-Ethernet (102),
                  eSpgtreePortstatchg (1000),
                  eSpgtreeRstpstatchg (1001),
                  eSpgtreeRootportchg (1002),
                  eHttpTunnelOpen (2000),
                  eHttpTunnelClose (2001),
                  eLanauthuseradd (3000),
                  eLanauthuserdel (3001),
                  eLanauthsessionstart (3002),
                  eLanauthsessionend (3003),
                  eTempmonovertemp (4000),
                  eTempmonnoovertemp (4001),
                  eTempmonundertemp (4002),
                  eTempmonnoundertemp (4003),
                  eVoltmonovervolt (4500),
                  eVoltmonnoovervolt (4501),
                  eVoltmonundervolt (4502),
                  eVoltmonnoundervolt (4503),
                  eLanDownshift (5001),
                  eLanOvertempThrottle (5002),
                  eLanOvertempThrottleEnd (5003),
                  eLanOvertempThrottleRecommend (5004),
                  eEthPortDownshift (5101),
                  eWlanConfadaptRadiochannel (6100),
                  eWlanConfadaptRadiomode (6101),
                  eWlanConfadaptBasicRate (6102),
                  eWlanConfadaptEapolRate (6103),
                  eWlanConfadaptEncryption (6104),
                  eWlanAlarmP2pSignal (6200),
                  eWlanAlarmP2pTxtotretries (6201),
                  eWlanAlarmP2pTxerrors (6202),
                  eWlanAlarmNetwSignal (6203),
                  eWlanAlarmNetwTxtotretries (6204),
                  eWlanAlarmNetwTxerrors (6205),
                  eWlanAlarmClientSignal (6206),
                  eWlanAlarmClientTxtotretries (6207),
                  eWlanAlarmClientTxerrors (6208),
                  eWlanDfsAllblocked (6300),
                  eUplinvversion (7000),
                  eUplfileexists (7001),
                  eSmsinboxmsgchanged (8000),
                  eSmsoutboxmsgchanged (8001),
                  eSmsoutboxcleared (8002),
                  eSmsinboxcleared (8003),
                  eSimstatuschanged (8100),
                  eUpsConnectionStart (9700),
                  eUpsConnectionStop (9701),
                  eUpsPowerFailure (9702),
                  eUpsPowerAvailable (9703),
                  eUpsBatteryLow (9704),
                  eUpsBatteryDefect (9705),
                  eUpsTempHigh (9706),
                  eUpsTempDown (9707),
                  eUpsService (9708),
                  eL7DetectionStatus (9800),
                  eIdsTrapEvent (10000)
            }
    MAX-ACCESS read-only
    STATUS     current
    DESCRIPTION
            ""
    ::= { lcsStatusSnmpEventEntry 2 }

-- {COLUMN} 1.3.6.1.4.1.2356.11.1.35.1.1.3
lcsStatusSnmpEventEntryCount OBJECT-TYPE
    SYNTAX     Integer32 (0..2147483647)
    MAX-ACCESS read-only
    STATUS     current
    DESCRIPTION
            ""
    ::= { lcsStatusSnmpEventEntry 3 }

-- {SCALAR} 1.3.6.1.4.1.2356.11.1.35.2
lcsStatusSnmpRejectedRequests OBJECT-TYPE
    SYNTAX     Integer32 (0..2147483647)
    MAX-ACCESS read-only
    STATUS     current
    DESCRIPTION
            ""
    ::= { lcsStatusSnmp 2 }

-- {SCALAR} 1.3.6.1.4.1.2356.11.1.35.3
lcsStatusSnmpQueueBlockErrors OBJECT-TYPE
    SYNTAX     Integer32 (0..2147483647)
    MAX-ACCESS read-only
    STATUS     current
    DESCRIPTION
            ""
    ::= { lcsStatusSnmp 3 }

-- {SCALAR} 1.3.6.1.4.1.2356.11.1.35.4
lcsStatusSnmpDroppedPackets OBJECT-TYPE
    SYNTAX     Integer32 (0..2147483647)
    MAX-ACCESS read-only
    STATUS     current
    DESCRIPTION
            ""
    ::= { lcsStatusSnmp 4 }

-- {SCALAR} 1.3.6.1.4.1.2356.11.1.35.5
lcsStatusSnmpPublicComment1 OBJECT-TYPE
    SYNTAX     DisplayString (SIZE(0..255))
    MAX-ACCESS read-only
    STATUS     current
    DESCRIPTION
            "-- empty --"
    ::= { lcsStatusSnmp 5 }

-- {TABLE} 1.3.6.1.4.1.2356.11.1.35.6
lcsStatusSnmpLogTableTable OBJECT-TYPE
    SYNTAX     SEQUENCE OF LcsStatusSnmpLogTableEntry
    MAX-ACCESS not-accessible
    STATUS     current
    DESCRIPTION
            ""
    ::= { lcsStatusSnmp 6 }

-- {ROW} 1.3.6.1.4.1.2356.11.1.35.6.1
lcsStatusSnmpLogTableEntry OBJECT-TYPE
    SYNTAX     LcsStatusSnmpLogTableEntry
    MAX-ACCESS not-accessible
    STATUS     current
    DESCRIPTION
            ""
    INDEX {
            lcsStatusSnmpLogTableEntryIndex
          }
    ::= { lcsStatusSnmpLogTableTable 1 }

LcsStatusSnmpLogTableEntry ::= SEQUENCE {
            lcsStatusSnmpLogTableEntryIndex Integer32,
            lcsStatusSnmpLogTableEntryTime DisplayString,
            lcsStatusSnmpLogTableEntryEvent DisplayString
    }

-- {COLUMN} 1.3.6.1.4.1.2356.11.1.35.6.1.1
lcsStatusSnmpLogTableEntryIndex OBJECT-TYPE
    SYNTAX     Integer32 (0..2147483647)
    MAX-ACCESS read-only
    STATUS     current
    DESCRIPTION
            ""
    ::= { lcsStatusSnmpLogTableEntry 1 }

-- {COLUMN} 1.3.6.1.4.1.2356.11.1.35.6.1.2
lcsStatusSnmpLogTableEntryTime OBJECT-TYPE
    SYNTAX     DisplayString (SIZE(0..21))
    MAX-ACCESS read-only
    STATUS     current
    DESCRIPTION
            ""
    ::= { lcsStatusSnmpLogTableEntry 2 }

-- {COLUMN} 1.3.6.1.4.1.2356.11.1.35.6.1.3
lcsStatusSnmpLogTableEntryEvent OBJECT-TYPE
    SYNTAX     DisplayString (SIZE(0..252))
    MAX-ACCESS read-only
    STATUS     current
    DESCRIPTION
            ""
    ::= { lcsStatusSnmpLogTableEntry 3 }

-- {SCALAR} 1.3.6.1.4.1.2356.11.1.35.7
lcsStatusSnmpPublicComment3 OBJECT-TYPE
    SYNTAX     DisplayString (SIZE(0..255))
    MAX-ACCESS read-only
    STATUS     current
    DESCRIPTION
            "-- empty --"
    ::= { lcsStatusSnmp 7 }

-- {SCALAR} 1.3.6.1.4.1.2356.11.1.35.8
lcsStatusSnmpPublicComment4 OBJECT-TYPE
    SYNTAX     DisplayString (SIZE(0..255))
    MAX-ACCESS read-only
    STATUS     current
    DESCRIPTION
            "-- empty --"
    ::= { lcsStatusSnmp 8 }

-- {SCALAR} 1.3.6.1.4.1.2356.11.1.35.9
lcsStatusSnmpPublicComment2 OBJECT-TYPE
    SYNTAX     DisplayString (SIZE(0..255))
    MAX-ACCESS read-only
    STATUS     current
    DESCRIPTION
            "-- empty --"
    ::= { lcsStatusSnmp 9 }

-- {TABLE} 1.3.6.1.4.1.2356.11.1.35.10
lcsStatusSnmpMonitorTableTable OBJECT-TYPE
    SYNTAX     SEQUENCE OF LcsStatusSnmpMonitorTableEntry
    MAX-ACCESS not-accessible
    STATUS     current
    DESCRIPTION
            "-- empty --"
    ::= { lcsStatusSnmp 10 }

-- {ROW} 1.3.6.1.4.1.2356.11.1.35.10.1
lcsStatusSnmpMonitorTableEntry OBJECT-TYPE
    SYNTAX     LcsStatusSnmpMonitorTableEntry
    MAX-ACCESS not-accessible
    STATUS     current
    DESCRIPTION
            ""
    INDEX {
            lcsStatusSnmpMonitorTableEntryIpAddress,
            lcsStatusSnmpMonitorTableEntrySourcePort
          }
    ::= { lcsStatusSnmpMonitorTableTable 1 }

LcsStatusSnmpMonitorTableEntry ::= SEQUENCE {
            lcsStatusSnmpMonitorTableEntryIpAddress DisplayString,
            lcsStatusSnmpMonitorTableEntrySourcePort Integer32,
            lcsStatusSnmpMonitorTableEntryVersion DisplayString,
            lcsStatusSnmpMonitorTableEntrySecurityName DisplayString,
            lcsStatusSnmpMonitorTableEntryTimeout Integer32
    }

-- {COLUMN} 1.3.6.1.4.1.2356.11.1.35.10.1.1
lcsStatusSnmpMonitorTableEntryIpAddress OBJECT-TYPE
    SYNTAX     DisplayString (SIZE(0..255))
    MAX-ACCESS read-only
    STATUS     current
    DESCRIPTION
            "-- empty --"
    ::= { lcsStatusSnmpMonitorTableEntry 1 }

-- {COLUMN} 1.3.6.1.4.1.2356.11.1.35.10.1.2
lcsStatusSnmpMonitorTableEntrySourcePort OBJECT-TYPE
    SYNTAX     Integer32 (0..65535)
    MAX-ACCESS read-only
    STATUS     current
    DESCRIPTION
            "-- empty --"
    ::= { lcsStatusSnmpMonitorTableEntry 2 }

-- {COLUMN} 1.3.6.1.4.1.2356.11.1.35.10.1.3
lcsStatusSnmpMonitorTableEntryVersion OBJECT-TYPE
    SYNTAX     DisplayString (SIZE(0..255))
    MAX-ACCESS read-only
    STATUS     current
    DESCRIPTION
            "-- empty --"
    ::= { lcsStatusSnmpMonitorTableEntry 3 }

-- {COLUMN} 1.3.6.1.4.1.2356.11.1.35.10.1.4
lcsStatusSnmpMonitorTableEntrySecurityName OBJECT-TYPE
    SYNTAX     DisplayString (SIZE(0..255))
    MAX-ACCESS read-only
    STATUS     current
    DESCRIPTION
            "-- empty --"
    ::= { lcsStatusSnmpMonitorTableEntry 4 }

-- {COLUMN} 1.3.6.1.4.1.2356.11.1.35.10.1.5
lcsStatusSnmpMonitorTableEntryTimeout OBJECT-TYPE
    SYNTAX     Integer32 (0..2147483647)
    MAX-ACCESS read-only
    STATUS     current
    DESCRIPTION
            "-- empty --"
    ::= { lcsStatusSnmpMonitorTableEntry 5 }

-- {NODE} 1.3.6.1.4.1.2356.11.1.35.11
lcsStatusSnmpCounter OBJECT IDENTIFIER ::= { lcsStatusSnmp 11 }

-- {SCALAR} 1.3.6.1.4.1.2356.11.1.35.11.1
lcsStatusSnmpCounterInPackets OBJECT-TYPE
    SYNTAX     Counter32
    MAX-ACCESS read-only
    STATUS     current
    DESCRIPTION
            "-- empty --"
    ::= { lcsStatusSnmpCounter 1 }

-- {SCALAR} 1.3.6.1.4.1.2356.11.1.35.11.2
lcsStatusSnmpCounterOutPackets OBJECT-TYPE
    SYNTAX     Counter32
    MAX-ACCESS read-only
    STATUS     current
    DESCRIPTION
            "-- empty --"
    ::= { lcsStatusSnmpCounter 2 }

-- {SCALAR} 1.3.6.1.4.1.2356.11.1.35.11.3
lcsStatusSnmpCounterInBadVersions OBJECT-TYPE
    SYNTAX     Counter32
    MAX-ACCESS read-only
    STATUS     current
    DESCRIPTION
            "-- empty --"
    ::= { lcsStatusSnmpCounter 3 }

-- {SCALAR} 1.3.6.1.4.1.2356.11.1.35.11.4
lcsStatusSnmpCounterInBadCommunityNames OBJECT-TYPE
    SYNTAX     Counter32
    MAX-ACCESS read-only
    STATUS     current
    DESCRIPTION
            "-- empty --"
    ::= { lcsStatusSnmpCounter 4 }

-- {SCALAR} 1.3.6.1.4.1.2356.11.1.35.11.5
lcsStatusSnmpCounterInBadCommunityUses OBJECT-TYPE
    SYNTAX     Counter32
    MAX-ACCESS read-only
    STATUS     current
    DESCRIPTION
            "-- empty --"
    ::= { lcsStatusSnmpCounter 5 }

-- {SCALAR} 1.3.6.1.4.1.2356.11.1.35.11.6
lcsStatusSnmpCounterInAsnParseErrors OBJECT-TYPE
    SYNTAX     Counter32
    MAX-ACCESS read-only
    STATUS     current
    DESCRIPTION
            "-- empty --"
    ::= { lcsStatusSnmpCounter 6 }

-- {SCALAR} 1.3.6.1.4.1.2356.11.1.35.11.8
lcsStatusSnmpCounterInTooBigs OBJECT-TYPE
    SYNTAX     Counter32
    MAX-ACCESS read-only
    STATUS     current
    DESCRIPTION
            "-- empty --"
    ::= { lcsStatusSnmpCounter 8 }

-- {SCALAR} 1.3.6.1.4.1.2356.11.1.35.11.9
lcsStatusSnmpCounterInNoSuchNames OBJECT-TYPE
    SYNTAX     Counter32
    MAX-ACCESS read-only
    STATUS     current
    DESCRIPTION
            "-- empty --"
    ::= { lcsStatusSnmpCounter 9 }

-- {SCALAR} 1.3.6.1.4.1.2356.11.1.35.11.10
lcsStatusSnmpCounterInBadValues OBJECT-TYPE
    SYNTAX     Counter32
    MAX-ACCESS read-only
    STATUS     current
    DESCRIPTION
            "-- empty --"
    ::= { lcsStatusSnmpCounter 10 }

-- {SCALAR} 1.3.6.1.4.1.2356.11.1.35.11.11
lcsStatusSnmpCounterInReadOnlys OBJECT-TYPE
    SYNTAX     Counter32
    MAX-ACCESS read-only
    STATUS     current
    DESCRIPTION
            "-- empty --"
    ::= { lcsStatusSnmpCounter 11 }

-- {SCALAR} 1.3.6.1.4.1.2356.11.1.35.11.12
lcsStatusSnmpCounterInGenErrors OBJECT-TYPE
    SYNTAX     Counter32
    MAX-ACCESS read-only
    STATUS     current
    DESCRIPTION
            "-- empty --"
    ::= { lcsStatusSnmpCounter 12 }

-- {SCALAR} 1.3.6.1.4.1.2356.11.1.35.11.13
lcsStatusSnmpCounterInTotalRequestVars OBJECT-TYPE
    SYNTAX     Counter32
    MAX-ACCESS read-only
    STATUS     current
    DESCRIPTION
            "-- empty --"
    ::= { lcsStatusSnmpCounter 13 }

-- {SCALAR} 1.3.6.1.4.1.2356.11.1.35.11.14
lcsStatusSnmpCounterInTotalSetVars OBJECT-TYPE
    SYNTAX     Counter32
    MAX-ACCESS read-only
    STATUS     current
    DESCRIPTION
            "-- empty --"
    ::= { lcsStatusSnmpCounter 14 }

-- {SCALAR} 1.3.6.1.4.1.2356.11.1.35.11.15
lcsStatusSnmpCounterInGetRequests OBJECT-TYPE
    SYNTAX     Counter32
    MAX-ACCESS read-only
    STATUS     current
    DESCRIPTION
            "-- empty --"
    ::= { lcsStatusSnmpCounter 15 }

-- {SCALAR} 1.3.6.1.4.1.2356.11.1.35.11.16
lcsStatusSnmpCounterInGetNexts OBJECT-TYPE
    SYNTAX     Counter32
    MAX-ACCESS read-only
    STATUS     current
    DESCRIPTION
            "-- empty --"
    ::= { lcsStatusSnmpCounter 16 }

-- {SCALAR} 1.3.6.1.4.1.2356.11.1.35.11.17
lcsStatusSnmpCounterInSetRequests OBJECT-TYPE
    SYNTAX     Counter32
    MAX-ACCESS read-only
    STATUS     current
    DESCRIPTION
            "-- empty --"
    ::= { lcsStatusSnmpCounter 17 }

-- {SCALAR} 1.3.6.1.4.1.2356.11.1.35.11.18
lcsStatusSnmpCounterInGetResponses OBJECT-TYPE
    SYNTAX     Counter32
    MAX-ACCESS read-only
    STATUS     current
    DESCRIPTION
            "-- empty --"
    ::= { lcsStatusSnmpCounter 18 }

-- {SCALAR} 1.3.6.1.4.1.2356.11.1.35.11.19
lcsStatusSnmpCounterInTraps OBJECT-TYPE
    SYNTAX     Counter32
    MAX-ACCESS read-only
    STATUS     current
    DESCRIPTION
            "-- empty --"
    ::= { lcsStatusSnmpCounter 19 }

-- {SCALAR} 1.3.6.1.4.1.2356.11.1.35.11.20
lcsStatusSnmpCounterOutTooBigs OBJECT-TYPE
    SYNTAX     Counter32
    MAX-ACCESS read-only
    STATUS     current
    DESCRIPTION
            "-- empty --"
    ::= { lcsStatusSnmpCounter 20 }

-- {SCALAR} 1.3.6.1.4.1.2356.11.1.35.11.21
lcsStatusSnmpCounterOutNoSuchNames OBJECT-TYPE
    SYNTAX     Counter32
    MAX-ACCESS read-only
    STATUS     current
    DESCRIPTION
            "-- empty --"
    ::= { lcsStatusSnmpCounter 21 }

-- {SCALAR} 1.3.6.1.4.1.2356.11.1.35.11.22
lcsStatusSnmpCounterOutBadValues OBJECT-TYPE
    SYNTAX     Counter32
    MAX-ACCESS read-only
    STATUS     current
    DESCRIPTION
            "-- empty --"
    ::= { lcsStatusSnmpCounter 22 }

-- {SCALAR} 1.3.6.1.4.1.2356.11.1.35.11.24
lcsStatusSnmpCounterOutGenErrors OBJECT-TYPE
    SYNTAX     Counter32
    MAX-ACCESS read-only
    STATUS     current
    DESCRIPTION
            "-- empty --"
    ::= { lcsStatusSnmpCounter 24 }

-- {SCALAR} 1.3.6.1.4.1.2356.11.1.35.11.25
lcsStatusSnmpCounterOutGetRequests OBJECT-TYPE
    SYNTAX     Counter32
    MAX-ACCESS read-only
    STATUS     current
    DESCRIPTION
            "-- empty --"
    ::= { lcsStatusSnmpCounter 25 }

-- {SCALAR} 1.3.6.1.4.1.2356.11.1.35.11.26
lcsStatusSnmpCounterOutGetNexts OBJECT-TYPE
    SYNTAX     Counter32
    MAX-ACCESS read-only
    STATUS     current
    DESCRIPTION
            "-- empty --"
    ::= { lcsStatusSnmpCounter 26 }

-- {SCALAR} 1.3.6.1.4.1.2356.11.1.35.11.27
lcsStatusSnmpCounterOutSetRequests OBJECT-TYPE
    SYNTAX     Counter32
    MAX-ACCESS read-only
    STATUS     current
    DESCRIPTION
            "-- empty --"
    ::= { lcsStatusSnmpCounter 27 }

-- {SCALAR} 1.3.6.1.4.1.2356.11.1.35.11.28
lcsStatusSnmpCounterOutGetReponses OBJECT-TYPE
    SYNTAX     Counter32
    MAX-ACCESS read-only
    STATUS     current
    DESCRIPTION
            "-- empty --"
    ::= { lcsStatusSnmpCounter 28 }

-- {SCALAR} 1.3.6.1.4.1.2356.11.1.35.11.29
lcsStatusSnmpCounterOutTraps OBJECT-TYPE
    SYNTAX     Counter32
    MAX-ACCESS read-only
    STATUS     current
    DESCRIPTION
            "-- empty --"
    ::= { lcsStatusSnmpCounter 29 }

-- {SCALAR} 1.3.6.1.4.1.2356.11.1.35.11.30
lcsStatusSnmpCounterEnableAuthenticationTraps OBJECT-TYPE
    SYNTAX     INTEGER {
                  eYes (1),
                  eNo (2)
            }
    MAX-ACCESS read-write
    STATUS     current
    DESCRIPTION
            "-- empty --"
    ::= { lcsStatusSnmpCounter 30 }

-- {SCALAR} 1.3.6.1.4.1.2356.11.1.35.11.31
lcsStatusSnmpCounterSilentDrop OBJECT-TYPE
    SYNTAX     Counter32
    MAX-ACCESS read-only
    STATUS     current
    DESCRIPTION
            "-- empty --"
    ::= { lcsStatusSnmpCounter 31 }

-- {SCALAR} 1.3.6.1.4.1.2356.11.1.35.11.32
lcsStatusSnmpCounterProxyDrop OBJECT-TYPE
    SYNTAX     Counter32
    MAX-ACCESS read-only
    STATUS     current
    DESCRIPTION
            "-- empty --"
    ::= { lcsStatusSnmpCounter 32 }

-- {NODE} 1.3.6.1.4.1.2356.11.1.35.12
lcsStatusSnmpUsmCounter OBJECT IDENTIFIER ::= { lcsStatusSnmp 12 }

-- {SCALAR} 1.3.6.1.4.1.2356.11.1.35.12.1
lcsStatusSnmpUsmCounterUnsupportedSecurityLevels OBJECT-TYPE
    SYNTAX     Counter32
    MAX-ACCESS read-only
    STATUS     current
    DESCRIPTION
            "-- empty --"
    ::= { lcsStatusSnmpUsmCounter 1 }

-- {SCALAR} 1.3.6.1.4.1.2356.11.1.35.12.2
lcsStatusSnmpUsmCounterNotInTimeWindows OBJECT-TYPE
    SYNTAX     Counter32
    MAX-ACCESS read-only
    STATUS     current
    DESCRIPTION
            "-- empty --"
    ::= { lcsStatusSnmpUsmCounter 2 }

-- {SCALAR} 1.3.6.1.4.1.2356.11.1.35.12.3
lcsStatusSnmpUsmCounterUnknownUserNames OBJECT-TYPE
    SYNTAX     Counter32
    MAX-ACCESS read-only
    STATUS     current
    DESCRIPTION
            "-- empty --"
    ::= { lcsStatusSnmpUsmCounter 3 }

-- {SCALAR} 1.3.6.1.4.1.2356.11.1.35.12.4
lcsStatusSnmpUsmCounterUnknownEngineIds OBJECT-TYPE
    SYNTAX     Counter32
    MAX-ACCESS read-only
    STATUS     current
    DESCRIPTION
            "-- empty --"
    ::= { lcsStatusSnmpUsmCounter 4 }

-- {SCALAR} 1.3.6.1.4.1.2356.11.1.35.12.5
lcsStatusSnmpUsmCounterWrongDigests OBJECT-TYPE
    SYNTAX     Counter32
    MAX-ACCESS read-only
    STATUS     current
    DESCRIPTION
            "-- empty --"
    ::= { lcsStatusSnmpUsmCounter 5 }

-- {SCALAR} 1.3.6.1.4.1.2356.11.1.35.12.6
lcsStatusSnmpUsmCounterDecryptionErrors OBJECT-TYPE
    SYNTAX     Counter32
    MAX-ACCESS read-only
    STATUS     current
    DESCRIPTION
            "-- empty --"
    ::= { lcsStatusSnmpUsmCounter 6 }

-- {NODE} 1.3.6.1.4.1.2356.11.1.36
lcsStatusSlaMonitor OBJECT IDENTIFIER ::= { lcsStatus 36 }

-- {NODE} 1.3.6.1.4.1.2356.11.1.36.1
lcsStatusSlaMonitorIcmp OBJECT IDENTIFIER ::= { lcsStatusSlaMonitor 1 }

-- {TABLE} 1.3.6.1.4.1.2356.11.1.36.1.1
lcsStatusSlaMonitorIcmpHistoryLogTable OBJECT-TYPE
    SYNTAX     SEQUENCE OF LcsStatusSlaMonitorIcmpHistoryLogEntry
    MAX-ACCESS not-accessible
    STATUS     current
    DESCRIPTION
            "-- empty --"
    ::= { lcsStatusSlaMonitorIcmp 1 }

-- {ROW} 1.3.6.1.4.1.2356.11.1.36.1.1.1
lcsStatusSlaMonitorIcmpHistoryLogEntry OBJECT-TYPE
    SYNTAX     LcsStatusSlaMonitorIcmpHistoryLogEntry
    MAX-ACCESS not-accessible
    STATUS     current
    DESCRIPTION
            ""
    INDEX {
            lcsStatusSlaMonitorIcmpHistoryLogEntryIndex
          }
    ::= { lcsStatusSlaMonitorIcmpHistoryLogTable 1 }

LcsStatusSlaMonitorIcmpHistoryLogEntry ::= SEQUENCE {
            lcsStatusSlaMonitorIcmpHistoryLogEntryIndex Integer32,
            lcsStatusSlaMonitorIcmpHistoryLogEntryTimestamp DisplayString,
            lcsStatusSlaMonitorIcmpHistoryLogEntryName DisplayString,
            lcsStatusSlaMonitorIcmpHistoryLogEntryDestination DisplayString,
            lcsStatusSlaMonitorIcmpHistoryLogEntryPktLossPercent Integer32,
            lcsStatusSlaMonitorIcmpHistoryLogEntryRttMin DisplayString,
            lcsStatusSlaMonitorIcmpHistoryLogEntryRttMax DisplayString,
            lcsStatusSlaMonitorIcmpHistoryLogEntryRttAvg DisplayString,
            lcsStatusSlaMonitorIcmpHistoryLogEntryWarning BITS,
            lcsStatusSlaMonitorIcmpHistoryLogEntryCritical BITS,
            lcsStatusSlaMonitorIcmpHistoryLogEntryTimestampSnmp Integer32,
            lcsStatusSlaMonitorIcmpHistoryLogEntryRttMinSnmp Integer32,
            lcsStatusSlaMonitorIcmpHistoryLogEntryRttMaxSnmp Integer32,
            lcsStatusSlaMonitorIcmpHistoryLogEntryRttAvgSnmp Integer32,
            lcsStatusSlaMonitorIcmpHistoryLogEntryJitter DisplayString,
            lcsStatusSlaMonitorIcmpHistoryLogEntryJitterSnmp Integer32,
            lcsStatusSlaMonitorIcmpHistoryLogEntryDscp INTEGER
    }

-- {COLUMN} 1.3.6.1.4.1.2356.11.1.36.1.1.1.1
lcsStatusSlaMonitorIcmpHistoryLogEntryIndex OBJECT-TYPE
    SYNTAX     Integer32 (0..2147483647)
    MAX-ACCESS read-only
    STATUS     current
    DESCRIPTION
            "-- empty --"
    ::= { lcsStatusSlaMonitorIcmpHistoryLogEntry 1 }

-- {COLUMN} 1.3.6.1.4.1.2356.11.1.36.1.1.1.2
lcsStatusSlaMonitorIcmpHistoryLogEntryTimestamp OBJECT-TYPE
    SYNTAX     DisplayString (SIZE(0..255))
    MAX-ACCESS read-only
    STATUS     current
    DESCRIPTION
            "-- empty --"
    ::= { lcsStatusSlaMonitorIcmpHistoryLogEntry 2 }

-- {COLUMN} 1.3.6.1.4.1.2356.11.1.36.1.1.1.3
lcsStatusSlaMonitorIcmpHistoryLogEntryName OBJECT-TYPE
    SYNTAX     DisplayString (SIZE(0..255))
    MAX-ACCESS read-only
    STATUS     current
    DESCRIPTION
            "-- empty --"
    ::= { lcsStatusSlaMonitorIcmpHistoryLogEntry 3 }

-- {COLUMN} 1.3.6.1.4.1.2356.11.1.36.1.1.1.4
lcsStatusSlaMonitorIcmpHistoryLogEntryDestination OBJECT-TYPE
    SYNTAX     DisplayString (SIZE(0..255))
    MAX-ACCESS read-only
    STATUS     current
    DESCRIPTION
            "-- empty --"
    ::= { lcsStatusSlaMonitorIcmpHistoryLogEntry 4 }

-- {COLUMN} 1.3.6.1.4.1.2356.11.1.36.1.1.1.5
lcsStatusSlaMonitorIcmpHistoryLogEntryPktLossPercent OBJECT-TYPE
    SYNTAX     Integer32 (0..2147483647)
    MAX-ACCESS read-only
    STATUS     current
    DESCRIPTION
            "-- empty --"
    ::= { lcsStatusSlaMonitorIcmpHistoryLogEntry 5 }

-- {COLUMN} 1.3.6.1.4.1.2356.11.1.36.1.1.1.6
lcsStatusSlaMonitorIcmpHistoryLogEntryRttMin OBJECT-TYPE
    SYNTAX     DisplayString (SIZE(0..255))
    MAX-ACCESS read-only
    STATUS     current
    DESCRIPTION
            "-- empty --"
    ::= { lcsStatusSlaMonitorIcmpHistoryLogEntry 6 }

-- {COLUMN} 1.3.6.1.4.1.2356.11.1.36.1.1.1.7
lcsStatusSlaMonitorIcmpHistoryLogEntryRttMax OBJECT-TYPE
    SYNTAX     DisplayString (SIZE(0..255))
    MAX-ACCESS read-only
    STATUS     current
    DESCRIPTION
            "-- empty --"
    ::= { lcsStatusSlaMonitorIcmpHistoryLogEntry 7 }

-- {COLUMN} 1.3.6.1.4.1.2356.11.1.36.1.1.1.8
lcsStatusSlaMonitorIcmpHistoryLogEntryRttAvg OBJECT-TYPE
    SYNTAX     DisplayString (SIZE(0..255))
    MAX-ACCESS read-only
    STATUS     current
    DESCRIPTION
            "-- empty --"
    ::= { lcsStatusSlaMonitorIcmpHistoryLogEntry 8 }

-- {COLUMN} 1.3.6.1.4.1.2356.11.1.36.1.1.1.9
lcsStatusSlaMonitorIcmpHistoryLogEntryWarning OBJECT-TYPE
    SYNTAX     BITS {
                  eJitter (8),
                  eRttAvg (28),
                  ePktLossPercent (29),
                  eRttMax (30),
                  eNone (31)
            }
    MAX-ACCESS read-only
    STATUS     current
    DESCRIPTION
            "-- empty --"
    ::= { lcsStatusSlaMonitorIcmpHistoryLogEntry 9 }

-- {COLUMN} 1.3.6.1.4.1.2356.11.1.36.1.1.1.10
lcsStatusSlaMonitorIcmpHistoryLogEntryCritical OBJECT-TYPE
    SYNTAX     BITS {
                  eJitter (8),
                  eFragNeededDfSet (9),
                  eSrcHostIso (10),
                  eSrcRouteError (11),
                  eDestNetworkUnknown (12),
                  eDestHostUnknown (13),
                  ePortUnreachable (14),
                  eProtocolUnreachable (15),
                  eHostUnreachable (16),
                  eNetworkUnreachable (17),
                  eBadDestAddress (18),
                  eIpv6NotOp (19),
                  eIpv4NotOp (20),
                  eAddressResPending (21),
                  eAddressResFailed (22),
                  eAddressResNa (23),
                  eDestIfcInvalid (24),
                  eDestAddressInvalid (25),
                  eSrcIfcInvalid (26),
                  eSrcAddressInvalid (27),
                  eRttAvg (28),
                  ePktLossPercent (29),
                  eRttMax (30),
                  eNone (31)
            }
    MAX-ACCESS read-only
    STATUS     current
    DESCRIPTION
            "-- empty --"
    ::= { lcsStatusSlaMonitorIcmpHistoryLogEntry 10 }

-- {COLUMN} 1.3.6.1.4.1.2356.11.1.36.1.1.1.11
lcsStatusSlaMonitorIcmpHistoryLogEntryTimestampSnmp OBJECT-TYPE
    SYNTAX     Integer32 (0..2147483647)
    MAX-ACCESS read-only
    STATUS     current
    DESCRIPTION
            "-- empty --"
    ::= { lcsStatusSlaMonitorIcmpHistoryLogEntry 11 }

-- {COLUMN} 1.3.6.1.4.1.2356.11.1.36.1.1.1.12
lcsStatusSlaMonitorIcmpHistoryLogEntryRttMinSnmp OBJECT-TYPE
    SYNTAX     Integer32 (0..2147483647)
    MAX-ACCESS read-only
    STATUS     current
    DESCRIPTION
            "-- empty --"
    ::= { lcsStatusSlaMonitorIcmpHistoryLogEntry 12 }

-- {COLUMN} 1.3.6.1.4.1.2356.11.1.36.1.1.1.13
lcsStatusSlaMonitorIcmpHistoryLogEntryRttMaxSnmp OBJECT-TYPE
    SYNTAX     Integer32 (0..2147483647)
    MAX-ACCESS read-only
    STATUS     current
    DESCRIPTION
            "-- empty --"
    ::= { lcsStatusSlaMonitorIcmpHistoryLogEntry 13 }

-- {COLUMN} 1.3.6.1.4.1.2356.11.1.36.1.1.1.14
lcsStatusSlaMonitorIcmpHistoryLogEntryRttAvgSnmp OBJECT-TYPE
    SYNTAX     Integer32 (0..2147483647)
    MAX-ACCESS read-only
    STATUS     current
    DESCRIPTION
            "-- empty --"
    ::= { lcsStatusSlaMonitorIcmpHistoryLogEntry 14 }

-- {COLUMN} 1.3.6.1.4.1.2356.11.1.36.1.1.1.15
lcsStatusSlaMonitorIcmpHistoryLogEntryJitter OBJECT-TYPE
    SYNTAX     DisplayString (SIZE(0..255))
    MAX-ACCESS read-only
    STATUS     current
    DESCRIPTION
            "-- empty --"
    ::= { lcsStatusSlaMonitorIcmpHistoryLogEntry 15 }

-- {COLUMN} 1.3.6.1.4.1.2356.11.1.36.1.1.1.16
lcsStatusSlaMonitorIcmpHistoryLogEntryJitterSnmp OBJECT-TYPE
    SYNTAX     Integer32 (0..2147483647)
    MAX-ACCESS read-only
    STATUS     current
    DESCRIPTION
            "-- empty --"
    ::= { lcsStatusSlaMonitorIcmpHistoryLogEntry 16 }

-- {COLUMN} 1.3.6.1.4.1.2356.11.1.36.1.1.1.17
lcsStatusSlaMonitorIcmpHistoryLogEntryDscp OBJECT-TYPE
    SYNTAX     INTEGER {
                  eBeCs0 (0),
                  eCs1 (32),
                  eAf11 (40),
                  eAf12 (48),
                  eAf13 (56),
                  eCs2 (64),
                  eAf21 (72),
                  eAf22 (80),
                  eAf23 (88),
                  eCs3 (96),
                  eAf31 (104),
                  eAf32 (112),
                  eAf33 (120),
                  eCs4 (128),
                  eAf41 (136),
                  eAf42 (144),
                  eAf43 (152),
                  eCs5 (160),
                  eEf (184),
                  eCs6 (192),
                  eCs7 (224)
            }
    MAX-ACCESS read-only
    STATUS     current
    DESCRIPTION
            "-- empty --"
    ::= { lcsStatusSlaMonitorIcmpHistoryLogEntry 17 }

-- {TABLE} 1.3.6.1.4.1.2356.11.1.36.1.2
lcsStatusSlaMonitorIcmpLastResultTable OBJECT-TYPE
    SYNTAX     SEQUENCE OF LcsStatusSlaMonitorIcmpLastResultEntry
    MAX-ACCESS not-accessible
    STATUS     current
    DESCRIPTION
            "-- empty --"
    ::= { lcsStatusSlaMonitorIcmp 2 }

-- {ROW} 1.3.6.1.4.1.2356.11.1.36.1.2.1
lcsStatusSlaMonitorIcmpLastResultEntry OBJECT-TYPE
    SYNTAX     LcsStatusSlaMonitorIcmpLastResultEntry
    MAX-ACCESS not-accessible
    STATUS     current
    DESCRIPTION
            ""
    INDEX {
            lcsStatusSlaMonitorIcmpLastResultEntryName
          }
    ::= { lcsStatusSlaMonitorIcmpLastResultTable 1 }

LcsStatusSlaMonitorIcmpLastResultEntry ::= SEQUENCE {
            lcsStatusSlaMonitorIcmpLastResultEntryName DisplayString,
            lcsStatusSlaMonitorIcmpLastResultEntryDestination DisplayString,
            lcsStatusSlaMonitorIcmpLastResultEntryTimestamp DisplayString,
            lcsStatusSlaMonitorIcmpLastResultEntryPktLossPercent Integer32,
            lcsStatusSlaMonitorIcmpLastResultEntryRttMin DisplayString,
            lcsStatusSlaMonitorIcmpLastResultEntryRttMax DisplayString,
            lcsStatusSlaMonitorIcmpLastResultEntryRttAvg DisplayString,
            lcsStatusSlaMonitorIcmpLastResultEntryWarning BITS,
            lcsStatusSlaMonitorIcmpLastResultEntryCritical BITS,
            lcsStatusSlaMonitorIcmpLastResultEntryTimestampSnmp Integer32,
            lcsStatusSlaMonitorIcmpLastResultEntryRttMinSnmp Integer32,
            lcsStatusSlaMonitorIcmpLastResultEntryRttMaxSnmp Integer32,
            lcsStatusSlaMonitorIcmpLastResultEntryRttAvgSnmp Integer32,
            lcsStatusSlaMonitorIcmpLastResultEntryJitter DisplayString,
            lcsStatusSlaMonitorIcmpLastResultEntryJitterSnmp Integer32,
            lcsStatusSlaMonitorIcmpLastResultEntryDscp INTEGER
    }

-- {COLUMN} 1.3.6.1.4.1.2356.11.1.36.1.2.1.1
lcsStatusSlaMonitorIcmpLastResultEntryName OBJECT-TYPE
    SYNTAX     DisplayString (SIZE(0..255))
    MAX-ACCESS read-only
    STATUS     current
    DESCRIPTION
            "-- empty --"
    ::= { lcsStatusSlaMonitorIcmpLastResultEntry 1 }

-- {COLUMN} 1.3.6.1.4.1.2356.11.1.36.1.2.1.2
lcsStatusSlaMonitorIcmpLastResultEntryDestination OBJECT-TYPE
    SYNTAX     DisplayString (SIZE(0..255))
    MAX-ACCESS read-only
    STATUS     current
    DESCRIPTION
            "-- empty --"
    ::= { lcsStatusSlaMonitorIcmpLastResultEntry 2 }

-- {COLUMN} 1.3.6.1.4.1.2356.11.1.36.1.2.1.3
lcsStatusSlaMonitorIcmpLastResultEntryTimestamp OBJECT-TYPE
    SYNTAX     DisplayString (SIZE(0..255))
    MAX-ACCESS read-only
    STATUS     current
    DESCRIPTION
            "-- empty --"
    ::= { lcsStatusSlaMonitorIcmpLastResultEntry 3 }

-- {COLUMN} 1.3.6.1.4.1.2356.11.1.36.1.2.1.4
lcsStatusSlaMonitorIcmpLastResultEntryPktLossPercent OBJECT-TYPE
    SYNTAX     Integer32 (0..2147483647)
    MAX-ACCESS read-only
    STATUS     current
    DESCRIPTION
            "-- empty --"
    ::= { lcsStatusSlaMonitorIcmpLastResultEntry 4 }

-- {COLUMN} 1.3.6.1.4.1.2356.11.1.36.1.2.1.5
lcsStatusSlaMonitorIcmpLastResultEntryRttMin OBJECT-TYPE
    SYNTAX     DisplayString (SIZE(0..255))
    MAX-ACCESS read-only
    STATUS     current
    DESCRIPTION
            "-- empty --"
    ::= { lcsStatusSlaMonitorIcmpLastResultEntry 5 }

-- {COLUMN} 1.3.6.1.4.1.2356.11.1.36.1.2.1.6
lcsStatusSlaMonitorIcmpLastResultEntryRttMax OBJECT-TYPE
    SYNTAX     DisplayString (SIZE(0..255))
    MAX-ACCESS read-only
    STATUS     current
    DESCRIPTION
            "-- empty --"
    ::= { lcsStatusSlaMonitorIcmpLastResultEntry 6 }

-- {COLUMN} 1.3.6.1.4.1.2356.11.1.36.1.2.1.7
lcsStatusSlaMonitorIcmpLastResultEntryRttAvg OBJECT-TYPE
    SYNTAX     DisplayString (SIZE(0..255))
    MAX-ACCESS read-only
    STATUS     current
    DESCRIPTION
            "-- empty --"
    ::= { lcsStatusSlaMonitorIcmpLastResultEntry 7 }

-- {COLUMN} 1.3.6.1.4.1.2356.11.1.36.1.2.1.8
lcsStatusSlaMonitorIcmpLastResultEntryWarning OBJECT-TYPE
    SYNTAX     BITS {
                  eJitter (8),
                  eRttAvg (28),
                  ePktLossPercent (29),
                  eRttMax (30),
                  eNone (31)
            }
    MAX-ACCESS read-only
    STATUS     current
    DESCRIPTION
            "-- empty --"
    ::= { lcsStatusSlaMonitorIcmpLastResultEntry 8 }

-- {COLUMN} 1.3.6.1.4.1.2356.11.1.36.1.2.1.9
lcsStatusSlaMonitorIcmpLastResultEntryCritical OBJECT-TYPE
    SYNTAX     BITS {
                  eJitter (8),
                  eFragNeededDfSet (9),
                  eSrcHostIso (10),
                  eSrcRouteError (11),
                  eDestNetworkUnknown (12),
                  eDestHostUnknown (13),
                  ePortUnreachable (14),
                  eProtocolUnreachable (15),
                  eHostUnreachable (16),
                  eNetworkUnreachable (17),
                  eBadDestAddress (18),
                  eIpv6NotOp (19),
                  eIpv4NotOp (20),
                  eAddressResPending (21),
                  eAddressResFailed (22),
                  eAddressResNa (23),
                  eDestIfcInvalid (24),
                  eDestAddressInvalid (25),
                  eSrcIfcInvalid (26),
                  eSrcAddressInvalid (27),
                  eRttAvg (28),
                  ePktLossPercent (29),
                  eRttMax (30),
                  eNone (31)
            }
    MAX-ACCESS read-only
    STATUS     current
    DESCRIPTION
            "-- empty --"
    ::= { lcsStatusSlaMonitorIcmpLastResultEntry 9 }

-- {COLUMN} 1.3.6.1.4.1.2356.11.1.36.1.2.1.10
lcsStatusSlaMonitorIcmpLastResultEntryTimestampSnmp OBJECT-TYPE
    SYNTAX     Integer32 (0..2147483647)
    MAX-ACCESS read-only
    STATUS     current
    DESCRIPTION
            "-- empty --"
    ::= { lcsStatusSlaMonitorIcmpLastResultEntry 10 }

-- {COLUMN} 1.3.6.1.4.1.2356.11.1.36.1.2.1.11
lcsStatusSlaMonitorIcmpLastResultEntryRttMinSnmp OBJECT-TYPE
    SYNTAX     Integer32 (0..2147483647)
    MAX-ACCESS read-only
    STATUS     current
    DESCRIPTION
            "-- empty --"
    ::= { lcsStatusSlaMonitorIcmpLastResultEntry 11 }

-- {COLUMN} 1.3.6.1.4.1.2356.11.1.36.1.2.1.12
lcsStatusSlaMonitorIcmpLastResultEntryRttMaxSnmp OBJECT-TYPE
    SYNTAX     Integer32 (0..2147483647)
    MAX-ACCESS read-only
    STATUS     current
    DESCRIPTION
            "-- empty --"
    ::= { lcsStatusSlaMonitorIcmpLastResultEntry 12 }

-- {COLUMN} 1.3.6.1.4.1.2356.11.1.36.1.2.1.13
lcsStatusSlaMonitorIcmpLastResultEntryRttAvgSnmp OBJECT-TYPE
    SYNTAX     Integer32 (0..2147483647)
    MAX-ACCESS read-only
    STATUS     current
    DESCRIPTION
            "-- empty --"
    ::= { lcsStatusSlaMonitorIcmpLastResultEntry 13 }

-- {COLUMN} 1.3.6.1.4.1.2356.11.1.36.1.2.1.14
lcsStatusSlaMonitorIcmpLastResultEntryJitter OBJECT-TYPE
    SYNTAX     DisplayString (SIZE(0..255))
    MAX-ACCESS read-only
    STATUS     current
    DESCRIPTION
            "-- empty --"
    ::= { lcsStatusSlaMonitorIcmpLastResultEntry 14 }

-- {COLUMN} 1.3.6.1.4.1.2356.11.1.36.1.2.1.15
lcsStatusSlaMonitorIcmpLastResultEntryJitterSnmp OBJECT-TYPE
    SYNTAX     Integer32 (0..2147483647)
    MAX-ACCESS read-only
    STATUS     current
    DESCRIPTION
            "-- empty --"
    ::= { lcsStatusSlaMonitorIcmpLastResultEntry 15 }

-- {COLUMN} 1.3.6.1.4.1.2356.11.1.36.1.2.1.16
lcsStatusSlaMonitorIcmpLastResultEntryDscp OBJECT-TYPE
    SYNTAX     INTEGER {
                  eBeCs0 (0),
                  eCs1 (32),
                  eAf11 (40),
                  eAf12 (48),
                  eAf13 (56),
                  eCs2 (64),
                  eAf21 (72),
                  eAf22 (80),
                  eAf23 (88),
                  eCs3 (96),
                  eAf31 (104),
                  eAf32 (112),
                  eAf33 (120),
                  eCs4 (128),
                  eAf41 (136),
                  eAf42 (144),
                  eAf43 (152),
                  eCs5 (160),
                  eEf (184),
                  eCs6 (192),
                  eCs7 (224)
            }
    MAX-ACCESS read-only
    STATUS     current
    DESCRIPTION
            "-- empty --"
    ::= { lcsStatusSlaMonitorIcmpLastResultEntry 16 }

-- {SCALAR} 1.3.6.1.4.1.2356.11.1.36.1.3
lcsStatusSlaMonitorIcmpDeleteValues OBJECT-TYPE
    SYNTAX     DisplayString
    MAX-ACCESS read-write
    STATUS     current
    DESCRIPTION
            "-- empty --"
    ::= { lcsStatusSlaMonitorIcmp 3 }

-- {NODE} 1.3.6.1.4.1.2356.11.1.36.2
lcsStatusSlaMonitorRadius OBJECT IDENTIFIER ::= { lcsStatusSlaMonitor 2 }

-- {TABLE} 1.3.6.1.4.1.2356.11.1.36.2.1
lcsStatusSlaMonitorRadiusServersTable OBJECT-TYPE
    SYNTAX     SEQUENCE OF LcsStatusSlaMonitorRadiusServersEntry
    MAX-ACCESS not-accessible
    STATUS     current
    DESCRIPTION
            "-- empty --"
    ::= { lcsStatusSlaMonitorRadius 1 }

-- {ROW} 1.3.6.1.4.1.2356.11.1.36.2.1.1
lcsStatusSlaMonitorRadiusServersEntry OBJECT-TYPE
    SYNTAX     LcsStatusSlaMonitorRadiusServersEntry
    MAX-ACCESS not-accessible
    STATUS     current
    DESCRIPTION
            ""
    INDEX {
            lcsStatusSlaMonitorRadiusServersEntryIndex
          }
    ::= { lcsStatusSlaMonitorRadiusServersTable 1 }

LcsStatusSlaMonitorRadiusServersEntry ::= SEQUENCE {
            lcsStatusSlaMonitorRadiusServersEntryIndex Integer32,
            lcsStatusSlaMonitorRadiusServersEntryServerHostname DisplayString,
            lcsStatusSlaMonitorRadiusServersEntryPort Integer32,
            lcsStatusSlaMonitorRadiusServersEntryLoopbackAddress DisplayString,
            lcsStatusSlaMonitorRadiusServersEntryProtocol INTEGER,
            lcsStatusSlaMonitorRadiusServersEntryState INTEGER
    }

-- {COLUMN} 1.3.6.1.4.1.2356.11.1.36.2.1.1.1
lcsStatusSlaMonitorRadiusServersEntryIndex OBJECT-TYPE
    SYNTAX     Integer32 (0..2147483647)
    MAX-ACCESS read-only
    STATUS     current
    DESCRIPTION
            "-- empty --"
    ::= { lcsStatusSlaMonitorRadiusServersEntry 1 }

-- {COLUMN} 1.3.6.1.4.1.2356.11.1.36.2.1.1.2
lcsStatusSlaMonitorRadiusServersEntryServerHostname OBJECT-TYPE
    SYNTAX     DisplayString (SIZE(0..255))
    MAX-ACCESS read-only
    STATUS     current
    DESCRIPTION
            "-- empty --"
    ::= { lcsStatusSlaMonitorRadiusServersEntry 2 }

-- {COLUMN} 1.3.6.1.4.1.2356.11.1.36.2.1.1.3
lcsStatusSlaMonitorRadiusServersEntryPort OBJECT-TYPE
    SYNTAX     Integer32 (0..65535)
    MAX-ACCESS read-only
    STATUS     current
    DESCRIPTION
            "-- empty --"
    ::= { lcsStatusSlaMonitorRadiusServersEntry 3 }

-- {COLUMN} 1.3.6.1.4.1.2356.11.1.36.2.1.1.4
lcsStatusSlaMonitorRadiusServersEntryLoopbackAddress OBJECT-TYPE
    SYNTAX     DisplayString (SIZE(0..255))
    MAX-ACCESS read-only
    STATUS     current
    DESCRIPTION
            "-- empty --"
    ::= { lcsStatusSlaMonitorRadiusServersEntry 4 }

-- {COLUMN} 1.3.6.1.4.1.2356.11.1.36.2.1.1.5
lcsStatusSlaMonitorRadiusServersEntryProtocol OBJECT-TYPE
    SYNTAX     INTEGER {
                  eRadius (0),
                  eRadsec (1)
            }
    MAX-ACCESS read-only
    STATUS     current
    DESCRIPTION
            "-- empty --"
    ::= { lcsStatusSlaMonitorRadiusServersEntry 5 }

-- {COLUMN} 1.3.6.1.4.1.2356.11.1.36.2.1.1.6
lcsStatusSlaMonitorRadiusServersEntryState OBJECT-TYPE
    SYNTAX     INTEGER {
                  eUnknown (0),
                  eUp (1),
                  eDnsError (2),
                  eAuthenticatorMismatch (3),
                  eHostUnreachable (4),
                  ePortUnreachable (5),
                  eNetworkUnreachable (6),
                  eTimeout (7)
            }
    MAX-ACCESS read-only
    STATUS     current
    DESCRIPTION
            "-- empty --"
    ::= { lcsStatusSlaMonitorRadiusServersEntry 6 }

-- {NODE} 1.3.6.1.4.1.2356.11.1.41
lcsStatusAdsl OBJECT IDENTIFIER ::= { lcsStatus 41 }

-- {SCALAR} 1.3.6.1.4.1.2356.11.1.41.1
lcsStatusAdslLineState OBJECT-TYPE
    SYNTAX     INTEGER {
                  eUnknown (0),
                  eDown (1),
                  eIdle (2),
                  eHandshake (3),
                  eTraining (4),
                  eShowtime (5),
                  eShutdown (6)
            }
    MAX-ACCESS read-only
    STATUS     current
    DESCRIPTION
            "-- empty --"
    ::= { lcsStatusAdsl 1 }

-- {SCALAR} 1.3.6.1.4.1.2356.11.1.41.2
lcsStatusAdslLineType OBJECT-TYPE
    SYNTAX     DisplayString
    MAX-ACCESS read-only
    STATUS     current
    DESCRIPTION
            "-- empty --"
    ::= { lcsStatusAdsl 2 }

-- {SCALAR} 1.3.6.1.4.1.2356.11.1.41.3
lcsStatusAdslStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGVector (254),
                  eUnknown (255)
            }
    MAX-ACCESS read-only
    STATUS     current
    DESCRIPTION
            "-- empty --"
    ::= { lcsStatusAdsl 3 }

-- {SCALAR} 1.3.6.1.4.1.2356.11.1.41.4
lcsStatusAdslDataRateUpstreamKbps OBJECT-TYPE
    SYNTAX     Integer32 (0..2147483647)
    MAX-ACCESS read-only
    STATUS     current
    DESCRIPTION
            "-- empty --"
    ::= { lcsStatusAdsl 4 }

-- {SCALAR} 1.3.6.1.4.1.2356.11.1.41.5
lcsStatusAdslDataRateDownstreamKbps OBJECT-TYPE
    SYNTAX     Integer32 (0..2147483647)
    MAX-ACCESS read-only
    STATUS     current
    DESCRIPTION
            "-- empty --"
    ::= { lcsStatusAdsl 5 }

-- {SCALAR} 1.3.6.1.4.1.2356.11.1.41.6
lcsStatusAdslSnrDownstreamDb OBJECT-TYPE
    SYNTAX     DisplayString (SIZE(0..3))
    MAX-ACCESS read-only
    STATUS     current
    DESCRIPTION
            "-- empty --"
    ::= { lcsStatusAdsl 6 }

-- {SCALAR} 1.3.6.1.4.1.2356.11.1.41.7
lcsStatusAdslSnrUpstreamDb OBJECT-TYPE
    SYNTAX     DisplayString (SIZE(0..3))
    MAX-ACCESS read-only
    STATUS     current
    DESCRIPTION
            "-- empty --"
    ::= { lcsStatusAdsl 7 }

-- {SCALAR} 1.3.6.1.4.1.2356.11.1.41.8
lcsStatusAdslAttenuationDownstreamDb OBJECT-TYPE
    SYNTAX     DisplayString (SIZE(0..3))
    MAX-ACCESS read-only
    STATUS     current
    DESCRIPTION
            "-- empty --"
    ::= { lcsStatusAdsl 8 }

-- {SCALAR} 1.3.6.1.4.1.2356.11.1.41.9
lcsStatusAdslAttenuationUpstreamDb OBJECT-TYPE
    SYNTAX     DisplayString (SIZE(0..3))
    MAX-ACCESS read-only
    STATUS     current
    DESCRIPTION
            "-- empty --"
    ::= { lcsStatusAdsl 9 }

-- {SCALAR} 1.3.6.1.4.1.2356.11.1.41.10
lcsStatusAdslInterleaveUpstreamMs OBJECT-TYPE
    SYNTAX     DisplayString
    MAX-ACCESS read-only
    STATUS     current
    DESCRIPTION
            "-- empty --"
    ::= { lcsStatusAdsl 10 }

-- {SCALAR} 1.3.6.1.4.1.2356.11.1.41.11
lcsStatusAdslInterleaveDownstreamMs OBJECT-TYPE
    SYNTAX     DisplayString
    MAX-ACCESS read-only
    STATUS     current
    DESCRIPTION
            "-- empty --"
    ::= { lcsStatusAdsl 11 }

-- {TABLE} 1.3.6.1.4.1.2356.11.1.41.12
lcsStatusAdslConnectionHistoryTable OBJECT-TYPE
    SYNTAX     SEQUENCE OF LcsStatusAdslConnectionHistoryEntry
    MAX-ACCESS not-accessible
    STATUS     current
    DESCRIPTION
            "-- empty --"
    ::= { lcsStatusAdsl 12 }

-- {ROW} 1.3.6.1.4.1.2356.11.1.41.12.1
lcsStatusAdslConnectionHistoryEntry OBJECT-TYPE
    SYNTAX     LcsStatusAdslConnectionHistoryEntry
    MAX-ACCESS not-accessible
    STATUS     current
    DESCRIPTION
            ""
    INDEX {
            lcsStatusAdslConnectionHistoryEntryIndex
          }
    ::= { lcsStatusAdslConnectionHistoryTable 1 }

LcsStatusAdslConnectionHistoryEntry ::= SEQUENCE {
            lcsStatusAdslConnectionHistoryEntrySyncTime Gauge32,
            lcsStatusAdslConnectionHistoryEntryStandard INTEGER,
            lcsStatusAdslConnectionHistoryEntryDsDatarate Integer32,
            lcsStatusAdslConnectionHistoryEntryUsDatarate Integer32,
            lcsStatusAdslConnectionHistoryEntryDsAttenuation DisplayString,
            lcsStatusAdslConnectionHistoryEntryDsSnr DisplayString,
            lcsStatusAdslConnectionHistoryEntryDisconnectTime Gauge32,
            lcsStatusAdslConnectionHistoryEntryIndex Integer32,
            lcsStatusAdslConnectionHistoryEntryReason INTEGER,
            lcsStatusAdslConnectionHistoryEntryUsAttenuation DisplayString,
            lcsStatusAdslConnectionHistoryEntryUsSnr DisplayString,
            lcsStatusAdslConnectionHistoryEntryLinecode DisplayString
    }

-- {COLUMN} 1.3.6.1.4.1.2356.11.1.41.12.1.1
lcsStatusAdslConnectionHistoryEntrySyncTime OBJECT-TYPE
    SYNTAX     Gauge32
    MAX-ACCESS read-only
    STATUS     current
    DESCRIPTION
            "-- empty --"
    ::= { lcsStatusAdslConnectionHistoryEntry 1 }

-- {COLUMN} 1.3.6.1.4.1.2356.11.1.41.12.1.2
lcsStatusAdslConnectionHistoryEntryStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGVector (254),
                  eUnknown (255)
            }
    MAX-ACCESS read-only
    STATUS     current
    DESCRIPTION
            "-- empty --"
    ::= { lcsStatusAdslConnectionHistoryEntry 2 }

-- {COLUMN} 1.3.6.1.4.1.2356.11.1.41.12.1.3
lcsStatusAdslConnectionHistoryEntryDsDatarate OBJECT-TYPE
    SYNTAX     Integer32 (0..2147483647)
    MAX-ACCESS read-only
    STATUS     current
    DESCRIPTION
            "-- empty --"
    ::= { lcsStatusAdslConnectionHistoryEntry 3 }

-- {COLUMN} 1.3.6.1.4.1.2356.11.1.41.12.1.4
lcsStatusAdslConnectionHistoryEntryUsDatarate OBJECT-TYPE
    SYNTAX     Integer32 (0..2147483647)
    MAX-ACCESS read-only
    STATUS     current
    DESCRIPTION
            "-- empty --"
    ::= { lcsStatusAdslConnectionHistoryEntry 4 }

-- {COLUMN} 1.3.6.1.4.1.2356.11.1.41.12.1.5
lcsStatusAdslConnectionHistoryEntryDsAttenuation OBJECT-TYPE
    SYNTAX     DisplayString (SIZE(0..1))
    MAX-ACCESS read-only
    STATUS     current
    DESCRIPTION
            "-- empty --"
    ::= { lcsStatusAdslConnectionHistoryEntry 5 }

-- {COLUMN} 1.3.6.1.4.1.2356.11.1.41.12.1.6
lcsStatusAdslConnectionHistoryEntryDsSnr OBJECT-TYPE
    SYNTAX     DisplayString (SIZE(0..1))
    MAX-ACCESS read-only
    STATUS     current
    DESCRIPTION
            "-- empty --"
    ::= { lcsStatusAdslConnectionHistoryEntry 6 }

-- {COLUMN} 1.3.6.1.4.1.2356.11.1.41.12.1.7
lcsStatusAdslConnectionHistoryEntryDisconnectTime OBJECT-TYPE
    SYNTAX     Gauge32
    MAX-ACCESS read-only
    STATUS     current
    DESCRIPTION
            "-- empty --"
    ::= { lcsStatusAdslConnectionHistoryEntry 7 }

-- {COLUMN} 1.3.6.1.4.1.2356.11.1.41.12.1.8
lcsStatusAdslConnectionHistoryEntryIndex OBJECT-TYPE
    SYNTAX     Integer32 (0..2147483647)
    MAX-ACCESS read-only
    STATUS     current
    DESCRIPTION
            "-- empty --"
    ::= { lcsStatusAdslConnectionHistoryEntry 8 }

-- {COLUMN} 1.3.6.1.4.1.2356.11.1.41.12.1.9
lcsStatusAdslConnectionHistoryEntryReason OBJECT-TYPE
    SYNTAX     INTEGER {
                  eModemReboot (1),
                  eRetrain (2),
                  eSilence (3),
                  eLineError (4),
                  eProtocol (5),
                  eLineType (6),
                  eAutomode (7),
                  eTimeout (8),
                  eVcParameters (13)
            }
    MAX-ACCESS read-only
    STATUS     current
    DESCRIPTION
            "-- empty --"
    ::= { lcsStatusAdslConnectionHistoryEntry 9 }

-- {COLUMN} 1.3.6.1.4.1.2356.11.1.41.12.1.10
lcsStatusAdslConnectionHistoryEntryUsAttenuation OBJECT-TYPE
    SYNTAX     DisplayString (SIZE(0..1))
    MAX-ACCESS read-only
    STATUS     current
    DESCRIPTION
            "-- empty --"
    ::= { lcsStatusAdslConnectionHistoryEntry 10 }

-- {COLUMN} 1.3.6.1.4.1.2356.11.1.41.12.1.11
lcsStatusAdslConnectionHistoryEntryUsSnr OBJECT-TYPE
    SYNTAX     DisplayString (SIZE(0..1))
    MAX-ACCESS read-only
    STATUS     current
    DESCRIPTION
            "-- empty --"
    ::= { lcsStatusAdslConnectionHistoryEntry 11 }

-- {COLUMN} 1.3.6.1.4.1.2356.11.1.41.12.1.12
lcsStatusAdslConnectionHistoryEntryLinecode OBJECT-TYPE
    SYNTAX     DisplayString (SIZE(0..1))
    MAX-ACCESS read-only
    STATUS     current
    DESCRIPTION
            "-- empty --"
    ::= { lcsStatusAdslConnectionHistoryEntry 12 }

-- {SCALAR} 1.3.6.1.4.1.2356.11.1.41.13
lcsStatusAdslRetrain OBJECT-TYPE
    SYNTAX     DisplayString
    MAX-ACCESS read-write
    STATUS     current
    DESCRIPTION
            "-- empty --"
    ::= { lcsStatusAdsl 13 }

-- {SCALAR} 1.3.6.1.4.1.2356.11.1.41.14
lcsStatusAdslDslamChipsetManufacturer OBJECT-TYPE
    SYNTAX     DisplayString (SIZE(0..63))
    MAX-ACCESS read-only
    STATUS     current
    DESCRIPTION
            "-- empty --"
    ::= { lcsStatusAdsl 14 }

-- {SCALAR} 1.3.6.1.4.1.2356.11.1.41.23
lcsStatusAdslModemType OBJECT-TYPE
    SYNTAX     DisplayString
    MAX-ACCESS read-only
    STATUS     current
    DESCRIPTION
            "-- empty --"
    ::= { lcsStatusAdsl 23 }

-- {NODE} 1.3.6.1.4.1.2356.11.1.41.25
lcsStatusAdslAdvanced OBJECT IDENTIFIER ::= { lcsStatusAdsl 25 }

-- {SCALAR} 1.3.6.1.4.1.2356.11.1.41.25.1
lcsStatusAdslAdvancedLineState OBJECT-TYPE
    SYNTAX     INTEGER {
                  eUnknown (0),
                  eDown (1),
                  eIdle (2),
                  eHandshake (3),
                  eTraining (4),
                  eShowtime (5),
                  eShutdown (6)
            }
    MAX-ACCESS read-only
    STATUS     current
    DESCRIPTION
            "-- empty --"
    ::= { lcsStatusAdslAdvanced 1 }

-- {SCALAR} 1.3.6.1.4.1.2356.11.1.41.25.2
lcsStatusAdslAdvancedStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGVector (254),
                  eUnknown (255)
            }
    MAX-ACCESS read-only
    STATUS     current
    DESCRIPTION
            "-- empty --"
    ::= { lcsStatusAdslAdvanced 2 }

-- {SCALAR} 1.3.6.1.4.1.2356.11.1.41.25.3
lcsStatusAdslAdvancedDsDataRateKbps OBJECT-TYPE
    SYNTAX     Integer32 (0..2147483647)
    MAX-ACCESS read-only
    STATUS     current
    DESCRIPTION
            "-- empty --"
    ::= { lcsStatusAdslAdvanced 3 }

-- {SCALAR} 1.3.6.1.4.1.2356.11.1.41.25.4
lcsStatusAdslAdvancedDsSnrMarginDb OBJECT-TYPE
    SYNTAX     DisplayString (SIZE(0..3))
    MAX-ACCESS read-only
    STATUS     current
    DESCRIPTION
            "-- empty --"
    ::= { lcsStatusAdslAdvanced 4 }

-- {SCALAR} 1.3.6.1.4.1.2356.11.1.41.25.5
lcsStatusAdslAdvancedDsLineAttenuationDb OBJECT-TYPE
    SYNTAX     DisplayString (SIZE(0..3))
    MAX-ACCESS read-only
    STATUS     current
    DESCRIPTION
            "-- empty --"
    ::= { lcsStatusAdslAdvanced 5 }

-- {SCALAR} 1.3.6.1.4.1.2356.11.1.41.25.6
lcsStatusAdslAdvancedDsInterleaveMs OBJECT-TYPE
    SYNTAX     DisplayString
    MAX-ACCESS read-only
    STATUS     current
    DESCRIPTION
            "-- empty --"
    ::= { lcsStatusAdslAdvanced 6 }

-- {TABLE} 1.3.6.1.4.1.2356.11.1.41.25.13
lcsStatusAdslAdvancedDsBitLoadingTable OBJECT-TYPE
    SYNTAX     SEQUENCE OF LcsStatusAdslAdvancedDsBitLoadingEntry
    MAX-ACCESS not-accessible
    STATUS     current
    DESCRIPTION
            "-- empty --"
    ::= { lcsStatusAdslAdvanced 13 }

-- {ROW} 1.3.6.1.4.1.2356.11.1.41.25.13.1
lcsStatusAdslAdvancedDsBitLoadingEntry OBJECT-TYPE
    SYNTAX     LcsStatusAdslAdvancedDsBitLoadingEntry
    MAX-ACCESS not-accessible
    STATUS     current
    DESCRIPTION
            ""
    INDEX {
            lcsStatusAdslAdvancedDsBitLoadingEntryBinNumber
          }
    ::= { lcsStatusAdslAdvancedDsBitLoadingTable 1 }

LcsStatusAdslAdvancedDsBitLoadingEntry ::= SEQUENCE {
            lcsStatusAdslAdvancedDsBitLoadingEntryBinNumber DisplayString,
            lcsStatusAdslAdvancedDsBitLoadingEntryX0 Integer32,
            lcsStatusAdslAdvancedDsBitLoadingEntryX1 Integer32,
            lcsStatusAdslAdvancedDsBitLoadingEntryX2 Integer32,
            lcsStatusAdslAdvancedDsBitLoadingEntryX3 Integer32,
            lcsStatusAdslAdvancedDsBitLoadingEntryX4 Integer32,
            lcsStatusAdslAdvancedDsBitLoadingEntryX5 Integer32,
            lcsStatusAdslAdvancedDsBitLoadingEntryX6 Integer32,
            lcsStatusAdslAdvancedDsBitLoadingEntryX7 Integer32,
            lcsStatusAdslAdvancedDsBitLoadingEntryX8 Integer32,
            lcsStatusAdslAdvancedDsBitLoadingEntryX9 Integer32,
            lcsStatusAdslAdvancedDsBitLoadingEntryGraph DisplayString
    }

-- {COLUMN} 1.3.6.1.4.1.2356.11.1.41.25.13.1.1
lcsStatusAdslAdvancedDsBitLoadingEntryBinNumber OBJECT-TYPE
    SYNTAX     DisplayString (SIZE(0..255))
    MAX-ACCESS read-only
    STATUS     current
    DESCRIPTION
            "-- empty --"
    ::= { lcsStatusAdslAdvancedDsBitLoadingEntry 1 }

-- {COLUMN} 1.3.6.1.4.1.2356.11.1.41.25.13.1.2
lcsStatusAdslAdvancedDsBitLoadingEntryX0 OBJECT-TYPE
    SYNTAX     Integer32 (0..2147483647)
    MAX-ACCESS read-only
    STATUS     current
    DESCRIPTION
            "-- empty --"
    ::= { lcsStatusAdslAdvancedDsBitLoadingEntry 2 }

-- {COLUMN} 1.3.6.1.4.1.2356.11.1.41.25.13.1.3
lcsStatusAdslAdvancedDsBitLoadingEntryX1 OBJECT-TYPE
    SYNTAX     Integer32 (0..2147483647)
    MAX-ACCESS read-only
    STATUS     current
    DESCRIPTION
            "-- empty --"
    ::= { lcsStatusAdslAdvancedDsBitLoadingEntry 3 }

-- {COLUMN} 1.3.6.1.4.1.2356.11.1.41.25.13.1.4
lcsStatusAdslAdvancedDsBitLoadingEntryX2 OBJECT-TYPE
    SYNTAX     Integer32 (0..2147483647)
    MAX-ACCESS read-only
    STATUS     current
    DESCRIPTION
            "-- empty --"
    ::= { lcsStatusAdslAdvancedDsBitLoadingEntry 4 }

-- {COLUMN} 1.3.6.1.4.1.2356.11.1.41.25.13.1.5
lcsStatusAdslAdvancedDsBitLoadingEntryX3 OBJECT-TYPE
    SYNTAX     Integer32 (0..2147483647)
    MAX-ACCESS read-only
    STATUS     current
    DESCRIPTION
            "-- empty --"
    ::= { lcsStatusAdslAdvancedDsBitLoadingEntry 5 }

-- {COLUMN} 1.3.6.1.4.1.2356.11.1.41.25.13.1.6
lcsStatusAdslAdvancedDsBitLoadingEntryX4 OBJECT-TYPE
    SYNTAX     Integer32 (0..2147483647)
    MAX-ACCESS read-only
    STATUS     current
    DESCRIPTION
            "-- empty --"
    ::= { lcsStatusAdslAdvancedDsBitLoadingEntry 6 }

-- {COLUMN} 1.3.6.1.4.1.2356.11.1.41.25.13.1.7
lcsStatusAdslAdvancedDsBitLoadingEntryX5 OBJECT-TYPE
    SYNTAX     Integer32 (0..2147483647)
    MAX-ACCESS read-only
    STATUS     current
    DESCRIPTION
            "-- empty --"
    ::= { lcsStatusAdslAdvancedDsBitLoadingEntry 7 }

-- {COLUMN} 1.3.6.1.4.1.2356.11.1.41.25.13.1.8
lcsStatusAdslAdvancedDsBitLoadingEntryX6 OBJECT-TYPE
    SYNTAX     Integer32 (0..2147483647)
    MAX-ACCESS read-only
    STATUS     current
    DESCRIPTION
            "-- empty --"
    ::= { lcsStatusAdslAdvancedDsBitLoadingEntry 8 }

-- {COLUMN} 1.3.6.1.4.1.2356.11.1.41.25.13.1.9
lcsStatusAdslAdvancedDsBitLoadingEntryX7 OBJECT-TYPE
    SYNTAX     Integer32 (0..2147483647)
    MAX-ACCESS read-only
    STATUS     current
    DESCRIPTION
            "-- empty --"
    ::= { lcsStatusAdslAdvancedDsBitLoadingEntry 9 }

-- {COLUMN} 1.3.6.1.4.1.2356.11.1.41.25.13.1.10
lcsStatusAdslAdvancedDsBitLoadingEntryX8 OBJECT-TYPE
    SYNTAX     Integer32 (0..2147483647)
    MAX-ACCESS read-only
    STATUS     current
    DESCRIPTION
            "-- empty --"
    ::= { lcsStatusAdslAdvancedDsBitLoadingEntry 10 }

-- {COLUMN} 1.3.6.1.4.1.2356.11.1.41.25.13.1.11
lcsStatusAdslAdvancedDsBitLoadingEntryX9 OBJECT-TYPE
    SYNTAX     Integer32 (0..2147483647)
    MAX-ACCESS read-only
    STATUS     current
    DESCRIPTION
            "-- empty --"
    ::= { lcsStatusAdslAdvancedDsBitLoadingEntry 11 }

-- {COLUMN} 1.3.6.1.4.1.2356.11.1.41.25.13.1.12
lcsStatusAdslAdvancedDsBitLoadingEntryGraph OBJECT-TYPE
    SYNTAX     DisplayString (SIZE(0..255))
    MAX-ACCESS read-only
    STATUS     current
    DESCRIPTION
            "-- empty --"
    ::= { lcsStatusAdslAdvancedDsBitLoadingEntry 12 }

-- {SCALAR} 1.3.6.1.4.1.2356.11.1.41.25.15
lcsStatusAdslAdvancedUsDataRateKbps OBJECT-TYPE
    SYNTAX     Integer32 (0..2147483647)
    MAX-ACCESS read-only
    STATUS     current
    DESCRIPTION
            "-- empty --"
    ::= { lcsStatusAdslAdvanced 15 }

-- {SCALAR} 1.3.6.1.4.1.2356.11.1.41.25.16
lcsStatusAdslAdvancedUsSnrMarginDb OBJECT-TYPE
    SYNTAX     DisplayString (SIZE(0..3))
    MAX-ACCESS read-only
    STATUS     current
    DESCRIPTION
            "-- empty --"
    ::= { lcsStatusAdslAdvanced 16 }

-- {SCALAR} 1.3.6.1.4.1.2356.11.1.41.25.17
lcsStatusAdslAdvancedUsLineAttenuationDb OBJECT-TYPE
    SYNTAX     DisplayString (SIZE(0..3))
    MAX-ACCESS read-only
    STATUS     current
    DESCRIPTION
            "-- empty --"
    ::= { lcsStatusAdslAdvanced 17 }

-- {SCALAR} 1.3.6.1.4.1.2356.11.1.41.25.18
lcsStatusAdslAdvancedUsInterleaveMs OBJECT-TYPE
    SYNTAX     DisplayString
    MAX-ACCESS read-only
    STATUS     current
    DESCRIPTION
            "-- empty --"
    ::= { lcsStatusAdslAdvanced 18 }

-- {TABLE} 1.3.6.1.4.1.2356.11.1.41.25.25
lcsStatusAdslAdvancedUsBitLoadingTable OBJECT-TYPE
    SYNTAX     SEQUENCE OF LcsStatusAdslAdvancedUsBitLoadingEntry
    MAX-ACCESS not-accessible
    STATUS     current
    DESCRIPTION
            "-- empty --"
    ::= { lcsStatusAdslAdvanced 25 }

-- {ROW} 1.3.6.1.4.1.2356.11.1.41.25.25.1
lcsStatusAdslAdvancedUsBitLoadingEntry OBJECT-TYPE
    SYNTAX     LcsStatusAdslAdvancedUsBitLoadingEntry
    MAX-ACCESS not-accessible
    STATUS     current
    DESCRIPTION
            ""
    INDEX {
            lcsStatusAdslAdvancedUsBitLoadingEntryBinNumber
          }
    ::= { lcsStatusAdslAdvancedUsBitLoadingTable 1 }

LcsStatusAdslAdvancedUsBitLoadingEntry ::= SEQUENCE {
            lcsStatusAdslAdvancedUsBitLoadingEntryBinNumber DisplayString,
            lcsStatusAdslAdvancedUsBitLoadingEntryX0 Integer32,
            lcsStatusAdslAdvancedUsBitLoadingEntryX1 Integer32,
            lcsStatusAdslAdvancedUsBitLoadingEntryX2 Integer32,
            lcsStatusAdslAdvancedUsBitLoadingEntryX3 Integer32,
            lcsStatusAdslAdvancedUsBitLoadingEntryX4 Integer32,
            lcsStatusAdslAdvancedUsBitLoadingEntryX5 Integer32,
            lcsStatusAdslAdvancedUsBitLoadingEntryX6 Integer32,
            lcsStatusAdslAdvancedUsBitLoadingEntryX7 Integer32,
            lcsStatusAdslAdvancedUsBitLoadingEntryX8 Integer32,
            lcsStatusAdslAdvancedUsBitLoadingEntryX9 Integer32,
            lcsStatusAdslAdvancedUsBitLoadingEntryGraph DisplayString
    }

-- {COLUMN} 1.3.6.1.4.1.2356.11.1.41.25.25.1.1
lcsStatusAdslAdvancedUsBitLoadingEntryBinNumber OBJECT-TYPE
    SYNTAX     DisplayString (SIZE(0..255))
    MAX-ACCESS read-only
    STATUS     current
    DESCRIPTION
            "-- empty --"
    ::= { lcsStatusAdslAdvancedUsBitLoadingEntry 1 }

-- {COLUMN} 1.3.6.1.4.1.2356.11.1.41.25.25.1.2
lcsStatusAdslAdvancedUsBitLoadingEntryX0 OBJECT-TYPE
    SYNTAX     Integer32 (0..2147483647)
    MAX-ACCESS read-only
    STATUS     current
    DESCRIPTION
            "-- empty --"
    ::= { lcsStatusAdslAdvancedUsBitLoadingEntry 2 }

-- {COLUMN} 1.3.6.1.4.1.2356.11.1.41.25.25.1.3
lcsStatusAdslAdvancedUsBitLoadingEntryX1 OBJECT-TYPE
    SYNTAX     Integer32 (0..2147483647)
    MAX-ACCESS read-only
    STATUS     current
    DESCRIPTION
            "-- empty --"
    ::= { lcsStatusAdslAdvancedUsBitLoadingEntry 3 }

-- {COLUMN} 1.3.6.1.4.1.2356.11.1.41.25.25.1.4
lcsStatusAdslAdvancedUsBitLoadingEntryX2 OBJECT-TYPE
    SYNTAX     Integer32 (0..2147483647)
    MAX-ACCESS read-only
    STATUS     current
    DESCRIPTION
            "-- empty --"
    ::= { lcsStatusAdslAdvancedUsBitLoadingEntry 4 }

-- {COLUMN} 1.3.6.1.4.1.2356.11.1.41.25.25.1.5
lcsStatusAdslAdvancedUsBitLoadingEntryX3 OBJECT-TYPE
    SYNTAX     Integer32 (0..2147483647)
    MAX-ACCESS read-only
    STATUS     current
    DESCRIPTION
            "-- empty --"
    ::= { lcsStatusAdslAdvancedUsBitLoadingEntry 5 }

-- {COLUMN} 1.3.6.1.4.1.2356.11.1.41.25.25.1.6
lcsStatusAdslAdvancedUsBitLoadingEntryX4 OBJECT-TYPE
    SYNTAX     Integer32 (0..2147483647)
    MAX-ACCESS read-only
    STATUS     current
    DESCRIPTION
            "-- empty --"
    ::= { lcsStatusAdslAdvancedUsBitLoadingEntry 6 }

-- {COLUMN} 1.3.6.1.4.1.2356.11.1.41.25.25.1.7
lcsStatusAdslAdvancedUsBitLoadingEntryX5 OBJECT-TYPE
    SYNTAX     Integer32 (0..2147483647)
    MAX-ACCESS read-only
    STATUS     current
    DESCRIPTION
            "-- empty --"
    ::= { lcsStatusAdslAdvancedUsBitLoadingEntry 7 }

-- {COLUMN} 1.3.6.1.4.1.2356.11.1.41.25.25.1.8
lcsStatusAdslAdvancedUsBitLoadingEntryX6 OBJECT-TYPE
    SYNTAX     Integer32 (0..2147483647)
    MAX-ACCESS read-only
    STATUS     current
    DESCRIPTION
            "-- empty --"
    ::= { lcsStatusAdslAdvancedUsBitLoadingEntry 8 }

-- {COLUMN} 1.3.6.1.4.1.2356.11.1.41.25.25.1.9
lcsStatusAdslAdvancedUsBitLoadingEntryX7 OBJECT-TYPE
    SYNTAX     Integer32 (0..2147483647)
    MAX-ACCESS read-only
    STATUS     current
    DESCRIPTION
            "-- empty --"
    ::= { lcsStatusAdslAdvancedUsBitLoadingEntry 9 }

-- {COLUMN} 1.3.6.1.4.1.2356.11.1.41.25.25.1.10
lcsStatusAdslAdvancedUsBitLoadingEntryX8 OBJECT-TYPE
    SYNTAX     Integer32 (0..2147483647)
    MAX-ACCESS read-only
    STATUS     current
    DESCRIPTION
            "-- empty --"
    ::= { lcsStatusAdslAdvancedUsBitLoadingEntry 10 }

-- {COLUMN} 1.3.6.1.4.1.2356.11.1.41.25.25.1.11
lcsStatusAdslAdvancedUsBitLoadingEntryX9 OBJECT-TYPE
    SYNTAX     Integer32 (0..2147483647)
    MAX-ACCESS read-only
    STATUS     current
    DESCRIPTION
            "-- empty --"
    ::= { lcsStatusAdslAdvancedUsBitLoadingEntry 11 }

-- {COLUMN} 1.3.6.1.4.1.2356.11.1.41.25.25.1.12
lcsStatusAdslAdvancedUsBitLoadingEntryGraph OBJECT-TYPE
    SYNTAX     DisplayString (SIZE(0..255))
    MAX-ACCESS read-only
    STATUS     current
    DESCRIPTION
            "-- empty --"
    ::= { lcsStatusAdslAdvancedUsBitLoadingEntry 12 }

-- {SCALAR} 1.3.6.1.4.1.2356.11.1.41.25.26
lcsStatusAdslAdvancedRetrain OBJECT-TYPE
    SYNTAX     DisplayString
    MAX-ACCESS read-write
    STATUS     current
    DESCRIPTION
            "-- empty --"
    ::= { lcsStatusAdslAdvanced 26 }

-- {SCALAR} 1.3.6.1.4.1.2356.11.1.41.25.41
lcsStatusAdslAdvancedDslamManufacturer OBJECT-TYPE
    SYNTAX     DisplayString (SIZE(0..63))
    MAX-ACCESS read-only
    STATUS     current
    DESCRIPTION
            "-- empty --"
    ::= { lcsStatusAdslAdvanced 41 }

-- {SCALAR} 1.3.6.1.4.1.2356.11.1.41.25.42
lcsStatusAdslAdvancedDslamVersion OBJECT-TYPE
    SYNTAX     DisplayString (SIZE(0..34))
    MAX-ACCESS read-only
    STATUS     current
    DESCRIPTION
            "-- empty --"
    ::= { lcsStatusAdslAdvanced 42 }

-- {SCALAR} 1.3.6.1.4.1.2356.11.1.41.25.43
lcsStatusAdslAdvancedDslamSerialNumber OBJECT-TYPE
    SYNTAX     DisplayString (SIZE(0..66))
    MAX-ACCESS read-only
    STATUS     current
    DESCRIPTION
            "-- empty --"
    ::= { lcsStatusAdslAdvanced 43 }

-- {SCALAR} 1.3.6.1.4.1.2356.11.1.41.25.44
lcsStatusAdslAdvancedDslamChipsetManufacturer OBJECT-TYPE
    SYNTAX     DisplayString (SIZE(0..63))
    MAX-ACCESS read-only
    STATUS     current
    DESCRIPTION
            "-- empty --"
    ::= { lcsStatusAdslAdvanced 44 }

-- {SCALAR} 1.3.6.1.4.1.2356.11.1.41.25.46
lcsStatusAdslAdvancedVectoring OBJECT-TYPE
    SYNTAX     INTEGER {
                  eNo (1),
                  eYes (2),
                  eFriendly (3)
            }
    MAX-ACCESS read-only
    STATUS     current
    DESCRIPTION
            "-- empty --"
    ::= { lcsStatusAdslAdvanced 46 }

-- {SCALAR} 1.3.6.1.4.1.2356.11.1.41.25.47
lcsStatusAdslAdvancedDslamChipsetManufacturerDump OBJECT-TYPE
    SYNTAX     OCTET STRING
    MAX-ACCESS read-only
    STATUS     current
    DESCRIPTION
            "-- empty --"
    ::= { lcsStatusAdslAdvanced 47 }

-- {SCALAR} 1.3.6.1.4.1.2356.11.1.41.25.48
lcsStatusAdslAdvancedDslamManufacturerDump OBJECT-TYPE
    SYNTAX     OCTET STRING
    MAX-ACCESS read-only
    STATUS     current
    DESCRIPTION
            "-- empty --"
    ::= { lcsStatusAdslAdvanced 48 }

-- {SCALAR} 1.3.6.1.4.1.2356.11.1.41.25.53
lcsStatusAdslAdvancedConnectionCount OBJECT-TYPE
    SYNTAX     Integer32 (0..2147483647)
    MAX-ACCESS read-only
    STATUS     current
    DESCRIPTION
            "-- empty --"
    ::= { lcsStatusAdslAdvanced 53 }

-- {SCALAR} 1.3.6.1.4.1.2356.11.1.41.25.54
lcsStatusAdslAdvancedConnectionDuration OBJECT-TYPE
    SYNTAX     Gauge32
    MAX-ACCESS read-only
    STATUS     current
    DESCRIPTION
            "-- empty --"
    ::= { lcsStatusAdslAdvanced 54 }

-- {SCALAR} 1.3.6.1.4.1.2356.11.1.41.25.100
lcsStatusAdslAdvancedDsAttainableDataRateKbps OBJECT-TYPE
    SYNTAX     Integer32 (0..2147483647)
    MAX-ACCESS read-only
    STATUS     current
    DESCRIPTION
            "-- empty --"
    ::= { lcsStatusAdslAdvanced 100 }

-- {SCALAR} 1.3.6.1.4.1.2356.11.1.41.25.101
lcsStatusAdslAdvancedDsInpSymbols OBJECT-TYPE
    SYNTAX     DisplayString (SIZE(0..3))
    MAX-ACCESS read-only
    STATUS     current
    DESCRIPTION
            "-- empty --"
    ::= { lcsStatusAdslAdvanced 101 }

-- {SCALAR} 1.3.6.1.4.1.2356.11.1.41.25.102
lcsStatusAdslAdvancedDsCrcErrors OBJECT-TYPE
    SYNTAX     Integer32 (0..2147483647)
    MAX-ACCESS read-only
    STATUS     current
    DESCRIPTION
            "-- empty --"
    ::= { lcsStatusAdslAdvanced 102 }

-- {SCALAR} 1.3.6.1.4.1.2356.11.1.41.25.103
lcsStatusAdslAdvancedDsFecErrors OBJECT-TYPE
    SYNTAX     Integer32 (0..2147483647)
    MAX-ACCESS read-only
    STATUS     current
    DESCRIPTION
            "-- empty --"
    ::= { lcsStatusAdslAdvanced 103 }

-- {SCALAR} 1.3.6.1.4.1.2356.11.1.41.25.104
lcsStatusAdslAdvancedDsAtmHecErrors OBJECT-TYPE
    SYNTAX     Integer32 (0..2147483647)
    MAX-ACCESS read-only
    STATUS     current
    DESCRIPTION
            "-- empty --"
    ::= { lcsStatusAdslAdvanced 104 }

-- {SCALAR} 1.3.6.1.4.1.2356.11.1.41.25.105
lcsStatusAdslAdvancedDsDataPathCrcpErrors OBJECT-TYPE
    SYNTAX     Integer32 (0..2147483647)
    MAX-ACCESS read-only
    STATUS     current
    DESCRIPTION
            "-- empty --"
    ::= { lcsStatusAdslAdvanced 105 }

-- {SCALAR} 1.3.6.1.4.1.2356.11.1.41.25.106
lcsStatusAdslAdvancedDsDataPathCrcnpErrors OBJECT-TYPE
    SYNTAX     Integer32 (0..2147483647)
    MAX-ACCESS read-only
    STATUS     current
    DESCRIPTION
            "-- empty --"
    ::= { lcsStatusAdslAdvanced 106 }

-- {SCALAR} 1.3.6.1.4.1.2356.11.1.41.25.107
lcsStatusAdslAdvancedDsDataPathCvpErrors OBJECT-TYPE
    SYNTAX     Integer32 (0..2147483647)
    MAX-ACCESS read-only
    STATUS     current
    DESCRIPTION
            "-- empty --"
    ::= { lcsStatusAdslAdvanced 107 }

-- {SCALAR} 1.3.6.1.4.1.2356.11.1.41.25.108
lcsStatusAdslAdvancedDsDataPathCvnpErrors OBJECT-TYPE
    SYNTAX     Integer32 (0..2147483647)
    MAX-ACCESS read-only
    STATUS     current
    DESCRIPTION
            "-- empty --"
    ::= { lcsStatusAdslAdvanced 108 }

-- {SCALAR} 1.3.6.1.4.1.2356.11.1.41.25.109
lcsStatusAdslAdvancedDsAtmIdleBitErrors OBJECT-TYPE
    SYNTAX     Integer32 (0..2147483647)
    MAX-ACCESS read-only
    STATUS     current
    DESCRIPTION
            "-- empty --"
    ::= { lcsStatusAdslAdvanced 109 }

-- {SCALAR} 1.3.6.1.4.1.2356.11.1.41.25.110
lcsStatusAdslAdvancedDsAtmCells OBJECT-TYPE
    SYNTAX     Integer32 (0..2147483647)
    MAX-ACCESS read-only
    STATUS     current
    DESCRIPTION
            "-- empty --"
    ::= { lcsStatusAdslAdvanced 110 }

-- {SCALAR} 1.3.6.1.4.1.2356.11.1.41.25.120
lcsStatusAdslAdvancedUsAttainableDataRateKbps OBJECT-TYPE
    SYNTAX     Integer32 (0..2147483647)
    MAX-ACCESS read-only
    STATUS     current
    DESCRIPTION
            "-- empty --"
    ::= { lcsStatusAdslAdvanced 120 }

-- {SCALAR} 1.3.6.1.4.1.2356.11.1.41.25.121
lcsStatusAdslAdvancedUsInpSymbols OBJECT-TYPE
    SYNTAX     DisplayString (SIZE(0..3))
    MAX-ACCESS read-only
    STATUS     current
    DESCRIPTION
            "-- empty --"
    ::= { lcsStatusAdslAdvanced 121 }

-- {SCALAR} 1.3.6.1.4.1.2356.11.1.41.25.122
lcsStatusAdslAdvancedUsCrcErrors OBJECT-TYPE
    SYNTAX     Integer32 (0..2147483647)
    MAX-ACCESS read-only
    STATUS     current
    DESCRIPTION
            "-- empty --"
    ::= { lcsStatusAdslAdvanced 122 }

-- {SCALAR} 1.3.6.1.4.1.2356.11.1.41.25.123
lcsStatusAdslAdvancedUsFecErrors OBJECT-TYPE
    SYNTAX     Integer32 (0..2147483647)
    MAX-ACCESS read-only
    STATUS     current
    DESCRIPTION
            "-- empty --"
    ::= { lcsStatusAdslAdvanced 123 }

-- {SCALAR} 1.3.6.1.4.1.2356.11.1.41.25.124
lcsStatusAdslAdvancedUsAtmHecErrors OBJECT-TYPE
    SYNTAX     Integer32 (0..2147483647)
    MAX-ACCESS read-only
    STATUS     current
    DESCRIPTION
            "-- empty --"
    ::= { lcsStatusAdslAdvanced 124 }

-- {SCALAR} 1.3.6.1.4.1.2356.11.1.41.25.125
lcsStatusAdslAdvancedUsDataPathCrcpErrors OBJECT-TYPE
    SYNTAX     Integer32 (0..2147483647)
    MAX-ACCESS read-only
    STATUS     current
    DESCRIPTION
            "-- empty --"
    ::= { lcsStatusAdslAdvanced 125 }

-- {SCALAR} 1.3.6.1.4.1.2356.11.1.41.25.126
lcsStatusAdslAdvancedUsDataPathCrcnpErrors OBJECT-TYPE
    SYNTAX     Integer32 (0..2147483647)
    MAX-ACCESS read-only
    STATUS     current
    DESCRIPTION
            "-- empty --"
    ::= { lcsStatusAdslAdvanced 126 }

-- {SCALAR} 1.3.6.1.4.1.2356.11.1.41.25.127
lcsStatusAdslAdvancedUsDataPathCvpErrors OBJECT-TYPE
    SYNTAX     Integer32 (0..2147483647)
    MAX-ACCESS read-only
    STATUS     current
    DESCRIPTION
            "-- empty --"
    ::= { lcsStatusAdslAdvanced 127 }

-- {SCALAR} 1.3.6.1.4.1.2356.11.1.41.25.128
lcsStatusAdslAdvancedUsDataPathCvnpErrors OBJECT-TYPE
    SYNTAX     Integer32 (0..2147483647)
    MAX-ACCESS read-only
    STATUS     current
    DESCRIPTION
            "-- empty --"
    ::= { lcsStatusAdslAdvanced 128 }

-- {SCALAR} 1.3.6.1.4.1.2356.11.1.41.25.129
lcsStatusAdslAdvancedUsAtmIdleBitErrors OBJECT-TYPE
    SYNTAX     Integer32 (0..2147483647)
    MAX-ACCESS read-only
    STATUS     current
    DESCRIPTION
            "-- empty --"
    ::= { lcsStatusAdslAdvanced 129 }

-- {SCALAR} 1.3.6.1.4.1.2356.11.1.41.25.130
lcsStatusAdslAdvancedUsAtmCells OBJECT-TYPE
    SYNTAX     Integer32 (0..2147483647)
    MAX-ACCESS read-only
    STATUS     current
    DESCRIPTION
            "-- empty --"
    ::= { lcsStatusAdslAdvanced 130 }

-- {SCALAR} 1.3.6.1.4.1.2356.11.1.41.25.140
lcsStatusAdslAdvancedWanTxPacketCount OBJECT-TYPE
    SYNTAX     Integer32 (0..2147483647)
    MAX-ACCESS read-only
    STATUS     current
    DESCRIPTION
            "-- empty --"
    ::= { lcsStatusAdslAdvanced 140 }

-- {SCALAR} 1.3.6.1.4.1.2356.11.1.41.25.141
lcsStatusAdslAdvancedWanTxPacketBytes OBJECT-TYPE
    SYNTAX     Integer32 (0..2147483647)
    MAX-ACCESS read-only
    STATUS     current
    DESCRIPTION
            "-- empty --"
    ::= { lcsStatusAdslAdvanced 141 }

-- {SCALAR} 1.3.6.1.4.1.2356.11.1.41.25.142
lcsStatusAdslAdvancedWanTxPacketErrors OBJECT-TYPE
    SYNTAX     Integer32 (0..2147483647)
    MAX-ACCESS read-only
    STATUS     current
    DESCRIPTION
            "-- empty --"
    ::= { lcsStatusAdslAdvanced 142 }

-- {SCALAR} 1.3.6.1.4.1.2356.11.1.41.25.143
lcsStatusAdslAdvancedWanTxPacketDrops OBJECT-TYPE
    SYNTAX     Integer32 (0..2147483647)
    MAX-ACCESS read-only
    STATUS     current
    DESCRIPTION
            "-- empty --"
    ::= { lcsStatusAdslAdvanced 143 }

-- {SCALAR} 1.3.6.1.4.1.2356.11.1.41.25.144
lcsStatusAdslAdvancedWanTxOverruns OBJECT-TYPE
    SYNTAX     Integer32 (0..2147483647)
    MAX-ACCESS read-only
    STATUS     current
    DESCRIPTION
            "-- empty --"
    ::= { lcsStatusAdslAdvanced 144 }

-- {SCALAR} 1.3.6.1.4.1.2356.11.1.41.25.146
lcsStatusAdslAdvancedTxPacketCount OBJECT-TYPE
    SYNTAX     Integer32 (0..2147483647)
    MAX-ACCESS read-only
    STATUS     current
    DESCRIPTION
            "-- empty --"
    ::= { lcsStatusAdslAdvanced 146 }

-- {SCALAR} 1.3.6.1.4.1.2356.11.1.41.25.150
lcsStatusAdslAdvancedWanRxPacketCount OBJECT-TYPE
    SYNTAX     Integer32 (0..2147483647)
    MAX-ACCESS read-only
    STATUS     current
    DESCRIPTION
            "-- empty --"
    ::= { lcsStatusAdslAdvanced 150 }

-- {SCALAR} 1.3.6.1.4.1.2356.11.1.41.25.151
lcsStatusAdslAdvancedWanRxPacketBytes OBJECT-TYPE
    SYNTAX     Integer32 (0..2147483647)
    MAX-ACCESS read-only
    STATUS     current
    DESCRIPTION
            "-- empty --"
    ::= { lcsStatusAdslAdvanced 151 }

-- {SCALAR} 1.3.6.1.4.1.2356.11.1.41.25.152
lcsStatusAdslAdvancedWanRxPacketErrors OBJECT-TYPE
    SYNTAX     Integer32 (0..2147483647)
    MAX-ACCESS read-only
    STATUS     current
    DESCRIPTION
            "-- empty --"
    ::= { lcsStatusAdslAdvanced 152 }

-- {SCALAR} 1.3.6.1.4.1.2356.11.1.41.25.153
lcsStatusAdslAdvancedWanRxPacketDrops OBJECT-TYPE
    SYNTAX     Integer32 (0..2147483647)
    MAX-ACCESS read-only
    STATUS     current
    DESCRIPTION
            "-- empty --"
    ::= { lcsStatusAdslAdvanced 153 }

-- {SCALAR} 1.3.6.1.4.1.2356.11.1.41.25.154
lcsStatusAdslAdvancedWanRxOverruns OBJECT-TYPE
    SYNTAX     Integer32 (0..2147483647)
    MAX-ACCESS read-only
    STATUS     current
    DESCRIPTION
            "-- empty --"
    ::= { lcsStatusAdslAdvanced 154 }

-- {SCALAR} 1.3.6.1.4.1.2356.11.1.41.25.156
lcsStatusAdslAdvancedRxPacketCount OBJECT-TYPE
    SYNTAX     Integer32 (0..2147483647)
    MAX-ACCESS read-only
    STATUS     current
    DESCRIPTION
            "-- empty --"
    ::= { lcsStatusAdslAdvanced 156 }

-- {SCALAR} 1.3.6.1.4.1.2356.11.1.41.34
lcsStatusAdslInpDownstreamSymbols OBJECT-TYPE
    SYNTAX     DisplayString (SIZE(0..3))
    MAX-ACCESS read-only
    STATUS     current
    DESCRIPTION
            "-- empty --"
    ::= { lcsStatusAdsl 34 }

-- {SCALAR} 1.3.6.1.4.1.2356.11.1.41.35
lcsStatusAdslInpUpstreamSymbols OBJECT-TYPE
    SYNTAX     DisplayString (SIZE(0..3))
    MAX-ACCESS read-only
    STATUS     current
    DESCRIPTION
            "-- empty --"
    ::= { lcsStatusAdsl 35 }

-- {SCALAR} 1.3.6.1.4.1.2356.11.1.41.36
lcsStatusAdslAttainableDataRateDownstreamKbps OBJECT-TYPE
    SYNTAX     Integer32 (0..2147483647)
    MAX-ACCESS read-only
    STATUS     current
    DESCRIPTION
            "-- empty --"
    ::= { lcsStatusAdsl 36 }

-- {SCALAR} 1.3.6.1.4.1.2356.11.1.41.37
lcsStatusAdslAttainableDataRateUpstreamKbps OBJECT-TYPE
    SYNTAX     Integer32 (0..2147483647)
    MAX-ACCESS read-only
    STATUS     current
    DESCRIPTION
            "-- empty --"
    ::= { lcsStatusAdsl 37 }

-- {SCALAR} 1.3.6.1.4.1.2356.11.1.41.41
lcsStatusAdslDslamManufacturer OBJECT-TYPE
    SYNTAX     DisplayString (SIZE(0..63))
    MAX-ACCESS read-only
    STATUS     current
    DESCRIPTION
            "-- empty --"
    ::= { lcsStatusAdsl 41 }

-- {SCALAR} 1.3.6.1.4.1.2356.11.1.41.42
lcsStatusAdslDslamVersion OBJECT-TYPE
    SYNTAX     DisplayString (SIZE(0..34))
    MAX-ACCESS read-only
    STATUS     current
    DESCRIPTION
            "-- empty --"
    ::= { lcsStatusAdsl 42 }

-- {SCALAR} 1.3.6.1.4.1.2356.11.1.41.43
lcsStatusAdslDslamSerialNumber OBJECT-TYPE
    SYNTAX     DisplayString (SIZE(0..66))
    MAX-ACCESS read-only
    STATUS     current
    DESCRIPTION
            "-- empty --"
    ::= { lcsStatusAdsl 43 }

-- {SCALAR} 1.3.6.1.4.1.2356.11.1.41.46
lcsStatusAdslVectoring OBJECT-TYPE
    SYNTAX     INTEGER {
                  eNo (1),
                  eYes (2),
                  eFriendly (3)
            }
    MAX-ACCESS read-only
    STATUS     current
    DESCRIPTION
            "-- empty --"
    ::= { lcsStatusAdsl 46 }

-- {SCALAR} 1.3.6.1.4.1.2356.11.1.41.53
lcsStatusAdslConnectionCount OBJECT-TYPE
    SYNTAX     Integer32 (0..2147483647)
    MAX-ACCESS read-only
    STATUS     current
    DESCRIPTION
            "-- empty --"
    ::= { lcsStatusAdsl 53 }

-- {SCALAR} 1.3.6.1.4.1.2356.11.1.41.54
lcsStatusAdslConnectionDuration OBJECT-TYPE
    SYNTAX     Gauge32
    MAX-ACCESS read-only
    STATUS     current
    DESCRIPTION
            "-- empty --"
    ::= { lcsStatusAdsl 54 }

-- {SCALAR} 1.3.6.1.4.1.2356.11.1.41.200
lcsStatusAdslWanBridge OBJECT-TYPE
    SYNTAX     INTEGER {
                  eNo (0),
                  eYes (1)
            }
    MAX-ACCESS read-only
    STATUS     current
    DESCRIPTION
            "-- empty --"
    ::= { lcsStatusAdsl 200 }

-- {NODE} 1.3.6.1.4.1.2356.11.1.41.500
lcsStatusAdslModem OBJECT IDENTIFIER ::= { lcsStatusAdsl 500 }

-- {SCALAR} 1.3.6.1.4.1.2356.11.1.41.500.1
lcsStatusAdslModemModemState OBJECT-TYPE
    SYNTAX     INTEGER {
                  eNoCommunicationsPort (0),
                  eError (1),
                  eFileSystem (2),
                  eBootHeader (3),
                  eUploadingBootstrap (4),
                  eUploadingMemoryTest (5),
                  eMemoryTest (6),
                  eOptions (7),
                  eUploadingUBoot (8),
                  eQuickMemoryTest (9),
                  eUploadingKernel (10),
                  eUploadingRamdisk (11),
                  eUploadingFirmware (12),
                  eWaitForHeartbeat (13),
                  eRunning (14),
                  eUploadingGphyFirmware (15),
                  eDisabled (16)
            }
    MAX-ACCESS read-only
    STATUS     current
    DESCRIPTION
            "-- empty --"
    ::= { lcsStatusAdslModem 1 }

-- {SCALAR} 1.3.6.1.4.1.2356.11.1.41.500.2
lcsStatusAdslModemOptions OBJECT-TYPE
    SYNTAX     Integer32 (0..255)
    MAX-ACCESS read-only
    STATUS     current
    DESCRIPTION
            "-- empty --"
    ::= { lcsStatusAdslModem 2 }

-- {SCALAR} 1.3.6.1.4.1.2356.11.1.41.500.3
lcsStatusAdslModemMemoryTest OBJECT-TYPE
    SYNTAX     INTEGER {
                  eNotTested (0),
                  eTimeout (1),
                  eFailed (2),
                  eOk (3)
            }
    MAX-ACCESS read-only
    STATUS     current
    DESCRIPTION
            "-- empty --"
    ::= { lcsStatusAdslModem 3 }

-- {SCALAR} 1.3.6.1.4.1.2356.11.1.41.500.4
lcsStatusAdslModemRebootModem OBJECT-TYPE
    SYNTAX     DisplayString
    MAX-ACCESS read-write
    STATUS     current
    DESCRIPTION
            "-- empty --"
    ::= { lcsStatusAdslModem 4 }

-- {SCALAR} 1.3.6.1.4.1.2356.11.1.41.500.5
lcsStatusAdslModemLink OBJECT-TYPE
    SYNTAX     Integer32 (0..2147483647)
    MAX-ACCESS read-only
    STATUS     current
    DESCRIPTION
            "-- empty --"
    ::= { lcsStatusAdslModem 5 }

-- {SCALAR} 1.3.6.1.4.1.2356.11.1.41.500.6
lcsStatusAdslModemLastError OBJECT-TYPE
    SYNTAX     DisplayString (SIZE(0..63))
    MAX-ACCESS read-only
    STATUS     current
    DESCRIPTION
            "-- empty --"
    ::= { lcsStatusAdslModem 6 }

-- {SCALAR} 1.3.6.1.4.1.2356.11.1.41.500.8
lcsStatusAdslModemAdslPotsFirmware OBJECT-TYPE
    SYNTAX     DisplayString (SIZE(0..63))
    MAX-ACCESS read-only
    STATUS     current
    DESCRIPTION
            "-- empty --"
    ::= { lcsStatusAdslModem 8 }

-- {SCALAR} 1.3.6.1.4.1.2356.11.1.41.500.9
lcsStatusAdslModemAdslIsdnFirmware OBJECT-TYPE
    SYNTAX     DisplayString (SIZE(0..63))
    MAX-ACCESS read-only
    STATUS     current
    DESCRIPTION
            "-- empty --"
    ::= { lcsStatusAdslModem 9 }

-- {SCALAR} 1.3.6.1.4.1.2356.11.1.41.500.10
lcsStatusAdslModemDslApiVersion OBJECT-TYPE
    SYNTAX     DisplayString (SIZE(0..31))
    MAX-ACCESS read-only
    STATUS     current
    DESCRIPTION
            "-- empty --"
    ::= { lcsStatusAdslModem 10 }

-- {SCALAR} 1.3.6.1.4.1.2356.11.1.41.500.11
lcsStatusAdslModemDspFirmwareVersion OBJECT-TYPE
    SYNTAX     DisplayString (SIZE(0..31))
    MAX-ACCESS read-only
    STATUS     current
    DESCRIPTION
            "-- empty --"
    ::= { lcsStatusAdslModem 11 }

-- {SCALAR} 1.3.6.1.4.1.2356.11.1.41.500.12
lcsStatusAdslModemHardwareVersion OBJECT-TYPE
    SYNTAX     DisplayString (SIZE(0..31))
    MAX-ACCESS read-only
    STATUS     current
    DESCRIPTION
            "-- empty --"
    ::= { lcsStatusAdslModem 12 }

-- {SCALAR} 1.3.6.1.4.1.2356.11.1.41.500.13
lcsStatusAdslModemChipsetType OBJECT-TYPE
    SYNTAX     DisplayString (SIZE(0..31))
    MAX-ACCESS read-only
    STATUS     current
    DESCRIPTION
            "-- empty --"
    ::= { lcsStatusAdslModem 13 }

-- {SCALAR} 1.3.6.1.4.1.2356.11.1.41.500.14
lcsStatusAdslModemDriverVersion OBJECT-TYPE
    SYNTAX     DisplayString (SIZE(0..31))
    MAX-ACCESS read-only
    STATUS     current
    DESCRIPTION
            "-- empty --"
    ::= { lcsStatusAdslModem 14 }

-- {SCALAR} 1.3.6.1.4.1.2356.11.1.41.500.15
lcsStatusAdslModemBootCount OBJECT-TYPE
    SYNTAX     Integer32 (0..2147483647)
    MAX-ACCESS read-only
    STATUS     current
    DESCRIPTION
            "-- empty --"
    ::= { lcsStatusAdslModem 15 }

-- {SCALAR} 1.3.6.1.4.1.2356.11.1.41.500.16
lcsStatusAdslModemHybrid OBJECT-TYPE
    SYNTAX     INTEGER {
                  eBJ (0),
                  eInvalid (1),
                  eB (2),
                  eA (3),
                  eUniversal (4),
                  eUnknown (256)
            }
    MAX-ACCESS read-only
    STATUS     current
    DESCRIPTION
            "-- empty --"
    ::= { lcsStatusAdslModem 16 }

-- {SCALAR} 1.3.6.1.4.1.2356.11.1.41.500.20
lcsStatusAdslModemDefaultLineType OBJECT-TYPE
    SYNTAX     INTEGER {
                  eUnknown (1),
                  eOverPots (2),
                  eOverIsdn (3)
            }
    MAX-ACCESS read-only
    STATUS     current
    DESCRIPTION
            "-- empty --"
    ::= { lcsStatusAdslModem 20 }

-- {SCALAR} 1.3.6.1.4.1.2356.11.1.41.500.25
lcsStatusAdslModemPotsFirmware OBJECT-TYPE
    SYNTAX     DisplayString (SIZE(0..71))
    MAX-ACCESS read-only
    STATUS     current
    DESCRIPTION
            "-- empty --"
    ::= { lcsStatusAdslModem 25 }

-- {SCALAR} 1.3.6.1.4.1.2356.11.1.41.500.26
lcsStatusAdslModemIsdnFirmware OBJECT-TYPE
    SYNTAX     DisplayString (SIZE(0..71))
    MAX-ACCESS read-only
    STATUS     current
    DESCRIPTION
            "-- empty --"
    ::= { lcsStatusAdslModem 26 }

-- {SCALAR} 1.3.6.1.4.1.2356.11.1.41.500.28
lcsStatusAdslModemWanAcceleration OBJECT-TYPE
    SYNTAX     INTEGER {
                  eNo (0),
                  eYes (1)
            }
    MAX-ACCESS read-only
    STATUS     current
    DESCRIPTION
            "-- empty --"
    ::= { lcsStatusAdslModem 28 }

-- {NODE} 1.3.6.1.4.1.2356.11.1.43
lcsStatusMail OBJECT IDENTIFIER ::= { lcsStatus 43 }

-- {SCALAR} 1.3.6.1.4.1.2356.11.1.43.1
lcsStatusMailBufferedMails OBJECT-TYPE
    SYNTAX     Integer32 (0..65535)
    MAX-ACCESS read-only
    STATUS     current
    DESCRIPTION
            ""
    ::= { lcsStatusMail 1 }

-- {SCALAR} 1.3.6.1.4.1.2356.11.1.43.2
lcsStatusMailSentMails OBJECT-TYPE
    SYNTAX     Counter32
    MAX-ACCESS read-only
    STATUS     current
    DESCRIPTION
            ""
    ::= { lcsStatusMail 2 }

-- {SCALAR} 1.3.6.1.4.1.2356.11.1.43.3
lcsStatusMailDiscardedMails OBJECT-TYPE
    SYNTAX     Counter32
    MAX-ACCESS read-only
    STATUS     current
    DESCRIPTION
            ""
    ::= { lcsStatusMail 3 }

-- {SCALAR} 1.3.6.1.4.1.2356.11.1.43.4
lcsStatusMailClearBuffer OBJECT-TYPE
    SYNTAX     DisplayString
    MAX-ACCESS read-write
    STATUS     current
    DESCRIPTION
            ""
    ::= { lcsStatusMail 4 }

-- {SCALAR} 1.3.6.1.4.1.2356.11.1.43.5
lcsStatusMailDeleteStatistics OBJECT-TYPE
    SYNTAX     DisplayString
    MAX-ACCESS read-write
    STATUS     current
    DESCRIPTION
            ""
    ::= { lcsStatusMail 5 }

-- {NODE} 1.3.6.1.4.1.2356.11.1.43.17
lcsStatusMailFreeLogin OBJECT IDENTIFIER ::= { lcsStatusMail 17 }

-- {TABLE} 1.3.6.1.4.1.2356.11.1.43.17.1
lcsStatusMailFreeLoginUsersTable OBJECT-TYPE
    SYNTAX     SEQUENCE OF LcsStatusMailFreeLoginUsersEntry
    MAX-ACCESS not-accessible
    STATUS     current
    DESCRIPTION
            "-- empty --"
    ::= { lcsStatusMailFreeLogin 1 }

-- {ROW} 1.3.6.1.4.1.2356.11.1.43.17.1.1
lcsStatusMailFreeLoginUsersEntry OBJECT-TYPE
    SYNTAX     LcsStatusMailFreeLoginUsersEntry
    MAX-ACCESS not-accessible
    STATUS     current
    DESCRIPTION
            ""
    INDEX {
            lcsStatusMailFreeLoginUsersEntryUsername
          }
    ::= { lcsStatusMailFreeLoginUsersTable 1 }

LcsStatusMailFreeLoginUsersEntry ::= SEQUENCE {
            lcsStatusMailFreeLoginUsersEntryUsername DisplayString,
            lcsStatusMailFreeLoginUsersEntryCreated Gauge32,
            lcsStatusMailFreeLoginUsersEntryEMail DisplayString
    }

-- {COLUMN} 1.3.6.1.4.1.2356.11.1.43.17.1.1.1
lcsStatusMailFreeLoginUsersEntryUsername OBJECT-TYPE
    SYNTAX     DisplayString (SIZE(0..64))
    MAX-ACCESS read-only
    STATUS     current
    DESCRIPTION
            "-- empty --"
    ::= { lcsStatusMailFreeLoginUsersEntry 1 }

-- {COLUMN} 1.3.6.1.4.1.2356.11.1.43.17.1.1.2
lcsStatusMailFreeLoginUsersEntryCreated OBJECT-TYPE
    SYNTAX     Gauge32
    MAX-ACCESS read-only
    STATUS     current
    DESCRIPTION
            "-- empty --"
    ::= { lcsStatusMailFreeLoginUsersEntry 2 }

-- {COLUMN} 1.3.6.1.4.1.2356.11.1.43.17.1.1.3
lcsStatusMailFreeLoginUsersEntryEMail OBJECT-TYPE
    SYNTAX     DisplayString (SIZE(0..64))
    MAX-ACCESS read-only
    STATUS     current
    DESCRIPTION
            "-- empty --"
    ::= { lcsStatusMailFreeLoginUsersEntry 3 }

-- {SCALAR} 1.3.6.1.4.1.2356.11.1.43.17.2
lcsStatusMailFreeLoginDeleteUser OBJECT-TYPE
    SYNTAX     DisplayString
    MAX-ACCESS read-write
    STATUS     current
    DESCRIPTION
            "-- empty --"
    ::= { lcsStatusMailFreeLogin 2 }

-- {NODE} 1.3.6.1.4.1.2356.11.1.44
lcsStatusPublicSpot OBJECT IDENTIFIER ::= { lcsStatus 44 }

-- {TABLE} 1.3.6.1.4.1.2356.11.1.44.1
lcsStatusPublicSpotStationTableTable OBJECT-TYPE
    SYNTAX     SEQUENCE OF LcsStatusPublicSpotStationTableEntry
    MAX-ACCESS not-accessible
    STATUS     current
    DESCRIPTION
            ""
    ::= { lcsStatusPublicSpot 1 }

-- {ROW} 1.3.6.1.4.1.2356.11.1.44.1.1
lcsStatusPublicSpotStationTableEntry OBJECT-TYPE
    SYNTAX     LcsStatusPublicSpotStationTableEntry
    MAX-ACCESS not-accessible
    STATUS     current
    DESCRIPTION
            ""
    INDEX {
            lcsStatusPublicSpotStationTableEntryMacAddress
          }
    ::= { lcsStatusPublicSpotStationTableTable 1 }

LcsStatusPublicSpotStationTableEntry ::= SEQUENCE {
            lcsStatusPublicSpotStationTableEntryMacAddress DisplayString,
            lcsStatusPublicSpotStationTableEntryIpAddress DisplayString,
            lcsStatusPublicSpotStationTableEntryName DisplayString,
            lcsStatusPublicSpotStationTableEntryProvider DisplayString,
            lcsStatusPublicSpotStationTableEntryTxBytes Integer32,
            lcsStatusPublicSpotStationTableEntryRxBytes Integer32,
            lcsStatusPublicSpotStationTableEntryTxPackets Integer32,
            lcsStatusPublicSpotStationTableEntryRxPackets Integer32,
            lcsStatusPublicSpotStationTableEntryLoginTime Integer32,
            lcsStatusPublicSpotStationTableEntryState INTEGER,
            lcsStatusPublicSpotStationTableEntrySessionId Integer32,
            lcsStatusPublicSpotStationTableEntrySecExpire Integer32,
            lcsStatusPublicSpotStationTableEntryVolExpire Integer32,
            lcsStatusPublicSpotStationTableEntryAccCycle Integer32,
            lcsStatusPublicSpotStationTableEntryIdleTimeout Integer32,
            lcsStatusPublicSpotStationTableEntryTxLimit Integer32,
            lcsStatusPublicSpotStationTableEntryRxLimit Integer32,
            lcsStatusPublicSpotStationTableEntryPort DisplayString,
            lcsStatusPublicSpotStationTableEntryOrigHost DisplayString,
            lcsStatusPublicSpotStationTableEntryVlanId Integer32,
            lcsStatusPublicSpotStationTableEntryVolExpireMbytes Integer32,
            lcsStatusPublicSpotStationTableEntryTxBytesNew Counter64,
            lcsStatusPublicSpotStationTableEntryRxBytesNew Counter64,
            lcsStatusPublicSpotStationTableEntryCircuitId DisplayString,
            lcsStatusPublicSpotStationTableEntryUnauthenticatedBytes Counter64,
            lcsStatusPublicSpotStationTableEntrySourceVlanId Integer32
    }

-- {COLUMN} 1.3.6.1.4.1.2356.11.1.44.1.1.1
lcsStatusPublicSpotStationTableEntryMacAddress OBJECT-TYPE
    SYNTAX     DisplayString (SIZE(0..12))
    MAX-ACCESS read-only
    STATUS     current
    DESCRIPTION
            ""
    ::= { lcsStatusPublicSpotStationTableEntry 1 }

-- {COLUMN} 1.3.6.1.4.1.2356.11.1.44.1.1.2
lcsStatusPublicSpotStationTableEntryIpAddress OBJECT-TYPE
    SYNTAX     DisplayString (SIZE(0..15))
    MAX-ACCESS read-only
    STATUS     current
    DESCRIPTION
            ""
    ::= { lcsStatusPublicSpotStationTableEntry 2 }

-- {COLUMN} 1.3.6.1.4.1.2356.11.1.44.1.1.3
lcsStatusPublicSpotStationTableEntryName OBJECT-TYPE
    SYNTAX     DisplayString (SIZE(0..64))
    MAX-ACCESS read-only
    STATUS     current
    DESCRIPTION
            ""
    ::= { lcsStatusPublicSpotStationTableEntry 3 }

-- {COLUMN} 1.3.6.1.4.1.2356.11.1.44.1.1.4
lcsStatusPublicSpotStationTableEntryProvider OBJECT-TYPE
    SYNTAX     DisplayString (SIZE(0..16))
    MAX-ACCESS read-only
    STATUS     current
    DESCRIPTION
            ""
    ::= { lcsStatusPublicSpotStationTableEntry 4 }

-- {COLUMN} 1.3.6.1.4.1.2356.11.1.44.1.1.5
lcsStatusPublicSpotStationTableEntryTxBytes OBJECT-TYPE
    SYNTAX     Integer32 (0..2147483647)
    MAX-ACCESS read-only
    STATUS     current
    DESCRIPTION
            ""
    ::= { lcsStatusPublicSpotStationTableEntry 5 }

-- {COLUMN} 1.3.6.1.4.1.2356.11.1.44.1.1.6
lcsStatusPublicSpotStationTableEntryRxBytes OBJECT-TYPE
    SYNTAX     Integer32 (0..2147483647)
    MAX-ACCESS read-only
    STATUS     current
    DESCRIPTION
            ""
    ::= { lcsStatusPublicSpotStationTableEntry 6 }

-- {COLUMN} 1.3.6.1.4.1.2356.11.1.44.1.1.7
lcsStatusPublicSpotStationTableEntryTxPackets OBJECT-TYPE
    SYNTAX     Integer32 (0..2147483647)
    MAX-ACCESS read-only
    STATUS     current
    DESCRIPTION
            ""
    ::= { lcsStatusPublicSpotStationTableEntry 7 }

-- {COLUMN} 1.3.6.1.4.1.2356.11.1.44.1.1.8
lcsStatusPublicSpotStationTableEntryRxPackets OBJECT-TYPE
    SYNTAX     Integer32 (0..2147483647)
    MAX-ACCESS read-only
    STATUS     current
    DESCRIPTION
            ""
    ::= { lcsStatusPublicSpotStationTableEntry 8 }

-- {COLUMN} 1.3.6.1.4.1.2356.11.1.44.1.1.9
lcsStatusPublicSpotStationTableEntryLoginTime OBJECT-TYPE
    SYNTAX     Integer32 (0..2147483647)
    MAX-ACCESS read-only
    STATUS     current
    DESCRIPTION
            ""
    ::= { lcsStatusPublicSpotStationTableEntry 9 }

-- {COLUMN} 1.3.6.1.4.1.2356.11.1.44.1.1.10
lcsStatusPublicSpotStationTableEntryState OBJECT-TYPE
    SYNTAX     INTEGER {
                  eUnauthenticated (0),
                  eAuthenticated (1),
                  eDeceased (2),
                  eAdvertisement (4)
            }
    MAX-ACCESS read-only
    STATUS     current
    DESCRIPTION
            ""
    ::= { lcsStatusPublicSpotStationTableEntry 10 }

-- {COLUMN} 1.3.6.1.4.1.2356.11.1.44.1.1.11
lcsStatusPublicSpotStationTableEntrySessionId OBJECT-TYPE
    SYNTAX     Integer32 (0..2147483647)
    MAX-ACCESS read-only
    STATUS     current
    DESCRIPTION
            ""
    ::= { lcsStatusPublicSpotStationTableEntry 11 }

-- {COLUMN} 1.3.6.1.4.1.2356.11.1.44.1.1.12
lcsStatusPublicSpotStationTableEntrySecExpire OBJECT-TYPE
    SYNTAX     Integer32 (0..2147483647)
    MAX-ACCESS read-only
    STATUS     current
    DESCRIPTION
            ""
    ::= { lcsStatusPublicSpotStationTableEntry 12 }

-- {COLUMN} 1.3.6.1.4.1.2356.11.1.44.1.1.13
lcsStatusPublicSpotStationTableEntryVolExpire OBJECT-TYPE
    SYNTAX     Integer32 (0..2147483647)
    MAX-ACCESS read-only
    STATUS     current
    DESCRIPTION
            ""
    ::= { lcsStatusPublicSpotStationTableEntry 13 }

-- {COLUMN} 1.3.6.1.4.1.2356.11.1.44.1.1.14
lcsStatusPublicSpotStationTableEntryAccCycle OBJECT-TYPE
    SYNTAX     Integer32 (0..2147483647)
    MAX-ACCESS read-only
    STATUS     current
    DESCRIPTION
            ""
    ::= { lcsStatusPublicSpotStationTableEntry 14 }

-- {COLUMN} 1.3.6.1.4.1.2356.11.1.44.1.1.16
lcsStatusPublicSpotStationTableEntryIdleTimeout OBJECT-TYPE
    SYNTAX     Integer32 (0..2147483647)
    MAX-ACCESS read-only
    STATUS     current
    DESCRIPTION
            ""
    ::= { lcsStatusPublicSpotStationTableEntry 16 }

-- {COLUMN} 1.3.6.1.4.1.2356.11.1.44.1.1.17
lcsStatusPublicSpotStationTableEntryTxLimit OBJECT-TYPE
    SYNTAX     Integer32 (0..2147483647)
    MAX-ACCESS read-only
    STATUS     current
    DESCRIPTION
            ""
    ::= { lcsStatusPublicSpotStationTableEntry 17 }

-- {COLUMN} 1.3.6.1.4.1.2356.11.1.44.1.1.18
lcsStatusPublicSpotStationTableEntryRxLimit OBJECT-TYPE
    SYNTAX     Integer32 (0..2147483647)
    MAX-ACCESS read-only
    STATUS     current
    DESCRIPTION
            ""
    ::= { lcsStatusPublicSpotStationTableEntry 18 }

-- {COLUMN} 1.3.6.1.4.1.2356.11.1.44.1.1.19
lcsStatusPublicSpotStationTableEntryPort OBJECT-TYPE
    SYNTAX     DisplayString (SIZE(0..18))
    MAX-ACCESS read-only
    STATUS     current
    DESCRIPTION
            ""
    ::= { lcsStatusPublicSpotStationTableEntry 19 }

-- {COLUMN} 1.3.6.1.4.1.2356.11.1.44.1.1.20
lcsStatusPublicSpotStationTableEntryOrigHost OBJECT-TYPE
    SYNTAX     DisplayString (SIZE(0..255))
    MAX-ACCESS read-only
    STATUS     current
    DESCRIPTION
            ""
    ::= { lcsStatusPublicSpotStationTableEntry 20 }

-- {COLUMN} 1.3.6.1.4.1.2356.11.1.44.1.1.21
lcsStatusPublicSpotStationTableEntryVlanId OBJECT-TYPE
    SYNTAX     Integer32 (0..65535)
    MAX-ACCESS read-only
    STATUS     current
    DESCRIPTION
            "-- empty --"
    ::= { lcsStatusPublicSpotStationTableEntry 21 }

-- {COLUMN} 1.3.6.1.4.1.2356.11.1.44.1.1.22
lcsStatusPublicSpotStationTableEntryVolExpireMbytes OBJECT-TYPE
    SYNTAX     Integer32 (0..2147483647)
    MAX-ACCESS read-only
    STATUS     current
    DESCRIPTION
            "-- empty --"
    ::= { lcsStatusPublicSpotStationTableEntry 22 }

-- {COLUMN} 1.3.6.1.4.1.2356.11.1.44.1.1.23
lcsStatusPublicSpotStationTableEntryTxBytesNew OBJECT-TYPE
    SYNTAX     Counter64
    MAX-ACCESS read-only
    STATUS     current
    DESCRIPTION
            "Amount of data sent to the client"
    ::= { lcsStatusPublicSpotStationTableEntry 23 }

-- {COLUMN} 1.3.6.1.4.1.2356.11.1.44.1.1.24
lcsStatusPublicSpotStationTableEntryRxBytesNew OBJECT-TYPE
    SYNTAX     Counter64
    MAX-ACCESS read-only
    STATUS     current
    DESCRIPTION
            "Amount of data received from the client"
    ::= { lcsStatusPublicSpotStationTableEntry 24 }

-- {COLUMN} 1.3.6.1.4.1.2356.11.1.44.1.1.25
lcsStatusPublicSpotStationTableEntryCircuitId OBJECT-TYPE
    SYNTAX     DisplayString (SIZE(0..64))
    MAX-ACCESS read-only
    STATUS     current
    DESCRIPTION
            "-- empty --"
    ::= { lcsStatusPublicSpotStationTableEntry 25 }

-- {COLUMN} 1.3.6.1.4.1.2356.11.1.44.1.1.26
lcsStatusPublicSpotStationTableEntryUnauthenticatedBytes OBJECT-TYPE
    SYNTAX     Counter64
    MAX-ACCESS read-only
    STATUS     current
    DESCRIPTION
            "-- empty --"
    ::= { lcsStatusPublicSpotStationTableEntry 26 }

-- {COLUMN} 1.3.6.1.4.1.2356.11.1.44.1.1.27
lcsStatusPublicSpotStationTableEntrySourceVlanId OBJECT-TYPE
    SYNTAX     Integer32 (0..65535)
    MAX-ACCESS read-only
    STATUS     current
    DESCRIPTION
            "-- empty --"
    ::= { lcsStatusPublicSpotStationTableEntry 27 }

-- {SCALAR} 1.3.6.1.4.1.2356.11.1.44.2
lcsStatusPublicSpotDeleteStation OBJECT-TYPE
    SYNTAX     DisplayString
    MAX-ACCESS read-write
    STATUS     current
    DESCRIPTION
            ""
    ::= { lcsStatusPublicSpot 2 }

-- {SCALAR} 1.3.6.1.4.1.2356.11.1.44.3
lcsStatusPublicSpotCleanupTable OBJECT-TYPE
    SYNTAX     DisplayString
    MAX-ACCESS read-write
    STATUS     current
    DESCRIPTION
            ""
    ::= { lcsStatusPublicSpot 3 }

-- {SCALAR} 1.3.6.1.4.1.2356.11.1.44.4
lcsStatusPublicSpotDeleteValues OBJECT-TYPE
    SYNTAX     DisplayString
    MAX-ACCESS read-write
    STATUS     current
    DESCRIPTION
            ""
    ::= { lcsStatusPublicSpot 4 }

-- {SCALAR} 1.3.6.1.4.1.2356.11.1.44.5
lcsStatusPublicSpotDisconnectUser OBJECT-TYPE
    SYNTAX     DisplayString
    MAX-ACCESS read-write
    STATUS     current
    DESCRIPTION
            ""
    ::= { lcsStatusPublicSpot 5 }

-- {TABLE} 1.3.6.1.4.1.2356.11.1.44.6
lcsStatusPublicSpotLogTableTable OBJECT-TYPE
    SYNTAX     SEQUENCE OF LcsStatusPublicSpotLogTableEntry
    MAX-ACCESS not-accessible
    STATUS     current
    DESCRIPTION
            ""
    ::= { lcsStatusPublicSpot 6 }

-- {ROW} 1.3.6.1.4.1.2356.11.1.44.6.1
lcsStatusPublicSpotLogTableEntry OBJECT-TYPE
    SYNTAX     LcsStatusPublicSpotLogTableEntry
    MAX-ACCESS not-accessible
    STATUS     current
    DESCRIPTION
            ""
    INDEX {
            lcsStatusPublicSpotLogTableEntryIndex
          }
    ::= { lcsStatusPublicSpotLogTableTable 1 }

LcsStatusPublicSpotLogTableEntry ::= SEQUENCE {
            lcsStatusPublicSpotLogTableEntryIndex Integer32,
            lcsStatusPublicSpotLogTableEntryTime DisplayString,
            lcsStatusPublicSpotLogTableEntryEvent DisplayString
    }

-- {COLUMN} 1.3.6.1.4.1.2356.11.1.44.6.1.1
lcsStatusPublicSpotLogTableEntryIndex OBJECT-TYPE
    SYNTAX     Integer32 (0..2147483647)
    MAX-ACCESS read-only
    STATUS     current
    DESCRIPTION
            ""
    ::= { lcsStatusPublicSpotLogTableEntry 1 }

-- {COLUMN} 1.3.6.1.4.1.2356.11.1.44.6.1.2
lcsStatusPublicSpotLogTableEntryTime OBJECT-TYPE
    SYNTAX     DisplayString (SIZE(0..21))
    MAX-ACCESS read-only
    STATUS     current
    DESCRIPTION
            ""
    ::= { lcsStatusPublicSpotLogTableEntry 2 }

-- {COLUMN} 1.3.6.1.4.1.2356.11.1.44.6.1.3
lcsStatusPublicSpotLogTableEntryEvent OBJECT-TYPE
    SYNTAX     DisplayString (SIZE(0..252))
    MAX-ACCESS read-only
    STATUS     current
    DESCRIPTION
            ""
    ::= { lcsStatusPublicSpotLogTableEntry 3 }

-- {TABLE} 1.3.6.1.4.1.2356.11.1.44.7
lcsStatusPublicSpotRadiusMacCheckCacheTable OBJECT-TYPE
    SYNTAX     SEQUENCE OF LcsStatusPublicSpotRadiusMacCheckCacheEntry
    MAX-ACCESS not-accessible
    STATUS     current
    DESCRIPTION
            ""
    ::= { lcsStatusPublicSpot 7 }

-- {ROW} 1.3.6.1.4.1.2356.11.1.44.7.1
lcsStatusPublicSpotRadiusMacCheckCacheEntry OBJECT-TYPE
    SYNTAX     LcsStatusPublicSpotRadiusMacCheckCacheEntry
    MAX-ACCESS not-accessible
    STATUS     current
    DESCRIPTION
            ""
    INDEX {
            lcsStatusPublicSpotRadiusMacCheckCacheEntryMacAddress
          }
    ::= { lcsStatusPublicSpotRadiusMacCheckCacheTable 1 }

LcsStatusPublicSpotRadiusMacCheckCacheEntry ::= SEQUENCE {
            lcsStatusPublicSpotRadiusMacCheckCacheEntryMacAddress MacAddress,
            lcsStatusPublicSpotRadiusMacCheckCacheEntryState INTEGER,
            lcsStatusPublicSpotRadiusMacCheckCacheEntryAge Integer32,
            lcsStatusPublicSpotRadiusMacCheckCacheEntryResponseAge Integer32
    }

-- {COLUMN} 1.3.6.1.4.1.2356.11.1.44.7.1.1
lcsStatusPublicSpotRadiusMacCheckCacheEntryMacAddress OBJECT-TYPE
    SYNTAX     MacAddress
    MAX-ACCESS read-only
    STATUS     current
    DESCRIPTION
            ""
    ::= { lcsStatusPublicSpotRadiusMacCheckCacheEntry 1 }

-- {COLUMN} 1.3.6.1.4.1.2356.11.1.44.7.1.2
lcsStatusPublicSpotRadiusMacCheckCacheEntryState OBJECT-TYPE
    SYNTAX     INTEGER {
                  ePending (1),
                  eReject (2),
                  eAccept (3)
            }
    MAX-ACCESS read-only
    STATUS     current
    DESCRIPTION
            ""
    ::= { lcsStatusPublicSpotRadiusMacCheckCacheEntry 2 }

-- {COLUMN} 1.3.6.1.4.1.2356.11.1.44.7.1.3
lcsStatusPublicSpotRadiusMacCheckCacheEntryAge OBJECT-TYPE
    SYNTAX     Integer32 (0..2147483647)
    MAX-ACCESS read-only
    STATUS     current
    DESCRIPTION
            ""
    ::= { lcsStatusPublicSpotRadiusMacCheckCacheEntry 3 }

-- {COLUMN} 1.3.6.1.4.1.2356.11.1.44.7.1.4
lcsStatusPublicSpotRadiusMacCheckCacheEntryResponseAge OBJECT-TYPE
    SYNTAX     Integer32 (0..2147483647)
    MAX-ACCESS read-only
    STATUS     current
    DESCRIPTION
            ""
    ::= { lcsStatusPublicSpotRadiusMacCheckCacheEntry 4 }

-- {NODE} 1.3.6.1.4.1.2356.11.1.44.8
lcsStatusPublicSpotAutoReLogin OBJECT IDENTIFIER ::= { lcsStatusPublicSpot 8 }

-- {TABLE} 1.3.6.1.4.1.2356.11.1.44.8.1
lcsStatusPublicSpotAutoReLoginStationTableTable OBJECT-TYPE
    SYNTAX     SEQUENCE OF LcsStatusPublicSpotAutoReLoginStationTableEntry
    MAX-ACCESS not-accessible
    STATUS     current
    DESCRIPTION
            "-- empty --"
    ::= { lcsStatusPublicSpotAutoReLogin 1 }

-- {ROW} 1.3.6.1.4.1.2356.11.1.44.8.1.1
lcsStatusPublicSpotAutoReLoginStationTableEntry OBJECT-TYPE
    SYNTAX     LcsStatusPublicSpotAutoReLoginStationTableEntry
    MAX-ACCESS not-accessible
    STATUS     current
    DESCRIPTION
            ""
    INDEX {
            lcsStatusPublicSpotAutoReLoginStationTableEntryMacAddress
          }
    ::= { lcsStatusPublicSpotAutoReLoginStationTableTable 1 }

LcsStatusPublicSpotAutoReLoginStationTableEntry ::= SEQUENCE {
            lcsStatusPublicSpotAutoReLoginStationTableEntryMacAddress MacAddress,
            lcsStatusPublicSpotAutoReLoginStationTableEntryIpAddress DisplayString,
            lcsStatusPublicSpotAutoReLoginStationTableEntryUserName DisplayString,
            lcsStatusPublicSpotAutoReLoginStationTableEntryExistTimeout Integer32,
            lcsStatusPublicSpotAutoReLoginStationTableEntryActive INTEGER,
            lcsStatusPublicSpotAutoReLoginStationTableEntrySecExpire Integer32,
            lcsStatusPublicSpotAutoReLoginStationTableEntryVolExpireMbytes Integer32
    }

-- {COLUMN} 1.3.6.1.4.1.2356.11.1.44.8.1.1.1
lcsStatusPublicSpotAutoReLoginStationTableEntryMacAddress OBJECT-TYPE
    SYNTAX     MacAddress
    MAX-ACCESS read-only
    STATUS     current
    DESCRIPTION
            "-- empty --"
    ::= { lcsStatusPublicSpotAutoReLoginStationTableEntry 1 }

-- {COLUMN} 1.3.6.1.4.1.2356.11.1.44.8.1.1.2
lcsStatusPublicSpotAutoReLoginStationTableEntryIpAddress OBJECT-TYPE
    SYNTAX     DisplayString (SIZE(0..15))
    MAX-ACCESS read-only
    STATUS     current
    DESCRIPTION
            "-- empty --"
    ::= { lcsStatusPublicSpotAutoReLoginStationTableEntry 2 }

-- {COLUMN} 1.3.6.1.4.1.2356.11.1.44.8.1.1.3
lcsStatusPublicSpotAutoReLoginStationTableEntryUserName OBJECT-TYPE
    SYNTAX     DisplayString (SIZE(0..64))
    MAX-ACCESS read-only
    STATUS     current
    DESCRIPTION
            "-- empty --"
    ::= { lcsStatusPublicSpotAutoReLoginStationTableEntry 3 }

-- {COLUMN} 1.3.6.1.4.1.2356.11.1.44.8.1.1.4
lcsStatusPublicSpotAutoReLoginStationTableEntryExistTimeout OBJECT-TYPE
    SYNTAX     Integer32 (0..2147483647)
    MAX-ACCESS read-only
    STATUS     current
    DESCRIPTION
            "-- empty --"
    ::= { lcsStatusPublicSpotAutoReLoginStationTableEntry 4 }

-- {COLUMN} 1.3.6.1.4.1.2356.11.1.44.8.1.1.5
lcsStatusPublicSpotAutoReLoginStationTableEntryActive OBJECT-TYPE
    SYNTAX     INTEGER {
                  eNo (0),
                  eYes (1)
            }
    MAX-ACCESS read-only
    STATUS     current
    DESCRIPTION
            "-- empty --"
    ::= { lcsStatusPublicSpotAutoReLoginStationTableEntry 5 }

-- {COLUMN} 1.3.6.1.4.1.2356.11.1.44.8.1.1.6
lcsStatusPublicSpotAutoReLoginStationTableEntrySecExpire OBJECT-TYPE
    SYNTAX     Integer32 (0..2147483647)
    MAX-ACCESS read-only
    STATUS     current
    DESCRIPTION
            "-- empty --"
    ::= { lcsStatusPublicSpotAutoReLoginStationTableEntry 6 }

-- {COLUMN} 1.3.6.1.4.1.2356.11.1.44.8.1.1.7
lcsStatusPublicSpotAutoReLoginStationTableEntryVolExpireMbytes OBJECT-TYPE
    SYNTAX     Integer32 (0..2147483647)
    MAX-ACCESS read-only
    STATUS     current
    DESCRIPTION
            "-- empty --"
    ::= { lcsStatusPublicSpotAutoReLoginStationTableEntry 7 }

-- {SCALAR} 1.3.6.1.4.1.2356.11.1.44.8.2
lcsStatusPublicSpotAutoReLoginDeleteStation OBJECT-TYPE
    SYNTAX     DisplayString
    MAX-ACCESS read-write
    STATUS     current
    DESCRIPTION
            "-- empty --"
    ::= { lcsStatusPublicSpotAutoReLogin 2 }

-- {SCALAR} 1.3.6.1.4.1.2356.11.1.44.9
lcsStatusPublicSpotFlushTemplateCache OBJECT-TYPE
    SYNTAX     DisplayString
    MAX-ACCESS read-write
    STATUS     current
    DESCRIPTION
            "-- empty --"
    ::= { lcsStatusPublicSpot 9 }

-- {NODE} 1.3.6.1.4.1.2356.11.1.44.10
lcsStatusPublicSpotAdvertisement OBJECT IDENTIFIER ::= { lcsStatusPublicSpot 10 }

-- {TABLE} 1.3.6.1.4.1.2356.11.1.44.10.1
lcsStatusPublicSpotAdvertisementFreeNetworksTable OBJECT-TYPE
    SYNTAX     SEQUENCE OF LcsStatusPublicSpotAdvertisementFreeNetworksEntry
    MAX-ACCESS not-accessible
    STATUS     current
    DESCRIPTION
            "-- empty --"
    ::= { lcsStatusPublicSpotAdvertisement 1 }

-- {ROW} 1.3.6.1.4.1.2356.11.1.44.10.1.1
lcsStatusPublicSpotAdvertisementFreeNetworksEntry OBJECT-TYPE
    SYNTAX     LcsStatusPublicSpotAdvertisementFreeNetworksEntry
    MAX-ACCESS not-accessible
    STATUS     current
    DESCRIPTION
            ""
    INDEX {
            lcsStatusPublicSpotAdvertisementFreeNetworksEntryHostName
          }
    ::= { lcsStatusPublicSpotAdvertisementFreeNetworksTable 1 }

LcsStatusPublicSpotAdvertisementFreeNetworksEntry ::= SEQUENCE {
            lcsStatusPublicSpotAdvertisementFreeNetworksEntryHostName IpAddress,
            lcsStatusPublicSpotAdvertisementFreeNetworksEntryMask IpAddress
    }

-- {COLUMN} 1.3.6.1.4.1.2356.11.1.44.10.1.1.1
lcsStatusPublicSpotAdvertisementFreeNetworksEntryHostName OBJECT-TYPE
    SYNTAX     IpAddress
    MAX-ACCESS read-only
    STATUS     current
    DESCRIPTION
            "-- empty --"
    ::= { lcsStatusPublicSpotAdvertisementFreeNetworksEntry 1 }

-- {COLUMN} 1.3.6.1.4.1.2356.11.1.44.10.1.1.2
lcsStatusPublicSpotAdvertisementFreeNetworksEntryMask OBJECT-TYPE
    SYNTAX     IpAddress
    MAX-ACCESS read-only
    STATUS     current
    DESCRIPTION
            "-- empty --"
    ::= { lcsStatusPublicSpotAdvertisementFreeNetworksEntry 2 }

-- {TABLE} 1.3.6.1.4.1.2356.11.1.44.10.2
lcsStatusPublicSpotAdvertisementFreeHostsTable OBJECT-TYPE
    SYNTAX     SEQUENCE OF LcsStatusPublicSpotAdvertisementFreeHostsEntry
    MAX-ACCESS not-accessible
    STATUS     current
    DESCRIPTION
            "-- empty --"
    ::= { lcsStatusPublicSpotAdvertisement 2 }

-- {ROW} 1.3.6.1.4.1.2356.11.1.44.10.2.1
lcsStatusPublicSpotAdvertisementFreeHostsEntry OBJECT-TYPE
    SYNTAX     LcsStatusPublicSpotAdvertisementFreeHostsEntry
    MAX-ACCESS not-accessible
    STATUS     current
    DESCRIPTION
            ""
    INDEX {
            lcsStatusPublicSpotAdvertisementFreeHostsEntryAddress,
            lcsStatusPublicSpotAdvertisementFreeHostsEntryHostName,
            lcsStatusPublicSpotAdvertisementFreeHostsEntrySource
          }
    ::= { lcsStatusPublicSpotAdvertisementFreeHostsTable 1 }

LcsStatusPublicSpotAdvertisementFreeHostsEntry ::= SEQUENCE {
            lcsStatusPublicSpotAdvertisementFreeHostsEntryAddress IpAddress,
            lcsStatusPublicSpotAdvertisementFreeHostsEntryHostName DisplayString,
            lcsStatusPublicSpotAdvertisementFreeHostsEntrySource INTEGER,
            lcsStatusPublicSpotAdvertisementFreeHostsEntryTtl Integer32,
            lcsStatusPublicSpotAdvertisementFreeHostsEntryAge Integer32
    }

-- {COLUMN} 1.3.6.1.4.1.2356.11.1.44.10.2.1.1
lcsStatusPublicSpotAdvertisementFreeHostsEntryAddress OBJECT-TYPE
    SYNTAX     IpAddress
    MAX-ACCESS read-only
    STATUS     current
    DESCRIPTION
            "-- empty --"
    ::= { lcsStatusPublicSpotAdvertisementFreeHostsEntry 1 }

-- {COLUMN} 1.3.6.1.4.1.2356.11.1.44.10.2.1.2
lcsStatusPublicSpotAdvertisementFreeHostsEntryHostName OBJECT-TYPE
    SYNTAX     DisplayString (SIZE(0..64))
    MAX-ACCESS read-only
    STATUS     current
    DESCRIPTION
            "-- empty --"
    ::= { lcsStatusPublicSpotAdvertisementFreeHostsEntry 2 }

-- {COLUMN} 1.3.6.1.4.1.2356.11.1.44.10.2.1.3
lcsStatusPublicSpotAdvertisementFreeHostsEntrySource OBJECT-TYPE
    SYNTAX     INTEGER {
                  eNone (0),
                  eDynamic (1),
                  eStatic (2)
            }
    MAX-ACCESS read-only
    STATUS     current
    DESCRIPTION
            "-- empty --"
    ::= { lcsStatusPublicSpotAdvertisementFreeHostsEntry 3 }

-- {COLUMN} 1.3.6.1.4.1.2356.11.1.44.10.2.1.4
lcsStatusPublicSpotAdvertisementFreeHostsEntryTtl OBJECT-TYPE
    SYNTAX     Integer32 (0..2147483647)
    MAX-ACCESS read-only
    STATUS     current
    DESCRIPTION
            "-- empty --"
    ::= { lcsStatusPublicSpotAdvertisementFreeHostsEntry 4 }

-- {COLUMN} 1.3.6.1.4.1.2356.11.1.44.10.2.1.5
lcsStatusPublicSpotAdvertisementFreeHostsEntryAge OBJECT-TYPE
    SYNTAX     Integer32 (0..2147483647)
    MAX-ACCESS read-only
    STATUS     current
    DESCRIPTION
            "-- empty --"
    ::= { lcsStatusPublicSpotAdvertisementFreeHostsEntry 5 }

-- {SCALAR} 1.3.6.1.4.1.2356.11.1.44.11
lcsStatusPublicSpotMaxNbUsers OBJECT-TYPE
    SYNTAX     Integer32 (0..2147483647)
    MAX-ACCESS read-only
    STATUS     current
    DESCRIPTION
            "-- empty --"
    ::= { lcsStatusPublicSpot 11 }

-- {SCALAR} 1.3.6.1.4.1.2356.11.1.44.12
lcsStatusPublicSpotPbspotAuthenticatedUsers OBJECT-TYPE
    SYNTAX     Integer32 (0..2147483647)
    MAX-ACCESS read-only
    STATUS     current
    DESCRIPTION
            "-- empty --"
    ::= { lcsStatusPublicSpot 12 }

-- {SCALAR} 1.3.6.1.4.1.2356.11.1.44.13
lcsStatusPublicSpotPmsAuthenticatedUsers OBJECT-TYPE
    SYNTAX     Integer32 (0..2147483647)
    MAX-ACCESS read-only
    STATUS     current
    DESCRIPTION
            "-- empty --"
    ::= { lcsStatusPublicSpot 13 }

-- {SCALAR} 1.3.6.1.4.1.2356.11.1.44.14
lcsStatusPublicSpotPbspotNbVoucher OBJECT-TYPE
    SYNTAX     Integer32 (0..2147483647)
    MAX-ACCESS read-only
    STATUS     current
    DESCRIPTION
            "-- empty --"
    ::= { lcsStatusPublicSpot 14 }

-- {SCALAR} 1.3.6.1.4.1.2356.11.1.44.15
lcsStatusPublicSpotRedirectTlsConnections OBJECT-TYPE
    SYNTAX     INTEGER {
                  eNo (0),
                  eYes (1)
            }
    MAX-ACCESS read-only
    STATUS     current
    DESCRIPTION
            "-- empty --"
    ::= { lcsStatusPublicSpot 15 }

-- {SCALAR} 1.3.6.1.4.1.2356.11.1.44.16
lcsStatusPublicSpotRecommendedCapacityReached OBJECT-TYPE
    SYNTAX     INTEGER {
                  eNo (0),
                  e80PercentExceeded (1),
                  e100PercentExceeded (2)
            }
    MAX-ACCESS read-only
    STATUS     current
    DESCRIPTION
            "-- empty --"
    ::= { lcsStatusPublicSpot 16 }

-- {NODE} 1.3.6.1.4.1.2356.11.1.44.17
lcsStatusPublicSpotFreeLogin OBJECT IDENTIFIER ::= { lcsStatusPublicSpot 17 }

-- {TABLE} 1.3.6.1.4.1.2356.11.1.44.17.1
lcsStatusPublicSpotFreeLoginUsersTable OBJECT-TYPE
    SYNTAX     SEQUENCE OF LcsStatusPublicSpotFreeLoginUsersEntry
    MAX-ACCESS not-accessible
    STATUS     current
    DESCRIPTION
            "-- empty --"
    ::= { lcsStatusPublicSpotFreeLogin 1 }

-- {ROW} 1.3.6.1.4.1.2356.11.1.44.17.1.1
lcsStatusPublicSpotFreeLoginUsersEntry OBJECT-TYPE
    SYNTAX     LcsStatusPublicSpotFreeLoginUsersEntry
    MAX-ACCESS not-accessible
    STATUS     current
    DESCRIPTION
            ""
    INDEX {
            lcsStatusPublicSpotFreeLoginUsersEntryUsername
          }
    ::= { lcsStatusPublicSpotFreeLoginUsersTable 1 }

LcsStatusPublicSpotFreeLoginUsersEntry ::= SEQUENCE {
            lcsStatusPublicSpotFreeLoginUsersEntryUsername DisplayString,
            lcsStatusPublicSpotFreeLoginUsersEntryCreated Gauge32,
            lcsStatusPublicSpotFreeLoginUsersEntryEMail DisplayString
    }

-- {COLUMN} 1.3.6.1.4.1.2356.11.1.44.17.1.1.1
lcsStatusPublicSpotFreeLoginUsersEntryUsername OBJECT-TYPE
    SYNTAX     DisplayString (SIZE(0..64))
    MAX-ACCESS read-only
    STATUS     current
    DESCRIPTION
            "-- empty --"
    ::= { lcsStatusPublicSpotFreeLoginUsersEntry 1 }

-- {COLUMN} 1.3.6.1.4.1.2356.11.1.44.17.1.1.2
lcsStatusPublicSpotFreeLoginUsersEntryCreated OBJECT-TYPE
    SYNTAX     Gauge32
    MAX-ACCESS read-only
    STATUS     current
    DESCRIPTION
            "-- empty --"
    ::= { lcsStatusPublicSpotFreeLoginUsersEntry 2 }

-- {COLUMN} 1.3.6.1.4.1.2356.11.1.44.17.1.1.3
lcsStatusPublicSpotFreeLoginUsersEntryEMail OBJECT-TYPE
    SYNTAX     DisplayString (SIZE(0..64))
    MAX-ACCESS read-only
    STATUS     current
    DESCRIPTION
            "-- empty --"
    ::= { lcsStatusPublicSpotFreeLoginUsersEntry 3 }

-- {SCALAR} 1.3.6.1.4.1.2356.11.1.44.17.2
lcsStatusPublicSpotFreeLoginDeleteUser OBJECT-TYPE
    SYNTAX     DisplayString
    MAX-ACCESS read-write
    STATUS     current
    DESCRIPTION
            "-- empty --"
    ::= { lcsStatusPublicSpotFreeLogin 2 }

-- {TABLE} 1.3.6.1.4.1.2356.11.1.44.30
lcsStatusPublicSpotFreeNetworksTable OBJECT-TYPE
    SYNTAX     SEQUENCE OF LcsStatusPublicSpotFreeNetworksEntry
    MAX-ACCESS not-accessible
    STATUS     current
    DESCRIPTION
            ""
    ::= { lcsStatusPublicSpot 30 }

-- {ROW} 1.3.6.1.4.1.2356.11.1.44.30.1
lcsStatusPublicSpotFreeNetworksEntry OBJECT-TYPE
    SYNTAX     LcsStatusPublicSpotFreeNetworksEntry
    MAX-ACCESS not-accessible
    STATUS     current
    DESCRIPTION
            ""
    INDEX {
            lcsStatusPublicSpotFreeNetworksEntryHostName
          }
    ::= { lcsStatusPublicSpotFreeNetworksTable 1 }

LcsStatusPublicSpotFreeNetworksEntry ::= SEQUENCE {
            lcsStatusPublicSpotFreeNetworksEntryHostName DisplayString,
            lcsStatusPublicSpotFreeNetworksEntryAddress IpAddress,
            lcsStatusPublicSpotFreeNetworksEntryMask IpAddress,
            lcsStatusPublicSpotFreeNetworksEntryTtl Integer32,
            lcsStatusPublicSpotFreeNetworksEntryAge Integer32
    }

-- {COLUMN} 1.3.6.1.4.1.2356.11.1.44.30.1.1
lcsStatusPublicSpotFreeNetworksEntryHostName OBJECT-TYPE
    SYNTAX     DisplayString (SIZE(0..64))
    MAX-ACCESS read-only
    STATUS     current
    DESCRIPTION
            ""
    ::= { lcsStatusPublicSpotFreeNetworksEntry 1 }

-- {COLUMN} 1.3.6.1.4.1.2356.11.1.44.30.1.2
lcsStatusPublicSpotFreeNetworksEntryAddress OBJECT-TYPE
    SYNTAX     IpAddress
    MAX-ACCESS read-only
    STATUS     current
    DESCRIPTION
            ""
    ::= { lcsStatusPublicSpotFreeNetworksEntry 2 }

-- {COLUMN} 1.3.6.1.4.1.2356.11.1.44.30.1.3
lcsStatusPublicSpotFreeNetworksEntryMask OBJECT-TYPE
    SYNTAX     IpAddress
    MAX-ACCESS read-only
    STATUS     current
    DESCRIPTION
            ""
    ::= { lcsStatusPublicSpotFreeNetworksEntry 3 }

-- {COLUMN} 1.3.6.1.4.1.2356.11.1.44.30.1.4
lcsStatusPublicSpotFreeNetworksEntryTtl OBJECT-TYPE
    SYNTAX     Integer32 (0..2147483647)
    MAX-ACCESS read-only
    STATUS     current
    DESCRIPTION
            ""
    ::= { lcsStatusPublicSpotFreeNetworksEntry 4 }

-- {COLUMN} 1.3.6.1.4.1.2356.11.1.44.30.1.5
lcsStatusPublicSpotFreeNetworksEntryAge OBJECT-TYPE
    SYNTAX     Integer32 (0..2147483647)
    MAX-ACCESS read-only
    STATUS     current
    DESCRIPTION
            ""
    ::= { lcsStatusPublicSpotFreeNetworksEntry 5 }

-- {TABLE} 1.3.6.1.4.1.2356.11.1.44.31
lcsStatusPublicSpotFreeNetsTable OBJECT-TYPE
    SYNTAX     SEQUENCE OF LcsStatusPublicSpotFreeNetsEntry
    MAX-ACCESS not-accessible
    STATUS     current
    DESCRIPTION
            ""
    ::= { lcsStatusPublicSpot 31 }

-- {ROW} 1.3.6.1.4.1.2356.11.1.44.31.1
lcsStatusPublicSpotFreeNetsEntry OBJECT-TYPE
    SYNTAX     LcsStatusPublicSpotFreeNetsEntry
    MAX-ACCESS not-accessible
    STATUS     current
    DESCRIPTION
            ""
    INDEX {
            lcsStatusPublicSpotFreeNetsEntryAddress
          }
    ::= { lcsStatusPublicSpotFreeNetsTable 1 }

LcsStatusPublicSpotFreeNetsEntry ::= SEQUENCE {
            lcsStatusPublicSpotFreeNetsEntryAddress IpAddress,
            lcsStatusPublicSpotFreeNetsEntryMask IpAddress,
            lcsStatusPublicSpotFreeNetsEntryVlans DisplayString
    }

-- {COLUMN} 1.3.6.1.4.1.2356.11.1.44.31.1.1
lcsStatusPublicSpotFreeNetsEntryAddress OBJECT-TYPE
    SYNTAX     IpAddress
    MAX-ACCESS read-only
    STATUS     current
    DESCRIPTION
            "-- empty --"
    ::= { lcsStatusPublicSpotFreeNetsEntry 1 }

-- {COLUMN} 1.3.6.1.4.1.2356.11.1.44.31.1.2
lcsStatusPublicSpotFreeNetsEntryMask OBJECT-TYPE
    SYNTAX     IpAddress
    MAX-ACCESS read-only
    STATUS     current
    DESCRIPTION
            "-- empty --"
    ::= { lcsStatusPublicSpotFreeNetsEntry 2 }

-- {COLUMN} 1.3.6.1.4.1.2356.11.1.44.31.1.3
lcsStatusPublicSpotFreeNetsEntryVlans OBJECT-TYPE
    SYNTAX     DisplayString (SIZE(0..254))
    MAX-ACCESS read-only
    STATUS     current
    DESCRIPTION
            "-- empty --"
    ::= { lcsStatusPublicSpotFreeNetsEntry 3 }

-- {TABLE} 1.3.6.1.4.1.2356.11.1.44.32
lcsStatusPublicSpotFreeHostsTable OBJECT-TYPE
    SYNTAX     SEQUENCE OF LcsStatusPublicSpotFreeHostsEntry
    MAX-ACCESS not-accessible
    STATUS     current
    DESCRIPTION
            "-- empty --"
    ::= { lcsStatusPublicSpot 32 }

-- {ROW} 1.3.6.1.4.1.2356.11.1.44.32.1
lcsStatusPublicSpotFreeHostsEntry OBJECT-TYPE
    SYNTAX     LcsStatusPublicSpotFreeHostsEntry
    MAX-ACCESS not-accessible
    STATUS     current
    DESCRIPTION
            ""
    INDEX {
            lcsStatusPublicSpotFreeHostsEntryAddress,
            lcsStatusPublicSpotFreeHostsEntryHostName,
            lcsStatusPublicSpotFreeHostsEntrySource
          }
    ::= { lcsStatusPublicSpotFreeHostsTable 1 }

LcsStatusPublicSpotFreeHostsEntry ::= SEQUENCE {
            lcsStatusPublicSpotFreeHostsEntryAddress IpAddress,
            lcsStatusPublicSpotFreeHostsEntryHostName DisplayString,
            lcsStatusPublicSpotFreeHostsEntrySource INTEGER,
            lcsStatusPublicSpotFreeHostsEntryTtl Integer32,
            lcsStatusPublicSpotFreeHostsEntryAge Integer32,
            lcsStatusPublicSpotFreeHostsEntryVlans DisplayString
    }

-- {COLUMN} 1.3.6.1.4.1.2356.11.1.44.32.1.1
lcsStatusPublicSpotFreeHostsEntryAddress OBJECT-TYPE
    SYNTAX     IpAddress
    MAX-ACCESS read-only
    STATUS     current
    DESCRIPTION
            "-- empty --"
    ::= { lcsStatusPublicSpotFreeHostsEntry 1 }

-- {COLUMN} 1.3.6.1.4.1.2356.11.1.44.32.1.2
lcsStatusPublicSpotFreeHostsEntryHostName OBJECT-TYPE
    SYNTAX     DisplayString (SIZE(0..64))
    MAX-ACCESS read-only
    STATUS     current
    DESCRIPTION
            "-- empty --"
    ::= { lcsStatusPublicSpotFreeHostsEntry 2 }

-- {COLUMN} 1.3.6.1.4.1.2356.11.1.44.32.1.3
lcsStatusPublicSpotFreeHostsEntrySource OBJECT-TYPE
    SYNTAX     INTEGER {
                  eNone (0),
                  eDynamic (1),
                  eStatic (2)
            }
    MAX-ACCESS read-only
    STATUS     current
    DESCRIPTION
            "-- empty --"
    ::= { lcsStatusPublicSpotFreeHostsEntry 3 }

-- {COLUMN} 1.3.6.1.4.1.2356.11.1.44.32.1.4
lcsStatusPublicSpotFreeHostsEntryTtl OBJECT-TYPE
    SYNTAX     Integer32 (0..2147483647)
    MAX-ACCESS read-only
    STATUS     current
    DESCRIPTION
            "-- empty --"
    ::= { lcsStatusPublicSpotFreeHostsEntry 4 }

-- {COLUMN} 1.3.6.1.4.1.2356.11.1.44.32.1.5
lcsStatusPublicSpotFreeHostsEntryAge OBJECT-TYPE
    SYNTAX     Integer32 (0..2147483647)
    MAX-ACCESS read-only
    STATUS     current
    DESCRIPTION
            "-- empty --"
    ::= { lcsStatusPublicSpotFreeHostsEntry 5 }

-- {COLUMN} 1.3.6.1.4.1.2356.11.1.44.32.1.6
lcsStatusPublicSpotFreeHostsEntryVlans OBJECT-TYPE
    SYNTAX     DisplayString (SIZE(0..254))
    MAX-ACCESS read-only
    STATUS     current
    DESCRIPTION
            "-- empty --"
    ::= { lcsStatusPublicSpotFreeHostsEntry 6 }

-- {SCALAR} 1.3.6.1.4.1.2356.11.1.44.40
lcsStatusPublicSpotPbspotStatus OBJECT-TYPE
    SYNTAX     INTEGER {
                  eDeactivated (0),
                  eActivated (1)
            }
    MAX-ACCESS read-only
    STATUS     current
    DESCRIPTION
            "-- empty --"
    ::= { lcsStatusPublicSpot 40 }

-- {NODE} 1.3.6.1.4.1.2356.11.1.46
lcsStatusIeee8021x OBJECT IDENTIFIER ::= { lcsStatus 46 }

-- {TABLE} 1.3.6.1.4.1.2356.11.1.46.1
lcsStatusIeee8021xStationTableTable OBJECT-TYPE
    SYNTAX     SEQUENCE OF LcsStatusIeee8021xStationTableEntry
    MAX-ACCESS not-accessible
    STATUS     current
    DESCRIPTION
            ""
    ::= { lcsStatusIeee8021x 1 }

-- {ROW} 1.3.6.1.4.1.2356.11.1.46.1.1
lcsStatusIeee8021xStationTableEntry OBJECT-TYPE
    SYNTAX     LcsStatusIeee8021xStationTableEntry
    MAX-ACCESS not-accessible
    STATUS     current
    DESCRIPTION
            ""
    INDEX {
            lcsStatusIeee8021xStationTableEntryMacAddress
          }
    ::= { lcsStatusIeee8021xStationTableTable 1 }

LcsStatusIeee8021xStationTableEntry ::= SEQUENCE {
            lcsStatusIeee8021xStationTableEntryMacAddress DisplayString,
            lcsStatusIeee8021xStationTableEntryAuthIfc DisplayString,
            lcsStatusIeee8021xStationTableEntrySessionId DisplayString,
            lcsStatusIeee8021xStationTableEntryPortMode INTEGER,
            lcsStatusIeee8021xStationTableEntryPortStatus INTEGER,
            lcsStatusIeee8021xStationTableEntryUserName DisplayString,
            lcsStatusIeee8021xStationTableEntryReplyMsg DisplayString,
            lcsStatusIeee8021xStationTableEntryCommIfc DisplayString
    }

-- {COLUMN} 1.3.6.1.4.1.2356.11.1.46.1.1.1
lcsStatusIeee8021xStationTableEntryMacAddress OBJECT-TYPE
    SYNTAX     DisplayString (SIZE(0..12))
    MAX-ACCESS read-only
    STATUS     current
    DESCRIPTION
            ""
    ::= { lcsStatusIeee8021xStationTableEntry 1 }

-- {COLUMN} 1.3.6.1.4.1.2356.11.1.46.1.1.2
lcsStatusIeee8021xStationTableEntryAuthIfc OBJECT-TYPE
    SYNTAX     DisplayString (SIZE(0..255))
    MAX-ACCESS read-only
    STATUS     current
    DESCRIPTION
            ""
    ::= { lcsStatusIeee8021xStationTableEntry 2 }

-- {COLUMN} 1.3.6.1.4.1.2356.11.1.46.1.1.3
lcsStatusIeee8021xStationTableEntrySessionId OBJECT-TYPE
    SYNTAX     DisplayString (SIZE(0..8))
    MAX-ACCESS read-only
    STATUS     current
    DESCRIPTION
            ""
    ::= { lcsStatusIeee8021xStationTableEntry 3 }

-- {COLUMN} 1.3.6.1.4.1.2356.11.1.46.1.1.4
lcsStatusIeee8021xStationTableEntryPortMode OBJECT-TYPE
    SYNTAX     INTEGER {
                  eForceUnauth (0),
                  eForceAuth (1),
                  eAuto (2)
            }
    MAX-ACCESS read-only
    STATUS     current
    DESCRIPTION
            ""
    ::= { lcsStatusIeee8021xStationTableEntry 4 }

-- {COLUMN} 1.3.6.1.4.1.2356.11.1.46.1.1.5
lcsStatusIeee8021xStationTableEntryPortStatus OBJECT-TYPE
    SYNTAX     INTEGER {
                  eUnauthorized (0),
                  eAuthorized (1)
            }
    MAX-ACCESS read-only
    STATUS     current
    DESCRIPTION
            ""
    ::= { lcsStatusIeee8021xStationTableEntry 5 }

-- {COLUMN} 1.3.6.1.4.1.2356.11.1.46.1.1.6
lcsStatusIeee8021xStationTableEntryUserName OBJECT-TYPE
    SYNTAX     DisplayString (SIZE(0..255))
    MAX-ACCESS read-only
    STATUS     current
    DESCRIPTION
            ""
    ::= { lcsStatusIeee8021xStationTableEntry 6 }

-- {COLUMN} 1.3.6.1.4.1.2356.11.1.46.1.1.7
lcsStatusIeee8021xStationTableEntryReplyMsg OBJECT-TYPE
    SYNTAX     DisplayString (SIZE(0..255))
    MAX-ACCESS read-only
    STATUS     current
    DESCRIPTION
            ""
    ::= { lcsStatusIeee8021xStationTableEntry 7 }

-- {COLUMN} 1.3.6.1.4.1.2356.11.1.46.1.1.8
lcsStatusIeee8021xStationTableEntryCommIfc OBJECT-TYPE
    SYNTAX     DisplayString (SIZE(0..255))
    MAX-ACCESS read-only
    STATUS     current
    DESCRIPTION
            ""
    ::= { lcsStatusIeee8021xStationTableEntry 8 }

-- {SCALAR} 1.3.6.1.4.1.2356.11.1.46.2
lcsStatusIeee8021xForceReauth OBJECT-TYPE
    SYNTAX     DisplayString
    MAX-ACCESS read-write
    STATUS     current
    DESCRIPTION
            "-- empty --"
    ::= { lcsStatusIeee8021x 2 }

-- {TABLE} 1.3.6.1.4.1.2356.11.1.46.3
lcsStatusIeee8021xPortsTable OBJECT-TYPE
    SYNTAX     SEQUENCE OF LcsStatusIeee8021xPortsEntry
    MAX-ACCESS not-accessible
    STATUS     current
    DESCRIPTION
            "-- empty --"
    ::= { lcsStatusIeee8021x 3 }

-- {ROW} 1.3.6.1.4.1.2356.11.1.46.3.1
lcsStatusIeee8021xPortsEntry OBJECT-TYPE
    SYNTAX     LcsStatusIeee8021xPortsEntry
    MAX-ACCESS not-accessible
    STATUS     current
    DESCRIPTION
            ""
    INDEX {
            lcsStatusIeee8021xPortsEntryPort
          }
    ::= { lcsStatusIeee8021xPortsTable 1 }

LcsStatusIeee8021xPortsEntry ::= SEQUENCE {
            lcsStatusIeee8021xPortsEntryPort DisplayString,
            lcsStatusIeee8021xPortsEntryNumAccept Counter32,
            lcsStatusIeee8021xPortsEntryNumReject Counter32,
            lcsStatusIeee8021xPortsEntryNumReauthmaxReached Counter32
    }

-- {COLUMN} 1.3.6.1.4.1.2356.11.1.46.3.1.1
lcsStatusIeee8021xPortsEntryPort OBJECT-TYPE
    SYNTAX     DisplayString (SIZE(0..18))
    MAX-ACCESS read-only
    STATUS     current
    DESCRIPTION
            "-- empty --"
    ::= { lcsStatusIeee8021xPortsEntry 1 }

-- {COLUMN} 1.3.6.1.4.1.2356.11.1.46.3.1.2
lcsStatusIeee8021xPortsEntryNumAccept OBJECT-TYPE
    SYNTAX     Counter32
    MAX-ACCESS read-only
    STATUS     current
    DESCRIPTION
            "-- empty --"
    ::= { lcsStatusIeee8021xPortsEntry 2 }

-- {COLUMN} 1.3.6.1.4.1.2356.11.1.46.3.1.3
lcsStatusIeee8021xPortsEntryNumReject OBJECT-TYPE
    SYNTAX     Counter32
    MAX-ACCESS read-only
    STATUS     current
    DESCRIPTION
            "-- empty --"
    ::= { lcsStatusIeee8021xPortsEntry 3 }

-- {COLUMN} 1.3.6.1.4.1.2356.11.1.46.3.1.4
lcsStatusIeee8021xPortsEntryNumReauthmaxReached OBJECT-TYPE
    SYNTAX     Counter32
    MAX-ACCESS read-only
    STATUS     current
    DESCRIPTION
            "-- empty --"
    ::= { lcsStatusIeee8021xPortsEntry 4 }

-- {SCALAR} 1.3.6.1.4.1.2356.11.1.46.99
lcsStatusIeee8021xDeleteValues OBJECT-TYPE
    SYNTAX     DisplayString
    MAX-ACCESS read-write
    STATUS     current
    DESCRIPTION
            "-- empty --"
    ::= { lcsStatusIeee8021x 99 }

-- {NODE} 1.3.6.1.4.1.2356.11.1.47
lcsStatusHardwareInfo OBJECT IDENTIFIER ::= { lcsStatus 47 }

-- {SCALAR} 1.3.6.1.4.1.2356.11.1.47.1
lcsStatusHardwareInfoCpuType OBJECT-TYPE
    SYNTAX     DisplayString (SIZE(0..49))
    MAX-ACCESS read-only
    STATUS     current
    DESCRIPTION
            ""
    ::= { lcsStatusHardwareInfo 1 }

-- {SCALAR} 1.3.6.1.4.1.2356.11.1.47.2
lcsStatusHardwareInfoCpuClockMhz OBJECT-TYPE
    SYNTAX     Integer32 (0..2147483647)
    MAX-ACCESS read-only
    STATUS     current
    DESCRIPTION
            ""
    ::= { lcsStatusHardwareInfo 2 }

-- {SCALAR} 1.3.6.1.4.1.2356.11.1.47.3
lcsStatusHardwareInfoCpuLoadPercent OBJECT-TYPE
    SYNTAX     Integer32 (0..255)
    MAX-ACCESS read-only
    STATUS     current
    DESCRIPTION
            ""
    ::= { lcsStatusHardwareInfo 3 }

-- {SCALAR} 1.3.6.1.4.1.2356.11.1.47.4
lcsStatusHardwareInfoTotalMemoryKbytes OBJECT-TYPE
    SYNTAX     Integer32 (0..2147483647)
    MAX-ACCESS read-only
    STATUS     current
    DESCRIPTION
            ""
    ::= { lcsStatusHardwareInfo 4 }

-- {SCALAR} 1.3.6.1.4.1.2356.11.1.47.5
lcsStatusHardwareInfoFreeMemoryKbytes OBJECT-TYPE
    SYNTAX     Integer32 (0..2147483647)
    MAX-ACCESS read-only
    STATUS     current
    DESCRIPTION
            ""
    ::= { lcsStatusHardwareInfo 5 }

-- {SCALAR} 1.3.6.1.4.1.2356.11.1.47.6
lcsStatusHardwareInfoModelNumber OBJECT-TYPE
    SYNTAX     DisplayString (SIZE(0..64))
    MAX-ACCESS read-only
    STATUS     current
    DESCRIPTION
            ""
    ::= { lcsStatusHardwareInfo 6 }

-- {SCALAR} 1.3.6.1.4.1.2356.11.1.47.7
lcsStatusHardwareInfoSerialNumber OBJECT-TYPE
    SYNTAX     DisplayString (SIZE(0..18))
    MAX-ACCESS read-only
    STATUS     current
    DESCRIPTION
            ""
    ::= { lcsStatusHardwareInfo 7 }

-- {SCALAR} 1.3.6.1.4.1.2356.11.1.47.8
lcsStatusHardwareInfoBoardRevision OBJECT-TYPE
    SYNTAX     DisplayString (SIZE(0..1))
    MAX-ACCESS read-only
    STATUS     current
    DESCRIPTION
            ""
    ::= { lcsStatusHardwareInfo 8 }

-- {SCALAR} 1.3.6.1.4.1.2356.11.1.47.9
lcsStatusHardwareInfoSwVersion OBJECT-TYPE
    SYNTAX     DisplayString (SIZE(0..39))
    MAX-ACCESS read-only
    STATUS     current
    DESCRIPTION
            ""
    ::= { lcsStatusHardwareInfo 9 }

-- {SCALAR} 1.3.6.1.4.1.2356.11.1.47.10
lcsStatusHardwareInfoEthernetSwitchType OBJECT-TYPE
    SYNTAX     DisplayString (SIZE(0..40))
    MAX-ACCESS read-only
    STATUS     current
    DESCRIPTION
            ""
    ::= { lcsStatusHardwareInfo 10 }

-- {SCALAR} 1.3.6.1.4.1.2356.11.1.47.11
lcsStatusHardwareInfoSecurityEngine OBJECT-TYPE
    SYNTAX     INTEGER {
                  eNo (0),
                  eYes (1)
            }
    MAX-ACCESS read-only
    STATUS     current
    DESCRIPTION
            ""
    ::= { lcsStatusHardwareInfo 11 }

-- {SCALAR} 1.3.6.1.4.1.2356.11.1.47.12
lcsStatusHardwareInfoCpuLoad1sPercent OBJECT-TYPE
    SYNTAX     Integer32 (0..255)
    MAX-ACCESS read-only
    STATUS     current
    DESCRIPTION
            ""
    ::= { lcsStatusHardwareInfo 12 }

-- {SCALAR} 1.3.6.1.4.1.2356.11.1.47.13
lcsStatusHardwareInfoCpuLoad5sPercent OBJECT-TYPE
    SYNTAX     Integer32 (0..255)
    MAX-ACCESS read-only
    STATUS     current
    DESCRIPTION
            ""
    ::= { lcsStatusHardwareInfo 13 }

-- {SCALAR} 1.3.6.1.4.1.2356.11.1.47.14
lcsStatusHardwareInfoCpuLoad60sPercent OBJECT-TYPE
    SYNTAX     Integer32 (0..255)
    MAX-ACCESS read-only
    STATUS     current
    DESCRIPTION
            ""
    ::= { lcsStatusHardwareInfo 14 }

-- {SCALAR} 1.3.6.1.4.1.2356.11.1.47.15
lcsStatusHardwareInfoCpuLoad300sPercent OBJECT-TYPE
    SYNTAX     Integer32 (0..255)
    MAX-ACCESS read-only
    STATUS     current
    DESCRIPTION
            ""
    ::= { lcsStatusHardwareInfo 15 }

-- {NODE} 1.3.6.1.4.1.2356.11.1.47.16
lcsStatusHardwareInfoSecUnit OBJECT IDENTIFIER ::= { lcsStatusHardwareInfo 16 }

-- {TABLE} 1.3.6.1.4.1.2356.11.1.47.16.1
lcsStatusHardwareInfoSecUnitChannelStateTable OBJECT-TYPE
    SYNTAX     SEQUENCE OF LcsStatusHardwareInfoSecUnitChannelStateEntry
    MAX-ACCESS not-accessible
    STATUS     current
    DESCRIPTION
            ""
    ::= { lcsStatusHardwareInfoSecUnit 1 }

-- {ROW} 1.3.6.1.4.1.2356.11.1.47.16.1.1
lcsStatusHardwareInfoSecUnitChannelStateEntry OBJECT-TYPE
    SYNTAX     LcsStatusHardwareInfoSecUnitChannelStateEntry
    MAX-ACCESS not-accessible
    STATUS     current
    DESCRIPTION
            ""
    INDEX {
            lcsStatusHardwareInfoSecUnitChannelStateEntryChan
          }
    ::= { lcsStatusHardwareInfoSecUnitChannelStateTable 1 }

LcsStatusHardwareInfoSecUnitChannelStateEntry ::= SEQUENCE {
            lcsStatusHardwareInfoSecUnitChannelStateEntryChan Integer32,
            lcsStatusHardwareInfoSecUnitChannelStateEntryDone Integer32,
            lcsStatusHardwareInfoSecUnitChannelStateEntryErrirq Integer32,
            lcsStatusHardwareInfoSecUnitChannelStateEntryOverrun Integer32,
            lcsStatusHardwareInfoSecUnitChannelStateEntryDoubleFetch Integer32,
            lcsStatusHardwareInfoSecUnitChannelStateEntrySingleFetch Integer32,
            lcsStatusHardwareInfoSecUnitChannelStateEntryMasterTranferError Integer32,
            lcsStatusHardwareInfoSecUnitChannelStateEntryScatGathDLen Integer32,
            lcsStatusHardwareInfoSecUnitChannelStateEntryFetchpointerZero Integer32,
            lcsStatusHardwareInfoSecUnitChannelStateEntryIllegalHeader Integer32,
            lcsStatusHardwareInfoSecUnitChannelStateEntryIllegalAssign Integer32,
            lcsStatusHardwareInfoSecUnitChannelStateEntryExeunit Integer32,
            lcsStatusHardwareInfoSecUnitChannelStateEntryGatherBound Integer32,
            lcsStatusHardwareInfoSecUnitChannelStateEntryGatherLen Integer32,
            lcsStatusHardwareInfoSecUnitChannelStateEntryScatterBound Integer32,
            lcsStatusHardwareInfoSecUnitChannelStateEntryScatterLen Integer32,
            lcsStatusHardwareInfoSecUnitChannelStateEntryOther Integer32,
            lcsStatusHardwareInfoSecUnitChannelStateEntryChannelReset Integer32,
            lcsStatusHardwareInfoSecUnitChannelStateEntryQueue Integer32
    }

-- {COLUMN} 1.3.6.1.4.1.2356.11.1.47.16.1.1.1
lcsStatusHardwareInfoSecUnitChannelStateEntryChan OBJECT-TYPE
    SYNTAX     Integer32 (-2147483648..2147483647)
    MAX-ACCESS read-only
    STATUS     current
    DESCRIPTION
            ""
    ::= { lcsStatusHardwareInfoSecUnitChannelStateEntry 1 }

-- {COLUMN} 1.3.6.1.4.1.2356.11.1.47.16.1.1.2
lcsStatusHardwareInfoSecUnitChannelStateEntryDone OBJECT-TYPE
    SYNTAX     Integer32 (-2147483648..2147483647)
    MAX-ACCESS read-only
    STATUS     current
    DESCRIPTION
            ""
    ::= { lcsStatusHardwareInfoSecUnitChannelStateEntry 2 }

-- {COLUMN} 1.3.6.1.4.1.2356.11.1.47.16.1.1.3
lcsStatusHardwareInfoSecUnitChannelStateEntryErrirq OBJECT-TYPE
    SYNTAX     Integer32 (-2147483648..2147483647)
    MAX-ACCESS read-only
    STATUS     current
    DESCRIPTION
            ""
    ::= { lcsStatusHardwareInfoSecUnitChannelStateEntry 3 }

-- {COLUMN} 1.3.6.1.4.1.2356.11.1.47.16.1.1.4
lcsStatusHardwareInfoSecUnitChannelStateEntryOverrun OBJECT-TYPE
    SYNTAX     Integer32 (-2147483648..2147483647)
    MAX-ACCESS read-only
    STATUS     current
    DESCRIPTION
            ""
    ::= { lcsStatusHardwareInfoSecUnitChannelStateEntry 4 }

-- {COLUMN} 1.3.6.1.4.1.2356.11.1.47.16.1.1.5
lcsStatusHardwareInfoSecUnitChannelStateEntryDoubleFetch OBJECT-TYPE
    SYNTAX     Integer32 (-2147483648..2147483647)
    MAX-ACCESS read-only
    STATUS     current
    DESCRIPTION
            ""
    ::= { lcsStatusHardwareInfoSecUnitChannelStateEntry 5 }

-- {COLUMN} 1.3.6.1.4.1.2356.11.1.47.16.1.1.6
lcsStatusHardwareInfoSecUnitChannelStateEntrySingleFetch OBJECT-TYPE
    SYNTAX     Integer32 (-2147483648..2147483647)
    MAX-ACCESS read-only
    STATUS     current
    DESCRIPTION
            ""
    ::= { lcsStatusHardwareInfoSecUnitChannelStateEntry 6 }

-- {COLUMN} 1.3.6.1.4.1.2356.11.1.47.16.1.1.7
lcsStatusHardwareInfoSecUnitChannelStateEntryMasterTranferError OBJECT-TYPE
    SYNTAX     Integer32 (-2147483648..2147483647)
    MAX-ACCESS read-only
    STATUS     current
    DESCRIPTION
            ""
    ::= { lcsStatusHardwareInfoSecUnitChannelStateEntry 7 }

-- {COLUMN} 1.3.6.1.4.1.2356.11.1.47.16.1.1.8
lcsStatusHardwareInfoSecUnitChannelStateEntryScatGathDLen OBJECT-TYPE
    SYNTAX     Integer32 (-2147483648..2147483647)
    MAX-ACCESS read-only
    STATUS     current
    DESCRIPTION
            ""
    ::= { lcsStatusHardwareInfoSecUnitChannelStateEntry 8 }

-- {COLUMN} 1.3.6.1.4.1.2356.11.1.47.16.1.1.9
lcsStatusHardwareInfoSecUnitChannelStateEntryFetchpointerZero OBJECT-TYPE
    SYNTAX     Integer32 (-2147483648..2147483647)
    MAX-ACCESS read-only
    STATUS     current
    DESCRIPTION
            ""
    ::= { lcsStatusHardwareInfoSecUnitChannelStateEntry 9 }

-- {COLUMN} 1.3.6.1.4.1.2356.11.1.47.16.1.1.10
lcsStatusHardwareInfoSecUnitChannelStateEntryIllegalHeader OBJECT-TYPE
    SYNTAX     Integer32 (-2147483648..2147483647)
    MAX-ACCESS read-only
    STATUS     current
    DESCRIPTION
            ""
    ::= { lcsStatusHardwareInfoSecUnitChannelStateEntry 10 }

-- {COLUMN} 1.3.6.1.4.1.2356.11.1.47.16.1.1.11
lcsStatusHardwareInfoSecUnitChannelStateEntryIllegalAssign OBJECT-TYPE
    SYNTAX     Integer32 (-2147483648..2147483647)
    MAX-ACCESS read-only
    STATUS     current
    DESCRIPTION
            ""
    ::= { lcsStatusHardwareInfoSecUnitChannelStateEntry 11 }

-- {COLUMN} 1.3.6.1.4.1.2356.11.1.47.16.1.1.12
lcsStatusHardwareInfoSecUnitChannelStateEntryExeunit OBJECT-TYPE
    SYNTAX     Integer32 (-2147483648..2147483647)
    MAX-ACCESS read-only
    STATUS     current
    DESCRIPTION
            ""
    ::= { lcsStatusHardwareInfoSecUnitChannelStateEntry 12 }

-- {COLUMN} 1.3.6.1.4.1.2356.11.1.47.16.1.1.13
lcsStatusHardwareInfoSecUnitChannelStateEntryGatherBound OBJECT-TYPE
    SYNTAX     Integer32 (-2147483648..2147483647)
    MAX-ACCESS read-only
    STATUS     current
    DESCRIPTION
            ""
    ::= { lcsStatusHardwareInfoSecUnitChannelStateEntry 13 }

-- {COLUMN} 1.3.6.1.4.1.2356.11.1.47.16.1.1.14
lcsStatusHardwareInfoSecUnitChannelStateEntryGatherLen OBJECT-TYPE
    SYNTAX     Integer32 (-2147483648..2147483647)
    MAX-ACCESS read-only
    STATUS     current
    DESCRIPTION
            ""
    ::= { lcsStatusHardwareInfoSecUnitChannelStateEntry 14 }

-- {COLUMN} 1.3.6.1.4.1.2356.11.1.47.16.1.1.15
lcsStatusHardwareInfoSecUnitChannelStateEntryScatterBound OBJECT-TYPE
    SYNTAX     Integer32 (-2147483648..2147483647)
    MAX-ACCESS read-only
    STATUS     current
    DESCRIPTION
            ""
    ::= { lcsStatusHardwareInfoSecUnitChannelStateEntry 15 }

-- {COLUMN} 1.3.6.1.4.1.2356.11.1.47.16.1.1.16
lcsStatusHardwareInfoSecUnitChannelStateEntryScatterLen OBJECT-TYPE
    SYNTAX     Integer32 (-2147483648..2147483647)
    MAX-ACCESS read-only
    STATUS     current
    DESCRIPTION
            ""
    ::= { lcsStatusHardwareInfoSecUnitChannelStateEntry 16 }

-- {COLUMN} 1.3.6.1.4.1.2356.11.1.47.16.1.1.17
lcsStatusHardwareInfoSecUnitChannelStateEntryOther OBJECT-TYPE
    SYNTAX     Integer32 (-2147483648..2147483647)
    MAX-ACCESS read-only
    STATUS     current
    DESCRIPTION
            ""
    ::= { lcsStatusHardwareInfoSecUnitChannelStateEntry 17 }

-- {COLUMN} 1.3.6.1.4.1.2356.11.1.47.16.1.1.18
lcsStatusHardwareInfoSecUnitChannelStateEntryChannelReset OBJECT-TYPE
    SYNTAX     Integer32 (-2147483648..2147483647)
    MAX-ACCESS read-only
    STATUS     current
    DESCRIPTION
            ""
    ::= { lcsStatusHardwareInfoSecUnitChannelStateEntry 18 }

-- {COLUMN} 1.3.6.1.4.1.2356.11.1.47.16.1.1.19
lcsStatusHardwareInfoSecUnitChannelStateEntryQueue OBJECT-TYPE
    SYNTAX     Integer32 (-2147483648..2147483647)
    MAX-ACCESS read-only
    STATUS     current
    DESCRIPTION
            "-- empty --"
    ::= { lcsStatusHardwareInfoSecUnitChannelStateEntry 19 }

-- {SCALAR} 1.3.6.1.4.1.2356.11.1.47.16.2
lcsStatusHardwareInfoSecUnitDeleteValues OBJECT-TYPE
    SYNTAX     DisplayString
    MAX-ACCESS read-write
    STATUS     current
    DESCRIPTION
            ""
    ::= { lcsStatusHardwareInfoSecUnit 2 }

-- {SCALAR} 1.3.6.1.4.1.2356.11.1.47.16.3
lcsStatusHardwareInfoSecUnitTestRandomNumbers OBJECT-TYPE
    SYNTAX     DisplayString
    MAX-ACCESS read-write
    STATUS     current
    DESCRIPTION
            ""
    ::= { lcsStatusHardwareInfoSecUnit 3 }

-- {TABLE} 1.3.6.1.4.1.2356.11.1.47.16.4
lcsStatusHardwareInfoSecUnitRingStateTable OBJECT-TYPE
    SYNTAX     SEQUENCE OF LcsStatusHardwareInfoSecUnitRingStateEntry
    MAX-ACCESS not-accessible
    STATUS     current
    DESCRIPTION
            "-- empty --"
    ::= { lcsStatusHardwareInfoSecUnit 4 }

-- {ROW} 1.3.6.1.4.1.2356.11.1.47.16.4.1
lcsStatusHardwareInfoSecUnitRingStateEntry OBJECT-TYPE
    SYNTAX     LcsStatusHardwareInfoSecUnitRingStateEntry
    MAX-ACCESS not-accessible
    STATUS     current
    DESCRIPTION
            ""
    INDEX {
            lcsStatusHardwareInfoSecUnitRingStateEntryRing
          }
    ::= { lcsStatusHardwareInfoSecUnitRingStateTable 1 }

LcsStatusHardwareInfoSecUnitRingStateEntry ::= SEQUENCE {
            lcsStatusHardwareInfoSecUnitRingStateEntryRing Integer32,
            lcsStatusHardwareInfoSecUnitRingStateEntryDone Integer32,
            lcsStatusHardwareInfoSecUnitRingStateEntryError Integer32,
            lcsStatusHardwareInfoSecUnitRingStateEntryDecoError Integer32,
            lcsStatusHardwareInfoSecUnitRingStateEntryJobRingError Integer32,
            lcsStatusHardwareInfoSecUnitRingStateEntryAesChaError Integer32,
            lcsStatusHardwareInfoSecUnitRingStateEntryDesChaError Integer32,
            lcsStatusHardwareInfoSecUnitRingStateEntryMdhaChaError Integer32,
            lcsStatusHardwareInfoSecUnitRingStateEntryPkhaChaError Integer32,
            lcsStatusHardwareInfoSecUnitRingStateEntryRngChaError Integer32
    }

-- {COLUMN} 1.3.6.1.4.1.2356.11.1.47.16.4.1.1
lcsStatusHardwareInfoSecUnitRingStateEntryRing OBJECT-TYPE
    SYNTAX     Integer32 (-2147483648..2147483647)
    MAX-ACCESS read-only
    STATUS     current
    DESCRIPTION
            "-- empty --"
    ::= { lcsStatusHardwareInfoSecUnitRingStateEntry 1 }

-- {COLUMN} 1.3.6.1.4.1.2356.11.1.47.16.4.1.2
lcsStatusHardwareInfoSecUnitRingStateEntryDone OBJECT-TYPE
    SYNTAX     Integer32 (-2147483648..2147483647)
    MAX-ACCESS read-only
    STATUS     current
    DESCRIPTION
            "-- empty --"
    ::= { lcsStatusHardwareInfoSecUnitRingStateEntry 2 }

-- {COLUMN} 1.3.6.1.4.1.2356.11.1.47.16.4.1.3
lcsStatusHardwareInfoSecUnitRingStateEntryError OBJECT-TYPE
    SYNTAX     Integer32 (-2147483648..2147483647)
    MAX-ACCESS read-only
    STATUS     current
    DESCRIPTION
            "-- empty --"
    ::= { lcsStatusHardwareInfoSecUnitRingStateEntry 3 }

-- {COLUMN} 1.3.6.1.4.1.2356.11.1.47.16.4.1.4
lcsStatusHardwareInfoSecUnitRingStateEntryDecoError OBJECT-TYPE
    SYNTAX     Integer32 (-2147483648..2147483647)
    MAX-ACCESS read-only
    STATUS     current
    DESCRIPTION
            "-- empty --"
    ::= { lcsStatusHardwareInfoSecUnitRingStateEntry 4 }

-- {COLUMN} 1.3.6.1.4.1.2356.11.1.47.16.4.1.5
lcsStatusHardwareInfoSecUnitRingStateEntryJobRingError OBJECT-TYPE
    SYNTAX     Integer32 (-2147483648..2147483647)
    MAX-ACCESS read-only
    STATUS     current
    DESCRIPTION
            "-- empty --"
    ::= { lcsStatusHardwareInfoSecUnitRingStateEntry 5 }

-- {COLUMN} 1.3.6.1.4.1.2356.11.1.47.16.4.1.6
lcsStatusHardwareInfoSecUnitRingStateEntryAesChaError OBJECT-TYPE
    SYNTAX     Integer32 (-2147483648..2147483647)
    MAX-ACCESS read-only
    STATUS     current
    DESCRIPTION
            "-- empty --"
    ::= { lcsStatusHardwareInfoSecUnitRingStateEntry 6 }

-- {COLUMN} 1.3.6.1.4.1.2356.11.1.47.16.4.1.7
lcsStatusHardwareInfoSecUnitRingStateEntryDesChaError OBJECT-TYPE
    SYNTAX     Integer32 (-2147483648..2147483647)
    MAX-ACCESS read-only
    STATUS     current
    DESCRIPTION
            "-- empty --"
    ::= { lcsStatusHardwareInfoSecUnitRingStateEntry 7 }

-- {COLUMN} 1.3.6.1.4.1.2356.11.1.47.16.4.1.8
lcsStatusHardwareInfoSecUnitRingStateEntryMdhaChaError OBJECT-TYPE
    SYNTAX     Integer32 (-2147483648..2147483647)
    MAX-ACCESS read-only
    STATUS     current
    DESCRIPTION
            "-- empty --"
    ::= { lcsStatusHardwareInfoSecUnitRingStateEntry 8 }

-- {COLUMN} 1.3.6.1.4.1.2356.11.1.47.16.4.1.9
lcsStatusHardwareInfoSecUnitRingStateEntryPkhaChaError OBJECT-TYPE
    SYNTAX     Integer32 (-2147483648..2147483647)
    MAX-ACCESS read-only
    STATUS     current
    DESCRIPTION
            "-- empty --"
    ::= { lcsStatusHardwareInfoSecUnitRingStateEntry 9 }

-- {COLUMN} 1.3.6.1.4.1.2356.11.1.47.16.4.1.10
lcsStatusHardwareInfoSecUnitRingStateEntryRngChaError OBJECT-TYPE
    SYNTAX     Integer32 (-2147483648..2147483647)
    MAX-ACCESS read-only
    STATUS     current
    DESCRIPTION
            "-- empty --"
    ::= { lcsStatusHardwareInfoSecUnitRingStateEntry 10 }

-- {TABLE} 1.3.6.1.4.1.2356.11.1.47.16.5
lcsStatusHardwareInfoSecUnitCpuCapabilitiesTable OBJECT-TYPE
    SYNTAX     SEQUENCE OF LcsStatusHardwareInfoSecUnitCpuCapabilitiesEntry
    MAX-ACCESS not-accessible
    STATUS     current
    DESCRIPTION
            "-- empty --"
    ::= { lcsStatusHardwareInfoSecUnit 5 }

-- {ROW} 1.3.6.1.4.1.2356.11.1.47.16.5.1
lcsStatusHardwareInfoSecUnitCpuCapabilitiesEntry OBJECT-TYPE
    SYNTAX     LcsStatusHardwareInfoSecUnitCpuCapabilitiesEntry
    MAX-ACCESS not-accessible
    STATUS     current
    DESCRIPTION
            ""
    INDEX {
            lcsStatusHardwareInfoSecUnitCpuCapabilitiesEntryCapability
          }
    ::= { lcsStatusHardwareInfoSecUnitCpuCapabilitiesTable 1 }

LcsStatusHardwareInfoSecUnitCpuCapabilitiesEntry ::= SEQUENCE {
            lcsStatusHardwareInfoSecUnitCpuCapabilitiesEntryCapability DisplayString,
            lcsStatusHardwareInfoSecUnitCpuCapabilitiesEntryAvailable INTEGER
    }

-- {COLUMN} 1.3.6.1.4.1.2356.11.1.47.16.5.1.1
lcsStatusHardwareInfoSecUnitCpuCapabilitiesEntryCapability OBJECT-TYPE
    SYNTAX     DisplayString (SIZE(0..12))
    MAX-ACCESS read-only
    STATUS     current
    DESCRIPTION
            "-- empty --"
    ::= { lcsStatusHardwareInfoSecUnitCpuCapabilitiesEntry 1 }

-- {COLUMN} 1.3.6.1.4.1.2356.11.1.47.16.5.1.2
lcsStatusHardwareInfoSecUnitCpuCapabilitiesEntryAvailable OBJECT-TYPE
    SYNTAX     INTEGER {
                  eNo (0),
                  eYes (1)
            }
    MAX-ACCESS read-only
    STATUS     current
    DESCRIPTION
            "-- empty --"
    ::= { lcsStatusHardwareInfoSecUnitCpuCapabilitiesEntry 2 }

-- {TABLE} 1.3.6.1.4.1.2356.11.1.47.16.6
lcsStatusHardwareInfoSecUnitStatisticTable OBJECT-TYPE
    SYNTAX     SEQUENCE OF LcsStatusHardwareInfoSecUnitStatisticEntry
    MAX-ACCESS not-accessible
    STATUS     current
    DESCRIPTION
            "-- empty --"
    ::= { lcsStatusHardwareInfoSecUnit 6 }

-- {ROW} 1.3.6.1.4.1.2356.11.1.47.16.6.1
lcsStatusHardwareInfoSecUnitStatisticEntry OBJECT-TYPE
    SYNTAX     LcsStatusHardwareInfoSecUnitStatisticEntry
    MAX-ACCESS not-accessible
    STATUS     current
    DESCRIPTION
            ""
    INDEX {
            lcsStatusHardwareInfoSecUnitStatisticEntryOperation
          }
    ::= { lcsStatusHardwareInfoSecUnitStatisticTable 1 }

LcsStatusHardwareInfoSecUnitStatisticEntry ::= SEQUENCE {
            lcsStatusHardwareInfoSecUnitStatisticEntryOperation DisplayString,
            lcsStatusHardwareInfoSecUnitStatisticEntrySuccess Integer32,
            lcsStatusHardwareInfoSecUnitStatisticEntryFailed Integer32
    }

-- {COLUMN} 1.3.6.1.4.1.2356.11.1.47.16.6.1.1
lcsStatusHardwareInfoSecUnitStatisticEntryOperation OBJECT-TYPE
    SYNTAX     DisplayString (SIZE(0..20))
    MAX-ACCESS read-only
    STATUS     current
    DESCRIPTION
            "-- empty --"
    ::= { lcsStatusHardwareInfoSecUnitStatisticEntry 1 }

-- {COLUMN} 1.3.6.1.4.1.2356.11.1.47.16.6.1.2
lcsStatusHardwareInfoSecUnitStatisticEntrySuccess OBJECT-TYPE
    SYNTAX     Integer32 (-2147483648..2147483647)
    MAX-ACCESS read-only
    STATUS     current
    DESCRIPTION
            "-- empty --"
    ::= { lcsStatusHardwareInfoSecUnitStatisticEntry 2 }

-- {COLUMN} 1.3.6.1.4.1.2356.11.1.47.16.6.1.3
lcsStatusHardwareInfoSecUnitStatisticEntryFailed OBJECT-TYPE
    SYNTAX     Integer32 (-2147483648..2147483647)
    MAX-ACCESS read-only
    STATUS     current
    DESCRIPTION
            "-- empty --"
    ::= { lcsStatusHardwareInfoSecUnitStatisticEntry 3 }

-- {SCALAR} 1.3.6.1.4.1.2356.11.1.47.16.7
lcsStatusHardwareInfoSecUnitFreeEngineIds OBJECT-TYPE
    SYNTAX     Integer32 (0..65535)
    MAX-ACCESS read-only
    STATUS     current
    DESCRIPTION
            "-- empty --"
    ::= { lcsStatusHardwareInfoSecUnit 7 }

-- {TABLE} 1.3.6.1.4.1.2356.11.1.47.16.10
lcsStatusHardwareInfoSecUnitLogTableTable OBJECT-TYPE
    SYNTAX     SEQUENCE OF LcsStatusHardwareInfoSecUnitLogTableEntry
    MAX-ACCESS not-accessible
    STATUS     current
    DESCRIPTION
            "-- empty --"
    ::= { lcsStatusHardwareInfoSecUnit 10 }

-- {ROW} 1.3.6.1.4.1.2356.11.1.47.16.10.1
lcsStatusHardwareInfoSecUnitLogTableEntry OBJECT-TYPE
    SYNTAX     LcsStatusHardwareInfoSecUnitLogTableEntry
    MAX-ACCESS not-accessible
    STATUS     current
    DESCRIPTION
            ""
    INDEX {
            lcsStatusHardwareInfoSecUnitLogTableEntryIndex
          }
    ::= { lcsStatusHardwareInfoSecUnitLogTableTable 1 }

LcsStatusHardwareInfoSecUnitLogTableEntry ::= SEQUENCE {
            lcsStatusHardwareInfoSecUnitLogTableEntryIndex Integer32,
            lcsStatusHardwareInfoSecUnitLogTableEntryTime DisplayString,
            lcsStatusHardwareInfoSecUnitLogTableEntryChan Integer32,
            lcsStatusHardwareInfoSecUnitLogTableEntryType INTEGER,
            lcsStatusHardwareInfoSecUnitLogTableEntryExecutionUnit1 INTEGER,
            lcsStatusHardwareInfoSecUnitLogTableEntryExecutionUnit1Isr DisplayString,
            lcsStatusHardwareInfoSecUnitLogTableEntryExecutionUnit2 INTEGER,
            lcsStatusHardwareInfoSecUnitLogTableEntryExecutionUnit2Isr DisplayString,
            lcsStatusHardwareInfoSecUnitLogTableEntryDescriptor DisplayString
    }

-- {COLUMN} 1.3.6.1.4.1.2356.11.1.47.16.10.1.1
lcsStatusHardwareInfoSecUnitLogTableEntryIndex OBJECT-TYPE
    SYNTAX     Integer32 (0..2147483647)
    MAX-ACCESS read-only
    STATUS     current
    DESCRIPTION
            "-- empty --"
    ::= { lcsStatusHardwareInfoSecUnitLogTableEntry 1 }

-- {COLUMN} 1.3.6.1.4.1.2356.11.1.47.16.10.1.2
lcsStatusHardwareInfoSecUnitLogTableEntryTime OBJECT-TYPE
    SYNTAX     DisplayString (SIZE(0..19))
    MAX-ACCESS read-only
    STATUS     current
    DESCRIPTION
            "-- empty --"
    ::= { lcsStatusHardwareInfoSecUnitLogTableEntry 2 }

-- {COLUMN} 1.3.6.1.4.1.2356.11.1.47.16.10.1.3
lcsStatusHardwareInfoSecUnitLogTableEntryChan OBJECT-TYPE
    SYNTAX     Integer32 (0..2147483647)
    MAX-ACCESS read-only
    STATUS     current
    DESCRIPTION
            ""
    ::= { lcsStatusHardwareInfoSecUnitLogTableEntry 3 }

-- {COLUMN} 1.3.6.1.4.1.2356.11.1.47.16.10.1.4
lcsStatusHardwareInfoSecUnitLogTableEntryType OBJECT-TYPE
    SYNTAX     INTEGER {
                  eUnknown (0),
                  eDoubleFetchFifoWriteOverflow (1),
                  eSingleFetchFifoWriteOverflow (2),
                  eMasterDataTransferError (3),
                  eScatterGatherDataLengthZero (4),
                  eFetchPointerZero (5),
                  eIllegalDescriptorHeader (6),
                  eInvalidEuAssignment (7),
                  eEuError (8),
                  eGatherBoundaryError (9),
                  eGatherReturnLengthError (10),
                  eScatterBoundaryError (11),
                  eScatterReturnLengthError (12),
                  eOverflow (13)
            }
    MAX-ACCESS read-only
    STATUS     current
    DESCRIPTION
            "-- empty --"
    ::= { lcsStatusHardwareInfoSecUnitLogTableEntry 4 }

-- {COLUMN} 1.3.6.1.4.1.2356.11.1.47.16.10.1.5
lcsStatusHardwareInfoSecUnitLogTableEntryExecutionUnit1 OBJECT-TYPE
    SYNTAX     INTEGER {
                  eNotSet (0),
                  eAfeu (1),
                  eDeu (2),
                  eMdeua (3),
                  eRng (4),
                  ePkeu (5),
                  eAesu (6),
                  eKeu (7),
                  eMdeub (11)
            }
    MAX-ACCESS read-only
    STATUS     current
    DESCRIPTION
            "-- empty --"
    ::= { lcsStatusHardwareInfoSecUnitLogTableEntry 5 }

-- {COLUMN} 1.3.6.1.4.1.2356.11.1.47.16.10.1.6
lcsStatusHardwareInfoSecUnitLogTableEntryExecutionUnit1Isr OBJECT-TYPE
    SYNTAX     DisplayString (SIZE(0..21))
    MAX-ACCESS read-only
    STATUS     current
    DESCRIPTION
            "-- empty --"
    ::= { lcsStatusHardwareInfoSecUnitLogTableEntry 6 }

-- {COLUMN} 1.3.6.1.4.1.2356.11.1.47.16.10.1.7
lcsStatusHardwareInfoSecUnitLogTableEntryExecutionUnit2 OBJECT-TYPE
    SYNTAX     INTEGER {
                  eNotSet (0),
                  eAfeu (1),
                  eDeu (2),
                  eMdeua (3),
                  eRng (4),
                  ePkeu (5),
                  eAesu (6),
                  eKeu (7),
                  eMdeub (11)
            }
    MAX-ACCESS read-only
    STATUS     current
    DESCRIPTION
            "-- empty --"
    ::= { lcsStatusHardwareInfoSecUnitLogTableEntry 7 }

-- {COLUMN} 1.3.6.1.4.1.2356.11.1.47.16.10.1.8
lcsStatusHardwareInfoSecUnitLogTableEntryExecutionUnit2Isr OBJECT-TYPE
    SYNTAX     DisplayString (SIZE(0..21))
    MAX-ACCESS read-only
    STATUS     current
    DESCRIPTION
            "-- empty --"
    ::= { lcsStatusHardwareInfoSecUnitLogTableEntry 8 }

-- {COLUMN} 1.3.6.1.4.1.2356.11.1.47.16.10.1.9
lcsStatusHardwareInfoSecUnitLogTableEntryDescriptor OBJECT-TYPE
    SYNTAX     DisplayString (SIZE(0..145))
    MAX-ACCESS read-only
    STATUS     current
    DESCRIPTION
            "-- empty --"
    ::= { lcsStatusHardwareInfoSecUnitLogTableEntry 9 }

-- {SCALAR} 1.3.6.1.4.1.2356.11.1.47.17
lcsStatusHardwareInfoOnboardUsbHub OBJECT-TYPE
    SYNTAX     INTEGER {
                  eNo (0),
                  eYes (1)
            }
    MAX-ACCESS read-only
    STATUS     current
    DESCRIPTION
            ""
    ::= { lcsStatusHardwareInfo 17 }

-- {SCALAR} 1.3.6.1.4.1.2356.11.1.47.20
lcsStatusHardwareInfoTemperatureDegrees OBJECT-TYPE
    SYNTAX     Integer32 (-32768..32767)
    MAX-ACCESS read-only
    STATUS     current
    DESCRIPTION
            ""
    ::= { lcsStatusHardwareInfo 20 }

-- {NODE} 1.3.6.1.4.1.2356.11.1.47.25
lcsStatusHardwareInfoPower OBJECT IDENTIFIER ::= { lcsStatusHardwareInfo 25 }

-- {SCALAR} 1.3.6.1.4.1.2356.11.1.47.25.1
lcsStatusHardwareInfoPowerSource OBJECT-TYPE
    SYNTAX     INTEGER {
                  eUnknown (0),
                  eAcAdapter (1),
                  ePoe (2),
                  eBattery (3),
                  eWindmill (4),
                  eSolarPanel (5),
                  eFuelCell (6),
                  eHamster (7),
                  ePerpetuumMobile (8)
            }
    MAX-ACCESS read-only
    STATUS     current
    DESCRIPTION
            "-- empty --"
    ::= { lcsStatusHardwareInfoPower 1 }

-- {SCALAR} 1.3.6.1.4.1.2356.11.1.47.25.2
lcsStatusHardwareInfoPowerPseType OBJECT-TYPE
    SYNTAX     INTEGER {
                  eUnknown (0),
                  eType1 (1),
                  eType2 (2)
            }
    MAX-ACCESS read-only
    STATUS     current
    DESCRIPTION
            "-- empty --"
    ::= { lcsStatusHardwareInfoPower 2 }

-- {SCALAR} 1.3.6.1.4.1.2356.11.1.47.25.3
lcsStatusHardwareInfoPowerPoePowerValueMw OBJECT-TYPE
    SYNTAX     Integer32 (0..2147483647)
    MAX-ACCESS read-only
    STATUS     current
    DESCRIPTION
            "-- empty --"
    ::= { lcsStatusHardwareInfoPower 3 }

-- {SCALAR} 1.3.6.1.4.1.2356.11.1.47.25.4
lcsStatusHardwareInfoPowerDataLinkLayerNegotiation OBJECT-TYPE
    SYNTAX     INTEGER {
                  eNo (0),
                  eYes (1)
            }
    MAX-ACCESS read-only
    STATUS     current
    DESCRIPTION
            "-- empty --"
    ::= { lcsStatusHardwareInfoPower 4 }

-- {TABLE} 1.3.6.1.4.1.2356.11.1.47.30
lcsStatusHardwareInfoPciDeviceListTable OBJECT-TYPE
    SYNTAX     SEQUENCE OF LcsStatusHardwareInfoPciDeviceListEntry
    MAX-ACCESS not-accessible
    STATUS     current
    DESCRIPTION
            ""
    ::= { lcsStatusHardwareInfo 30 }

-- {ROW} 1.3.6.1.4.1.2356.11.1.47.30.1
lcsStatusHardwareInfoPciDeviceListEntry OBJECT-TYPE
    SYNTAX     LcsStatusHardwareInfoPciDeviceListEntry
    MAX-ACCESS not-accessible
    STATUS     current
    DESCRIPTION
            ""
    INDEX {
            lcsStatusHardwareInfoPciDeviceListEntryHostBridge,
            lcsStatusHardwareInfoPciDeviceListEntryBus,
            lcsStatusHardwareInfoPciDeviceListEntryDevice,
            lcsStatusHardwareInfoPciDeviceListEntryFunction
          }
    ::= { lcsStatusHardwareInfoPciDeviceListTable 1 }

LcsStatusHardwareInfoPciDeviceListEntry ::= SEQUENCE {
            lcsStatusHardwareInfoPciDeviceListEntryHostBridge Integer32,
            lcsStatusHardwareInfoPciDeviceListEntryBus Integer32,
            lcsStatusHardwareInfoPciDeviceListEntryDevice Integer32,
            lcsStatusHardwareInfoPciDeviceListEntryFunction Integer32,
            lcsStatusHardwareInfoPciDeviceListEntryDeviceId DisplayString,
            lcsStatusHardwareInfoPciDeviceListEntrySubsystemId DisplayString,
            lcsStatusHardwareInfoPciDeviceListEntryClass INTEGER,
            lcsStatusHardwareInfoPciDeviceListEntryType INTEGER,
            lcsStatusHardwareInfoPciDeviceListEntryInterruptCount Counter64,
            lcsStatusHardwareInfoPciDeviceListEntryDriverName DisplayString
    }

-- {COLUMN} 1.3.6.1.4.1.2356.11.1.47.30.1.1
lcsStatusHardwareInfoPciDeviceListEntryHostBridge OBJECT-TYPE
    SYNTAX     Integer32 (0..2147483647)
    MAX-ACCESS read-only
    STATUS     current
    DESCRIPTION
            ""
    ::= { lcsStatusHardwareInfoPciDeviceListEntry 1 }

-- {COLUMN} 1.3.6.1.4.1.2356.11.1.47.30.1.2
lcsStatusHardwareInfoPciDeviceListEntryBus OBJECT-TYPE
    SYNTAX     Integer32 (0..2147483647)
    MAX-ACCESS read-only
    STATUS     current
    DESCRIPTION
            ""
    ::= { lcsStatusHardwareInfoPciDeviceListEntry 2 }

-- {COLUMN} 1.3.6.1.4.1.2356.11.1.47.30.1.3
lcsStatusHardwareInfoPciDeviceListEntryDevice OBJECT-TYPE
    SYNTAX     Integer32 (0..2147483647)
    MAX-ACCESS read-only
    STATUS     current
    DESCRIPTION
            ""
    ::= { lcsStatusHardwareInfoPciDeviceListEntry 3 }

-- {COLUMN} 1.3.6.1.4.1.2356.11.1.47.30.1.4
lcsStatusHardwareInfoPciDeviceListEntryFunction OBJECT-TYPE
    SYNTAX     Integer32 (0..2147483647)
    MAX-ACCESS read-only
    STATUS     current
    DESCRIPTION
            ""
    ::= { lcsStatusHardwareInfoPciDeviceListEntry 4 }

-- {COLUMN} 1.3.6.1.4.1.2356.11.1.47.30.1.5
lcsStatusHardwareInfoPciDeviceListEntryDeviceId OBJECT-TYPE
    SYNTAX     DisplayString (SIZE(0..255))
    MAX-ACCESS read-only
    STATUS     current
    DESCRIPTION
            ""
    ::= { lcsStatusHardwareInfoPciDeviceListEntry 5 }

-- {COLUMN} 1.3.6.1.4.1.2356.11.1.47.30.1.6
lcsStatusHardwareInfoPciDeviceListEntrySubsystemId OBJECT-TYPE
    SYNTAX     DisplayString (SIZE(0..255))
    MAX-ACCESS read-only
    STATUS     current
    DESCRIPTION
            ""
    ::= { lcsStatusHardwareInfoPciDeviceListEntry 6 }

-- {COLUMN} 1.3.6.1.4.1.2356.11.1.47.30.1.7
lcsStatusHardwareInfoPciDeviceListEntryClass OBJECT-TYPE
    SYNTAX     INTEGER {
                  eIdeIsaOnlyBusmaster (65920),
                  eIdeIsaAndPciBusmaster (65930),
                  eEthernet (131072),
                  eTokenRing (131328),
                  eNetwork (163840),
                  eVga (196608),
                  eAudio (262400),
                  eHostBridge (393216),
                  eIsaBridge (393472),
                  ePciBridge (394240),
                  ePciBridgeSubtractive (394241),
                  eCardbusBridge (395008),
                  eBridge (425984),
                  eUart16550 (458754),
                  eUart16950 (458758),
                  eCommunication (491520),
                  eOtherSystemPeripheral (557056),
                  ePowerpc (729088),
                  eOhci1394 (786448),
                  eUsbUhci (787200),
                  eUsbOhci (787216),
                  eUsbEhci (787232),
                  eUsbXhci (787248)
            }
    MAX-ACCESS read-only
    STATUS     current
    DESCRIPTION
            ""
    ::= { lcsStatusHardwareInfoPciDeviceListEntry 7 }

-- {COLUMN} 1.3.6.1.4.1.2356.11.1.47.30.1.8
lcsStatusHardwareInfoPciDeviceListEntryType OBJECT-TYPE
    SYNTAX     INTEGER {
                  ePci (0),
                  ePcie (1)
            }
    MAX-ACCESS read-only
    STATUS     current
    DESCRIPTION
            ""
    ::= { lcsStatusHardwareInfoPciDeviceListEntry 8 }

-- {COLUMN} 1.3.6.1.4.1.2356.11.1.47.30.1.9
lcsStatusHardwareInfoPciDeviceListEntryInterruptCount OBJECT-TYPE
    SYNTAX     Counter64
    MAX-ACCESS read-only
    STATUS     current
    DESCRIPTION
            ""
    ::= { lcsStatusHardwareInfoPciDeviceListEntry 9 }

-- {COLUMN} 1.3.6.1.4.1.2356.11.1.47.30.1.10
lcsStatusHardwareInfoPciDeviceListEntryDriverName OBJECT-TYPE
    SYNTAX     DisplayString (SIZE(0..255))
    MAX-ACCESS read-only
    STATUS     current
    DESCRIPTION
            "-- empty --"
    ::= { lcsStatusHardwareInfoPciDeviceListEntry 10 }

-- {TABLE} 1.3.6.1.4.1.2356.11.1.47.31
lcsStatusHardwareInfoPciClocksTable OBJECT-TYPE
    SYNTAX     SEQUENCE OF LcsStatusHardwareInfoPciClocksEntry
    MAX-ACCESS not-accessible
    STATUS     current
    DESCRIPTION
            ""
    ::= { lcsStatusHardwareInfo 31 }

-- {ROW} 1.3.6.1.4.1.2356.11.1.47.31.1
lcsStatusHardwareInfoPciClocksEntry OBJECT-TYPE
    SYNTAX     LcsStatusHardwareInfoPciClocksEntry
    MAX-ACCESS not-accessible
    STATUS     current
    DESCRIPTION
            ""
    INDEX {
            lcsStatusHardwareInfoPciClocksEntryHostBridge,
            lcsStatusHardwareInfoPciClocksEntryBus
          }
    ::= { lcsStatusHardwareInfoPciClocksTable 1 }

LcsStatusHardwareInfoPciClocksEntry ::= SEQUENCE {
            lcsStatusHardwareInfoPciClocksEntryHostBridge Integer32,
            lcsStatusHardwareInfoPciClocksEntryBus Integer32,
            lcsStatusHardwareInfoPciClocksEntryClockKhz Integer32
    }

-- {COLUMN} 1.3.6.1.4.1.2356.11.1.47.31.1.1
lcsStatusHardwareInfoPciClocksEntryHostBridge OBJECT-TYPE
    SYNTAX     Integer32 (0..2147483647)
    MAX-ACCESS read-only
    STATUS     current
    DESCRIPTION
            ""
    ::= { lcsStatusHardwareInfoPciClocksEntry 1 }

-- {COLUMN} 1.3.6.1.4.1.2356.11.1.47.31.1.2
lcsStatusHardwareInfoPciClocksEntryBus OBJECT-TYPE
    SYNTAX     Integer32 (0..2147483647)
    MAX-ACCESS read-only
    STATUS     current
    DESCRIPTION
            ""
    ::= { lcsStatusHardwareInfoPciClocksEntry 2 }

-- {COLUMN} 1.3.6.1.4.1.2356.11.1.47.31.1.3
lcsStatusHardwareInfoPciClocksEntryClockKhz OBJECT-TYPE
    SYNTAX     Integer32 (0..2147483647)
    MAX-ACCESS read-only
    STATUS     current
    DESCRIPTION
            ""
    ::= { lcsStatusHardwareInfoPciClocksEntry 3 }

-- {TABLE} 1.3.6.1.4.1.2356.11.1.47.32
lcsStatusHardwareInfoAdvErrorReportingLogTable OBJECT-TYPE
    SYNTAX     SEQUENCE OF LcsStatusHardwareInfoAdvErrorReportingLogEntry
    MAX-ACCESS not-accessible
    STATUS     current
    DESCRIPTION
            ""
    ::= { lcsStatusHardwareInfo 32 }

-- {ROW} 1.3.6.1.4.1.2356.11.1.47.32.1
lcsStatusHardwareInfoAdvErrorReportingLogEntry OBJECT-TYPE
    SYNTAX     LcsStatusHardwareInfoAdvErrorReportingLogEntry
    MAX-ACCESS not-accessible
    STATUS     current
    DESCRIPTION
            ""
    INDEX {
            lcsStatusHardwareInfoAdvErrorReportingLogEntryIndex
          }
    ::= { lcsStatusHardwareInfoAdvErrorReportingLogTable 1 }

LcsStatusHardwareInfoAdvErrorReportingLogEntry ::= SEQUENCE {
            lcsStatusHardwareInfoAdvErrorReportingLogEntryIndex Integer32,
            lcsStatusHardwareInfoAdvErrorReportingLogEntryTime DisplayString,
            lcsStatusHardwareInfoAdvErrorReportingLogEntrySeverity INTEGER,
            lcsStatusHardwareInfoAdvErrorReportingLogEntryMultiple INTEGER,
            lcsStatusHardwareInfoAdvErrorReportingLogEntrySource Integer32,
            lcsStatusHardwareInfoAdvErrorReportingLogEntryLayer INTEGER,
            lcsStatusHardwareInfoAdvErrorReportingLogEntryEvent DisplayString
    }

-- {COLUMN} 1.3.6.1.4.1.2356.11.1.47.32.1.1
lcsStatusHardwareInfoAdvErrorReportingLogEntryIndex OBJECT-TYPE
    SYNTAX     Integer32 (0..2147483647)
    MAX-ACCESS read-only
    STATUS     current
    DESCRIPTION
            ""
    ::= { lcsStatusHardwareInfoAdvErrorReportingLogEntry 1 }

-- {COLUMN} 1.3.6.1.4.1.2356.11.1.47.32.1.2
lcsStatusHardwareInfoAdvErrorReportingLogEntryTime OBJECT-TYPE
    SYNTAX     DisplayString (SIZE(0..19))
    MAX-ACCESS read-only
    STATUS     current
    DESCRIPTION
            ""
    ::= { lcsStatusHardwareInfoAdvErrorReportingLogEntry 2 }

-- {COLUMN} 1.3.6.1.4.1.2356.11.1.47.32.1.3
lcsStatusHardwareInfoAdvErrorReportingLogEntrySeverity OBJECT-TYPE
    SYNTAX     INTEGER {
                  eCorrectable (0),
                  eUncorrectableNonFatal (1),
                  eUncorrectableFatal (2)
            }
    MAX-ACCESS read-only
    STATUS     current
    DESCRIPTION
            ""
    ::= { lcsStatusHardwareInfoAdvErrorReportingLogEntry 3 }

-- {COLUMN} 1.3.6.1.4.1.2356.11.1.47.32.1.4
lcsStatusHardwareInfoAdvErrorReportingLogEntryMultiple OBJECT-TYPE
    SYNTAX     INTEGER {
                  eNo (0),
                  eYes (1)
            }
    MAX-ACCESS read-only
    STATUS     current
    DESCRIPTION
            ""
    ::= { lcsStatusHardwareInfoAdvErrorReportingLogEntry 4 }

-- {COLUMN} 1.3.6.1.4.1.2356.11.1.47.32.1.5
lcsStatusHardwareInfoAdvErrorReportingLogEntrySource OBJECT-TYPE
    SYNTAX     Integer32 (0..65535)
    MAX-ACCESS read-only
    STATUS     current
    DESCRIPTION
            ""
    ::= { lcsStatusHardwareInfoAdvErrorReportingLogEntry 5 }

-- {COLUMN} 1.3.6.1.4.1.2356.11.1.47.32.1.6
lcsStatusHardwareInfoAdvErrorReportingLogEntryLayer OBJECT-TYPE
    SYNTAX     INTEGER {
                  eUnknown (0),
                  ePhysical (1),
                  eDataLink (2),
                  eTransaction (3)
            }
    MAX-ACCESS read-only
    STATUS     current
    DESCRIPTION
            ""
    ::= { lcsStatusHardwareInfoAdvErrorReportingLogEntry 6 }

-- {COLUMN} 1.3.6.1.4.1.2356.11.1.47.32.1.7
lcsStatusHardwareInfoAdvErrorReportingLogEntryEvent OBJECT-TYPE
    SYNTAX     DisplayString (SIZE(0..251))
    MAX-ACCESS read-only
    STATUS     current
    DESCRIPTION
            ""
    ::= { lcsStatusHardwareInfoAdvErrorReportingLogEntry 7 }

-- {SCALAR} 1.3.6.1.4.1.2356.11.1.47.36
lcsStatusHardwareInfoPcieCorrErrors OBJECT-TYPE
    SYNTAX     Integer32 (0..2147483647)
    MAX-ACCESS read-only
    STATUS     current
    DESCRIPTION
            "-- empty --"
    ::= { lcsStatusHardwareInfo 36 }

-- {SCALAR} 1.3.6.1.4.1.2356.11.1.47.37
lcsStatusHardwareInfoPcieUncorrErrors OBJECT-TYPE
    SYNTAX     Integer32 (0..2147483647)
    MAX-ACCESS read-only
    STATUS     current
    DESCRIPTION
            "-- empty --"
    ::= { lcsStatusHardwareInfo 37 }

-- {SCALAR} 1.3.6.1.4.1.2356.11.1.47.38
lcsStatusHardwareInfoPcieLinkResets OBJECT-TYPE
    SYNTAX     Integer32 (0..2147483647)
    MAX-ACCESS read-only
    STATUS     current
    DESCRIPTION
            "-- empty --"
    ::= { lcsStatusHardwareInfo 38 }

-- {SCALAR} 1.3.6.1.4.1.2356.11.1.47.39
lcsStatusHardwareInfoExtendedName OBJECT-TYPE
    SYNTAX     DisplayString (SIZE(0..127))
    MAX-ACCESS read-only
    STATUS     current
    DESCRIPTION
            "-- empty --"
    ::= { lcsStatusHardwareInfo 39 }

-- {SCALAR} 1.3.6.1.4.1.2356.11.1.47.40
lcsStatusHardwareInfoModLevel OBJECT-TYPE
    SYNTAX     DisplayString (SIZE(0..32))
    MAX-ACCESS read-only
    STATUS     current
    DESCRIPTION
            "-- empty --"
    ::= { lcsStatusHardwareInfo 40 }

-- {SCALAR} 1.3.6.1.4.1.2356.11.1.47.41
lcsStatusHardwareInfoProductionDate OBJECT-TYPE
    SYNTAX     DisplayString (SIZE(0..10))
    MAX-ACCESS read-only
    STATUS     current
    DESCRIPTION
            "-- empty --"
    ::= { lcsStatusHardwareInfo 41 }

-- {TABLE} 1.3.6.1.4.1.2356.11.1.47.42
lcsStatusHardwareInfoEccErrorReportingTable OBJECT-TYPE
    SYNTAX     SEQUENCE OF LcsStatusHardwareInfoEccErrorReportingEntry
    MAX-ACCESS not-accessible
    STATUS     current
    DESCRIPTION
            "-- empty --"
    ::= { lcsStatusHardwareInfo 42 }

-- {ROW} 1.3.6.1.4.1.2356.11.1.47.42.1
lcsStatusHardwareInfoEccErrorReportingEntry OBJECT-TYPE
    SYNTAX     LcsStatusHardwareInfoEccErrorReportingEntry
    MAX-ACCESS not-accessible
    STATUS     current
    DESCRIPTION
            ""
    INDEX {
            lcsStatusHardwareInfoEccErrorReportingEntryIndex
          }
    ::= { lcsStatusHardwareInfoEccErrorReportingTable 1 }

LcsStatusHardwareInfoEccErrorReportingEntry ::= SEQUENCE {
            lcsStatusHardwareInfoEccErrorReportingEntryIndex Integer32,
            lcsStatusHardwareInfoEccErrorReportingEntryTime DisplayString,
            lcsStatusHardwareInfoEccErrorReportingEntryEvent DisplayString
    }

-- {COLUMN} 1.3.6.1.4.1.2356.11.1.47.42.1.1
lcsStatusHardwareInfoEccErrorReportingEntryIndex OBJECT-TYPE
    SYNTAX     Integer32 (0..2147483647)
    MAX-ACCESS read-only
    STATUS     current
    DESCRIPTION
            "-- empty --"
    ::= { lcsStatusHardwareInfoEccErrorReportingEntry 1 }

-- {COLUMN} 1.3.6.1.4.1.2356.11.1.47.42.1.2
lcsStatusHardwareInfoEccErrorReportingEntryTime OBJECT-TYPE
    SYNTAX     DisplayString (SIZE(0..19))
    MAX-ACCESS read-only
    STATUS     current
    DESCRIPTION
            "-- empty --"
    ::= { lcsStatusHardwareInfoEccErrorReportingEntry 2 }

-- {COLUMN} 1.3.6.1.4.1.2356.11.1.47.42.1.3
lcsStatusHardwareInfoEccErrorReportingEntryEvent OBJECT-TYPE
    SYNTAX     DisplayString (SIZE(0..251))
    MAX-ACCESS read-only
    STATUS     current
    DESCRIPTION
            "-- empty --"
    ::= { lcsStatusHardwareInfoEccErrorReportingEntry 3 }

-- {SCALAR} 1.3.6.1.4.1.2356.11.1.47.44
lcsStatusHardwareInfoPldVersion OBJECT-TYPE
    SYNTAX     DisplayString (SIZE(0..7))
    MAX-ACCESS read-only
    STATUS     current
    DESCRIPTION
            "-- empty --"
    ::= { lcsStatusHardwareInfo 44 }

-- {SCALAR} 1.3.6.1.4.1.2356.11.1.47.45
lcsStatusHardwareInfoResetButtonState OBJECT-TYPE
    SYNTAX     INTEGER {
                  eInactive (0),
                  eActive (1)
            }
    MAX-ACCESS read-only
    STATUS     current
    DESCRIPTION
            "-- empty --"
    ::= { lcsStatusHardwareInfo 45 }

-- {SCALAR} 1.3.6.1.4.1.2356.11.1.47.46
lcsStatusHardwareInfoHwmonVersion OBJECT-TYPE
    SYNTAX     DisplayString (SIZE(0..39))
    MAX-ACCESS read-only
    STATUS     current
    DESCRIPTION
            "-- empty --"
    ::= { lcsStatusHardwareInfo 46 }

-- {TABLE} 1.3.6.1.4.1.2356.11.1.47.47
lcsStatusHardwareInfoMonitoringTable OBJECT-TYPE
    SYNTAX     SEQUENCE OF LcsStatusHardwareInfoMonitoringEntry
    MAX-ACCESS not-accessible
    STATUS     current
    DESCRIPTION
            "-- empty --"
    ::= { lcsStatusHardwareInfo 47 }

-- {ROW} 1.3.6.1.4.1.2356.11.1.47.47.1
lcsStatusHardwareInfoMonitoringEntry OBJECT-TYPE
    SYNTAX     LcsStatusHardwareInfoMonitoringEntry
    MAX-ACCESS not-accessible
    STATUS     current
    DESCRIPTION
            ""
    INDEX {
            lcsStatusHardwareInfoMonitoringEntryParameter
          }
    ::= { lcsStatusHardwareInfoMonitoringTable 1 }

LcsStatusHardwareInfoMonitoringEntry ::= SEQUENCE {
            lcsStatusHardwareInfoMonitoringEntryParameter INTEGER,
            lcsStatusHardwareInfoMonitoringEntryValue Integer32
    }

-- {COLUMN} 1.3.6.1.4.1.2356.11.1.47.47.1.1
lcsStatusHardwareInfoMonitoringEntryParameter OBJECT-TYPE
    SYNTAX     INTEGER {
                  eTemperatureBoardDegrees (1),
                  eTemperatureCpuDegrees (2),
                  eRelativeHumidityPercent (3),
                  eTemperatureHumiditySensorDegrees (4),
                  eDewpointDegrees (5),
                  eAfeHeatingPercent (6),
                  eDfeHeatingPercent (7)
            }
    MAX-ACCESS read-only
    STATUS     current
    DESCRIPTION
            "-- empty --"
    ::= { lcsStatusHardwareInfoMonitoringEntry 1 }

-- {COLUMN} 1.3.6.1.4.1.2356.11.1.47.47.1.2
lcsStatusHardwareInfoMonitoringEntryValue OBJECT-TYPE
    SYNTAX     Integer32 (-32768..32767)
    MAX-ACCESS read-only
    STATUS     current
    DESCRIPTION
            "-- empty --"
    ::= { lcsStatusHardwareInfoMonitoringEntry 2 }

-- {SCALAR} 1.3.6.1.4.1.2356.11.1.47.48
lcsStatusHardwareInfoMonitoringStatus OBJECT-TYPE
    SYNTAX     INTEGER {
                  eUnknown (0),
                  eActive (1),
                  eDisabled (2),
                  eFailure (3),
                  eUpdating (4)
            }
    MAX-ACCESS read-only
    STATUS     current
    DESCRIPTION
            "-- empty --"
    ::= { lcsStatusHardwareInfo 48 }

-- {SCALAR} 1.3.6.1.4.1.2356.11.1.47.50
lcsStatusHardwareInfoWideRangePowerSupplyMv OBJECT-TYPE
    SYNTAX     Integer32 (-2147483648..2147483647)
    MAX-ACCESS read-only
    STATUS     current
    DESCRIPTION
            "-- empty --"
    ::= { lcsStatusHardwareInfo 50 }

-- {SCALAR} 1.3.6.1.4.1.2356.11.1.47.90
lcsStatusHardwareInfoEslBleHardwareRelease OBJECT-TYPE
    SYNTAX     DisplayString (SIZE(0..1))
    MAX-ACCESS read-only
    STATUS     current
    DESCRIPTION
            "-- empty --"
    ::= { lcsStatusHardwareInfo 90 }

-- {NODE} 1.3.6.1.4.1.2356.11.1.47.91
lcsStatusHardwareInfoPE OBJECT IDENTIFIER ::= { lcsStatusHardwareInfo 91 }

-- {NODE} 1.3.6.1.4.1.2356.11.1.47.91.1
lcsStatusHardwareInfoPEBMAN OBJECT IDENTIFIER ::= { lcsStatusHardwareInfoPE 1 }

-- {SCALAR} 1.3.6.1.4.1.2356.11.1.47.91.1.1
lcsStatusHardwareInfoPEBMANInvalidCommands OBJECT-TYPE
    SYNTAX     Integer32 (0..2147483647)
    MAX-ACCESS read-only
    STATUS     current
    DESCRIPTION
            "-- empty --"
    ::= { lcsStatusHardwareInfoPEBMAN 1 }

-- {SCALAR} 1.3.6.1.4.1.2356.11.1.47.91.1.2
lcsStatusHardwareInfoPEBMANFbprThresholdReached OBJECT-TYPE
    SYNTAX     Integer32 (0..2147483647)
    MAX-ACCESS read-only
    STATUS     current
    DESCRIPTION
            "-- empty --"
    ::= { lcsStatusHardwareInfoPEBMAN 2 }

-- {SCALAR} 1.3.6.1.4.1.2356.11.1.47.91.1.3
lcsStatusHardwareInfoPEBMANSingleBitEccError OBJECT-TYPE
    SYNTAX     Integer32 (0..2147483647)
    MAX-ACCESS read-only
    STATUS     current
    DESCRIPTION
            "-- empty --"
    ::= { lcsStatusHardwareInfoPEBMAN 3 }

-- {SCALAR} 1.3.6.1.4.1.2356.11.1.47.91.1.4
lcsStatusHardwareInfoPEBMANMultipleBitEccErrors OBJECT-TYPE
    SYNTAX     Integer32 (0..2147483647)
    MAX-ACCESS read-only
    STATUS     current
    DESCRIPTION
            "-- empty --"
    ::= { lcsStatusHardwareInfoPEBMAN 4 }

-- {SCALAR} 1.3.6.1.4.1.2356.11.1.47.91.1.5
lcsStatusHardwareInfoPEBMANInvalidExceptions OBJECT-TYPE
    SYNTAX     Integer32 (0..2147483647)
    MAX-ACCESS read-only
    STATUS     current
    DESCRIPTION
            "-- empty --"
    ::= { lcsStatusHardwareInfoPEBMAN 5 }

-- {SCALAR} 1.3.6.1.4.1.2356.11.1.47.91.1.6
lcsStatusHardwareInfoPEBMANOutOfBuffer OBJECT-TYPE
    SYNTAX     Integer32 (0..2147483647)
    MAX-ACCESS read-only
    STATUS     current
    DESCRIPTION
            "-- empty --"
    ::= { lcsStatusHardwareInfoPEBMAN 6 }

-- {NODE} 1.3.6.1.4.1.2356.11.1.47.91.2
lcsStatusHardwareInfoPEQMAN OBJECT IDENTIFIER ::= { lcsStatusHardwareInfoPE 2 }

-- {SCALAR} 1.3.6.1.4.1.2356.11.1.47.91.2.1
lcsStatusHardwareInfoPEQMANInitiatorDataError OBJECT-TYPE
    SYNTAX     Integer32 (0..2147483647)
    MAX-ACCESS read-only
    STATUS     current
    DESCRIPTION
            "-- empty --"
    ::= { lcsStatusHardwareInfoPEQMAN 1 }

-- {SCALAR} 1.3.6.1.4.1.2356.11.1.47.91.2.2
lcsStatusHardwareInfoPEQMANCorenetTargetDataError OBJECT-TYPE
    SYNTAX     Integer32 (0..2147483647)
    MAX-ACCESS read-only
    STATUS     current
    DESCRIPTION
            "-- empty --"
    ::= { lcsStatusHardwareInfoPEQMAN 2 }

-- {SCALAR} 1.3.6.1.4.1.2356.11.1.47.91.2.3
lcsStatusHardwareInfoPEQMANInvalidTargetTransaction OBJECT-TYPE
    SYNTAX     Integer32 (0..2147483647)
    MAX-ACCESS read-only
    STATUS     current
    DESCRIPTION
            "-- empty --"
    ::= { lcsStatusHardwareInfoPEQMAN 3 }

-- {SCALAR} 1.3.6.1.4.1.2356.11.1.47.91.2.4
lcsStatusHardwareInfoPEQMANPfdrLowWatermarkInterrupt OBJECT-TYPE
    SYNTAX     Integer32 (0..2147483647)
    MAX-ACCESS read-only
    STATUS     current
    DESCRIPTION
            "-- empty --"
    ::= { lcsStatusHardwareInfoPEQMAN 4 }

-- {SCALAR} 1.3.6.1.4.1.2356.11.1.47.91.2.5
lcsStatusHardwareInfoPEQMANPfdrEnqueuesBlockedInterrupt OBJECT-TYPE
    SYNTAX     Integer32 (0..2147483647)
    MAX-ACCESS read-only
    STATUS     current
    DESCRIPTION
            "-- empty --"
    ::= { lcsStatusHardwareInfoPEQMAN 5 }

-- {SCALAR} 1.3.6.1.4.1.2356.11.1.47.91.2.6
lcsStatusHardwareInfoPEQMANSingleBitEccError OBJECT-TYPE
    SYNTAX     Integer32 (0..2147483647)
    MAX-ACCESS read-only
    STATUS     current
    DESCRIPTION
            "-- empty --"
    ::= { lcsStatusHardwareInfoPEQMAN 6 }

-- {SCALAR} 1.3.6.1.4.1.2356.11.1.47.91.2.7
lcsStatusHardwareInfoPEQMANMultipleBitEccErrors OBJECT-TYPE
    SYNTAX     Integer32 (0..2147483647)
    MAX-ACCESS read-only
    STATUS     current
    DESCRIPTION
            "-- empty --"
    ::= { lcsStatusHardwareInfoPEQMAN 7 }

-- {SCALAR} 1.3.6.1.4.1.2356.11.1.47.91.2.8
lcsStatusHardwareInfoPEQMANInvalidCommands OBJECT-TYPE
    SYNTAX     Integer32 (0..2147483647)
    MAX-ACCESS read-only
    STATUS     current
    DESCRIPTION
            "-- empty --"
    ::= { lcsStatusHardwareInfoPEQMAN 8 }

-- {SCALAR} 1.3.6.1.4.1.2356.11.1.47.91.2.9
lcsStatusHardwareInfoPEQMANDequeueDCP OBJECT-TYPE
    SYNTAX     Integer32 (0..2147483647)
    MAX-ACCESS read-only
    STATUS     current
    DESCRIPTION
            ""
    ::= { lcsStatusHardwareInfoPEQMAN 9 }

-- {SCALAR} 1.3.6.1.4.1.2356.11.1.47.91.2.10
lcsStatusHardwareInfoPEQMANInvalidDequeueFqInterrupt OBJECT-TYPE
    SYNTAX     Integer32 (0..2147483647)
    MAX-ACCESS read-only
    STATUS     current
    DESCRIPTION
            "-- empty --"
    ::= { lcsStatusHardwareInfoPEQMAN 10 }

-- {SCALAR} 1.3.6.1.4.1.2356.11.1.47.91.2.11
lcsStatusHardwareInfoPEQMANInvalidDequeueSourceInterrupt OBJECT-TYPE
    SYNTAX     Integer32 (0..2147483647)
    MAX-ACCESS read-only
    STATUS     current
    DESCRIPTION
            "-- empty --"
    ::= { lcsStatusHardwareInfoPEQMAN 11 }

-- {SCALAR} 1.3.6.1.4.1.2356.11.1.47.91.2.12
lcsStatusHardwareInfoPEQMANInvalidDequeueQueueInterrupt OBJECT-TYPE
    SYNTAX     Integer32 (0..2147483647)
    MAX-ACCESS read-only
    STATUS     current
    DESCRIPTION
            "-- empty --"
    ::= { lcsStatusHardwareInfoPEQMAN 12 }

-- {SCALAR} 1.3.6.1.4.1.2356.11.1.47.91.2.13
lcsStatusHardwareInfoPEQMANInvalidEnqueueOverflowInterrupt OBJECT-TYPE
    SYNTAX     Integer32 (0..2147483647)
    MAX-ACCESS read-only
    STATUS     current
    DESCRIPTION
            "-- empty --"
    ::= { lcsStatusHardwareInfoPEQMAN 13 }

-- {SCALAR} 1.3.6.1.4.1.2356.11.1.47.91.2.14
lcsStatusHardwareInfoPEQMANInvalidEnqueueStateInterrupt OBJECT-TYPE
    SYNTAX     Integer32 (0..2147483647)
    MAX-ACCESS read-only
    STATUS     current
    DESCRIPTION
            "-- empty --"
    ::= { lcsStatusHardwareInfoPEQMAN 14 }

-- {SCALAR} 1.3.6.1.4.1.2356.11.1.47.91.2.15
lcsStatusHardwareInfoPEQMANInvalidEnqueueChannelInterrupt OBJECT-TYPE
    SYNTAX     Integer32 (0..2147483647)
    MAX-ACCESS read-only
    STATUS     current
    DESCRIPTION
            "-- empty --"
    ::= { lcsStatusHardwareInfoPEQMAN 15 }

-- {SCALAR} 1.3.6.1.4.1.2356.11.1.47.91.2.16
lcsStatusHardwareInfoPEQMANInvalidEnqueueQueueInterrupt OBJECT-TYPE
    SYNTAX     Integer32 (0..2147483647)
    MAX-ACCESS read-only
    STATUS     current
    DESCRIPTION
            "-- empty --"
    ::= { lcsStatusHardwareInfoPEQMAN 16 }

-- {SCALAR} 1.3.6.1.4.1.2356.11.1.47.91.2.17
lcsStatusHardwareInfoPEQMANInvalidExceptions OBJECT-TYPE
    SYNTAX     Integer32 (0..2147483647)
    MAX-ACCESS read-only
    STATUS     current
    DESCRIPTION
            "-- empty --"
    ::= { lcsStatusHardwareInfoPEQMAN 17 }

-- {NODE} 1.3.6.1.4.1.2356.11.1.47.91.3
lcsStatusHardwareInfoPEFMAN OBJECT IDENTIFIER ::= { lcsStatusHardwareInfoPE 3 }

-- {SCALAR} 1.3.6.1.4.1.2356.11.1.47.91.3.1
lcsStatusHardwareInfoPEFMANDmaBusError OBJECT-TYPE
    SYNTAX     Integer32 (0..2147483647)
    MAX-ACCESS read-only
    STATUS     current
    DESCRIPTION
            "-- empty --"
    ::= { lcsStatusHardwareInfoPEFMAN 1 }

-- {SCALAR} 1.3.6.1.4.1.2356.11.1.47.91.3.2
lcsStatusHardwareInfoPEFMANReadBufferEccError OBJECT-TYPE
    SYNTAX     Integer32 (0..2147483647)
    MAX-ACCESS read-only
    STATUS     current
    DESCRIPTION
            "-- empty --"
    ::= { lcsStatusHardwareInfoPEFMAN 2 }

-- {SCALAR} 1.3.6.1.4.1.2356.11.1.47.91.3.3
lcsStatusHardwareInfoPEFMANSystemWriteBufferEccError OBJECT-TYPE
    SYNTAX     Integer32 (0..2147483647)
    MAX-ACCESS read-only
    STATUS     current
    DESCRIPTION
            "-- empty --"
    ::= { lcsStatusHardwareInfoPEFMAN 3 }

-- {SCALAR} 1.3.6.1.4.1.2356.11.1.47.91.3.4
lcsStatusHardwareInfoPEFMANFmanWriteBufferEccError OBJECT-TYPE
    SYNTAX     Integer32 (0..2147483647)
    MAX-ACCESS read-only
    STATUS     current
    DESCRIPTION
            "-- empty --"
    ::= { lcsStatusHardwareInfoPEFMAN 4 }

-- {SCALAR} 1.3.6.1.4.1.2356.11.1.47.91.3.5
lcsStatusHardwareInfoPEFMANStallOfTasksOnFpm OBJECT-TYPE
    SYNTAX     Integer32 (0..2147483647)
    MAX-ACCESS read-only
    STATUS     current
    DESCRIPTION
            "-- empty --"
    ::= { lcsStatusHardwareInfoPEFMAN 5 }

-- {SCALAR} 1.3.6.1.4.1.2356.11.1.47.91.3.6
lcsStatusHardwareInfoPEFMANSingleEccErrorOnFpm OBJECT-TYPE
    SYNTAX     Integer32 (0..2147483647)
    MAX-ACCESS read-only
    STATUS     current
    DESCRIPTION
            "-- empty --"
    ::= { lcsStatusHardwareInfoPEFMAN 6 }

-- {SCALAR} 1.3.6.1.4.1.2356.11.1.47.91.3.7
lcsStatusHardwareInfoPEFMANDoubleEccErrorOnFpm OBJECT-TYPE
    SYNTAX     Integer32 (0..2147483647)
    MAX-ACCESS read-only
    STATUS     current
    DESCRIPTION
            "-- empty --"
    ::= { lcsStatusHardwareInfoPEFMAN 7 }

-- {SCALAR} 1.3.6.1.4.1.2356.11.1.47.91.3.8
lcsStatusHardwareInfoPEFMANSingleEccErrorOnQmi OBJECT-TYPE
    SYNTAX     Integer32 (0..2147483647)
    MAX-ACCESS read-only
    STATUS     current
    DESCRIPTION
            "-- empty --"
    ::= { lcsStatusHardwareInfoPEFMAN 8 }

-- {SCALAR} 1.3.6.1.4.1.2356.11.1.47.91.3.9
lcsStatusHardwareInfoPEFMANDoubleEccErrorOnQmi OBJECT-TYPE
    SYNTAX     Integer32 (0..2147483647)
    MAX-ACCESS read-only
    STATUS     current
    DESCRIPTION
            "-- empty --"
    ::= { lcsStatusHardwareInfoPEFMAN 9 }

-- {SCALAR} 1.3.6.1.4.1.2356.11.1.47.91.3.10
lcsStatusHardwareInfoPEFMANDequeueFromUnknownPortId OBJECT-TYPE
    SYNTAX     Integer32 (0..2147483647)
    MAX-ACCESS read-only
    STATUS     current
    DESCRIPTION
            "-- empty --"
    ::= { lcsStatusHardwareInfoPEFMAN 10 }

-- {SCALAR} 1.3.6.1.4.1.2356.11.1.47.91.3.11
lcsStatusHardwareInfoPEFMANLinkedListRamEccError OBJECT-TYPE
    SYNTAX     Integer32 (0..2147483647)
    MAX-ACCESS read-only
    STATUS     current
    DESCRIPTION
            "-- empty --"
    ::= { lcsStatusHardwareInfoPEFMAN 11 }

-- {SCALAR} 1.3.6.1.4.1.2356.11.1.47.91.3.12
lcsStatusHardwareInfoPEFMANStorageProfileEccError OBJECT-TYPE
    SYNTAX     Integer32 (0..2147483647)
    MAX-ACCESS read-only
    STATUS     current
    DESCRIPTION
            "-- empty --"
    ::= { lcsStatusHardwareInfoPEFMAN 12 }

-- {SCALAR} 1.3.6.1.4.1.2356.11.1.47.91.3.13
lcsStatusHardwareInfoPEFMANStatisticsCountRamEccError OBJECT-TYPE
    SYNTAX     Integer32 (0..2147483647)
    MAX-ACCESS read-only
    STATUS     current
    DESCRIPTION
            "-- empty --"
    ::= { lcsStatusHardwareInfoPEFMAN 13 }

-- {SCALAR} 1.3.6.1.4.1.2356.11.1.47.91.3.14
lcsStatusHardwareInfoPEFMANDispatchRamEccError OBJECT-TYPE
    SYNTAX     Integer32 (0..2147483647)
    MAX-ACCESS read-only
    STATUS     current
    DESCRIPTION
            "-- empty --"
    ::= { lcsStatusHardwareInfoPEFMAN 14 }

-- {SCALAR} 1.3.6.1.4.1.2356.11.1.47.91.3.15
lcsStatusHardwareInfoPEFMANDoubleBitEccErrorOnIram OBJECT-TYPE
    SYNTAX     Integer32 (0..2147483647)
    MAX-ACCESS read-only
    STATUS     current
    DESCRIPTION
            "-- empty --"
    ::= { lcsStatusHardwareInfoPEFMAN 15 }

-- {SCALAR} 1.3.6.1.4.1.2356.11.1.47.91.3.16
lcsStatusHardwareInfoPEFMANDoubleBitEccErrorOnMuram OBJECT-TYPE
    SYNTAX     Integer32 (0..2147483647)
    MAX-ACCESS read-only
    STATUS     current
    DESCRIPTION
            "-- empty --"
    ::= { lcsStatusHardwareInfoPEFMAN 16 }

-- {SCALAR} 1.3.6.1.4.1.2356.11.1.47.91.3.17
lcsStatusHardwareInfoPEFMANInvalidExceptions OBJECT-TYPE
    SYNTAX     Integer32 (0..2147483647)
    MAX-ACCESS read-only
    STATUS     current
    DESCRIPTION
            "-- empty --"
    ::= { lcsStatusHardwareInfoPEFMAN 17 }

-- {SCALAR} 1.3.6.1.4.1.2356.11.1.47.91.3.18
lcsStatusHardwareInfoPEFMANZeroLengthPacket OBJECT-TYPE
    SYNTAX     Integer32 (0..2147483647)
    MAX-ACCESS read-only
    STATUS     current
    DESCRIPTION
            "-- empty --"
    ::= { lcsStatusHardwareInfoPEFMAN 18 }

-- {SCALAR} 1.3.6.1.4.1.2356.11.1.47.91.3.19
lcsStatusHardwareInfoPEFMANBadFrameReceived OBJECT-TYPE
    SYNTAX     Integer32 (0..2147483647)
    MAX-ACCESS read-only
    STATUS     current
    DESCRIPTION
            "-- empty --"
    ::= { lcsStatusHardwareInfoPEFMAN 19 }

-- {NODE} 1.3.6.1.4.1.2356.11.1.47.91.4
lcsStatusHardwareInfoPEDrpPack OBJECT IDENTIFIER ::= { lcsStatusHardwareInfoPE 4 }

-- {SCALAR} 1.3.6.1.4.1.2356.11.1.47.91.4.1
lcsStatusHardwareInfoPEDrpPackCongestionGroupTailDrop OBJECT-TYPE
    SYNTAX     Integer32 (0..2147483647)
    MAX-ACCESS read-only
    STATUS     current
    DESCRIPTION
            "-- empty --"
    ::= { lcsStatusHardwareInfoPEDrpPack 1 }

-- {SCALAR} 1.3.6.1.4.1.2356.11.1.47.91.4.2
lcsStatusHardwareInfoPEDrpPackCongestionGroupWredDrop OBJECT-TYPE
    SYNTAX     Integer32 (0..2147483647)
    MAX-ACCESS read-only
    STATUS     current
    DESCRIPTION
            "-- empty --"
    ::= { lcsStatusHardwareInfoPEDrpPack 2 }

-- {SCALAR} 1.3.6.1.4.1.2356.11.1.47.91.4.3
lcsStatusHardwareInfoPEDrpPackFqidTailDrop OBJECT-TYPE
    SYNTAX     Integer32 (0..2147483647)
    MAX-ACCESS read-only
    STATUS     current
    DESCRIPTION
            "-- empty --"
    ::= { lcsStatusHardwareInfoPEDrpPack 3 }

-- {SCALAR} 1.3.6.1.4.1.2356.11.1.47.91.4.4
lcsStatusHardwareInfoPEDrpPackCongestionGroupOverflow OBJECT-TYPE
    SYNTAX     Integer32 (0..2147483647)
    MAX-ACCESS read-only
    STATUS     current
    DESCRIPTION
            "-- empty --"
    ::= { lcsStatusHardwareInfoPEDrpPack 4 }

-- {NODE} 1.3.6.1.4.1.2356.11.1.47.91.5
lcsStatusHardwareInfoPEMAC OBJECT IDENTIFIER ::= { lcsStatusHardwareInfoPE 5 }

-- {SCALAR} 1.3.6.1.4.1.2356.11.1.47.91.5.18
lcsStatusHardwareInfoPEMACBabblingReceiveError OBJECT-TYPE
    SYNTAX     Integer32 (0..2147483647)
    MAX-ACCESS read-only
    STATUS     current
    DESCRIPTION
            "-- empty --"
    ::= { lcsStatusHardwareInfoPEMAC 18 }

-- {SCALAR} 1.3.6.1.4.1.2356.11.1.47.91.5.19
lcsStatusHardwareInfoPEMACReceiveControl OBJECT-TYPE
    SYNTAX     Integer32 (0..2147483647)
    MAX-ACCESS read-only
    STATUS     current
    DESCRIPTION
            "-- empty --"
    ::= { lcsStatusHardwareInfoPEMAC 19 }

-- {SCALAR} 1.3.6.1.4.1.2356.11.1.47.91.5.20
lcsStatusHardwareInfoPEMACGracefulTransmitStop OBJECT-TYPE
    SYNTAX     Integer32 (0..2147483647)
    MAX-ACCESS read-only
    STATUS     current
    DESCRIPTION
            "-- empty --"
    ::= { lcsStatusHardwareInfoPEMAC 20 }

-- {SCALAR} 1.3.6.1.4.1.2356.11.1.47.91.5.21
lcsStatusHardwareInfoPEMACBabblingTransmitError OBJECT-TYPE
    SYNTAX     Integer32 (0..2147483647)
    MAX-ACCESS read-only
    STATUS     current
    DESCRIPTION
            "-- empty --"
    ::= { lcsStatusHardwareInfoPEMAC 21 }

-- {SCALAR} 1.3.6.1.4.1.2356.11.1.47.91.5.22
lcsStatusHardwareInfoPEMACTransmitControl OBJECT-TYPE
    SYNTAX     Integer32 (0..2147483647)
    MAX-ACCESS read-only
    STATUS     current
    DESCRIPTION
            "-- empty --"
    ::= { lcsStatusHardwareInfoPEMAC 22 }

-- {SCALAR} 1.3.6.1.4.1.2356.11.1.47.91.5.23
lcsStatusHardwareInfoPEMACTransmitError OBJECT-TYPE
    SYNTAX     Integer32 (0..2147483647)
    MAX-ACCESS read-only
    STATUS     current
    DESCRIPTION
            "-- empty --"
    ::= { lcsStatusHardwareInfoPEMAC 23 }

-- {SCALAR} 1.3.6.1.4.1.2356.11.1.47.91.5.24
lcsStatusHardwareInfoPEMACLateCollision OBJECT-TYPE
    SYNTAX     Integer32 (0..2147483647)
    MAX-ACCESS read-only
    STATUS     current
    DESCRIPTION
            "-- empty --"
    ::= { lcsStatusHardwareInfoPEMAC 24 }

-- {SCALAR} 1.3.6.1.4.1.2356.11.1.47.91.5.25
lcsStatusHardwareInfoPEMACCollisionRetryLimit OBJECT-TYPE
    SYNTAX     Integer32 (0..2147483647)
    MAX-ACCESS read-only
    STATUS     current
    DESCRIPTION
            "-- empty --"
    ::= { lcsStatusHardwareInfoPEMAC 25 }

-- {SCALAR} 1.3.6.1.4.1.2356.11.1.47.91.5.26
lcsStatusHardwareInfoPEMACTransmitFifoUnderrun OBJECT-TYPE
    SYNTAX     Integer32 (0..2147483647)
    MAX-ACCESS read-only
    STATUS     current
    DESCRIPTION
            "-- empty --"
    ::= { lcsStatusHardwareInfoPEMAC 26 }

-- {SCALAR} 1.3.6.1.4.1.2356.11.1.47.91.5.27
lcsStatusHardwareInfoPEMACMagicPacketDetection OBJECT-TYPE
    SYNTAX     Integer32 (0..2147483647)
    MAX-ACCESS read-only
    STATUS     current
    DESCRIPTION
            "-- empty --"
    ::= { lcsStatusHardwareInfoPEMAC 27 }

-- {SCALAR} 1.3.6.1.4.1.2356.11.1.47.91.5.28
lcsStatusHardwareInfoPEMACMiiManagementReadCompletion OBJECT-TYPE
    SYNTAX     Integer32 (0..2147483647)
    MAX-ACCESS read-only
    STATUS     current
    DESCRIPTION
            "-- empty --"
    ::= { lcsStatusHardwareInfoPEMAC 28 }

-- {SCALAR} 1.3.6.1.4.1.2356.11.1.47.91.5.29
lcsStatusHardwareInfoPEMACMiiManagementWriteCompletion OBJECT-TYPE
    SYNTAX     Integer32 (0..2147483647)
    MAX-ACCESS read-only
    STATUS     current
    DESCRIPTION
            "-- empty --"
    ::= { lcsStatusHardwareInfoPEMAC 29 }

-- {SCALAR} 1.3.6.1.4.1.2356.11.1.47.91.5.30
lcsStatusHardwareInfoPEMACGracefulReceiveStop OBJECT-TYPE
    SYNTAX     Integer32 (0..2147483647)
    MAX-ACCESS read-only
    STATUS     current
    DESCRIPTION
            "-- empty --"
    ::= { lcsStatusHardwareInfoPEMAC 30 }

-- {SCALAR} 1.3.6.1.4.1.2356.11.1.47.91.5.31
lcsStatusHardwareInfoPEMACInternalDataErrorOnTransmit OBJECT-TYPE
    SYNTAX     Integer32 (0..2147483647)
    MAX-ACCESS read-only
    STATUS     current
    DESCRIPTION
            "-- empty --"
    ::= { lcsStatusHardwareInfoPEMAC 31 }

-- {SCALAR} 1.3.6.1.4.1.2356.11.1.47.91.5.32
lcsStatusHardwareInfoPEMACInternalDataErrorOnReceive OBJECT-TYPE
    SYNTAX     Integer32 (0..2147483647)
    MAX-ACCESS read-only
    STATUS     current
    DESCRIPTION
            "-- empty --"
    ::= { lcsStatusHardwareInfoPEMAC 32 }

-- {SCALAR} 1.3.6.1.4.1.2356.11.1.47.91.5.33
lcsStatusHardwareInfoPEMACTimeStampReceiveError OBJECT-TYPE
    SYNTAX     Integer32 (0..2147483647)
    MAX-ACCESS read-only
    STATUS     current
    DESCRIPTION
            "-- empty --"
    ::= { lcsStatusHardwareInfoPEMAC 33 }

-- {SCALAR} 1.3.6.1.4.1.2356.11.1.47.91.5.34
lcsStatusHardwareInfoPEMACTimeStampFifoEccError OBJECT-TYPE
    SYNTAX     Integer32 (0..2147483647)
    MAX-ACCESS read-only
    STATUS     current
    DESCRIPTION
            "-- empty --"
    ::= { lcsStatusHardwareInfoPEMAC 34 }

-- {SCALAR} 1.3.6.1.4.1.2356.11.1.47.91.5.35
lcsStatusHardwareInfoPEMACInvalidExceptions OBJECT-TYPE
    SYNTAX     Integer32 (0..2147483647)
    MAX-ACCESS read-only
    STATUS     current
    DESCRIPTION
            "-- empty --"
    ::= { lcsStatusHardwareInfoPEMAC 35 }

-- {NODE} 1.3.6.1.4.1.2356.11.1.47.91.6
lcsStatusHardwareInfoPEPCD OBJECT IDENTIFIER ::= { lcsStatusHardwareInfoPE 6 }

-- {SCALAR} 1.3.6.1.4.1.2356.11.1.47.91.6.1
lcsStatusHardwareInfoPEPCDInvalidExceptions OBJECT-TYPE
    SYNTAX     Integer32 (0..2147483647)
    MAX-ACCESS read-only
    STATUS     current
    DESCRIPTION
            "-- empty --"
    ::= { lcsStatusHardwareInfoPEPCD 1 }

-- {SCALAR} 1.3.6.1.4.1.2356.11.1.47.91.6.2
lcsStatusHardwareInfoPEPCDKeygenDoubleBitEccError OBJECT-TYPE
    SYNTAX     Integer32 (0..2147483647)
    MAX-ACCESS read-only
    STATUS     current
    DESCRIPTION
            "-- empty --"
    ::= { lcsStatusHardwareInfoPEPCD 2 }

-- {SCALAR} 1.3.6.1.4.1.2356.11.1.47.91.6.3
lcsStatusHardwareInfoPEPCDPolicerDoubleBitEccError OBJECT-TYPE
    SYNTAX     Integer32 (0..2147483647)
    MAX-ACCESS read-only
    STATUS     current
    DESCRIPTION
            "-- empty --"
    ::= { lcsStatusHardwareInfoPEPCD 3 }

-- {SCALAR} 1.3.6.1.4.1.2356.11.1.47.91.6.4
lcsStatusHardwareInfoPEPCDKeygenKeySizeOverflow OBJECT-TYPE
    SYNTAX     Integer32 (0..2147483647)
    MAX-ACCESS read-only
    STATUS     current
    DESCRIPTION
            "-- empty --"
    ::= { lcsStatusHardwareInfoPEPCD 4 }

-- {SCALAR} 1.3.6.1.4.1.2356.11.1.47.91.6.5
lcsStatusHardwareInfoPEPCDPolicerAccessToNonInitializedProfile OBJECT-TYPE
    SYNTAX     Integer32 (0..2147483647)
    MAX-ACCESS read-only
    STATUS     current
    DESCRIPTION
            "-- empty --"
    ::= { lcsStatusHardwareInfoPEPCD 5 }

-- {SCALAR} 1.3.6.1.4.1.2356.11.1.47.91.6.6
lcsStatusHardwareInfoPEPCDPolicerRamSelfInitialization OBJECT-TYPE
    SYNTAX     Integer32 (0..2147483647)
    MAX-ACCESS read-only
    STATUS     current
    DESCRIPTION
            "-- empty --"
    ::= { lcsStatusHardwareInfoPEPCD 6 }

-- {SCALAR} 1.3.6.1.4.1.2356.11.1.47.91.6.7
lcsStatusHardwareInfoPEPCDPolicerAtomicAction OBJECT-TYPE
    SYNTAX     Integer32 (0..2147483647)
    MAX-ACCESS read-only
    STATUS     current
    DESCRIPTION
            "-- empty --"
    ::= { lcsStatusHardwareInfoPEPCD 7 }

-- {SCALAR} 1.3.6.1.4.1.2356.11.1.47.91.6.8
lcsStatusHardwareInfoPEPCDParserSingleBitEccError OBJECT-TYPE
    SYNTAX     Integer32 (0..2147483647)
    MAX-ACCESS read-only
    STATUS     current
    DESCRIPTION
            "-- empty --"
    ::= { lcsStatusHardwareInfoPEPCD 8 }

-- {SCALAR} 1.3.6.1.4.1.2356.11.1.47.91.6.9
lcsStatusHardwareInfoPEPCDParserDoubleBitEccError OBJECT-TYPE
    SYNTAX     Integer32 (0..2147483647)
    MAX-ACCESS read-only
    STATUS     current
    DESCRIPTION
            "-- empty --"
    ::= { lcsStatusHardwareInfoPEPCD 9 }

-- {NODE} 1.3.6.1.4.1.2356.11.1.47.91.7
lcsStatusHardwareInfoPEPAMU OBJECT IDENTIFIER ::= { lcsStatusHardwareInfoPE 7 }

-- {SCALAR} 1.3.6.1.4.1.2356.11.1.47.91.7.1
lcsStatusHardwareInfoPEPAMUAccessViolations OBJECT-TYPE
    SYNTAX     Integer32 (0..2147483647)
    MAX-ACCESS read-only
    STATUS     current
    DESCRIPTION
            "-- empty --"
    ::= { lcsStatusHardwareInfoPEPAMU 1 }

-- {TABLE} 1.3.6.1.4.1.2356.11.1.47.92
lcsStatusHardwareInfoNandStatisticTable OBJECT-TYPE
    SYNTAX     SEQUENCE OF LcsStatusHardwareInfoNandStatisticEntry
    MAX-ACCESS not-accessible
    STATUS     current
    DESCRIPTION
            "-- empty --"
    ::= { lcsStatusHardwareInfo 92 }

-- {ROW} 1.3.6.1.4.1.2356.11.1.47.92.1
lcsStatusHardwareInfoNandStatisticEntry OBJECT-TYPE
    SYNTAX     LcsStatusHardwareInfoNandStatisticEntry
    MAX-ACCESS not-accessible
    STATUS     current
    DESCRIPTION
            ""
    INDEX {
            lcsStatusHardwareInfoNandStatisticEntryNandStatistic
          }
    ::= { lcsStatusHardwareInfoNandStatisticTable 1 }

LcsStatusHardwareInfoNandStatisticEntry ::= SEQUENCE {
            lcsStatusHardwareInfoNandStatisticEntryNandStatistic INTEGER,
            lcsStatusHardwareInfoNandStatisticEntryManufacturer DisplayString,
            lcsStatusHardwareInfoNandStatisticEntryIdBits DisplayString,
            lcsStatusHardwareInfoNandStatisticEntryTotalSize Integer32,
            lcsStatusHardwareInfoNandStatisticEntryBlocks Integer32,
            lcsStatusHardwareInfoNandStatisticEntryBlockSize Integer32,
            lcsStatusHardwareInfoNandStatisticEntryPages Integer32,
            lcsStatusHardwareInfoNandStatisticEntryPageSize Integer32,
            lcsStatusHardwareInfoNandStatisticEntryOobSize Integer32,
            lcsStatusHardwareInfoNandStatisticEntryCorrectableReadErrors Integer32,
            lcsStatusHardwareInfoNandStatisticEntryUncorrectableReadErrors Integer32,
            lcsStatusHardwareInfoNandStatisticEntryFlashTimeouts Integer32,
            lcsStatusHardwareInfoNandStatisticEntryInterruptTimeouts Integer32,
            lcsStatusHardwareInfoNandStatisticEntryWriteFailures Integer32,
            lcsStatusHardwareInfoNandStatisticEntryEraseFailures Integer32,
            lcsStatusHardwareInfoNandStatisticEntryAbsoluteMaxEraseTime Integer32,
            lcsStatusHardwareInfoNandStatisticEntryAbsoluteMinEraseTime Integer32,
            lcsStatusHardwareInfoNandStatisticEntryAverageMaxEraseTime Integer32,
            lcsStatusHardwareInfoNandStatisticEntryAverageMinEraseTime Integer32
    }

-- {COLUMN} 1.3.6.1.4.1.2356.11.1.47.92.1.1
lcsStatusHardwareInfoNandStatisticEntryNandStatistic OBJECT-TYPE
    SYNTAX     INTEGER {
                  eChip1 (1)
            }
    MAX-ACCESS read-only
    STATUS     current
    DESCRIPTION
            "-- empty --"
    ::= { lcsStatusHardwareInfoNandStatisticEntry 1 }

-- {COLUMN} 1.3.6.1.4.1.2356.11.1.47.92.1.2
lcsStatusHardwareInfoNandStatisticEntryManufacturer OBJECT-TYPE
    SYNTAX     DisplayString (SIZE(0..255))
    MAX-ACCESS read-only
    STATUS     current
    DESCRIPTION
            "-- empty --"
    ::= { lcsStatusHardwareInfoNandStatisticEntry 2 }

-- {COLUMN} 1.3.6.1.4.1.2356.11.1.47.92.1.3
lcsStatusHardwareInfoNandStatisticEntryIdBits OBJECT-TYPE
    SYNTAX     DisplayString (SIZE(0..255))
    MAX-ACCESS read-only
    STATUS     current
    DESCRIPTION
            "-- empty --"
    ::= { lcsStatusHardwareInfoNandStatisticEntry 3 }

-- {COLUMN} 1.3.6.1.4.1.2356.11.1.47.92.1.4
lcsStatusHardwareInfoNandStatisticEntryTotalSize OBJECT-TYPE
    SYNTAX     Integer32 (0..2147483647)
    MAX-ACCESS read-only
    STATUS     current
    DESCRIPTION
            "-- empty --"
    ::= { lcsStatusHardwareInfoNandStatisticEntry 4 }

-- {COLUMN} 1.3.6.1.4.1.2356.11.1.47.92.1.5
lcsStatusHardwareInfoNandStatisticEntryBlocks OBJECT-TYPE
    SYNTAX     Integer32 (0..2147483647)
    MAX-ACCESS read-only
    STATUS     current
    DESCRIPTION
            "-- empty --"
    ::= { lcsStatusHardwareInfoNandStatisticEntry 5 }

-- {COLUMN} 1.3.6.1.4.1.2356.11.1.47.92.1.6
lcsStatusHardwareInfoNandStatisticEntryBlockSize OBJECT-TYPE
    SYNTAX     Integer32 (0..2147483647)
    MAX-ACCESS read-only
    STATUS     current
    DESCRIPTION
            "-- empty --"
    ::= { lcsStatusHardwareInfoNandStatisticEntry 6 }

-- {COLUMN} 1.3.6.1.4.1.2356.11.1.47.92.1.7
lcsStatusHardwareInfoNandStatisticEntryPages OBJECT-TYPE
    SYNTAX     Integer32 (0..2147483647)
    MAX-ACCESS read-only
    STATUS     current
    DESCRIPTION
            "-- empty --"
    ::= { lcsStatusHardwareInfoNandStatisticEntry 7 }

-- {COLUMN} 1.3.6.1.4.1.2356.11.1.47.92.1.8
lcsStatusHardwareInfoNandStatisticEntryPageSize OBJECT-TYPE
    SYNTAX     Integer32 (0..2147483647)
    MAX-ACCESS read-only
    STATUS     current
    DESCRIPTION
            "-- empty --"
    ::= { lcsStatusHardwareInfoNandStatisticEntry 8 }

-- {COLUMN} 1.3.6.1.4.1.2356.11.1.47.92.1.9
lcsStatusHardwareInfoNandStatisticEntryOobSize OBJECT-TYPE
    SYNTAX     Integer32 (0..2147483647)
    MAX-ACCESS read-only
    STATUS     current
    DESCRIPTION
            "-- empty --"
    ::= { lcsStatusHardwareInfoNandStatisticEntry 9 }

-- {COLUMN} 1.3.6.1.4.1.2356.11.1.47.92.1.10
lcsStatusHardwareInfoNandStatisticEntryCorrectableReadErrors OBJECT-TYPE
    SYNTAX     Integer32 (0..2147483647)
    MAX-ACCESS read-only
    STATUS     current
    DESCRIPTION
            "-- empty --"
    ::= { lcsStatusHardwareInfoNandStatisticEntry 10 }

-- {COLUMN} 1.3.6.1.4.1.2356.11.1.47.92.1.11
lcsStatusHardwareInfoNandStatisticEntryUncorrectableReadErrors OBJECT-TYPE
    SYNTAX     Integer32 (0..2147483647)
    MAX-ACCESS read-only
    STATUS     current
    DESCRIPTION
            "-- empty --"
    ::= { lcsStatusHardwareInfoNandStatisticEntry 11 }

-- {COLUMN} 1.3.6.1.4.1.2356.11.1.47.92.1.12
lcsStatusHardwareInfoNandStatisticEntryFlashTimeouts OBJECT-TYPE
    SYNTAX     Integer32 (0..2147483647)
    MAX-ACCESS read-only
    STATUS     current
    DESCRIPTION
            "-- empty --"
    ::= { lcsStatusHardwareInfoNandStatisticEntry 12 }

-- {COLUMN} 1.3.6.1.4.1.2356.11.1.47.92.1.13
lcsStatusHardwareInfoNandStatisticEntryInterruptTimeouts OBJECT-TYPE
    SYNTAX     Integer32 (0..2147483647)
    MAX-ACCESS read-only
    STATUS     current
    DESCRIPTION
            "-- empty --"
    ::= { lcsStatusHardwareInfoNandStatisticEntry 13 }

-- {COLUMN} 1.3.6.1.4.1.2356.11.1.47.92.1.14
lcsStatusHardwareInfoNandStatisticEntryWriteFailures OBJECT-TYPE
    SYNTAX     Integer32 (0..2147483647)
    MAX-ACCESS read-only
    STATUS     current
    DESCRIPTION
            "-- empty --"
    ::= { lcsStatusHardwareInfoNandStatisticEntry 14 }

-- {COLUMN} 1.3.6.1.4.1.2356.11.1.47.92.1.15
lcsStatusHardwareInfoNandStatisticEntryEraseFailures OBJECT-TYPE
    SYNTAX     Integer32 (0..2147483647)
    MAX-ACCESS read-only
    STATUS     current
    DESCRIPTION
            "-- empty --"
    ::= { lcsStatusHardwareInfoNandStatisticEntry 15 }

-- {COLUMN} 1.3.6.1.4.1.2356.11.1.47.92.1.16
lcsStatusHardwareInfoNandStatisticEntryAbsoluteMaxEraseTime OBJECT-TYPE
    SYNTAX     Integer32 (0..2147483647)
    MAX-ACCESS read-only
    STATUS     current
    DESCRIPTION
            "-- empty --"
    ::= { lcsStatusHardwareInfoNandStatisticEntry 16 }

-- {COLUMN} 1.3.6.1.4.1.2356.11.1.47.92.1.17
lcsStatusHardwareInfoNandStatisticEntryAbsoluteMinEraseTime OBJECT-TYPE
    SYNTAX     Integer32 (0..2147483647)
    MAX-ACCESS read-only
    STATUS     current
    DESCRIPTION
            "-- empty --"
    ::= { lcsStatusHardwareInfoNandStatisticEntry 17 }

-- {COLUMN} 1.3.6.1.4.1.2356.11.1.47.92.1.18
lcsStatusHardwareInfoNandStatisticEntryAverageMaxEraseTime OBJECT-TYPE
    SYNTAX     Integer32 (0..2147483647)
    MAX-ACCESS read-only
    STATUS     current
    DESCRIPTION
            "-- empty --"
    ::= { lcsStatusHardwareInfoNandStatisticEntry 18 }

-- {COLUMN} 1.3.6.1.4.1.2356.11.1.47.92.1.19
lcsStatusHardwareInfoNandStatisticEntryAverageMinEraseTime OBJECT-TYPE
    SYNTAX     Integer32 (0..2147483647)
    MAX-ACCESS read-only
    STATUS     current
    DESCRIPTION
            "-- empty --"
    ::= { lcsStatusHardwareInfoNandStatisticEntry 19 }

-- {TABLE} 1.3.6.1.4.1.2356.11.1.48
lcsStatusChannelTable OBJECT-TYPE
    SYNTAX     SEQUENCE OF LcsStatusChannelEntry
    MAX-ACCESS not-accessible
    STATUS     current
    DESCRIPTION
            ""
    ::= { lcsStatus 48 }

-- {ROW} 1.3.6.1.4.1.2356.11.1.48.1
lcsStatusChannelEntry OBJECT-TYPE
    SYNTAX     LcsStatusChannelEntry
    MAX-ACCESS not-accessible
    STATUS     current
    DESCRIPTION
            ""
    INDEX {
            lcsStatusChannelEntryChan
          }
    ::= { lcsStatusChannelTable 1 }

LcsStatusChannelEntry ::= SEQUENCE {
            lcsStatusChannelEntryChan INTEGER,
            lcsStatusChannelEntryPlci Integer32,
            lcsStatusChannelEntryBus Integer32,
            lcsStatusChannelEntryState Integer32,
            lcsStatusChannelEntryApp INTEGER,
            lcsStatusChannelEntryConnector INTEGER,
            lcsStatusChannelEntryCause Integer32,
            lcsStatusChannelEntryNumber DisplayString,
            lcsStatusChannelEntryCharge Integer32,
            lcsStatusChannelEntryExtra DisplayString,
            lcsStatusChannelEntryConnTime Integer32,
            lcsStatusChannelEntryConnStart Integer32,
            lcsStatusChannelEntryIsdnDisplay DisplayString,
            lcsStatusChannelEntryPhChan Integer32,
            lcsStatusChannelEntryPptpConns Integer32,
            lcsStatusChannelEntryVpnConns Integer32,
            lcsStatusChannelEntrySubaddress Integer32
    }

-- {COLUMN} 1.3.6.1.4.1.2356.11.1.48.1.1
lcsStatusChannelEntryChan OBJECT-TYPE
    SYNTAX     INTEGER {
                  eAdslErr (1),
                  eAdsl1 (2),
                  eAdsl2 (3),
                  eAdsl3 (4),
                  eAdsl4 (5),
                  eAdsl5 (6),
                  eAdsl6 (7),
                  eAdsl7 (8),
                  eAdsl8 (9),
                  eDslErr (257),
                  eDslCh1 (258),
                  eDslCh2 (259),
                  eDslCh3 (260),
                  eDslCh4 (261),
                  eDslCh5 (262),
                  eDslCh6 (263),
                  eDslCh7 (264),
                  eDslCh8 (265),
                  eS01Err (513),
                  eS01B1 (514),
                  eS01B2 (515),
                  eS02Err (516),
                  eS02B1 (517),
                  eS02B2 (518),
                  eAnalog1Err (1025),
                  eAnalog1 (1026),
                  eAnalog2Err (1027),
                  eAnalog2 (1028),
                  eAnalog3Err (1029),
                  eAnalog3 (1030),
                  eAnalog4Err (1031),
                  eAnalog4 (1032),
                  eExtErr (1281),
                  eExt (1282),
                  eVdslErr (2049),
                  eVdslCh1 (2050),
                  eVdslCh2 (2051),
                  eVdslCh3 (2052),
                  eVdslCh4 (2053),
                  eVdslCh5 (2054),
                  eVdslCh6 (2055),
                  eVdslCh7 (2056),
                  eVdslCh8 (2057),
                  eVdsl2Err (2058),
                  eVdsl2Ch1 (2059),
                  eVdsl2Ch2 (2060),
                  eVdsl2Ch3 (2061),
                  eVdsl2Ch4 (2062),
                  eVdsl2Ch5 (2063),
                  eVdsl2Ch6 (2064),
                  eVdsl2Ch7 (2065),
                  eVdsl2Ch8 (2066)
            }
    MAX-ACCESS read-only
    STATUS     current
    DESCRIPTION
            ""
    ::= { lcsStatusChannelEntry 1 }

-- {COLUMN} 1.3.6.1.4.1.2356.11.1.48.1.2
lcsStatusChannelEntryPlci OBJECT-TYPE
    SYNTAX     Integer32 (0..2147483647)
    MAX-ACCESS read-only
    STATUS     current
    DESCRIPTION
            ""
    ::= { lcsStatusChannelEntry 2 }

-- {COLUMN} 1.3.6.1.4.1.2356.11.1.48.1.3
lcsStatusChannelEntryBus OBJECT-TYPE
    SYNTAX     Integer32 (0..2147483647)
    MAX-ACCESS read-only
    STATUS     current
    DESCRIPTION
            ""
    ::= { lcsStatusChannelEntry 3 }

-- {COLUMN} 1.3.6.1.4.1.2356.11.1.48.1.4
lcsStatusChannelEntryState OBJECT-TYPE
    SYNTAX     Integer32 (0..2147483647)
    MAX-ACCESS read-only
    STATUS     current
    DESCRIPTION
            ""
    ::= { lcsStatusChannelEntry 4 }

-- {COLUMN} 1.3.6.1.4.1.2356.11.1.48.1.5
lcsStatusChannelEntryApp OBJECT-TYPE
    SYNTAX     INTEGER {
                  eNone (0),
                  eRouter (1),
                  eCapi (2),
                  eAB (3),
                  eVcm (4),
                  eTimeModule (255)
            }
    MAX-ACCESS read-only
    STATUS     current
    DESCRIPTION
            ""
    ::= { lcsStatusChannelEntry 5 }

-- {COLUMN} 1.3.6.1.4.1.2356.11.1.48.1.6
lcsStatusChannelEntryConnector OBJECT-TYPE
    SYNTAX     INTEGER {
                  eUnk (0),
                  eAct (1),
                  ePas (2),
                  ePerm (3)
            }
    MAX-ACCESS read-only
    STATUS     current
    DESCRIPTION
            ""
    ::= { lcsStatusChannelEntry 6 }

-- {COLUMN} 1.3.6.1.4.1.2356.11.1.48.1.7
lcsStatusChannelEntryCause OBJECT-TYPE
    SYNTAX     Integer32 (0..65535)
    MAX-ACCESS read-write
    STATUS     current
    DESCRIPTION
            ""
    ::= { lcsStatusChannelEntry 7 }

-- {COLUMN} 1.3.6.1.4.1.2356.11.1.48.1.8
lcsStatusChannelEntryNumber OBJECT-TYPE
    SYNTAX     DisplayString (SIZE(0..40))
    MAX-ACCESS read-only
    STATUS     current
    DESCRIPTION
            ""
    ::= { lcsStatusChannelEntry 8 }

-- {COLUMN} 1.3.6.1.4.1.2356.11.1.48.1.10
lcsStatusChannelEntryCharge OBJECT-TYPE
    SYNTAX     Integer32 (0..2147483647)
    MAX-ACCESS read-only
    STATUS     current
    DESCRIPTION
            ""
    ::= { lcsStatusChannelEntry 10 }

-- {COLUMN} 1.3.6.1.4.1.2356.11.1.48.1.11
lcsStatusChannelEntryExtra OBJECT-TYPE
    SYNTAX     DisplayString (SIZE(0..16))
    MAX-ACCESS read-only
    STATUS     current
    DESCRIPTION
            ""
    ::= { lcsStatusChannelEntry 11 }

-- {COLUMN} 1.3.6.1.4.1.2356.11.1.48.1.12
lcsStatusChannelEntryConnTime OBJECT-TYPE
    SYNTAX     Integer32 (0..2147483647)
    MAX-ACCESS read-only
    STATUS     current
    DESCRIPTION
            ""
    ::= { lcsStatusChannelEntry 12 }

-- {COLUMN} 1.3.6.1.4.1.2356.11.1.48.1.13
lcsStatusChannelEntryConnStart OBJECT-TYPE
    SYNTAX     Integer32 (0..2147483647)
    MAX-ACCESS read-only
    STATUS     current
    DESCRIPTION
            ""
    ::= { lcsStatusChannelEntry 13 }

-- {COLUMN} 1.3.6.1.4.1.2356.11.1.48.1.14
lcsStatusChannelEntryIsdnDisplay OBJECT-TYPE
    SYNTAX     DisplayString (SIZE(0..34))
    MAX-ACCESS read-only
    STATUS     current
    DESCRIPTION
            ""
    ::= { lcsStatusChannelEntry 14 }

-- {COLUMN} 1.3.6.1.4.1.2356.11.1.48.1.15
lcsStatusChannelEntryPhChan OBJECT-TYPE
    SYNTAX     Integer32 (0..2147483647)
    MAX-ACCESS read-only
    STATUS     current
    DESCRIPTION
            ""
    ::= { lcsStatusChannelEntry 15 }

-- {COLUMN} 1.3.6.1.4.1.2356.11.1.48.1.16
lcsStatusChannelEntryPptpConns OBJECT-TYPE
    SYNTAX     Integer32 (0..2147483647)
    MAX-ACCESS read-only
    STATUS     current
    DESCRIPTION
            ""
    ::= { lcsStatusChannelEntry 16 }

-- {COLUMN} 1.3.6.1.4.1.2356.11.1.48.1.17
lcsStatusChannelEntryVpnConns OBJECT-TYPE
    SYNTAX     Integer32 (0..2147483647)
    MAX-ACCESS read-only
    STATUS     current
    DESCRIPTION
            ""
    ::= { lcsStatusChannelEntry 17 }

-- {COLUMN} 1.3.6.1.4.1.2356.11.1.48.1.18
lcsStatusChannelEntrySubaddress OBJECT-TYPE
    SYNTAX     Integer32 (0..2147483647)
    MAX-ACCESS read-only
    STATUS     current
    DESCRIPTION
            ""
    ::= { lcsStatusChannelEntry 18 }

-- {NODE} 1.3.6.1.4.1.2356.11.1.49
lcsStatusModemMobile OBJECT IDENTIFIER ::= { lcsStatus 49 }

-- {SCALAR} 1.3.6.1.4.1.2356.11.1.49.1
lcsStatusModemMobileModemInfo OBJECT-TYPE
    SYNTAX     DisplayString (SIZE(0..255))
    MAX-ACCESS read-only
    STATUS     current
    DESCRIPTION
            ""
    ::= { lcsStatusModemMobile 1 }

-- {SCALAR} 1.3.6.1.4.1.2356.11.1.49.2
lcsStatusModemMobileConnectInfo OBJECT-TYPE
    SYNTAX     DisplayString (SIZE(0..63))
    MAX-ACCESS read-only
    STATUS     current
    DESCRIPTION
            ""
    ::= { lcsStatusModemMobile 2 }

-- {SCALAR} 1.3.6.1.4.1.2356.11.1.49.3
lcsStatusModemMobileState OBJECT-TYPE
    SYNTAX     INTEGER {
                  eDeactivated (0),
                  eDeviceDetection (1),
                  eReset (2),
                  eInitializing (3),
                  eModemId (4),
                  eReady (5),
                  eConnecting (6),
                  ePassConnecting (7),
                  eDataMode (8),
                  eNetworkScan (9),
                  eSetPin (10),
                  ePinInvalid (11),
                  eUnexpectedResponse (12),
                  ePukRequired (13),
                  eNetwork (14),
                  eWaitForDevice (15),
                  ePinMissing (16),
                  eGpsPoll (17),
                  eHwPoll (18),
                  eNetworkScanExtended (19)
            }
    MAX-ACCESS read-only
    STATUS     current
    DESCRIPTION
            ""
    ::= { lcsStatusModemMobile 3 }

-- {SCALAR} 1.3.6.1.4.1.2356.11.1.49.4
lcsStatusModemMobileOperating OBJECT-TYPE
    SYNTAX     INTEGER {
                  eNo (0),
                  eModem (1),
                  eWwan (2)
            }
    MAX-ACCESS read-only
    STATUS     current
    DESCRIPTION
            ""
    ::= { lcsStatusModemMobile 4 }

-- {SCALAR} 1.3.6.1.4.1.2356.11.1.49.5
lcsStatusModemMobileDataRate OBJECT-TYPE
    SYNTAX     Integer32 (0..2147483647)
    MAX-ACCESS read-only
    STATUS     current
    DESCRIPTION
            ""
    ::= { lcsStatusModemMobile 5 }

-- {SCALAR} 1.3.6.1.4.1.2356.11.1.49.6
lcsStatusModemMobileSignalDbm OBJECT-TYPE
    SYNTAX     Integer32 (-2147483648..2147483647)
    MAX-ACCESS read-only
    STATUS     current
    DESCRIPTION
            ""
    ::= { lcsStatusModemMobile 6 }

-- {SCALAR} 1.3.6.1.4.1.2356.11.1.49.7
lcsStatusModemMobileRegistration OBJECT-TYPE
    SYNTAX     INTEGER {
                  eNoNetwork (0),
                  eHomeNetwork (1),
                  eSearching (2),
                  eDenied (3),
                  eUnknown (4),
                  eRoaming (5),
                  eNoNetworkDenied (128),
                  eSearchingDenied (130),
                  eRegistrationDenied (131),
                  eUnknownDenied (132)
            }
    MAX-ACCESS read-only
    STATUS     current
    DESCRIPTION
            ""
    ::= { lcsStatusModemMobile 7 }

-- {SCALAR} 1.3.6.1.4.1.2356.11.1.49.8
lcsStatusModemMobileNetwork OBJECT-TYPE
    SYNTAX     DisplayString (SIZE(0..16))
    MAX-ACCESS read-only
    STATUS     current
    DESCRIPTION
            ""
    ::= { lcsStatusModemMobile 8 }

-- {TABLE} 1.3.6.1.4.1.2356.11.1.49.9
lcsStatusModemMobileNetworkListTable OBJECT-TYPE
    SYNTAX     SEQUENCE OF LcsStatusModemMobileNetworkListEntry
    MAX-ACCESS not-accessible
    STATUS     current
    DESCRIPTION
            ""
    ::= { lcsStatusModemMobile 9 }

-- {ROW} 1.3.6.1.4.1.2356.11.1.49.9.1
lcsStatusModemMobileNetworkListEntry OBJECT-TYPE
    SYNTAX     LcsStatusModemMobileNetworkListEntry
    MAX-ACCESS not-accessible
    STATUS     current
    DESCRIPTION
            ""
    INDEX {
            lcsStatusModemMobileNetworkListEntryNetwork
          }
    ::= { lcsStatusModemMobileNetworkListTable 1 }

LcsStatusModemMobileNetworkListEntry ::= SEQUENCE {
            lcsStatusModemMobileNetworkListEntryNetwork DisplayString,
            lcsStatusModemMobileNetworkListEntryState INTEGER,
            lcsStatusModemMobileNetworkListEntryMode BITS,
            lcsStatusModemMobileNetworkListEntryNumeric Integer32
    }

-- {COLUMN} 1.3.6.1.4.1.2356.11.1.49.9.1.1
lcsStatusModemMobileNetworkListEntryNetwork OBJECT-TYPE
    SYNTAX     DisplayString (SIZE(0..16))
    MAX-ACCESS read-only
    STATUS     current
    DESCRIPTION
            ""
    ::= { lcsStatusModemMobileNetworkListEntry 1 }

-- {COLUMN} 1.3.6.1.4.1.2356.11.1.49.9.1.2
lcsStatusModemMobileNetworkListEntryState OBJECT-TYPE
    SYNTAX     INTEGER {
                  eUnknown (1),
                  eAvailable (2),
                  eCurrent (3),
                  eForbidden (4)
            }
    MAX-ACCESS read-only
    STATUS     current
    DESCRIPTION
            ""
    ::= { lcsStatusModemMobileNetworkListEntry 2 }

-- {COLUMN} 1.3.6.1.4.1.2356.11.1.49.9.1.3
lcsStatusModemMobileNetworkListEntryMode OBJECT-TYPE
    SYNTAX     BITS {
                  eUnknown (0),
                  e4g (29),
                  e3g (30),
                  e2g (31)
            }
    MAX-ACCESS read-only
    STATUS     current
    DESCRIPTION
            ""
    ::= { lcsStatusModemMobileNetworkListEntry 3 }

-- {COLUMN} 1.3.6.1.4.1.2356.11.1.49.9.1.4
lcsStatusModemMobileNetworkListEntryNumeric OBJECT-TYPE
    SYNTAX     Integer32 (0..2147483647)
    MAX-ACCESS read-only
    STATUS     current
    DESCRIPTION
            ""
    ::= { lcsStatusModemMobileNetworkListEntry 4 }

-- {SCALAR} 1.3.6.1.4.1.2356.11.1.49.10
lcsStatusModemMobileScanNetworks OBJECT-TYPE
    SYNTAX     DisplayString
    MAX-ACCESS read-write
    STATUS     current
    DESCRIPTION
            ""
    ::= { lcsStatusModemMobile 10 }

-- {SCALAR} 1.3.6.1.4.1.2356.11.1.49.11
lcsStatusModemMobileInputPuk OBJECT-TYPE
    SYNTAX     DisplayString
    MAX-ACCESS read-write
    STATUS     current
    DESCRIPTION
            ""
    ::= { lcsStatusModemMobile 11 }

-- {SCALAR} 1.3.6.1.4.1.2356.11.1.49.12
lcsStatusModemMobileMode OBJECT-TYPE
    SYNTAX     INTEGER {
                  eUnknown (0),
                  eUmts3g (1),
                  eGprs2g (2),
                  eGsm2g (3),
                  eEdge25g (4),
                  eHsdpa35g (5),
                  eHsupa35g (6),
                  eHspaPlus35g (7),
                  eLte4g (8),
                  eHspa35g (9)
            }
    MAX-ACCESS read-only
    STATUS     current
    DESCRIPTION
            ""
    ::= { lcsStatusModemMobile 12 }

-- {SCALAR} 1.3.6.1.4.1.2356.11.1.49.13
lcsStatusModemMobilePort OBJECT-TYPE
    SYNTAX     INTEGER {
                  eNone (0),
                  eOutband (1),
                  eUsb (2)
            }
    MAX-ACCESS read-only
    STATUS     current
    DESCRIPTION
            ""
    ::= { lcsStatusModemMobile 13 }

-- {SCALAR} 1.3.6.1.4.1.2356.11.1.49.14
lcsStatusModemMobileDroppedTxPackets OBJECT-TYPE
    SYNTAX     Integer32 (0..2147483647)
    MAX-ACCESS read-only
    STATUS     current
    DESCRIPTION
            ""
    ::= { lcsStatusModemMobile 14 }

-- {SCALAR} 1.3.6.1.4.1.2356.11.1.49.15
lcsStatusModemMobileHardwareResets OBJECT-TYPE
    SYNTAX     Integer32 (0..2147483647)
    MAX-ACCESS read-only
    STATUS     current
    DESCRIPTION
            ""
    ::= { lcsStatusModemMobile 15 }

-- {TABLE} 1.3.6.1.4.1.2356.11.1.49.16
lcsStatusModemMobileHistoryTable OBJECT-TYPE
    SYNTAX     SEQUENCE OF LcsStatusModemMobileHistoryEntry
    MAX-ACCESS not-accessible
    STATUS     current
    DESCRIPTION
            ""
    ::= { lcsStatusModemMobile 16 }

-- {ROW} 1.3.6.1.4.1.2356.11.1.49.16.1
lcsStatusModemMobileHistoryEntry OBJECT-TYPE
    SYNTAX     LcsStatusModemMobileHistoryEntry
    MAX-ACCESS not-accessible
    STATUS     current
    DESCRIPTION
            ""
    INDEX {
            lcsStatusModemMobileHistoryEntryIndex
          }
    ::= { lcsStatusModemMobileHistoryTable 1 }

LcsStatusModemMobileHistoryEntry ::= SEQUENCE {
            lcsStatusModemMobileHistoryEntryIndex Integer32,
            lcsStatusModemMobileHistoryEntryTimestamp Gauge32,
            lcsStatusModemMobileHistoryEntrySignalDbm Integer32,
            lcsStatusModemMobileHistoryEntryNetwork DisplayString,
            lcsStatusModemMobileHistoryEntryMode INTEGER,
            lcsStatusModemMobileHistoryEntryRegistration INTEGER,
            lcsStatusModemMobileHistoryEntryRsrp Integer32,
            lcsStatusModemMobileHistoryEntryRscp Integer32
    }

-- {COLUMN} 1.3.6.1.4.1.2356.11.1.49.16.1.1
lcsStatusModemMobileHistoryEntryIndex OBJECT-TYPE
    SYNTAX     Integer32 (0..2147483647)
    MAX-ACCESS read-only
    STATUS     current
    DESCRIPTION
            ""
    ::= { lcsStatusModemMobileHistoryEntry 1 }

-- {COLUMN} 1.3.6.1.4.1.2356.11.1.49.16.1.2
lcsStatusModemMobileHistoryEntryTimestamp OBJECT-TYPE
    SYNTAX     Gauge32
    MAX-ACCESS read-only
    STATUS     current
    DESCRIPTION
            ""
    ::= { lcsStatusModemMobileHistoryEntry 2 }

-- {COLUMN} 1.3.6.1.4.1.2356.11.1.49.16.1.3
lcsStatusModemMobileHistoryEntrySignalDbm OBJECT-TYPE
    SYNTAX     Integer32 (-2147483648..2147483647)
    MAX-ACCESS read-only
    STATUS     current
    DESCRIPTION
            ""
    ::= { lcsStatusModemMobileHistoryEntry 3 }

-- {COLUMN} 1.3.6.1.4.1.2356.11.1.49.16.1.4
lcsStatusModemMobileHistoryEntryNetwork OBJECT-TYPE
    SYNTAX     DisplayString (SIZE(0..1))
    MAX-ACCESS read-only
    STATUS     current
    DESCRIPTION
            ""
    ::= { lcsStatusModemMobileHistoryEntry 4 }

-- {COLUMN} 1.3.6.1.4.1.2356.11.1.49.16.1.5
lcsStatusModemMobileHistoryEntryMode OBJECT-TYPE
    SYNTAX     INTEGER {
                  eUnknown (0),
                  eUmts3g (1),
                  eGprs2g (2),
                  eGsm2g (3),
                  eEdge25g (4),
                  eHsdpa35g (5),
                  eHsupa35g (6),
                  eHspaPlus35g (7),
                  eLte4g (8),
                  eHspa35g (9)
            }
    MAX-ACCESS read-only
    STATUS     current
    DESCRIPTION
            ""
    ::= { lcsStatusModemMobileHistoryEntry 5 }

-- {COLUMN} 1.3.6.1.4.1.2356.11.1.49.16.1.6
lcsStatusModemMobileHistoryEntryRegistration OBJECT-TYPE
    SYNTAX     INTEGER {
                  eNoNetwork (0),
                  eHomeNetwork (1),
                  eSearching (2),
                  eDenied (3),
                  eUnknown (4),
                  eRoaming (5),
                  eNoNetworkDenied (128),
                  eSearchingDenied (130),
                  eRegistrationDenied (131),
                  eUnknownDenied (132)
            }
    MAX-ACCESS read-only
    STATUS     current
    DESCRIPTION
            ""
    ::= { lcsStatusModemMobileHistoryEntry 6 }

-- {COLUMN} 1.3.6.1.4.1.2356.11.1.49.16.1.7
lcsStatusModemMobileHistoryEntryRsrp OBJECT-TYPE
    SYNTAX     Integer32 (-32768..32767)
    MAX-ACCESS read-only
    STATUS     current
    DESCRIPTION
            "-- empty --"
    ::= { lcsStatusModemMobileHistoryEntry 7 }

-- {COLUMN} 1.3.6.1.4.1.2356.11.1.49.16.1.8
lcsStatusModemMobileHistoryEntryRscp OBJECT-TYPE
    SYNTAX     Integer32 (-32768..32767)
    MAX-ACCESS read-only
    STATUS     current
    DESCRIPTION
            "-- empty --"
    ::= { lcsStatusModemMobileHistoryEntry 8 }

-- {SCALAR} 1.3.6.1.4.1.2356.11.1.49.17
lcsStatusModemMobileTemperatureStatus OBJECT-TYPE
    SYNTAX     INTEGER {
                  eUnknown (0),
                  eNormal (1),
                  eLow (2),
                  eHigh (3),
                  eLowCritical (5),
                  eHighCritical (6)
            }
    MAX-ACCESS read-only
    STATUS     current
    DESCRIPTION
            ""
    ::= { lcsStatusModemMobile 17 }

-- {SCALAR} 1.3.6.1.4.1.2356.11.1.49.18
lcsStatusModemMobileTemperatureDegc OBJECT-TYPE
    SYNTAX     Integer32 (0..255)
    MAX-ACCESS read-only
    STATUS     current
    DESCRIPTION
            ""
    ::= { lcsStatusModemMobile 18 }

-- {SCALAR} 1.3.6.1.4.1.2356.11.1.49.19
lcsStatusModemMobileSupplyVoltageStatus OBJECT-TYPE
    SYNTAX     INTEGER {
                  eUnknown (0),
                  eNormal (1),
                  eLow (2),
                  eHigh (3),
                  eLowCritical (5),
                  eHighCritical (6)
            }
    MAX-ACCESS read-only
    STATUS     current
    DESCRIPTION
            ""
    ::= { lcsStatusModemMobile 19 }

-- {SCALAR} 1.3.6.1.4.1.2356.11.1.49.20
lcsStatusModemMobileSupplyVoltageMv OBJECT-TYPE
    SYNTAX     Integer32 (0..65535)
    MAX-ACCESS read-only
    STATUS     current
    DESCRIPTION
            ""
    ::= { lcsStatusModemMobile 20 }

-- {SCALAR} 1.3.6.1.4.1.2356.11.1.49.21
lcsStatusModemMobilePinStatus OBJECT-TYPE
    SYNTAX     DisplayString (SIZE(0..47))
    MAX-ACCESS read-only
    STATUS     current
    DESCRIPTION
            ""
    ::= { lcsStatusModemMobile 21 }

-- {SCALAR} 1.3.6.1.4.1.2356.11.1.49.22
lcsStatusModemMobileRxTimeouts OBJECT-TYPE
    SYNTAX     Integer32 (0..2147483647)
    MAX-ACCESS read-only
    STATUS     current
    DESCRIPTION
            ""
    ::= { lcsStatusModemMobile 22 }

-- {SCALAR} 1.3.6.1.4.1.2356.11.1.49.23
lcsStatusModemMobileSimIdIccid OBJECT-TYPE
    SYNTAX     DisplayString (SIZE(0..22))
    MAX-ACCESS read-only
    STATUS     current
    DESCRIPTION
            ""
    ::= { lcsStatusModemMobile 23 }

-- {SCALAR} 1.3.6.1.4.1.2356.11.1.49.25
lcsStatusModemMobileFallbackTo2g OBJECT-TYPE
    SYNTAX     INTEGER {
                  eNo (0),
                  eYes (1)
            }
    MAX-ACCESS read-only
    STATUS     current
    DESCRIPTION
            ""
    ::= { lcsStatusModemMobile 25 }

-- {SCALAR} 1.3.6.1.4.1.2356.11.1.49.26
lcsStatusModemMobileMobileCountryCode OBJECT-TYPE
    SYNTAX     INTEGER {
                  eUnknown (0),
                  eDe (262)
            }
    MAX-ACCESS read-only
    STATUS     current
    DESCRIPTION
            ""
    ::= { lcsStatusModemMobile 26 }

-- {SCALAR} 1.3.6.1.4.1.2356.11.1.49.27
lcsStatusModemMobileMobileNetworkCode OBJECT-TYPE
    SYNTAX     Integer32 (0..2147483647)
    MAX-ACCESS read-only
    STATUS     current
    DESCRIPTION
            ""
    ::= { lcsStatusModemMobile 27 }

-- {SCALAR} 1.3.6.1.4.1.2356.11.1.49.28
lcsStatusModemMobileMobileCellId OBJECT-TYPE
    SYNTAX     Integer32 (0..2147483647)
    MAX-ACCESS read-only
    STATUS     current
    DESCRIPTION
            "-- empty --"
    ::= { lcsStatusModemMobile 28 }

-- {SCALAR} 1.3.6.1.4.1.2356.11.1.49.29
lcsStatusModemMobileMobileLocalAreaCode OBJECT-TYPE
    SYNTAX     Integer32 (0..2147483647)
    MAX-ACCESS read-only
    STATUS     current
    DESCRIPTION
            "-- empty --"
    ::= { lcsStatusModemMobile 29 }

-- {SCALAR} 1.3.6.1.4.1.2356.11.1.49.30
lcsStatusModemMobileRelease OBJECT-TYPE
    SYNTAX     Integer32 (0..2147483647)
    MAX-ACCESS read-only
    STATUS     current
    DESCRIPTION
            "-- empty --"
    ::= { lcsStatusModemMobile 30 }

-- {SCALAR} 1.3.6.1.4.1.2356.11.1.49.31
lcsStatusModemMobileMaxDownstreamRateKbS OBJECT-TYPE
    SYNTAX     Integer32 (0..2147483647)
    MAX-ACCESS read-only
    STATUS     current
    DESCRIPTION
            "-- empty --"
    ::= { lcsStatusModemMobile 31 }

-- {SCALAR} 1.3.6.1.4.1.2356.11.1.49.32
lcsStatusModemMobileMaxUpstreamRateKbS OBJECT-TYPE
    SYNTAX     Integer32 (0..2147483647)
    MAX-ACCESS read-only
    STATUS     current
    DESCRIPTION
            "-- empty --"
    ::= { lcsStatusModemMobile 32 }

-- {SCALAR} 1.3.6.1.4.1.2356.11.1.49.33
lcsStatusModemMobileMobileBand OBJECT-TYPE
    SYNTAX     DisplayString (SIZE(0..39))
    MAX-ACCESS read-only
    STATUS     current
    DESCRIPTION
            "-- empty --"
    ::= { lcsStatusModemMobile 33 }

-- {SCALAR} 1.3.6.1.4.1.2356.11.1.49.34
lcsStatusModemMobileMobileBandwidthMhz OBJECT-TYPE
    SYNTAX     Integer32 (0..2147483647)
    MAX-ACCESS read-only
    STATUS     current
    DESCRIPTION
            "-- empty --"
    ::= { lcsStatusModemMobile 34 }

-- {SCALAR} 1.3.6.1.4.1.2356.11.1.49.35
lcsStatusModemMobileMobileTxChannel OBJECT-TYPE
    SYNTAX     Integer32 (0..2147483647)
    MAX-ACCESS read-only
    STATUS     current
    DESCRIPTION
            "-- empty --"
    ::= { lcsStatusModemMobile 35 }

-- {SCALAR} 1.3.6.1.4.1.2356.11.1.49.36
lcsStatusModemMobileMobileRxChannel OBJECT-TYPE
    SYNTAX     Integer32 (0..2147483647)
    MAX-ACCESS read-only
    STATUS     current
    DESCRIPTION
            "-- empty --"
    ::= { lcsStatusModemMobile 36 }

-- {SCALAR} 1.3.6.1.4.1.2356.11.1.49.37
lcsStatusModemMobileImei OBJECT-TYPE
    SYNTAX     DisplayString (SIZE(0..15))
    MAX-ACCESS read-only
    STATUS     current
    DESCRIPTION
            "-- empty --"
    ::= { lcsStatusModemMobile 37 }

-- {SCALAR} 1.3.6.1.4.1.2356.11.1.49.38
lcsStatusModemMobileSimInserted OBJECT-TYPE
    SYNTAX     INTEGER {
                  eNo (0),
                  eYes (1)
            }
    MAX-ACCESS read-only
    STATUS     current
    DESCRIPTION
            "-- empty --"
    ::= { lcsStatusModemMobile 38 }

-- {SCALAR} 1.3.6.1.4.1.2356.11.1.49.39
lcsStatusModemMobileImsi OBJECT-TYPE
    SYNTAX     DisplayString (SIZE(0..15))
    MAX-ACCESS read-only
    STATUS     current
    DESCRIPTION
            "-- empty --"
    ::= { lcsStatusModemMobile 39 }

-- {SCALAR} 1.3.6.1.4.1.2356.11.1.49.40
lcsStatusModemMobilePhoneNumber OBJECT-TYPE
    SYNTAX     DisplayString (SIZE(0..31))
    MAX-ACCESS read-only
    STATUS     current
    DESCRIPTION
            "-- empty --"
    ::= { lcsStatusModemMobile 40 }

-- {SCALAR} 1.3.6.1.4.1.2356.11.1.49.41
lcsStatusModemMobileSetApn OBJECT-TYPE
    SYNTAX     DisplayString (SIZE(0..63))
    MAX-ACCESS read-only
    STATUS     current
    DESCRIPTION
            "-- empty --"
    ::= { lcsStatusModemMobile 41 }

-- {SCALAR} 1.3.6.1.4.1.2356.11.1.49.42
lcsStatusModemMobilePinChange OBJECT-TYPE
    SYNTAX     DisplayString
    MAX-ACCESS read-write
    STATUS     current
    DESCRIPTION
            "-- empty --"
    ::= { lcsStatusModemMobile 42 }

-- {TABLE} 1.3.6.1.4.1.2356.11.1.49.43
lcsStatusModemMobileSimstatusTable OBJECT-TYPE
    SYNTAX     SEQUENCE OF LcsStatusModemMobileSimstatusEntry
    MAX-ACCESS not-accessible
    STATUS     current
    DESCRIPTION
            "-- empty --"
    ::= { lcsStatusModemMobile 43 }

-- {ROW} 1.3.6.1.4.1.2356.11.1.49.43.1
lcsStatusModemMobileSimstatusEntry OBJECT-TYPE
    SYNTAX     LcsStatusModemMobileSimstatusEntry
    MAX-ACCESS not-accessible
    STATUS     current
    DESCRIPTION
            ""
    INDEX {
            lcsStatusModemMobileSimstatusEntryIndex
          }
    ::= { lcsStatusModemMobileSimstatusTable 1 }

LcsStatusModemMobileSimstatusEntry ::= SEQUENCE {
            lcsStatusModemMobileSimstatusEntryIndex Integer32,
            lcsStatusModemMobileSimstatusEntrySimstatus INTEGER,
            lcsStatusModemMobileSimstatusEntrySimIdIccid DisplayString,
            lcsStatusModemMobileSimstatusEntryProvidername DisplayString,
            lcsStatusModemMobileSimstatusEntryImsi DisplayString,
            lcsStatusModemMobileSimstatusEntryPhoneNumber DisplayString
    }

-- {COLUMN} 1.3.6.1.4.1.2356.11.1.49.43.1.1
lcsStatusModemMobileSimstatusEntryIndex OBJECT-TYPE
    SYNTAX     Integer32 (0..2147483647)
    MAX-ACCESS read-only
    STATUS     current
    DESCRIPTION
            "-- empty --"
    ::= { lcsStatusModemMobileSimstatusEntry 1 }

-- {COLUMN} 1.3.6.1.4.1.2356.11.1.49.43.1.2
lcsStatusModemMobileSimstatusEntrySimstatus OBJECT-TYPE
    SYNTAX     INTEGER {
                  eMissing (0),
                  eActive (1),
                  eStandby (2)
            }
    MAX-ACCESS read-only
    STATUS     current
    DESCRIPTION
            "-- empty --"
    ::= { lcsStatusModemMobileSimstatusEntry 2 }

-- {COLUMN} 1.3.6.1.4.1.2356.11.1.49.43.1.3
lcsStatusModemMobileSimstatusEntrySimIdIccid OBJECT-TYPE
    SYNTAX     DisplayString (SIZE(0..1))
    MAX-ACCESS read-only
    STATUS     current
    DESCRIPTION
            "-- empty --"
    ::= { lcsStatusModemMobileSimstatusEntry 3 }

-- {COLUMN} 1.3.6.1.4.1.2356.11.1.49.43.1.4
lcsStatusModemMobileSimstatusEntryProvidername OBJECT-TYPE
    SYNTAX     DisplayString (SIZE(0..1))
    MAX-ACCESS read-only
    STATUS     current
    DESCRIPTION
            "-- empty --"
    ::= { lcsStatusModemMobileSimstatusEntry 4 }

-- {COLUMN} 1.3.6.1.4.1.2356.11.1.49.43.1.5
lcsStatusModemMobileSimstatusEntryImsi OBJECT-TYPE
    SYNTAX     DisplayString (SIZE(0..1))
    MAX-ACCESS read-only
    STATUS     current
    DESCRIPTION
            "-- empty --"
    ::= { lcsStatusModemMobileSimstatusEntry 5 }

-- {COLUMN} 1.3.6.1.4.1.2356.11.1.49.43.1.6
lcsStatusModemMobileSimstatusEntryPhoneNumber OBJECT-TYPE
    SYNTAX     DisplayString (SIZE(0..1))
    MAX-ACCESS read-only
    STATUS     current
    DESCRIPTION
            "-- empty --"
    ::= { lcsStatusModemMobileSimstatusEntry 6 }

-- {SCALAR} 1.3.6.1.4.1.2356.11.1.49.44
lcsStatusModemMobileSimstatusRefresh OBJECT-TYPE
    SYNTAX     DisplayString
    MAX-ACCESS read-write
    STATUS     current
    DESCRIPTION
            "-- empty --"
    ::= { lcsStatusModemMobile 44 }

-- {SCALAR} 1.3.6.1.4.1.2356.11.1.49.45
lcsStatusModemMobileProfile OBJECT-TYPE
    SYNTAX     DisplayString (SIZE(0..16))
    MAX-ACCESS read-only
    STATUS     current
    DESCRIPTION
            "-- empty --"
    ::= { lcsStatusModemMobile 45 }

-- {SCALAR} 1.3.6.1.4.1.2356.11.1.49.46
lcsStatusModemMobileNetworkselection OBJECT-TYPE
    SYNTAX     INTEGER {
                  eAuto (0),
                  eManual (1),
                  eUnknown (3)
            }
    MAX-ACCESS read-only
    STATUS     current
    DESCRIPTION
            "-- empty --"
    ::= { lcsStatusModemMobile 46 }

-- {TABLE} 1.3.6.1.4.1.2356.11.1.49.47
lcsStatusModemMobileNetworkList2Table OBJECT-TYPE
    SYNTAX     SEQUENCE OF LcsStatusModemMobileNetworkList2Entry
    MAX-ACCESS not-accessible
    STATUS     current
    DESCRIPTION
            ""
    ::= { lcsStatusModemMobile 47 }

-- {ROW} 1.3.6.1.4.1.2356.11.1.49.47.1
lcsStatusModemMobileNetworkList2Entry OBJECT-TYPE
    SYNTAX     LcsStatusModemMobileNetworkList2Entry
    MAX-ACCESS not-accessible
    STATUS     current
    DESCRIPTION
            ""
    INDEX {
            lcsStatusModemMobileNetworkList2EntryMcc,
            lcsStatusModemMobileNetworkList2EntryMnc,
            lcsStatusModemMobileNetworkList2EntryLac,
            lcsStatusModemMobileNetworkList2EntryCellid,
            lcsStatusModemMobileNetworkList2EntryAct,
            lcsStatusModemMobileNetworkList2EntrySim
          }
    ::= { lcsStatusModemMobileNetworkList2Table 1 }

LcsStatusModemMobileNetworkList2Entry ::= SEQUENCE {
            lcsStatusModemMobileNetworkList2EntryMcc Integer32,
            lcsStatusModemMobileNetworkList2EntryMnc Integer32,
            lcsStatusModemMobileNetworkList2EntryLac Integer32,
            lcsStatusModemMobileNetworkList2EntryCellid Integer32,
            lcsStatusModemMobileNetworkList2EntryAct INTEGER,
            lcsStatusModemMobileNetworkList2EntrySim Integer32,
            lcsStatusModemMobileNetworkList2EntryNetwork DisplayString,
            lcsStatusModemMobileNetworkList2EntryAccess INTEGER,
            lcsStatusModemMobileNetworkList2EntryRoaming INTEGER,
            lcsStatusModemMobileNetworkList2EntryRssi Gauge32,
            lcsStatusModemMobileNetworkList2EntryRsrp Gauge32,
            lcsStatusModemMobileNetworkList2EntryRsrq Gauge32,
            lcsStatusModemMobileNetworkList2EntrySinr Gauge32,
            lcsStatusModemMobileNetworkList2EntryRscp Gauge32,
            lcsStatusModemMobileNetworkList2EntryEcio Gauge32,
            lcsStatusModemMobileNetworkList2EntryBand INTEGER,
            lcsStatusModemMobileNetworkList2EntryTimestamp Gauge32,
            lcsStatusModemMobileNetworkList2EntryState INTEGER
    }

-- {COLUMN} 1.3.6.1.4.1.2356.11.1.49.47.1.1
lcsStatusModemMobileNetworkList2EntryMcc OBJECT-TYPE
    SYNTAX     Integer32 (0..65535)
    MAX-ACCESS read-only
    STATUS     current
    DESCRIPTION
            "-- empty --"
    ::= { lcsStatusModemMobileNetworkList2Entry 1 }

-- {COLUMN} 1.3.6.1.4.1.2356.11.1.49.47.1.2
lcsStatusModemMobileNetworkList2EntryMnc OBJECT-TYPE
    SYNTAX     Integer32 (0..65535)
    MAX-ACCESS read-only
    STATUS     current
    DESCRIPTION
            "-- empty --"
    ::= { lcsStatusModemMobileNetworkList2Entry 2 }

-- {COLUMN} 1.3.6.1.4.1.2356.11.1.49.47.1.3
lcsStatusModemMobileNetworkList2EntryLac OBJECT-TYPE
    SYNTAX     Integer32 (0..65535)
    MAX-ACCESS read-only
    STATUS     current
    DESCRIPTION
            "-- empty --"
    ::= { lcsStatusModemMobileNetworkList2Entry 3 }

-- {COLUMN} 1.3.6.1.4.1.2356.11.1.49.47.1.4
lcsStatusModemMobileNetworkList2EntryCellid OBJECT-TYPE
    SYNTAX     Integer32 (0..2147483647)
    MAX-ACCESS read-only
    STATUS     current
    DESCRIPTION
            "-- empty --"
    ::= { lcsStatusModemMobileNetworkList2Entry 4 }

-- {COLUMN} 1.3.6.1.4.1.2356.11.1.49.47.1.5
lcsStatusModemMobileNetworkList2EntryAct OBJECT-TYPE
    SYNTAX     INTEGER {
                  e2g (0),
                  e3g (2),
                  e4g (7),
                  eUnknown (255)
            }
    MAX-ACCESS read-only
    STATUS     current
    DESCRIPTION
            "-- empty --"
    ::= { lcsStatusModemMobileNetworkList2Entry 5 }

-- {COLUMN} 1.3.6.1.4.1.2356.11.1.49.47.1.6
lcsStatusModemMobileNetworkList2EntrySim OBJECT-TYPE
    SYNTAX     Integer32 (0..65535)
    MAX-ACCESS read-only
    STATUS     current
    DESCRIPTION
            "-- empty --"
    ::= { lcsStatusModemMobileNetworkList2Entry 6 }

-- {COLUMN} 1.3.6.1.4.1.2356.11.1.49.47.1.7
lcsStatusModemMobileNetworkList2EntryNetwork OBJECT-TYPE
    SYNTAX     DisplayString (SIZE(0..255))
    MAX-ACCESS read-only
    STATUS     current
    DESCRIPTION
            "-- empty --"
    ::= { lcsStatusModemMobileNetworkList2Entry 7 }

-- {COLUMN} 1.3.6.1.4.1.2356.11.1.49.47.1.8
lcsStatusModemMobileNetworkList2EntryAccess OBJECT-TYPE
    SYNTAX     INTEGER {
                  eUnknown (0),
                  eAvailable (1),
                  eCurrent (2),
                  eForbidden (3)
            }
    MAX-ACCESS read-only
    STATUS     current
    DESCRIPTION
            "-- empty --"
    ::= { lcsStatusModemMobileNetworkList2Entry 8 }

-- {COLUMN} 1.3.6.1.4.1.2356.11.1.49.47.1.9
lcsStatusModemMobileNetworkList2EntryRoaming OBJECT-TYPE
    SYNTAX     INTEGER {
                  eHomeNetwork (1),
                  eUnknown (4),
                  eRoaming (5)
            }
    MAX-ACCESS read-only
    STATUS     current
    DESCRIPTION
            "-- empty --"
    ::= { lcsStatusModemMobileNetworkList2Entry 9 }

-- {COLUMN} 1.3.6.1.4.1.2356.11.1.49.47.1.10
lcsStatusModemMobileNetworkList2EntryRssi OBJECT-TYPE
    SYNTAX     Gauge32
    MAX-ACCESS read-only
    STATUS     current
    DESCRIPTION
            "-- empty --"
    ::= { lcsStatusModemMobileNetworkList2Entry 10 }

-- {COLUMN} 1.3.6.1.4.1.2356.11.1.49.47.1.11
lcsStatusModemMobileNetworkList2EntryRsrp OBJECT-TYPE
    SYNTAX     Gauge32
    MAX-ACCESS read-only
    STATUS     current
    DESCRIPTION
            "-- empty --"
    ::= { lcsStatusModemMobileNetworkList2Entry 11 }

-- {COLUMN} 1.3.6.1.4.1.2356.11.1.49.47.1.12
lcsStatusModemMobileNetworkList2EntryRsrq OBJECT-TYPE
    SYNTAX     Gauge32
    MAX-ACCESS read-only
    STATUS     current
    DESCRIPTION
            "-- empty --"
    ::= { lcsStatusModemMobileNetworkList2Entry 12 }

-- {COLUMN} 1.3.6.1.4.1.2356.11.1.49.47.1.13
lcsStatusModemMobileNetworkList2EntrySinr OBJECT-TYPE
    SYNTAX     Gauge32
    MAX-ACCESS read-only
    STATUS     current
    DESCRIPTION
            "-- empty --"
    ::= { lcsStatusModemMobileNetworkList2Entry 13 }

-- {COLUMN} 1.3.6.1.4.1.2356.11.1.49.47.1.14
lcsStatusModemMobileNetworkList2EntryRscp OBJECT-TYPE
    SYNTAX     Gauge32
    MAX-ACCESS read-only
    STATUS     current
    DESCRIPTION
            "-- empty --"
    ::= { lcsStatusModemMobileNetworkList2Entry 14 }

-- {COLUMN} 1.3.6.1.4.1.2356.11.1.49.47.1.15
lcsStatusModemMobileNetworkList2EntryEcio OBJECT-TYPE
    SYNTAX     Gauge32
    MAX-ACCESS read-only
    STATUS     current
    DESCRIPTION
            "-- empty --"
    ::= { lcsStatusModemMobileNetworkList2Entry 15 }

-- {COLUMN} 1.3.6.1.4.1.2356.11.1.49.47.1.16
lcsStatusModemMobileNetworkList2EntryBand OBJECT-TYPE
    SYNTAX     INTEGER {
                  eUnknown (0),
                  eB12100 (1),
                  eB31800 (2),
                  eB72600 (3),
                  eB8900 (4),
                  eB20800 (5),
                  eB21900 (6),
                  eB42100 (7),
                  eB5850 (8),
                  eB12700 (9),
                  eB13700 (10),
                  eB251900 (11),
                  eB26800 (12),
                  eB29700 (13),
                  eB302300 (14),
                  eB412600 (15)
            }
    MAX-ACCESS read-only
    STATUS     current
    DESCRIPTION
            "-- empty --"
    ::= { lcsStatusModemMobileNetworkList2Entry 16 }

-- {COLUMN} 1.3.6.1.4.1.2356.11.1.49.47.1.17
lcsStatusModemMobileNetworkList2EntryTimestamp OBJECT-TYPE
    SYNTAX     Gauge32
    MAX-ACCESS read-only
    STATUS     current
    DESCRIPTION
            "-- empty --"
    ::= { lcsStatusModemMobileNetworkList2Entry 17 }

-- {COLUMN} 1.3.6.1.4.1.2356.11.1.49.47.1.18
lcsStatusModemMobileNetworkList2EntryState OBJECT-TYPE
    SYNTAX     INTEGER {
                  eCurrent (0),
                  eIncomplete (1),
                  eHistorical (2)
            }
    MAX-ACCESS read-only
    STATUS     current
    DESCRIPTION
            "-- empty --"
    ::= { lcsStatusModemMobileNetworkList2Entry 18 }

-- {SCALAR} 1.3.6.1.4.1.2356.11.1.49.48
lcsStatusModemMobileMobileAggregatedCarriers OBJECT-TYPE
    SYNTAX     Integer32 (0..255)
    MAX-ACCESS read-only
    STATUS     current
    DESCRIPTION
            "-- empty --"
    ::= { lcsStatusModemMobile 48 }

-- {NODE} 1.3.6.1.4.1.2356.11.1.50
lcsStatusFileSystem OBJECT IDENTIFIER ::= { lcsStatus 50 }

-- {TABLE} 1.3.6.1.4.1.2356.11.1.50.1
lcsStatusFileSystemContentsTable OBJECT-TYPE
    SYNTAX     SEQUENCE OF LcsStatusFileSystemContentsEntry
    MAX-ACCESS not-accessible
    STATUS     current
    DESCRIPTION
            ""
    ::= { lcsStatusFileSystem 1 }

-- {ROW} 1.3.6.1.4.1.2356.11.1.50.1.1
lcsStatusFileSystemContentsEntry OBJECT-TYPE
    SYNTAX     LcsStatusFileSystemContentsEntry
    MAX-ACCESS not-accessible
    STATUS     current
    DESCRIPTION
            ""
    INDEX {
            lcsStatusFileSystemContentsEntryName
          }
    ::= { lcsStatusFileSystemContentsTable 1 }

LcsStatusFileSystemContentsEntry ::= SEQUENCE {
            lcsStatusFileSystemContentsEntryName DisplayString,
            lcsStatusFileSystemContentsEntrySize Integer32
    }

-- {COLUMN} 1.3.6.1.4.1.2356.11.1.50.1.1.1
lcsStatusFileSystemContentsEntryName OBJECT-TYPE
    SYNTAX     DisplayString (SIZE(0..255))
    MAX-ACCESS read-only
    STATUS     current
    DESCRIPTION
            ""
    ::= { lcsStatusFileSystemContentsEntry 1 }

-- {COLUMN} 1.3.6.1.4.1.2356.11.1.50.1.1.2
lcsStatusFileSystemContentsEntrySize OBJECT-TYPE
    SYNTAX     Integer32 (0..2147483647)
    MAX-ACCESS read-only
    STATUS     current
    DESCRIPTION
            ""
    ::= { lcsStatusFileSystemContentsEntry 2 }

-- {TABLE} 1.3.6.1.4.1.2356.11.1.50.2
lcsStatusFileSystemVolumesTable OBJECT-TYPE
    SYNTAX     SEQUENCE OF LcsStatusFileSystemVolumesEntry
    MAX-ACCESS not-accessible
    STATUS     current
    DESCRIPTION
            ""
    ::= { lcsStatusFileSystem 2 }

-- {ROW} 1.3.6.1.4.1.2356.11.1.50.2.1
lcsStatusFileSystemVolumesEntry OBJECT-TYPE
    SYNTAX     LcsStatusFileSystemVolumesEntry
    MAX-ACCESS not-accessible
    STATUS     current
    DESCRIPTION
            ""
    INDEX {
            lcsStatusFileSystemVolumesEntryId
          }
    ::= { lcsStatusFileSystemVolumesTable 1 }

LcsStatusFileSystemVolumesEntry ::= SEQUENCE {
            lcsStatusFileSystemVolumesEntryId DisplayString,
            lcsStatusFileSystemVolumesEntryMountpoints DisplayString,
            lcsStatusFileSystemVolumesEntryFilesystem DisplayString,
            lcsStatusFileSystemVolumesEntryUnmountable Integer32,
            lcsStatusFileSystemVolumesEntryFree DisplayString,
            lcsStatusFileSystemVolumesEntrySize DisplayString,
            lcsStatusFileSystemVolumesEntryFb Integer32,
            lcsStatusFileSystemVolumesEntrySb Integer32
    }

-- {COLUMN} 1.3.6.1.4.1.2356.11.1.50.2.1.1
lcsStatusFileSystemVolumesEntryId OBJECT-TYPE
    SYNTAX     DisplayString (SIZE(0..255))
    MAX-ACCESS read-only
    STATUS     current
    DESCRIPTION
            ""
    ::= { lcsStatusFileSystemVolumesEntry 1 }

-- {COLUMN} 1.3.6.1.4.1.2356.11.1.50.2.1.2
lcsStatusFileSystemVolumesEntryMountpoints OBJECT-TYPE
    SYNTAX     DisplayString (SIZE(0..255))
    MAX-ACCESS read-only
    STATUS     current
    DESCRIPTION
            ""
    ::= { lcsStatusFileSystemVolumesEntry 2 }

-- {COLUMN} 1.3.6.1.4.1.2356.11.1.50.2.1.3
lcsStatusFileSystemVolumesEntryFilesystem OBJECT-TYPE
    SYNTAX     DisplayString (SIZE(0..255))
    MAX-ACCESS read-only
    STATUS     current
    DESCRIPTION
            ""
    ::= { lcsStatusFileSystemVolumesEntry 3 }

-- {COLUMN} 1.3.6.1.4.1.2356.11.1.50.2.1.4
lcsStatusFileSystemVolumesEntryUnmountable OBJECT-TYPE
    SYNTAX     Integer32 (0..255)
    MAX-ACCESS read-only
    STATUS     current
    DESCRIPTION
            ""
    ::= { lcsStatusFileSystemVolumesEntry 4 }

-- {COLUMN} 1.3.6.1.4.1.2356.11.1.50.2.1.5
lcsStatusFileSystemVolumesEntryFree OBJECT-TYPE
    SYNTAX     DisplayString (SIZE(0..255))
    MAX-ACCESS read-only
    STATUS     current
    DESCRIPTION
            ""
    ::= { lcsStatusFileSystemVolumesEntry 5 }

-- {COLUMN} 1.3.6.1.4.1.2356.11.1.50.2.1.6
lcsStatusFileSystemVolumesEntrySize OBJECT-TYPE
    SYNTAX     DisplayString (SIZE(0..255))
    MAX-ACCESS read-only
    STATUS     current
    DESCRIPTION
            ""
    ::= { lcsStatusFileSystemVolumesEntry 6 }

-- {COLUMN} 1.3.6.1.4.1.2356.11.1.50.2.1.7
lcsStatusFileSystemVolumesEntryFb OBJECT-TYPE
    SYNTAX     Integer32 (0..2147483647)
    MAX-ACCESS read-only
    STATUS     current
    DESCRIPTION
            ""
    ::= { lcsStatusFileSystemVolumesEntry 7 }

-- {COLUMN} 1.3.6.1.4.1.2356.11.1.50.2.1.8
lcsStatusFileSystemVolumesEntrySb OBJECT-TYPE
    SYNTAX     Integer32 (0..2147483647)
    MAX-ACCESS read-only
    STATUS     current
    DESCRIPTION
            ""
    ::= { lcsStatusFileSystemVolumesEntry 8 }

-- {SCALAR} 1.3.6.1.4.1.2356.11.1.50.3
lcsStatusFileSystemUnmount OBJECT-TYPE
    SYNTAX     DisplayString
    MAX-ACCESS read-write
    STATUS     current
    DESCRIPTION
            ""
    ::= { lcsStatusFileSystem 3 }

-- {SCALAR} 1.3.6.1.4.1.2356.11.1.50.4
lcsStatusFileSystemSecureErase OBJECT-TYPE
    SYNTAX     DisplayString
    MAX-ACCESS read-write
    STATUS     current
    DESCRIPTION
            "-- empty --"
    ::= { lcsStatusFileSystem 4 }

-- {NODE} 1.3.6.1.4.1.2356.11.1.51
lcsStatusEthernetPorts OBJECT IDENTIFIER ::= { lcsStatus 51 }

-- {TABLE} 1.3.6.1.4.1.2356.11.1.51.1
lcsStatusEthernetPortsPortsTable OBJECT-TYPE
    SYNTAX     SEQUENCE OF LcsStatusEthernetPortsPortsEntry
    MAX-ACCESS not-accessible
    STATUS     current
    DESCRIPTION
            ""
    ::= { lcsStatusEthernetPorts 1 }

-- {ROW} 1.3.6.1.4.1.2356.11.1.51.1.1
lcsStatusEthernetPortsPortsEntry OBJECT-TYPE
    SYNTAX     LcsStatusEthernetPortsPortsEntry
    MAX-ACCESS not-accessible
    STATUS     current
    DESCRIPTION
            ""
    INDEX {
            lcsStatusEthernetPortsPortsEntryPort
          }
    ::= { lcsStatusEthernetPortsPortsTable 1 }

LcsStatusEthernetPortsPortsEntry ::= SEQUENCE {
            lcsStatusEthernetPortsPortsEntryPort INTEGER,
            lcsStatusEthernetPortsPortsEntryLinkActive INTEGER,
            lcsStatusEthernetPortsPortsEntryConnector INTEGER,
            lcsStatusEthernetPortsPortsEntryMdiMode INTEGER,
            lcsStatusEthernetPortsPortsEntryAssignment INTEGER,
            lcsStatusEthernetPortsPortsEntryFlowControl INTEGER,
            lcsStatusEthernetPortsPortsEntryPrivateMode INTEGER,
            lcsStatusEthernetPortsPortsEntryAutoNegotiation INTEGER,
            lcsStatusEthernetPortsPortsEntryDownshift INTEGER,
            lcsStatusEthernetPortsPortsEntryClockRole INTEGER,
            lcsStatusEthernetPortsPortsEntryPowerSaving INTEGER,
            lcsStatusEthernetPortsPortsEntryRemoteFault INTEGER,
            lcsStatusEthernetPortsPortsEntryTemperature DisplayString,
            lcsStatusEthernetPortsPortsEntryDescription DisplayString
    }

-- {COLUMN} 1.3.6.1.4.1.2356.11.1.51.1.1.1
lcsStatusEthernetPortsPortsEntryPort OBJECT-TYPE
    SYNTAX     INTEGER {
                  eUnknown (0),
                  eUplink (1),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            ""
    ::= { lcsStatusEthernetPortsPortsEntry 1 }

-- {COLUMN} 1.3.6.1.4.1.2356.11.1.51.1.1.3
lcsStatusEthernetPortsPortsEntryLinkActive OBJECT-TYPE
    SYNTAX     INTEGER {
                  eNo (0),
                  eYes (1)
            }
    MAX-ACCESS read-only
    STATUS     current
    DESCRIPTION
            ""
    ::= { lcsStatusEthernetPortsPortsEntry 3 }

-- {COLUMN} 1.3.6.1.4.1.2356.11.1.51.1.1.4
lcsStatusEthernetPortsPortsEntryConnector OBJECT-TYPE
    SYNTAX     INTEGER {
                  eNone (0),
                  e10bT (1),
                  eFd10bTx (2),
                  e100bTx (3),
                  eFd100bTx (4),
                  eFd1000bTx (6),
                  eFd2500bTx (9),
                  eFd5000bTx (10),
                  eFd10gbTx (11),
                  e10b2 (33),
                  e10b5 (34),
                  eFd100bF (68),
                  eFd1000bF (70),
                  eFd10gbF (75),
                  ePowerDown (255)
            }
    MAX-ACCESS read-only
    STATUS     current
    DESCRIPTION
            ""
    ::= { lcsStatusEthernetPortsPortsEntry 4 }

-- {COLUMN} 1.3.6.1.4.1.2356.11.1.51.1.1.6
lcsStatusEthernetPortsPortsEntryMdiMode OBJECT-TYPE
    SYNTAX     INTEGER {
                  eUnknown (0),
                  eMdi (1),
                  eMdix (2),
                  eNotApplicable (3)
            }
    MAX-ACCESS read-only
    STATUS     current
    DESCRIPTION
            ""
    ::= { lcsStatusEthernetPortsPortsEntry 6 }

-- {COLUMN} 1.3.6.1.4.1.2356.11.1.51.1.1.7
lcsStatusEthernetPortsPortsEntryAssignment OBJECT-TYPE
    SYNTAX     INTEGER {
                  eLan1 (0),
                  eLan2 (1),
                  eLan3 (2),
                  eLan4 (3),
                  eLan5 (4),
                  eLan6 (5),
                  eDsl1 (512),
                  eDsl2 (513),
                  eDsl3 (514),
                  eDsl4 (515),
                  eDsl5 (516),
                  eIdle (65533),
                  eMonitor (65534),
                  ePowerDown (65535)
            }
    MAX-ACCESS read-only
    STATUS     current
    DESCRIPTION
            ""
    ::= { lcsStatusEthernetPortsPortsEntry 7 }

-- {COLUMN} 1.3.6.1.4.1.2356.11.1.51.1.1.8
lcsStatusEthernetPortsPortsEntryFlowControl OBJECT-TYPE
    SYNTAX     INTEGER {
                  eNo (0),
                  eYes (1),
                  eTxOnly (3),
                  eRxOnly (4)
            }
    MAX-ACCESS read-only
    STATUS     current
    DESCRIPTION
            ""
    ::= { lcsStatusEthernetPortsPortsEntry 8 }

-- {COLUMN} 1.3.6.1.4.1.2356.11.1.51.1.1.9
lcsStatusEthernetPortsPortsEntryPrivateMode OBJECT-TYPE
    SYNTAX     INTEGER {
                  eNo (0),
                  eYes (1)
            }
    MAX-ACCESS read-only
    STATUS     current
    DESCRIPTION
            ""
    ::= { lcsStatusEthernetPortsPortsEntry 9 }

-- {COLUMN} 1.3.6.1.4.1.2356.11.1.51.1.1.10
lcsStatusEthernetPortsPortsEntryAutoNegotiation OBJECT-TYPE
    SYNTAX     INTEGER {
                  ePending (0),
                  eCompleted (1),
                  eDisabled (2),
                  eNotAvailable (3)
            }
    MAX-ACCESS read-only
    STATUS     current
    DESCRIPTION
            ""
    ::= { lcsStatusEthernetPortsPortsEntry 10 }

-- {COLUMN} 1.3.6.1.4.1.2356.11.1.51.1.1.11
lcsStatusEthernetPortsPortsEntryDownshift OBJECT-TYPE
    SYNTAX     INTEGER {
                  eNo (0),
                  eYes (1)
            }
    MAX-ACCESS read-only
    STATUS     current
    DESCRIPTION
            ""
    ::= { lcsStatusEthernetPortsPortsEntry 11 }

-- {COLUMN} 1.3.6.1.4.1.2356.11.1.51.1.1.12
lcsStatusEthernetPortsPortsEntryClockRole OBJECT-TYPE
    SYNTAX     INTEGER {
                  eNone (0),
                  eMaster (1),
                  eSlave (2),
                  eFault (3)
            }
    MAX-ACCESS read-only
    STATUS     current
    DESCRIPTION
            ""
    ::= { lcsStatusEthernetPortsPortsEntry 12 }

-- {COLUMN} 1.3.6.1.4.1.2356.11.1.51.1.1.13
lcsStatusEthernetPortsPortsEntryPowerSaving OBJECT-TYPE
    SYNTAX     INTEGER {
                  eNo (0),
                  eYes (1)
            }
    MAX-ACCESS read-only
    STATUS     current
    DESCRIPTION
            "-- empty --"
    ::= { lcsStatusEthernetPortsPortsEntry 13 }

-- {COLUMN} 1.3.6.1.4.1.2356.11.1.51.1.1.14
lcsStatusEthernetPortsPortsEntryRemoteFault OBJECT-TYPE
    SYNTAX     INTEGER {
                  eNo (0),
                  eYes (1)
            }
    MAX-ACCESS read-only
    STATUS     current
    DESCRIPTION
            "-- empty --"
    ::= { lcsStatusEthernetPortsPortsEntry 14 }

-- {COLUMN} 1.3.6.1.4.1.2356.11.1.51.1.1.16
lcsStatusEthernetPortsPortsEntryTemperature OBJECT-TYPE
    SYNTAX     DisplayString (SIZE(0..255))
    MAX-ACCESS read-only
    STATUS     current
    DESCRIPTION
            "-- empty --"
    ::= { lcsStatusEthernetPortsPortsEntry 16 }

-- {COLUMN} 1.3.6.1.4.1.2356.11.1.51.1.1.17
lcsStatusEthernetPortsPortsEntryDescription OBJECT-TYPE
    SYNTAX     DisplayString (SIZE(0..255))
    MAX-ACCESS read-only
    STATUS     current
    DESCRIPTION
            "-- empty --"
    ::= { lcsStatusEthernetPortsPortsEntry 17 }

-- {SCALAR} 1.3.6.1.4.1.2356.11.1.51.2
lcsStatusEthernetPortsCableTest OBJECT-TYPE
    SYNTAX     DisplayString
    MAX-ACCESS read-write
    STATUS     current
    DESCRIPTION
            ""
    ::= { lcsStatusEthernetPorts 2 }

-- {TABLE} 1.3.6.1.4.1.2356.11.1.51.3
lcsStatusEthernetPortsCableTestResultsTable OBJECT-TYPE
    SYNTAX     SEQUENCE OF LcsStatusEthernetPortsCableTestResultsEntry
    MAX-ACCESS not-accessible
    STATUS     current
    DESCRIPTION
            ""
    ::= { lcsStatusEthernetPorts 3 }

-- {ROW} 1.3.6.1.4.1.2356.11.1.51.3.1
lcsStatusEthernetPortsCableTestResultsEntry OBJECT-TYPE
    SYNTAX     LcsStatusEthernetPortsCableTestResultsEntry
    MAX-ACCESS not-accessible
    STATUS     current
    DESCRIPTION
            ""
    INDEX {
            lcsStatusEthernetPortsCableTestResultsEntryIfc
          }
    ::= { lcsStatusEthernetPortsCableTestResultsTable 1 }

LcsStatusEthernetPortsCableTestResultsEntry ::= SEQUENCE {
            lcsStatusEthernetPortsCableTestResultsEntryIfc INTEGER,
            lcsStatusEthernetPortsCableTestResultsEntryRxStatus INTEGER,
            lcsStatusEthernetPortsCableTestResultsEntryRxDistance DisplayString,
            lcsStatusEthernetPortsCableTestResultsEntryTxStatus INTEGER,
            lcsStatusEthernetPortsCableTestResultsEntryTxDistance DisplayString,
            lcsStatusEthernetPortsCableTestResultsEntryMdi0Status INTEGER,
            lcsStatusEthernetPortsCableTestResultsEntryMdi0Distance DisplayString,
            lcsStatusEthernetPortsCableTestResultsEntryMdi1Status INTEGER,
            lcsStatusEthernetPortsCableTestResultsEntryMdi1Distance DisplayString,
            lcsStatusEthernetPortsCableTestResultsEntryMdi2Status INTEGER,
            lcsStatusEthernetPortsCableTestResultsEntryMdi2Distance DisplayString,
            lcsStatusEthernetPortsCableTestResultsEntryMdi3Status INTEGER,
            lcsStatusEthernetPortsCableTestResultsEntryMdi3Distance DisplayString,
            lcsStatusEthernetPortsCableTestResultsEntryMdi0Impedance DisplayString,
            lcsStatusEthernetPortsCableTestResultsEntryMdi1Impedance DisplayString,
            lcsStatusEthernetPortsCableTestResultsEntryMdi2Impedance DisplayString,
            lcsStatusEthernetPortsCableTestResultsEntryMdi3Impedance DisplayString
    }

-- {COLUMN} 1.3.6.1.4.1.2356.11.1.51.3.1.1
lcsStatusEthernetPortsCableTestResultsEntryIfc OBJECT-TYPE
    SYNTAX     INTEGER {
                  eUnknown (0),
                  eUplink (1),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            ""
    ::= { lcsStatusEthernetPortsCableTestResultsEntry 1 }

-- {COLUMN} 1.3.6.1.4.1.2356.11.1.51.3.1.2
lcsStatusEthernetPortsCableTestResultsEntryRxStatus OBJECT-TYPE
    SYNTAX     INTEGER {
                  eUnknown (0),
                  eOk (1),
                  eOpen (2),
                  eShort (3),
                  eImpedanceFault (4),
                  eFail (5),
                  eBusy (6),
                  eLinkUp (7)
            }
    MAX-ACCESS read-only
    STATUS     current
    DESCRIPTION
            ""
    ::= { lcsStatusEthernetPortsCableTestResultsEntry 2 }

-- {COLUMN} 1.3.6.1.4.1.2356.11.1.51.3.1.3
lcsStatusEthernetPortsCableTestResultsEntryRxDistance OBJECT-TYPE
    SYNTAX     DisplayString (SIZE(0..10))
    MAX-ACCESS read-only
    STATUS     current
    DESCRIPTION
            ""
    ::= { lcsStatusEthernetPortsCableTestResultsEntry 3 }

-- {COLUMN} 1.3.6.1.4.1.2356.11.1.51.3.1.4
lcsStatusEthernetPortsCableTestResultsEntryTxStatus OBJECT-TYPE
    SYNTAX     INTEGER {
                  eUnknown (0),
                  eOk (1),
                  eOpen (2),
                  eShort (3),
                  eImpedanceFault (4),
                  eFail (5),
                  eBusy (6),
                  eLinkUp (7)
            }
    MAX-ACCESS read-only
    STATUS     current
    DESCRIPTION
            ""
    ::= { lcsStatusEthernetPortsCableTestResultsEntry 4 }

-- {COLUMN} 1.3.6.1.4.1.2356.11.1.51.3.1.5
lcsStatusEthernetPortsCableTestResultsEntryTxDistance OBJECT-TYPE
    SYNTAX     DisplayString (SIZE(0..10))
    MAX-ACCESS read-only
    STATUS     current
    DESCRIPTION
            ""
    ::= { lcsStatusEthernetPortsCableTestResultsEntry 5 }

-- {COLUMN} 1.3.6.1.4.1.2356.11.1.51.3.1.6
lcsStatusEthernetPortsCableTestResultsEntryMdi0Status OBJECT-TYPE
    SYNTAX     INTEGER {
                  eUnknown (0),
                  eOk (1),
                  eOpen (2),
                  eShort (3),
                  eImpedanceFault (4),
                  eFail (5),
                  eBusy (6),
                  eLinkUp (7),
                  eInterPairShort (8),
                  eNotSupported (9)
            }
    MAX-ACCESS read-only
    STATUS     current
    DESCRIPTION
            ""
    ::= { lcsStatusEthernetPortsCableTestResultsEntry 6 }

-- {COLUMN} 1.3.6.1.4.1.2356.11.1.51.3.1.7
lcsStatusEthernetPortsCableTestResultsEntryMdi0Distance OBJECT-TYPE
    SYNTAX     DisplayString (SIZE(0..10))
    MAX-ACCESS read-only
    STATUS     current
    DESCRIPTION
            ""
    ::= { lcsStatusEthernetPortsCableTestResultsEntry 7 }

-- {COLUMN} 1.3.6.1.4.1.2356.11.1.51.3.1.8
lcsStatusEthernetPortsCableTestResultsEntryMdi1Status OBJECT-TYPE
    SYNTAX     INTEGER {
                  eUnknown (0),
                  eOk (1),
                  eOpen (2),
                  eShort (3),
                  eImpedanceFault (4),
                  eFail (5),
                  eBusy (6),
                  eLinkUp (7),
                  eInterPairShort (8),
                  eNotSupported (9)
            }
    MAX-ACCESS read-only
    STATUS     current
    DESCRIPTION
            ""
    ::= { lcsStatusEthernetPortsCableTestResultsEntry 8 }

-- {COLUMN} 1.3.6.1.4.1.2356.11.1.51.3.1.9
lcsStatusEthernetPortsCableTestResultsEntryMdi1Distance OBJECT-TYPE
    SYNTAX     DisplayString (SIZE(0..10))
    MAX-ACCESS read-only
    STATUS     current
    DESCRIPTION
            ""
    ::= { lcsStatusEthernetPortsCableTestResultsEntry 9 }

-- {COLUMN} 1.3.6.1.4.1.2356.11.1.51.3.1.10
lcsStatusEthernetPortsCableTestResultsEntryMdi2Status OBJECT-TYPE
    SYNTAX     INTEGER {
                  eUnknown (0),
                  eOk (1),
                  eOpen (2),
                  eShort (3),
                  eImpedanceFault (4),
                  eFail (5),
                  eBusy (6),
                  eLinkUp (7),
                  eInterPairShort (8),
                  eNotSupported (9)
            }
    MAX-ACCESS read-only
    STATUS     current
    DESCRIPTION
            ""
    ::= { lcsStatusEthernetPortsCableTestResultsEntry 10 }

-- {COLUMN} 1.3.6.1.4.1.2356.11.1.51.3.1.11
lcsStatusEthernetPortsCableTestResultsEntryMdi2Distance OBJECT-TYPE
    SYNTAX     DisplayString (SIZE(0..10))
    MAX-ACCESS read-only
    STATUS     current
    DESCRIPTION
            ""
    ::= { lcsStatusEthernetPortsCableTestResultsEntry 11 }

-- {COLUMN} 1.3.6.1.4.1.2356.11.1.51.3.1.12
lcsStatusEthernetPortsCableTestResultsEntryMdi3Status OBJECT-TYPE
    SYNTAX     INTEGER {
                  eUnknown (0),
                  eOk (1),
                  eOpen (2),
                  eShort (3),
                  eImpedanceFault (4),
                  eFail (5),
                  eBusy (6),
                  eLinkUp (7),
                  eInterPairShort (8),
                  eNotSupported (9)
            }
    MAX-ACCESS read-only
    STATUS     current
    DESCRIPTION
            ""
    ::= { lcsStatusEthernetPortsCableTestResultsEntry 12 }

-- {COLUMN} 1.3.6.1.4.1.2356.11.1.51.3.1.13
lcsStatusEthernetPortsCableTestResultsEntryMdi3Distance OBJECT-TYPE
    SYNTAX     DisplayString (SIZE(0..10))
    MAX-ACCESS read-only
    STATUS     current
    DESCRIPTION
            ""
    ::= { lcsStatusEthernetPortsCableTestResultsEntry 13 }

-- {COLUMN} 1.3.6.1.4.1.2356.11.1.51.3.1.16
lcsStatusEthernetPortsCableTestResultsEntryMdi0Impedance OBJECT-TYPE
    SYNTAX     DisplayString (SIZE(0..10))
    MAX-ACCESS read-only
    STATUS     current
    DESCRIPTION
            "-- empty --"
    ::= { lcsStatusEthernetPortsCableTestResultsEntry 16 }

-- {COLUMN} 1.3.6.1.4.1.2356.11.1.51.3.1.17
lcsStatusEthernetPortsCableTestResultsEntryMdi1Impedance OBJECT-TYPE
    SYNTAX     DisplayString (SIZE(0..10))
    MAX-ACCESS read-only
    STATUS     current
    DESCRIPTION
            "-- empty --"
    ::= { lcsStatusEthernetPortsCableTestResultsEntry 17 }

-- {COLUMN} 1.3.6.1.4.1.2356.11.1.51.3.1.18
lcsStatusEthernetPortsCableTestResultsEntryMdi2Impedance OBJECT-TYPE
    SYNTAX     DisplayString (SIZE(0..10))
    MAX-ACCESS read-only
    STATUS     current
    DESCRIPTION
            "-- empty --"
    ::= { lcsStatusEthernetPortsCableTestResultsEntry 18 }

-- {COLUMN} 1.3.6.1.4.1.2356.11.1.51.3.1.19
lcsStatusEthernetPortsCableTestResultsEntryMdi3Impedance OBJECT-TYPE
    SYNTAX     DisplayString (SIZE(0..10))
    MAX-ACCESS read-only
    STATUS     current
    DESCRIPTION
            "-- empty --"
    ::= { lcsStatusEthernetPortsCableTestResultsEntry 19 }

-- {TABLE} 1.3.6.1.4.1.2356.11.1.51.4
lcsStatusEthernetPortsErrorsTable OBJECT-TYPE
    SYNTAX     SEQUENCE OF LcsStatusEthernetPortsErrorsEntry
    MAX-ACCESS not-accessible
    STATUS     current
    DESCRIPTION
            ""
    ::= { lcsStatusEthernetPorts 4 }

-- {ROW} 1.3.6.1.4.1.2356.11.1.51.4.1
lcsStatusEthernetPortsErrorsEntry OBJECT-TYPE
    SYNTAX     LcsStatusEthernetPortsErrorsEntry
    MAX-ACCESS not-accessible
    STATUS     current
    DESCRIPTION
            ""
    INDEX {
            lcsStatusEthernetPortsErrorsEntryIfc
          }
    ::= { lcsStatusEthernetPortsErrorsTable 1 }

LcsStatusEthernetPortsErrorsEntry ::= SEQUENCE {
            lcsStatusEthernetPortsErrorsEntryIfc INTEGER,
            lcsStatusEthernetPortsErrorsEntryRxErrors Counter32,
            lcsStatusEthernetPortsErrorsEntryTxErrors Counter32,
            lcsStatusEthernetPortsErrorsEntryStackErrors Counter32,
            lcsStatusEthernetPortsErrorsEntryNicErrors Counter32,
            lcsStatusEthernetPortsErrorsEntryQueueErrors Counter32,
            lcsStatusEthernetPortsErrorsEntryRxCrcErrors Counter32,
            lcsStatusEthernetPortsErrorsEntryCollisions Counter32,
            lcsStatusEthernetPortsErrorsEntrySingleCollisions Counter32,
            lcsStatusEthernetPortsErrorsEntryMultipleCollisions Counter32,
            lcsStatusEthernetPortsErrorsEntryLateCollisions Counter32,
            lcsStatusEthernetPortsErrorsEntryExcessiveCollisions Counter32,
            lcsStatusEthernetPortsErrorsEntryRxAlignErrors Counter32,
            lcsStatusEthernetPortsErrorsEntryRxTooShort Counter32,
            lcsStatusEthernetPortsErrorsEntryRxTooLong Counter32,
            lcsStatusEthernetPortsErrorsEntryTxCarrier Counter32,
            lcsStatusEthernetPortsErrorsEntryTxDeferred Counter32,
            lcsStatusEthernetPortsErrorsEntryRxPhyErrors Counter32,
            lcsStatusEthernetPortsErrorsEntryRxFifoOverflow Counter32,
            lcsStatusEthernetPortsErrorsEntryTxDiscarded Counter32,
            lcsStatusEthernetPortsErrorsEntryRxDscrUnderflow Counter32
    }

-- {COLUMN} 1.3.6.1.4.1.2356.11.1.51.4.1.1
lcsStatusEthernetPortsErrorsEntryIfc OBJECT-TYPE
    SYNTAX     INTEGER {
                  eUnknown (0),
                  eUplink (1),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            ""
    ::= { lcsStatusEthernetPortsErrorsEntry 1 }

-- {COLUMN} 1.3.6.1.4.1.2356.11.1.51.4.1.2
lcsStatusEthernetPortsErrorsEntryRxErrors OBJECT-TYPE
    SYNTAX     Counter32
    MAX-ACCESS read-only
    STATUS     current
    DESCRIPTION
            ""
    ::= { lcsStatusEthernetPortsErrorsEntry 2 }

-- {COLUMN} 1.3.6.1.4.1.2356.11.1.51.4.1.3
lcsStatusEthernetPortsErrorsEntryTxErrors OBJECT-TYPE
    SYNTAX     Counter32
    MAX-ACCESS read-only
    STATUS     current
    DESCRIPTION
            ""
    ::= { lcsStatusEthernetPortsErrorsEntry 3 }

-- {COLUMN} 1.3.6.1.4.1.2356.11.1.51.4.1.4
lcsStatusEthernetPortsErrorsEntryStackErrors OBJECT-TYPE
    SYNTAX     Counter32
    MAX-ACCESS read-only
    STATUS     current
    DESCRIPTION
            ""
    ::= { lcsStatusEthernetPortsErrorsEntry 4 }

-- {COLUMN} 1.3.6.1.4.1.2356.11.1.51.4.1.5
lcsStatusEthernetPortsErrorsEntryNicErrors OBJECT-TYPE
    SYNTAX     Counter32
    MAX-ACCESS read-only
    STATUS     current
    DESCRIPTION
            ""
    ::= { lcsStatusEthernetPortsErrorsEntry 5 }

-- {COLUMN} 1.3.6.1.4.1.2356.11.1.51.4.1.6
lcsStatusEthernetPortsErrorsEntryQueueErrors OBJECT-TYPE
    SYNTAX     Counter32
    MAX-ACCESS read-only
    STATUS     current
    DESCRIPTION
            ""
    ::= { lcsStatusEthernetPortsErrorsEntry 6 }

-- {COLUMN} 1.3.6.1.4.1.2356.11.1.51.4.1.7
lcsStatusEthernetPortsErrorsEntryRxCrcErrors OBJECT-TYPE
    SYNTAX     Counter32
    MAX-ACCESS read-only
    STATUS     current
    DESCRIPTION
            ""
    ::= { lcsStatusEthernetPortsErrorsEntry 7 }

-- {COLUMN} 1.3.6.1.4.1.2356.11.1.51.4.1.8
lcsStatusEthernetPortsErrorsEntryCollisions OBJECT-TYPE
    SYNTAX     Counter32
    MAX-ACCESS read-only
    STATUS     current
    DESCRIPTION
            ""
    ::= { lcsStatusEthernetPortsErrorsEntry 8 }

-- {COLUMN} 1.3.6.1.4.1.2356.11.1.51.4.1.9
lcsStatusEthernetPortsErrorsEntrySingleCollisions OBJECT-TYPE
    SYNTAX     Counter32
    MAX-ACCESS read-only
    STATUS     current
    DESCRIPTION
            ""
    ::= { lcsStatusEthernetPortsErrorsEntry 9 }

-- {COLUMN} 1.3.6.1.4.1.2356.11.1.51.4.1.10
lcsStatusEthernetPortsErrorsEntryMultipleCollisions OBJECT-TYPE
    SYNTAX     Counter32
    MAX-ACCESS read-only
    STATUS     current
    DESCRIPTION
            ""
    ::= { lcsStatusEthernetPortsErrorsEntry 10 }

-- {COLUMN} 1.3.6.1.4.1.2356.11.1.51.4.1.11
lcsStatusEthernetPortsErrorsEntryLateCollisions OBJECT-TYPE
    SYNTAX     Counter32
    MAX-ACCESS read-only
    STATUS     current
    DESCRIPTION
            ""
    ::= { lcsStatusEthernetPortsErrorsEntry 11 }

-- {COLUMN} 1.3.6.1.4.1.2356.11.1.51.4.1.12
lcsStatusEthernetPortsErrorsEntryExcessiveCollisions OBJECT-TYPE
    SYNTAX     Counter32
    MAX-ACCESS read-only
    STATUS     current
    DESCRIPTION
            ""
    ::= { lcsStatusEthernetPortsErrorsEntry 12 }

-- {COLUMN} 1.3.6.1.4.1.2356.11.1.51.4.1.13
lcsStatusEthernetPortsErrorsEntryRxAlignErrors OBJECT-TYPE
    SYNTAX     Counter32
    MAX-ACCESS read-only
    STATUS     current
    DESCRIPTION
            ""
    ::= { lcsStatusEthernetPortsErrorsEntry 13 }

-- {COLUMN} 1.3.6.1.4.1.2356.11.1.51.4.1.14
lcsStatusEthernetPortsErrorsEntryRxTooShort OBJECT-TYPE
    SYNTAX     Counter32
    MAX-ACCESS read-only
    STATUS     current
    DESCRIPTION
            ""
    ::= { lcsStatusEthernetPortsErrorsEntry 14 }

-- {COLUMN} 1.3.6.1.4.1.2356.11.1.51.4.1.15
lcsStatusEthernetPortsErrorsEntryRxTooLong OBJECT-TYPE
    SYNTAX     Counter32
    MAX-ACCESS read-only
    STATUS     current
    DESCRIPTION
            ""
    ::= { lcsStatusEthernetPortsErrorsEntry 15 }

-- {COLUMN} 1.3.6.1.4.1.2356.11.1.51.4.1.16
lcsStatusEthernetPortsErrorsEntryTxCarrier OBJECT-TYPE
    SYNTAX     Counter32
    MAX-ACCESS read-only
    STATUS     current
    DESCRIPTION
            ""
    ::= { lcsStatusEthernetPortsErrorsEntry 16 }

-- {COLUMN} 1.3.6.1.4.1.2356.11.1.51.4.1.17
lcsStatusEthernetPortsErrorsEntryTxDeferred OBJECT-TYPE
    SYNTAX     Counter32
    MAX-ACCESS read-only
    STATUS     current
    DESCRIPTION
            ""
    ::= { lcsStatusEthernetPortsErrorsEntry 17 }

-- {COLUMN} 1.3.6.1.4.1.2356.11.1.51.4.1.18
lcsStatusEthernetPortsErrorsEntryRxPhyErrors OBJECT-TYPE
    SYNTAX     Counter32
    MAX-ACCESS read-only
    STATUS     current
    DESCRIPTION
            ""
    ::= { lcsStatusEthernetPortsErrorsEntry 18 }

-- {COLUMN} 1.3.6.1.4.1.2356.11.1.51.4.1.19
lcsStatusEthernetPortsErrorsEntryRxFifoOverflow OBJECT-TYPE
    SYNTAX     Counter32
    MAX-ACCESS read-only
    STATUS     current
    DESCRIPTION
            "-- empty --"
    ::= { lcsStatusEthernetPortsErrorsEntry 19 }

-- {COLUMN} 1.3.6.1.4.1.2356.11.1.51.4.1.20
lcsStatusEthernetPortsErrorsEntryTxDiscarded OBJECT-TYPE
    SYNTAX     Counter32
    MAX-ACCESS read-only
    STATUS     current
    DESCRIPTION
            "-- empty --"
    ::= { lcsStatusEthernetPortsErrorsEntry 20 }

-- {COLUMN} 1.3.6.1.4.1.2356.11.1.51.4.1.21
lcsStatusEthernetPortsErrorsEntryRxDscrUnderflow OBJECT-TYPE
    SYNTAX     Counter32
    MAX-ACCESS read-only
    STATUS     current
    DESCRIPTION
            "-- empty --"
    ::= { lcsStatusEthernetPortsErrorsEntry 21 }

-- {SCALAR} 1.3.6.1.4.1.2356.11.1.51.5
lcsStatusEthernetPortsLimitKbpsNumeric OBJECT-TYPE
    SYNTAX     Integer32 (0..2147483647)
    MAX-ACCESS read-only
    STATUS     current
    DESCRIPTION
            "-- empty --"
    ::= { lcsStatusEthernetPorts 5 }

-- {SCALAR} 1.3.6.1.4.1.2356.11.1.51.6
lcsStatusEthernetPortsLimitKbps OBJECT-TYPE
    SYNTAX     DisplayString
    MAX-ACCESS read-only
    STATUS     current
    DESCRIPTION
            "-- empty --"
    ::= { lcsStatusEthernetPorts 6 }

-- {TABLE} 1.3.6.1.4.1.2356.11.1.51.7
lcsStatusEthernetPortsPacketTransportTable OBJECT-TYPE
    SYNTAX     SEQUENCE OF LcsStatusEthernetPortsPacketTransportEntry
    MAX-ACCESS not-accessible
    STATUS     current
    DESCRIPTION
            "-- empty --"
    ::= { lcsStatusEthernetPorts 7 }

-- {ROW} 1.3.6.1.4.1.2356.11.1.51.7.1
lcsStatusEthernetPortsPacketTransportEntry OBJECT-TYPE
    SYNTAX     LcsStatusEthernetPortsPacketTransportEntry
    MAX-ACCESS not-accessible
    STATUS     current
    DESCRIPTION
            ""
    INDEX {
            lcsStatusEthernetPortsPacketTransportEntryIfc
          }
    ::= { lcsStatusEthernetPortsPacketTransportTable 1 }

LcsStatusEthernetPortsPacketTransportEntry ::= SEQUENCE {
            lcsStatusEthernetPortsPacketTransportEntryIfc INTEGER,
            lcsStatusEthernetPortsPacketTransportEntryRxPackets Counter32,
            lcsStatusEthernetPortsPacketTransportEntryTxPackets Counter32,
            lcsStatusEthernetPortsPacketTransportEntryRxBroadcasts Counter32,
            lcsStatusEthernetPortsPacketTransportEntryRxMulticasts Counter32,
            lcsStatusEthernetPortsPacketTransportEntryRxUnicasts Counter32,
            lcsStatusEthernetPortsPacketTransportEntryTxBroadcasts Counter32,
            lcsStatusEthernetPortsPacketTransportEntryTxMulticasts Counter32,
            lcsStatusEthernetPortsPacketTransportEntryTxUnicasts Counter32
    }

-- {COLUMN} 1.3.6.1.4.1.2356.11.1.51.7.1.1
lcsStatusEthernetPortsPacketTransportEntryIfc OBJECT-TYPE
    SYNTAX     INTEGER {
                  eUnknown (0),
                  eUplink (1),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            "-- empty --"
    ::= { lcsStatusEthernetPortsPacketTransportEntry 1 }

-- {COLUMN} 1.3.6.1.4.1.2356.11.1.51.7.1.2
lcsStatusEthernetPortsPacketTransportEntryRxPackets OBJECT-TYPE
    SYNTAX     Counter32
    MAX-ACCESS read-only
    STATUS     current
    DESCRIPTION
            "-- empty --"
    ::= { lcsStatusEthernetPortsPacketTransportEntry 2 }

-- {COLUMN} 1.3.6.1.4.1.2356.11.1.51.7.1.3
lcsStatusEthernetPortsPacketTransportEntryTxPackets OBJECT-TYPE
    SYNTAX     Counter32
    MAX-ACCESS read-only
    STATUS     current
    DESCRIPTION
            "-- empty --"
    ::= { lcsStatusEthernetPortsPacketTransportEntry 3 }

-- {COLUMN} 1.3.6.1.4.1.2356.11.1.51.7.1.4
lcsStatusEthernetPortsPacketTransportEntryRxBroadcasts OBJECT-TYPE
    SYNTAX     Counter32
    MAX-ACCESS read-only
    STATUS     current
    DESCRIPTION
            "-- empty --"
    ::= { lcsStatusEthernetPortsPacketTransportEntry 4 }

-- {COLUMN} 1.3.6.1.4.1.2356.11.1.51.7.1.5
lcsStatusEthernetPortsPacketTransportEntryRxMulticasts OBJECT-TYPE
    SYNTAX     Counter32
    MAX-ACCESS read-only
    STATUS     current
    DESCRIPTION
            "-- empty --"
    ::= { lcsStatusEthernetPortsPacketTransportEntry 5 }

-- {COLUMN} 1.3.6.1.4.1.2356.11.1.51.7.1.6
lcsStatusEthernetPortsPacketTransportEntryRxUnicasts OBJECT-TYPE
    SYNTAX     Counter32
    MAX-ACCESS read-only
    STATUS     current
    DESCRIPTION
            "-- empty --"
    ::= { lcsStatusEthernetPortsPacketTransportEntry 6 }

-- {COLUMN} 1.3.6.1.4.1.2356.11.1.51.7.1.7
lcsStatusEthernetPortsPacketTransportEntryTxBroadcasts OBJECT-TYPE
    SYNTAX     Counter32
    MAX-ACCESS read-only
    STATUS     current
    DESCRIPTION
            "-- empty --"
    ::= { lcsStatusEthernetPortsPacketTransportEntry 7 }

-- {COLUMN} 1.3.6.1.4.1.2356.11.1.51.7.1.8
lcsStatusEthernetPortsPacketTransportEntryTxMulticasts OBJECT-TYPE
    SYNTAX     Counter32
    MAX-ACCESS read-only
    STATUS     current
    DESCRIPTION
            "-- empty --"
    ::= { lcsStatusEthernetPortsPacketTransportEntry 8 }

-- {COLUMN} 1.3.6.1.4.1.2356.11.1.51.7.1.9
lcsStatusEthernetPortsPacketTransportEntryTxUnicasts OBJECT-TYPE
    SYNTAX     Counter32
    MAX-ACCESS read-only
    STATUS     current
    DESCRIPTION
            "-- empty --"
    ::= { lcsStatusEthernetPortsPacketTransportEntry 9 }

-- {TABLE} 1.3.6.1.4.1.2356.11.1.51.8
lcsStatusEthernetPortsByteTransportTable OBJECT-TYPE
    SYNTAX     SEQUENCE OF LcsStatusEthernetPortsByteTransportEntry
    MAX-ACCESS not-accessible
    STATUS     current
    DESCRIPTION
            "-- empty --"
    ::= { lcsStatusEthernetPorts 8 }

-- {ROW} 1.3.6.1.4.1.2356.11.1.51.8.1
lcsStatusEthernetPortsByteTransportEntry OBJECT-TYPE
    SYNTAX     LcsStatusEthernetPortsByteTransportEntry
    MAX-ACCESS not-accessible
    STATUS     current
    DESCRIPTION
            ""
    INDEX {
            lcsStatusEthernetPortsByteTransportEntryIfc
          }
    ::= { lcsStatusEthernetPortsByteTransportTable 1 }

LcsStatusEthernetPortsByteTransportEntry ::= SEQUENCE {
            lcsStatusEthernetPortsByteTransportEntryIfc INTEGER,
            lcsStatusEthernetPortsByteTransportEntryTxBytes Counter64,
            lcsStatusEthernetPortsByteTransportEntryRxBytes Counter64,
            lcsStatusEthernetPortsByteTransportEntryThroughput DisplayString,
            lcsStatusEthernetPortsByteTransportEntryMaxThroughput DisplayString,
            lcsStatusEthernetPortsByteTransportEntryBytesThroughput Integer32,
            lcsStatusEthernetPortsByteTransportEntryBytesMaxThroughput Integer32
    }

-- {COLUMN} 1.3.6.1.4.1.2356.11.1.51.8.1.1
lcsStatusEthernetPortsByteTransportEntryIfc OBJECT-TYPE
    SYNTAX     INTEGER {
                  eUnknown (0),
                  eUplink (1),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            "-- empty --"
    ::= { lcsStatusEthernetPortsByteTransportEntry 1 }

-- {COLUMN} 1.3.6.1.4.1.2356.11.1.51.8.1.2
lcsStatusEthernetPortsByteTransportEntryTxBytes OBJECT-TYPE
    SYNTAX     Counter64
    MAX-ACCESS read-only
    STATUS     current
    DESCRIPTION
            "-- empty --"
    ::= { lcsStatusEthernetPortsByteTransportEntry 2 }

-- {COLUMN} 1.3.6.1.4.1.2356.11.1.51.8.1.3
lcsStatusEthernetPortsByteTransportEntryRxBytes OBJECT-TYPE
    SYNTAX     Counter64
    MAX-ACCESS read-only
    STATUS     current
    DESCRIPTION
            "-- empty --"
    ::= { lcsStatusEthernetPortsByteTransportEntry 3 }

-- {COLUMN} 1.3.6.1.4.1.2356.11.1.51.8.1.4
lcsStatusEthernetPortsByteTransportEntryThroughput OBJECT-TYPE
    SYNTAX     DisplayString (SIZE(0..255))
    MAX-ACCESS read-only
    STATUS     current
    DESCRIPTION
            "-- empty --"
    ::= { lcsStatusEthernetPortsByteTransportEntry 4 }

-- {COLUMN} 1.3.6.1.4.1.2356.11.1.51.8.1.5
lcsStatusEthernetPortsByteTransportEntryMaxThroughput OBJECT-TYPE
    SYNTAX     DisplayString (SIZE(0..255))
    MAX-ACCESS read-only
    STATUS     current
    DESCRIPTION
            "-- empty --"
    ::= { lcsStatusEthernetPortsByteTransportEntry 5 }

-- {COLUMN} 1.3.6.1.4.1.2356.11.1.51.8.1.6
lcsStatusEthernetPortsByteTransportEntryBytesThroughput OBJECT-TYPE
    SYNTAX     Integer32 (0..2147483647)
    MAX-ACCESS read-only
    STATUS     current
    DESCRIPTION
            "-- empty --"
    ::= { lcsStatusEthernetPortsByteTransportEntry 6 }

-- {COLUMN} 1.3.6.1.4.1.2356.11.1.51.8.1.7
lcsStatusEthernetPortsByteTransportEntryBytesMaxThroughput OBJECT-TYPE
    SYNTAX     Integer32 (0..2147483647)
    MAX-ACCESS read-only
    STATUS     current
    DESCRIPTION
            "-- empty --"
    ::= { lcsStatusEthernetPortsByteTransportEntry 7 }

-- {TABLE} 1.3.6.1.4.1.2356.11.1.51.11
lcsStatusEthernetPortsSfpPortsTable OBJECT-TYPE
    SYNTAX     SEQUENCE OF LcsStatusEthernetPortsSfpPortsEntry
    MAX-ACCESS not-accessible
    STATUS     current
    DESCRIPTION
            "-- empty --"
    ::= { lcsStatusEthernetPorts 11 }

-- {ROW} 1.3.6.1.4.1.2356.11.1.51.11.1
lcsStatusEthernetPortsSfpPortsEntry OBJECT-TYPE
    SYNTAX     LcsStatusEthernetPortsSfpPortsEntry
    MAX-ACCESS not-accessible
    STATUS     current
    DESCRIPTION
            ""
    INDEX {
            lcsStatusEthernetPortsSfpPortsEntryPort
          }
    ::= { lcsStatusEthernetPortsSfpPortsTable 1 }

LcsStatusEthernetPortsSfpPortsEntry ::= SEQUENCE {
            lcsStatusEthernetPortsSfpPortsEntryPort INTEGER,
            lcsStatusEthernetPortsSfpPortsEntryVendor DisplayString,
            lcsStatusEthernetPortsSfpPortsEntryPartNo DisplayString,
            lcsStatusEthernetPortsSfpPortsEntryRevision DisplayString,
            lcsStatusEthernetPortsSfpPortsEntrySerialNo DisplayString,
            lcsStatusEthernetPortsSfpPortsEntryStatus INTEGER,
            lcsStatusEthernetPortsSfpPortsEntryMedium BITS,
            lcsStatusEthernetPortsSfpPortsEntryWavelength Integer32,
            lcsStatusEthernetPortsSfpPortsEntryDate DisplayString,
            lcsStatusEthernetPortsSfpPortsEntryConnector INTEGER,
            lcsStatusEthernetPortsSfpPortsEntryTemperature Integer32,
            lcsStatusEthernetPortsSfpPortsEntrySupplyVoltage Integer32,
            lcsStatusEthernetPortsSfpPortsEntryTxBias Integer32,
            lcsStatusEthernetPortsSfpPortsEntryTxPower Integer32,
            lcsStatusEthernetPortsSfpPortsEntryRxPower Integer32,
            lcsStatusEthernetPortsSfpPortsEntryMonitoring INTEGER
    }

-- {COLUMN} 1.3.6.1.4.1.2356.11.1.51.11.1.1
lcsStatusEthernetPortsSfpPortsEntryPort OBJECT-TYPE
    SYNTAX     INTEGER {
                  eUnknown (0),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            "-- empty --"
    ::= { lcsStatusEthernetPortsSfpPortsEntry 1 }

-- {COLUMN} 1.3.6.1.4.1.2356.11.1.51.11.1.2
lcsStatusEthernetPortsSfpPortsEntryVendor OBJECT-TYPE
    SYNTAX     DisplayString (SIZE(0..255))
    MAX-ACCESS read-only
    STATUS     current
    DESCRIPTION
            "-- empty --"
    ::= { lcsStatusEthernetPortsSfpPortsEntry 2 }

-- {COLUMN} 1.3.6.1.4.1.2356.11.1.51.11.1.3
lcsStatusEthernetPortsSfpPortsEntryPartNo OBJECT-TYPE
    SYNTAX     DisplayString (SIZE(0..255))
    MAX-ACCESS read-only
    STATUS     current
    DESCRIPTION
            "-- empty --"
    ::= { lcsStatusEthernetPortsSfpPortsEntry 3 }

-- {COLUMN} 1.3.6.1.4.1.2356.11.1.51.11.1.4
lcsStatusEthernetPortsSfpPortsEntryRevision OBJECT-TYPE
    SYNTAX     DisplayString (SIZE(0..255))
    MAX-ACCESS read-only
    STATUS     current
    DESCRIPTION
            "-- empty --"
    ::= { lcsStatusEthernetPortsSfpPortsEntry 4 }

-- {COLUMN} 1.3.6.1.4.1.2356.11.1.51.11.1.5
lcsStatusEthernetPortsSfpPortsEntrySerialNo OBJECT-TYPE
    SYNTAX     DisplayString (SIZE(0..255))
    MAX-ACCESS read-only
    STATUS     current
    DESCRIPTION
            "-- empty --"
    ::= { lcsStatusEthernetPortsSfpPortsEntry 5 }

-- {COLUMN} 1.3.6.1.4.1.2356.11.1.51.11.1.6
lcsStatusEthernetPortsSfpPortsEntryStatus OBJECT-TYPE
    SYNTAX     INTEGER {
                  eNotPresent (0),
                  eOk (1),
                  eChksumError (2),
                  eUnsupported (3),
                  eTxFault (4),
                  eDisabled (5),
                  eNotReady (6),
                  eOvercurrent (7)
            }
    MAX-ACCESS read-only
    STATUS     current
    DESCRIPTION
            "-- empty --"
    ::= { lcsStatusEthernetPortsSfpPortsEntry 6 }

-- {COLUMN} 1.3.6.1.4.1.2356.11.1.51.11.1.7
lcsStatusEthernetPortsSfpPortsEntryMedium OBJECT-TYPE
    SYNTAX     BITS {
                  eNone (0),
                  e1000baseBx10 (1),
                  e100baseFx (2),
                  e100baseLx (3),
                  e1000baseT (4),
                  e1000baseCx (5),
                  e1000baseLx (6),
                  e1000baseSx (7)
            }
    MAX-ACCESS read-only
    STATUS     current
    DESCRIPTION
            "-- empty --"
    ::= { lcsStatusEthernetPortsSfpPortsEntry 7 }

-- {COLUMN} 1.3.6.1.4.1.2356.11.1.51.11.1.8
lcsStatusEthernetPortsSfpPortsEntryWavelength OBJECT-TYPE
    SYNTAX     Integer32 (0..65535)
    MAX-ACCESS read-only
    STATUS     current
    DESCRIPTION
            "-- empty --"
    ::= { lcsStatusEthernetPortsSfpPortsEntry 8 }

-- {COLUMN} 1.3.6.1.4.1.2356.11.1.51.11.1.9
lcsStatusEthernetPortsSfpPortsEntryDate OBJECT-TYPE
    SYNTAX     DisplayString (SIZE(0..255))
    MAX-ACCESS read-only
    STATUS     current
    DESCRIPTION
            "-- empty --"
    ::= { lcsStatusEthernetPortsSfpPortsEntry 9 }

-- {COLUMN} 1.3.6.1.4.1.2356.11.1.51.11.1.10
lcsStatusEthernetPortsSfpPortsEntryConnector OBJECT-TYPE
    SYNTAX     INTEGER {
                  eUnknown (0),
                  eSc (2),
                  eLc (7),
                  eSg (10),
                  eCopperPigtail (33),
                  eRj45 (34)
            }
    MAX-ACCESS read-only
    STATUS     current
    DESCRIPTION
            "-- empty --"
    ::= { lcsStatusEthernetPortsSfpPortsEntry 10 }

-- {COLUMN} 1.3.6.1.4.1.2356.11.1.51.11.1.11
lcsStatusEthernetPortsSfpPortsEntryTemperature OBJECT-TYPE
    SYNTAX     Integer32 (-32768..32767)
    MAX-ACCESS read-only
    STATUS     current
    DESCRIPTION
            "-- empty --"
    ::= { lcsStatusEthernetPortsSfpPortsEntry 11 }

-- {COLUMN} 1.3.6.1.4.1.2356.11.1.51.11.1.12
lcsStatusEthernetPortsSfpPortsEntrySupplyVoltage OBJECT-TYPE
    SYNTAX     Integer32 (0..65535)
    MAX-ACCESS read-only
    STATUS     current
    DESCRIPTION
            "-- empty --"
    ::= { lcsStatusEthernetPortsSfpPortsEntry 12 }

-- {COLUMN} 1.3.6.1.4.1.2356.11.1.51.11.1.13
lcsStatusEthernetPortsSfpPortsEntryTxBias OBJECT-TYPE
    SYNTAX     Integer32 (0..65535)
    MAX-ACCESS read-only
    STATUS     current
    DESCRIPTION
            "-- empty --"
    ::= { lcsStatusEthernetPortsSfpPortsEntry 13 }

-- {COLUMN} 1.3.6.1.4.1.2356.11.1.51.11.1.14
lcsStatusEthernetPortsSfpPortsEntryTxPower OBJECT-TYPE
    SYNTAX     Integer32 (0..65535)
    MAX-ACCESS read-only
    STATUS     current
    DESCRIPTION
            "-- empty --"
    ::= { lcsStatusEthernetPortsSfpPortsEntry 14 }

-- {COLUMN} 1.3.6.1.4.1.2356.11.1.51.11.1.15
lcsStatusEthernetPortsSfpPortsEntryRxPower OBJECT-TYPE
    SYNTAX     Integer32 (0..65535)
    MAX-ACCESS read-only
    STATUS     current
    DESCRIPTION
            "-- empty --"
    ::= { lcsStatusEthernetPortsSfpPortsEntry 15 }

-- {COLUMN} 1.3.6.1.4.1.2356.11.1.51.11.1.16
lcsStatusEthernetPortsSfpPortsEntryMonitoring OBJECT-TYPE
    SYNTAX     INTEGER {
                  eNo (0),
                  eYes (1)
            }
    MAX-ACCESS read-only
    STATUS     current
    DESCRIPTION
            "-- empty --"
    ::= { lcsStatusEthernetPortsSfpPortsEntry 16 }

-- {SCALAR} 1.3.6.1.4.1.2356.11.1.51.99
lcsStatusEthernetPortsDeleteValues OBJECT-TYPE
    SYNTAX     DisplayString
    MAX-ACCESS read-write
    STATUS     current
    DESCRIPTION
            ""
    ::= { lcsStatusEthernetPorts 99 }

-- {NODE} 1.3.6.1.4.1.2356.11.1.52
lcsStatusPppoeServer OBJECT IDENTIFIER ::= { lcsStatus 52 }

-- {SCALAR} 1.3.6.1.4.1.2356.11.1.52.1
lcsStatusPppoeServerRxPackets OBJECT-TYPE
    SYNTAX     Counter32
    MAX-ACCESS read-only
    STATUS     current
    DESCRIPTION
            ""
    ::= { lcsStatusPppoeServer 1 }

-- {SCALAR} 1.3.6.1.4.1.2356.11.1.52.2
lcsStatusPppoeServerTxPackets OBJECT-TYPE
    SYNTAX     Counter32
    MAX-ACCESS read-only
    STATUS     current
    DESCRIPTION
            ""
    ::= { lcsStatusPppoeServer 2 }

-- {SCALAR} 1.3.6.1.4.1.2356.11.1.52.5
lcsStatusPppoeServerDroppedPackets OBJECT-TYPE
    SYNTAX     Counter32
    MAX-ACCESS read-only
    STATUS     current
    DESCRIPTION
            ""
    ::= { lcsStatusPppoeServer 5 }

-- {SCALAR} 1.3.6.1.4.1.2356.11.1.52.6
lcsStatusPppoeServerRxErrors OBJECT-TYPE
    SYNTAX     Counter32
    MAX-ACCESS read-only
    STATUS     current
    DESCRIPTION
            ""
    ::= { lcsStatusPppoeServer 6 }

-- {SCALAR} 1.3.6.1.4.1.2356.11.1.52.8
lcsStatusPppoeServerSessionErrors OBJECT-TYPE
    SYNTAX     Counter32
    MAX-ACCESS read-only
    STATUS     current
    DESCRIPTION
            ""
    ::= { lcsStatusPppoeServer 8 }

-- {TABLE} 1.3.6.1.4.1.2356.11.1.52.9
lcsStatusPppoeServerConnectionsTable OBJECT-TYPE
    SYNTAX     SEQUENCE OF LcsStatusPppoeServerConnectionsEntry
    MAX-ACCESS not-accessible
    STATUS     current
    DESCRIPTION
            ""
    ::= { lcsStatusPppoeServer 9 }

-- {ROW} 1.3.6.1.4.1.2356.11.1.52.9.1
lcsStatusPppoeServerConnectionsEntry OBJECT-TYPE
    SYNTAX     LcsStatusPppoeServerConnectionsEntry
    MAX-ACCESS not-accessible
    STATUS     current
    DESCRIPTION
            ""
    INDEX {
            lcsStatusPppoeServerConnectionsEntryChannel,
            lcsStatusPppoeServerConnectionsEntryMacAddress
          }
    ::= { lcsStatusPppoeServerConnectionsTable 1 }

LcsStatusPppoeServerConnectionsEntry ::= SEQUENCE {
            lcsStatusPppoeServerConnectionsEntryChannel DisplayString,
            lcsStatusPppoeServerConnectionsEntryMacAddress DisplayString,
            lcsStatusPppoeServerConnectionsEntryState INTEGER,
            lcsStatusPppoeServerConnectionsEntryLastError INTEGER,
            lcsStatusPppoeServerConnectionsEntryShTime Integer32,
            lcsStatusPppoeServerConnectionsEntryPeerAddress IpAddress,
            lcsStatusPppoeServerConnectionsEntryConnTime Gauge32
    }

-- {COLUMN} 1.3.6.1.4.1.2356.11.1.52.9.1.1
lcsStatusPppoeServerConnectionsEntryChannel OBJECT-TYPE
    SYNTAX     DisplayString (SIZE(0..16))
    MAX-ACCESS read-only
    STATUS     current
    DESCRIPTION
            ""
    ::= { lcsStatusPppoeServerConnectionsEntry 1 }

-- {COLUMN} 1.3.6.1.4.1.2356.11.1.52.9.1.2
lcsStatusPppoeServerConnectionsEntryMacAddress OBJECT-TYPE
    SYNTAX     DisplayString (SIZE(0..12))
    MAX-ACCESS read-only
    STATUS     current
    DESCRIPTION
            ""
    ::= { lcsStatusPppoeServerConnectionsEntry 2 }

-- {COLUMN} 1.3.6.1.4.1.2356.11.1.52.9.1.3
lcsStatusPppoeServerConnectionsEntryState OBJECT-TYPE
    SYNTAX     INTEGER {
                  eInit (0),
                  eSetupWan (1),
                  eReady (2),
                  eWaitForCb (3),
                  eDial (4),
                  eIncomingCall (5),
                  eProtocol (6),
                  eConnection (7),
                  eDisconnecting (8),
                  eCallBack (9),
                  eBundleConnect (10),
                  eProtocol2 (11),
                  eReserved (12),
                  eBundle (13)
            }
    MAX-ACCESS read-only
    STATUS     current
    DESCRIPTION
            ""
    ::= { lcsStatusPppoeServerConnectionsEntry 3 }

-- {COLUMN} 1.3.6.1.4.1.2356.11.1.52.9.1.4
lcsStatusPppoeServerConnectionsEntryLastError OBJECT-TYPE
    SYNTAX     INTEGER {
                  eNone (0),
                  eRemoteDoubled (267),
                  eIcmpConnError (275),
                  eDhcpTimeout (277),
                  ePptpNoResponse (278),
                  eVpnNoResponse (279),
                  eArpNoResponse (280),
                  ePptpNoChannel (513),
                  ePptpBadFormat (514),
                  ePptpBadValue (515),
                  ePptpNoRessource (516),
                  ePptpBadCallId (517),
                  ePptpGenError (518),
                  eRemoteDisconnected (17153),
                  eManualDisconnect (17154),
                  eShortholdExpired (17155),
                  ePhysicalDisconnected (17156),
                  eInvalidPhysicalChannel (17157),
                  eDynamicVpnReconnect (17158),
                  eConfigurationChanged (17159),
                  eRemovedFromConfig (17160),
                  eLcpRejected (32768),
                  eAuthError (32769),
                  eAuthRejected (32770),
                  eLcpConnError (32771),
                  ePapRejected (32784),
                  ePapRxTimeout (32785),
                  ePapTxTimeout (32786),
                  eWrongPapReq (32787),
                  ePapNakReceived (32788),
                  eUnknPapPeer (32789),
                  eChapRejected (32800),
                  eChapRxTimeout (32801),
                  eChapTxTimeout (32802),
                  eWrongChapResp (32803),
                  eChapFailRecvd (32804),
                  eUnknChapPeer (32805),
                  eIpxcpRejected (32816),
                  eWrongIpxcpNet (32817),
                  eIpxcpNetReject (32818),
                  eIpxcpRouteUnkn (32819),
                  eIpcpRejected (32832),
                  eCcpRejected (32848),
                  eNoNcpAvailable (33008)
            }
    MAX-ACCESS read-write
    STATUS     current
    DESCRIPTION
            ""
    ::= { lcsStatusPppoeServerConnectionsEntry 4 }

-- {COLUMN} 1.3.6.1.4.1.2356.11.1.52.9.1.5
lcsStatusPppoeServerConnectionsEntryShTime OBJECT-TYPE
    SYNTAX     Integer32 (0..65535)
    MAX-ACCESS read-only
    STATUS     current
    DESCRIPTION
            ""
    ::= { lcsStatusPppoeServerConnectionsEntry 5 }

-- {COLUMN} 1.3.6.1.4.1.2356.11.1.52.9.1.6
lcsStatusPppoeServerConnectionsEntryPeerAddress OBJECT-TYPE
    SYNTAX     IpAddress
    MAX-ACCESS read-only
    STATUS     current
    DESCRIPTION
            ""
    ::= { lcsStatusPppoeServerConnectionsEntry 6 }

-- {COLUMN} 1.3.6.1.4.1.2356.11.1.52.9.1.7
lcsStatusPppoeServerConnectionsEntryConnTime OBJECT-TYPE
    SYNTAX     Gauge32
    MAX-ACCESS read-only
    STATUS     current
    DESCRIPTION
            ""
    ::= { lcsStatusPppoeServerConnectionsEntry 7 }

-- {SCALAR} 1.3.6.1.4.1.2356.11.1.52.10
lcsStatusPppoeServerNumConnections OBJECT-TYPE
    SYNTAX     Integer32 (0..2147483647)
    MAX-ACCESS read-only
    STATUS     current
    DESCRIPTION
            ""
    ::= { lcsStatusPppoeServer 10 }

-- {SCALAR} 1.3.6.1.4.1.2356.11.1.52.11
lcsStatusPppoeServerDeleteValues OBJECT-TYPE
    SYNTAX     DisplayString
    MAX-ACCESS read-write
    STATUS     current
    DESCRIPTION
            ""
    ::= { lcsStatusPppoeServer 11 }

-- {NODE} 1.3.6.1.4.1.2356.11.1.53
lcsStatusVcCllMngr OBJECT IDENTIFIER ::= { lcsStatus 53 }

-- {SCALAR} 1.3.6.1.4.1.2356.11.1.53.1
lcsStatusVcCllMngrOperating OBJECT-TYPE
    SYNTAX     INTEGER {
                  eNo (0),
                  eYes (1)
            }
    MAX-ACCESS read-only
    STATUS     current
    DESCRIPTION
            "-- empty --"
    ::= { lcsStatusVcCllMngr 1 }

-- {TABLE} 1.3.6.1.4.1.2356.11.1.53.3
lcsStatusVcCllMngrUsersTable OBJECT-TYPE
    SYNTAX     SEQUENCE OF LcsStatusVcCllMngrUsersEntry
    MAX-ACCESS not-accessible
    STATUS     current
    DESCRIPTION
            "-- empty --"
    ::= { lcsStatusVcCllMngr 3 }

-- {ROW} 1.3.6.1.4.1.2356.11.1.53.3.1
lcsStatusVcCllMngrUsersEntry OBJECT-TYPE
    SYNTAX     LcsStatusVcCllMngrUsersEntry
    MAX-ACCESS not-accessible
    STATUS     current
    DESCRIPTION
            ""
    INDEX {
            lcsStatusVcCllMngrUsersEntryIndex
          }
    ::= { lcsStatusVcCllMngrUsersTable 1 }

LcsStatusVcCllMngrUsersEntry ::= SEQUENCE {
            lcsStatusVcCllMngrUsersEntryIndex Integer32,
            lcsStatusVcCllMngrUsersEntryNumberName DisplayString,
            lcsStatusVcCllMngrUsersEntryType INTEGER,
            lcsStatusVcCllMngrUsersEntryDisplayName DisplayString,
            lcsStatusVcCllMngrUsersEntryDomain DisplayString,
            lcsStatusVcCllMngrUsersEntryLocalRegister INTEGER,
            lcsStatusVcCllMngrUsersEntryRemoteRegister INTEGER,
            lcsStatusVcCllMngrUsersEntryIfc BITS,
            lcsStatusVcCllMngrUsersEntryStatus INTEGER,
            lcsStatusVcCllMngrUsersEntryAddress DisplayString,
            lcsStatusVcCllMngrUsersEntryCfuActive INTEGER,
            lcsStatusVcCllMngrUsersEntryCfuTarget DisplayString,
            lcsStatusVcCllMngrUsersEntryCfnrActive INTEGER,
            lcsStatusVcCllMngrUsersEntryCfnrTarget DisplayString,
            lcsStatusVcCllMngrUsersEntryCfnrTimeout Integer32,
            lcsStatusVcCllMngrUsersEntryCfbActive INTEGER,
            lcsStatusVcCllMngrUsersEntryCfbTarget DisplayString,
            lcsStatusVcCllMngrUsersEntryAccessFromWan INTEGER,
            lcsStatusVcCllMngrUsersEntryExpires Integer32
    }

-- {COLUMN} 1.3.6.1.4.1.2356.11.1.53.3.1.1
lcsStatusVcCllMngrUsersEntryIndex OBJECT-TYPE
    SYNTAX     Integer32 (0..255)
    MAX-ACCESS read-only
    STATUS     current
    DESCRIPTION
            "-- empty --"
    ::= { lcsStatusVcCllMngrUsersEntry 1 }

-- {COLUMN} 1.3.6.1.4.1.2356.11.1.53.3.1.2
lcsStatusVcCllMngrUsersEntryNumberName OBJECT-TYPE
    SYNTAX     DisplayString (SIZE(0..20))
    MAX-ACCESS read-only
    STATUS     current
    DESCRIPTION
            "-- empty --"
    ::= { lcsStatusVcCllMngrUsersEntry 2 }

-- {COLUMN} 1.3.6.1.4.1.2356.11.1.53.3.1.3
lcsStatusVcCllMngrUsersEntryType OBJECT-TYPE
    SYNTAX     INTEGER {
                  eIsdnUser (0),
                  eSipUser (1),
                  eUnspecified (2),
                  eAnalogUser (3),
                  eDectUser (4)
            }
    MAX-ACCESS read-only
    STATUS     current
    DESCRIPTION
            "-- empty --"
    ::= { lcsStatusVcCllMngrUsersEntry 3 }

-- {COLUMN} 1.3.6.1.4.1.2356.11.1.53.3.1.4
lcsStatusVcCllMngrUsersEntryDisplayName OBJECT-TYPE
    SYNTAX     DisplayString (SIZE(0..19))
    MAX-ACCESS read-only
    STATUS     current
    DESCRIPTION
            "-- empty --"
    ::= { lcsStatusVcCllMngrUsersEntry 4 }

-- {COLUMN} 1.3.6.1.4.1.2356.11.1.53.3.1.5
lcsStatusVcCllMngrUsersEntryDomain OBJECT-TYPE
    SYNTAX     DisplayString (SIZE(0..63))
    MAX-ACCESS read-only
    STATUS     current
    DESCRIPTION
            "-- empty --"
    ::= { lcsStatusVcCllMngrUsersEntry 5 }

-- {COLUMN} 1.3.6.1.4.1.2356.11.1.53.3.1.6
lcsStatusVcCllMngrUsersEntryLocalRegister OBJECT-TYPE
    SYNTAX     INTEGER {
                  eNotPossible (0),
                  eRegistered (1),
                  eNotRegistered (2),
                  eFailed (3),
                  eBadDomain (4),
                  eAuthFailure (5),
                  eUnknownUser (6),
                  eNotConfigured (7),
                  eSerialnoFailure (8),
                  eTimeout (9),
                  eBlocked (10)
            }
    MAX-ACCESS read-only
    STATUS     current
    DESCRIPTION
            "-- empty --"
    ::= { lcsStatusVcCllMngrUsersEntry 6 }

-- {COLUMN} 1.3.6.1.4.1.2356.11.1.53.3.1.7
lcsStatusVcCllMngrUsersEntryRemoteRegister OBJECT-TYPE
    SYNTAX     INTEGER {
                  eNotPossible (0),
                  eRegistered (1),
                  eNotRegistered (2),
                  eFailed (3),
                  eBadDomain (4),
                  eAuthFailure (5),
                  eUnknownUser (6),
                  eNotConfigured (7),
                  eSerialnoFailure (8),
                  eTimeout (9),
                  eBlocked (10)
            }
    MAX-ACCESS read-only
    STATUS     current
    DESCRIPTION
            "-- empty --"
    ::= { lcsStatusVcCllMngrUsersEntry 7 }

-- {COLUMN} 1.3.6.1.4.1.2356.11.1.53.3.1.8
lcsStatusVcCllMngrUsersEntryIfc OBJECT-TYPE
    SYNTAX     BITS {
                  eAnalog4Out (16),
                  eAnalog3Out (17),
                  eAnalog2Out (18),
                  eAnalog1Out (19),
                  eAnalog4 (24),
                  eAnalog3 (25),
                  eAnalog2 (26),
                  eAnalog1 (27),
                  eS02 (30),
                  eS01 (31)
            }
    MAX-ACCESS read-only
    STATUS     current
    DESCRIPTION
            "-- empty --"
    ::= { lcsStatusVcCllMngrUsersEntry 8 }

-- {COLUMN} 1.3.6.1.4.1.2356.11.1.53.3.1.9
lcsStatusVcCllMngrUsersEntryStatus OBJECT-TYPE
    SYNTAX     INTEGER {
                  eUnspecified (0),
                  eGood (1)
            }
    MAX-ACCESS read-only
    STATUS     current
    DESCRIPTION
            "-- empty --"
    ::= { lcsStatusVcCllMngrUsersEntry 9 }

-- {COLUMN} 1.3.6.1.4.1.2356.11.1.53.3.1.10
lcsStatusVcCllMngrUsersEntryAddress OBJECT-TYPE
    SYNTAX     DisplayString (SIZE(0..95))
    MAX-ACCESS read-only
    STATUS     current
    DESCRIPTION
            "-- empty --"
    ::= { lcsStatusVcCllMngrUsersEntry 10 }

-- {COLUMN} 1.3.6.1.4.1.2356.11.1.53.3.1.11
lcsStatusVcCllMngrUsersEntryCfuActive OBJECT-TYPE
    SYNTAX     INTEGER {
                  eNo (0),
                  eYes (1)
            }
    MAX-ACCESS read-only
    STATUS     current
    DESCRIPTION
            "-- empty --"
    ::= { lcsStatusVcCllMngrUsersEntry 11 }

-- {COLUMN} 1.3.6.1.4.1.2356.11.1.53.3.1.12
lcsStatusVcCllMngrUsersEntryCfuTarget OBJECT-TYPE
    SYNTAX     DisplayString (SIZE(0..64))
    MAX-ACCESS read-only
    STATUS     current
    DESCRIPTION
            "-- empty --"
    ::= { lcsStatusVcCllMngrUsersEntry 12 }

-- {COLUMN} 1.3.6.1.4.1.2356.11.1.53.3.1.13
lcsStatusVcCllMngrUsersEntryCfnrActive OBJECT-TYPE
    SYNTAX     INTEGER {
                  eNo (0),
                  eYes (1)
            }
    MAX-ACCESS read-only
    STATUS     current
    DESCRIPTION
            "-- empty --"
    ::= { lcsStatusVcCllMngrUsersEntry 13 }

-- {COLUMN} 1.3.6.1.4.1.2356.11.1.53.3.1.14
lcsStatusVcCllMngrUsersEntryCfnrTarget OBJECT-TYPE
    SYNTAX     DisplayString (SIZE(0..64))
    MAX-ACCESS read-only
    STATUS     current
    DESCRIPTION
            "-- empty --"
    ::= { lcsStatusVcCllMngrUsersEntry 14 }

-- {COLUMN} 1.3.6.1.4.1.2356.11.1.53.3.1.15
lcsStatusVcCllMngrUsersEntryCfnrTimeout OBJECT-TYPE
    SYNTAX     Integer32 (0..2147483647)
    MAX-ACCESS read-only
    STATUS     current
    DESCRIPTION
            "-- empty --"
    ::= { lcsStatusVcCllMngrUsersEntry 15 }

-- {COLUMN} 1.3.6.1.4.1.2356.11.1.53.3.1.16
lcsStatusVcCllMngrUsersEntryCfbActive OBJECT-TYPE
    SYNTAX     INTEGER {
                  eNo (0),
                  eYes (1)
            }
    MAX-ACCESS read-only
    STATUS     current
    DESCRIPTION
            "-- empty --"
    ::= { lcsStatusVcCllMngrUsersEntry 16 }

-- {COLUMN} 1.3.6.1.4.1.2356.11.1.53.3.1.17
lcsStatusVcCllMngrUsersEntryCfbTarget OBJECT-TYPE
    SYNTAX     DisplayString (SIZE(0..64))
    MAX-ACCESS read-only
    STATUS     current
    DESCRIPTION
            "-- empty --"
    ::= { lcsStatusVcCllMngrUsersEntry 17 }

-- {COLUMN} 1.3.6.1.4.1.2356.11.1.53.3.1.18
lcsStatusVcCllMngrUsersEntryAccessFromWan OBJECT-TYPE
    SYNTAX     INTEGER {
                  eVpn (1),
                  eNo (2)
            }
    MAX-ACCESS read-only
    STATUS     current
    DESCRIPTION
            "-- empty --"
    ::= { lcsStatusVcCllMngrUsersEntry 18 }

-- {COLUMN} 1.3.6.1.4.1.2356.11.1.53.3.1.19
lcsStatusVcCllMngrUsersEntryExpires OBJECT-TYPE
    SYNTAX     Integer32 (-2147483648..2147483647)
    MAX-ACCESS read-only
    STATUS     current
    DESCRIPTION
            "-- empty --"
    ::= { lcsStatusVcCllMngrUsersEntry 19 }

-- {TABLE} 1.3.6.1.4.1.2356.11.1.53.4
lcsStatusVcCllMngrLinesTable OBJECT-TYPE
    SYNTAX     SEQUENCE OF LcsStatusVcCllMngrLinesEntry
    MAX-ACCESS not-accessible
    STATUS     current
    DESCRIPTION
            "-- empty --"
    ::= { lcsStatusVcCllMngr 4 }

-- {ROW} 1.3.6.1.4.1.2356.11.1.53.4.1
lcsStatusVcCllMngrLinesEntry OBJECT-TYPE
    SYNTAX     LcsStatusVcCllMngrLinesEntry
    MAX-ACCESS not-accessible
    STATUS     current
    DESCRIPTION
            ""
    INDEX {
            lcsStatusVcCllMngrLinesEntryIndex
          }
    ::= { lcsStatusVcCllMngrLinesTable 1 }

LcsStatusVcCllMngrLinesEntry ::= SEQUENCE {
            lcsStatusVcCllMngrLinesEntryIndex Integer32,
            lcsStatusVcCllMngrLinesEntryName DisplayString,
            lcsStatusVcCllMngrLinesEntryType INTEGER,
            lcsStatusVcCllMngrLinesEntryRegStatus INTEGER,
            lcsStatusVcCllMngrLinesEntryLineStatus INTEGER,
            lcsStatusVcCllMngrLinesEntryQuality INTEGER,
            lcsStatusVcCllMngrLinesEntryNumber DisplayString,
            lcsStatusVcCllMngrLinesEntryDomain DisplayString,
            lcsStatusVcCllMngrLinesEntryRegState INTEGER,
            lcsStatusVcCllMngrLinesEntryInccallrecv Integer32,
            lcsStatusVcCllMngrLinesEntryInccallansw Integer32,
            lcsStatusVcCllMngrLinesEntryInccallconn Integer32,
            lcsStatusVcCllMngrLinesEntryInccallfail Integer32,
            lcsStatusVcCllMngrLinesEntryOutcallattm Integer32,
            lcsStatusVcCllMngrLinesEntryOutcallansw Integer32,
            lcsStatusVcCllMngrLinesEntryOutcallconn Integer32,
            lcsStatusVcCllMngrLinesEntryOutcallfail Integer32,
            lcsStatusVcCllMngrLinesEntryRemoteIpAddress DisplayString
    }

-- {COLUMN} 1.3.6.1.4.1.2356.11.1.53.4.1.1
lcsStatusVcCllMngrLinesEntryIndex OBJECT-TYPE
    SYNTAX     Integer32 (0..255)
    MAX-ACCESS read-only
    STATUS     current
    DESCRIPTION
            "-- empty --"
    ::= { lcsStatusVcCllMngrLinesEntry 1 }

-- {COLUMN} 1.3.6.1.4.1.2356.11.1.53.4.1.2
lcsStatusVcCllMngrLinesEntryName OBJECT-TYPE
    SYNTAX     DisplayString (SIZE(0..32))
    MAX-ACCESS read-only
    STATUS     current
    DESCRIPTION
            "-- empty --"
    ::= { lcsStatusVcCllMngrLinesEntry 2 }

-- {COLUMN} 1.3.6.1.4.1.2356.11.1.53.4.1.3
lcsStatusVcCllMngrLinesEntryType OBJECT-TYPE
    SYNTAX     INTEGER {
                  eIsdn (0),
                  eSipPbx (1),
                  eSipProvider (2),
                  eAnalog (3)
            }
    MAX-ACCESS read-only
    STATUS     current
    DESCRIPTION
            "-- empty --"
    ::= { lcsStatusVcCllMngrLinesEntry 3 }

-- {COLUMN} 1.3.6.1.4.1.2356.11.1.53.4.1.4
lcsStatusVcCllMngrLinesEntryRegStatus OBJECT-TYPE
    SYNTAX     INTEGER {
                  eNotPossible (0),
                  eRegistered (1),
                  eNotRegistered (2),
                  eFailed (3),
                  eBadDomain (4),
                  eAuthFailure (5),
                  eUnknownUser (6),
                  eNotConfigured (7),
                  eSerialnoFailure (8),
                  eTimeout (9),
                  eBlocked (10)
            }
    MAX-ACCESS read-only
    STATUS     current
    DESCRIPTION
            "-- empty --"
    ::= { lcsStatusVcCllMngrLinesEntry 4 }

-- {COLUMN} 1.3.6.1.4.1.2356.11.1.53.4.1.5
lcsStatusVcCllMngrLinesEntryLineStatus OBJECT-TYPE
    SYNTAX     INTEGER {
                  eUnspecified (0),
                  eFailure (1),
                  eBusy (2),
                  eReady (3)
            }
    MAX-ACCESS read-only
    STATUS     current
    DESCRIPTION
            "-- empty --"
    ::= { lcsStatusVcCllMngrLinesEntry 5 }

-- {COLUMN} 1.3.6.1.4.1.2356.11.1.53.4.1.6
lcsStatusVcCllMngrLinesEntryQuality OBJECT-TYPE
    SYNTAX     INTEGER {
                  eUnspecified (0),
                  eBad (1),
                  ePoor (2),
                  eFair (3),
                  eGood (4),
                  eExcellent (5)
            }
    MAX-ACCESS read-only
    STATUS     current
    DESCRIPTION
            "-- empty --"
    ::= { lcsStatusVcCllMngrLinesEntry 6 }

-- {COLUMN} 1.3.6.1.4.1.2356.11.1.53.4.1.7
lcsStatusVcCllMngrLinesEntryNumber OBJECT-TYPE
    SYNTAX     DisplayString (SIZE(0..19))
    MAX-ACCESS read-only
    STATUS     current
    DESCRIPTION
            "-- empty --"
    ::= { lcsStatusVcCllMngrLinesEntry 7 }

-- {COLUMN} 1.3.6.1.4.1.2356.11.1.53.4.1.8
lcsStatusVcCllMngrLinesEntryDomain OBJECT-TYPE
    SYNTAX     DisplayString (SIZE(0..63))
    MAX-ACCESS read-only
    STATUS     current
    DESCRIPTION
            "-- empty --"
    ::= { lcsStatusVcCllMngrLinesEntry 8 }

-- {COLUMN} 1.3.6.1.4.1.2356.11.1.53.4.1.9
lcsStatusVcCllMngrLinesEntryRegState OBJECT-TYPE
    SYNTAX     INTEGER {
                  eIdle (0),
                  eTrying (1),
                  eDnsPending (2),
                  eTransportConnected (3)
            }
    MAX-ACCESS read-only
    STATUS     current
    DESCRIPTION
            "-- empty --"
    ::= { lcsStatusVcCllMngrLinesEntry 9 }

-- {COLUMN} 1.3.6.1.4.1.2356.11.1.53.4.1.10
lcsStatusVcCllMngrLinesEntryInccallrecv OBJECT-TYPE
    SYNTAX     Integer32 (0..2147483647)
    MAX-ACCESS read-only
    STATUS     current
    DESCRIPTION
            "-- empty --"
    ::= { lcsStatusVcCllMngrLinesEntry 10 }

-- {COLUMN} 1.3.6.1.4.1.2356.11.1.53.4.1.11
lcsStatusVcCllMngrLinesEntryInccallansw OBJECT-TYPE
    SYNTAX     Integer32 (0..2147483647)
    MAX-ACCESS read-only
    STATUS     current
    DESCRIPTION
            "-- empty --"
    ::= { lcsStatusVcCllMngrLinesEntry 11 }

-- {COLUMN} 1.3.6.1.4.1.2356.11.1.53.4.1.12
lcsStatusVcCllMngrLinesEntryInccallconn OBJECT-TYPE
    SYNTAX     Integer32 (0..2147483647)
    MAX-ACCESS read-only
    STATUS     current
    DESCRIPTION
            "-- empty --"
    ::= { lcsStatusVcCllMngrLinesEntry 12 }

-- {COLUMN} 1.3.6.1.4.1.2356.11.1.53.4.1.13
lcsStatusVcCllMngrLinesEntryInccallfail OBJECT-TYPE
    SYNTAX     Integer32 (0..2147483647)
    MAX-ACCESS read-only
    STATUS     current
    DESCRIPTION
            "-- empty --"
    ::= { lcsStatusVcCllMngrLinesEntry 13 }

-- {COLUMN} 1.3.6.1.4.1.2356.11.1.53.4.1.14
lcsStatusVcCllMngrLinesEntryOutcallattm OBJECT-TYPE
    SYNTAX     Integer32 (0..2147483647)
    MAX-ACCESS read-only
    STATUS     current
    DESCRIPTION
            "-- empty --"
    ::= { lcsStatusVcCllMngrLinesEntry 14 }

-- {COLUMN} 1.3.6.1.4.1.2356.11.1.53.4.1.15
lcsStatusVcCllMngrLinesEntryOutcallansw OBJECT-TYPE
    SYNTAX     Integer32 (0..2147483647)
    MAX-ACCESS read-only
    STATUS     current
    DESCRIPTION
            "-- empty --"
    ::= { lcsStatusVcCllMngrLinesEntry 15 }

-- {COLUMN} 1.3.6.1.4.1.2356.11.1.53.4.1.16
lcsStatusVcCllMngrLinesEntryOutcallconn OBJECT-TYPE
    SYNTAX     Integer32 (0..2147483647)
    MAX-ACCESS read-only
    STATUS     current
    DESCRIPTION
            "-- empty --"
    ::= { lcsStatusVcCllMngrLinesEntry 16 }

-- {COLUMN} 1.3.6.1.4.1.2356.11.1.53.4.1.17
lcsStatusVcCllMngrLinesEntryOutcallfail OBJECT-TYPE
    SYNTAX     Integer32 (0..2147483647)
    MAX-ACCESS read-only
    STATUS     current
    DESCRIPTION
            "-- empty --"
    ::= { lcsStatusVcCllMngrLinesEntry 17 }

-- {COLUMN} 1.3.6.1.4.1.2356.11.1.53.4.1.18
lcsStatusVcCllMngrLinesEntryRemoteIpAddress OBJECT-TYPE
    SYNTAX     DisplayString (SIZE(0..56))
    MAX-ACCESS read-only
    STATUS     current
    DESCRIPTION
            "-- empty --"
    ::= { lcsStatusVcCllMngrLinesEntry 18 }

-- {TABLE} 1.3.6.1.4.1.2356.11.1.53.5
lcsStatusVcCllMngrCallsTable OBJECT-TYPE
    SYNTAX     SEQUENCE OF LcsStatusVcCllMngrCallsEntry
    MAX-ACCESS not-accessible
    STATUS     current
    DESCRIPTION
            "-- empty --"
    ::= { lcsStatusVcCllMngr 5 }

-- {ROW} 1.3.6.1.4.1.2356.11.1.53.5.1
lcsStatusVcCllMngrCallsEntry OBJECT-TYPE
    SYNTAX     LcsStatusVcCllMngrCallsEntry
    MAX-ACCESS not-accessible
    STATUS     current
    DESCRIPTION
            ""
    INDEX {
            lcsStatusVcCllMngrCallsEntryIndex
          }
    ::= { lcsStatusVcCllMngrCallsTable 1 }

LcsStatusVcCllMngrCallsEntry ::= SEQUENCE {
            lcsStatusVcCllMngrCallsEntryIndex Integer32,
            lcsStatusVcCllMngrCallsEntryFromLine DisplayString,
            lcsStatusVcCllMngrCallsEntryFromDisplayname DisplayString,
            lcsStatusVcCllMngrCallsEntryFromNumberName DisplayString,
            lcsStatusVcCllMngrCallsEntryFromDomain DisplayString,
            lcsStatusVcCllMngrCallsEntryToDomain DisplayString,
            lcsStatusVcCllMngrCallsEntryToNumberName DisplayString,
            lcsStatusVcCllMngrCallsEntryDestLine DisplayString,
            lcsStatusVcCllMngrCallsEntryDestNumberName DisplayString,
            lcsStatusVcCllMngrCallsEntryStatus INTEGER,
            lcsStatusVcCllMngrCallsEntryStart Gauge32,
            lcsStatusVcCllMngrCallsEntryEnd Gauge32,
            lcsStatusVcCllMngrCallsEntryDestDisplayname DisplayString,
            lcsStatusVcCllMngrCallsEntryDestDomain DisplayString,
            lcsStatusVcCllMngrCallsEntryFromtocodec DisplayString,
            lcsStatusVcCllMngrCallsEntryTofromcodec DisplayString,
            lcsStatusVcCllMngrCallsEntryConnect Gauge32,
            lcsStatusVcCllMngrCallsEntryCfMethod DisplayString,
            lcsStatusVcCllMngrCallsEntryFaxDetected INTEGER,
            lcsStatusVcCllMngrCallsEntryJitterUnderrun Integer32,
            lcsStatusVcCllMngrCallsEntryJitterOverrun Integer32,
            lcsStatusVcCllMngrCallsEntryMissingPackets Integer32,
            lcsStatusVcCllMngrCallsEntryWrongOrderPackets Integer32,
            lcsStatusVcCllMngrCallsEntryCallRef Integer32,
            lcsStatusVcCllMngrCallsEntryFromSrtp INTEGER,
            lcsStatusVcCllMngrCallsEntryDestSrtp INTEGER
    }

-- {COLUMN} 1.3.6.1.4.1.2356.11.1.53.5.1.1
lcsStatusVcCllMngrCallsEntryIndex OBJECT-TYPE
    SYNTAX     Integer32 (0..2147483647)
    MAX-ACCESS read-only
    STATUS     current
    DESCRIPTION
            "-- empty --"
    ::= { lcsStatusVcCllMngrCallsEntry 1 }

-- {COLUMN} 1.3.6.1.4.1.2356.11.1.53.5.1.2
lcsStatusVcCllMngrCallsEntryFromLine OBJECT-TYPE
    SYNTAX     DisplayString (SIZE(0..32))
    MAX-ACCESS read-only
    STATUS     current
    DESCRIPTION
            "-- empty --"
    ::= { lcsStatusVcCllMngrCallsEntry 2 }

-- {COLUMN} 1.3.6.1.4.1.2356.11.1.53.5.1.3
lcsStatusVcCllMngrCallsEntryFromDisplayname OBJECT-TYPE
    SYNTAX     DisplayString (SIZE(0..19))
    MAX-ACCESS read-only
    STATUS     current
    DESCRIPTION
            "-- empty --"
    ::= { lcsStatusVcCllMngrCallsEntry 3 }

-- {COLUMN} 1.3.6.1.4.1.2356.11.1.53.5.1.4
lcsStatusVcCllMngrCallsEntryFromNumberName OBJECT-TYPE
    SYNTAX     DisplayString (SIZE(0..19))
    MAX-ACCESS read-only
    STATUS     current
    DESCRIPTION
            "-- empty --"
    ::= { lcsStatusVcCllMngrCallsEntry 4 }

-- {COLUMN} 1.3.6.1.4.1.2356.11.1.53.5.1.5
lcsStatusVcCllMngrCallsEntryFromDomain OBJECT-TYPE
    SYNTAX     DisplayString (SIZE(0..63))
    MAX-ACCESS read-only
    STATUS     current
    DESCRIPTION
            "-- empty --"
    ::= { lcsStatusVcCllMngrCallsEntry 5 }

-- {COLUMN} 1.3.6.1.4.1.2356.11.1.53.5.1.6
lcsStatusVcCllMngrCallsEntryToDomain OBJECT-TYPE
    SYNTAX     DisplayString (SIZE(0..63))
    MAX-ACCESS read-only
    STATUS     current
    DESCRIPTION
            "-- empty --"
    ::= { lcsStatusVcCllMngrCallsEntry 6 }

-- {COLUMN} 1.3.6.1.4.1.2356.11.1.53.5.1.7
lcsStatusVcCllMngrCallsEntryToNumberName OBJECT-TYPE
    SYNTAX     DisplayString (SIZE(0..19))
    MAX-ACCESS read-only
    STATUS     current
    DESCRIPTION
            "-- empty --"
    ::= { lcsStatusVcCllMngrCallsEntry 7 }

-- {COLUMN} 1.3.6.1.4.1.2356.11.1.53.5.1.8
lcsStatusVcCllMngrCallsEntryDestLine OBJECT-TYPE
    SYNTAX     DisplayString (SIZE(0..32))
    MAX-ACCESS read-only
    STATUS     current
    DESCRIPTION
            "-- empty --"
    ::= { lcsStatusVcCllMngrCallsEntry 8 }

-- {COLUMN} 1.3.6.1.4.1.2356.11.1.53.5.1.9
lcsStatusVcCllMngrCallsEntryDestNumberName OBJECT-TYPE
    SYNTAX     DisplayString (SIZE(0..19))
    MAX-ACCESS read-only
    STATUS     current
    DESCRIPTION
            "-- empty --"
    ::= { lcsStatusVcCllMngrCallsEntry 9 }

-- {COLUMN} 1.3.6.1.4.1.2356.11.1.53.5.1.10
lcsStatusVcCllMngrCallsEntryStatus OBJECT-TYPE
    SYNTAX     INTEGER {
                  eUnspecified (0),
                  eDialing (1),
                  eRinging (2),
                  eConnected (3),
                  eUnallocatedNumber (4),
                  eNoRouteToDestination (5),
                  eNormalCallClearing (6),
                  eUserBusy (7),
                  eNoUserResponding (8),
                  eUserAlertingNoAnswer (9),
                  eCallRejected (10),
                  eNumberChanged (11),
                  eNonSelectedUserClearing (12),
                  eDestinationOutOfOrder (13),
                  eNormalUnspecified (14),
                  eNoChannelAvailable (15),
                  eSwitchingEquipmentCongestion (16),
                  eIncompatibleDestination (17),
                  eUnauthorized (18),
                  ePaymentRequired (19),
                  eForbidden (20),
                  eUnsupportedMediaType (21),
                  eBandwidthNotAvailable (22),
                  eCodecNotAllowed (23),
                  eCodecNotSupported (24),
                  eLineNotAvailable (25)
            }
    MAX-ACCESS read-only
    STATUS     current
    DESCRIPTION
            "-- empty --"
    ::= { lcsStatusVcCllMngrCallsEntry 10 }

-- {COLUMN} 1.3.6.1.4.1.2356.11.1.53.5.1.11
lcsStatusVcCllMngrCallsEntryStart OBJECT-TYPE
    SYNTAX     Gauge32
    MAX-ACCESS read-only
    STATUS     current
    DESCRIPTION
            "-- empty --"
    ::= { lcsStatusVcCllMngrCallsEntry 11 }

-- {COLUMN} 1.3.6.1.4.1.2356.11.1.53.5.1.12
lcsStatusVcCllMngrCallsEntryEnd OBJECT-TYPE
    SYNTAX     Gauge32
    MAX-ACCESS read-only
    STATUS     current
    DESCRIPTION
            "-- empty --"
    ::= { lcsStatusVcCllMngrCallsEntry 12 }

-- {COLUMN} 1.3.6.1.4.1.2356.11.1.53.5.1.13
lcsStatusVcCllMngrCallsEntryDestDisplayname OBJECT-TYPE
    SYNTAX     DisplayString (SIZE(0..19))
    MAX-ACCESS read-only
    STATUS     current
    DESCRIPTION
            "-- empty --"
    ::= { lcsStatusVcCllMngrCallsEntry 13 }

-- {COLUMN} 1.3.6.1.4.1.2356.11.1.53.5.1.14
lcsStatusVcCllMngrCallsEntryDestDomain OBJECT-TYPE
    SYNTAX     DisplayString (SIZE(0..63))
    MAX-ACCESS read-only
    STATUS     current
    DESCRIPTION
            "-- empty --"
    ::= { lcsStatusVcCllMngrCallsEntry 14 }

-- {COLUMN} 1.3.6.1.4.1.2356.11.1.53.5.1.15
lcsStatusVcCllMngrCallsEntryFromtocodec OBJECT-TYPE
    SYNTAX     DisplayString (SIZE(0..11))
    MAX-ACCESS read-only
    STATUS     current
    DESCRIPTION
            "-- empty --"
    ::= { lcsStatusVcCllMngrCallsEntry 15 }

-- {COLUMN} 1.3.6.1.4.1.2356.11.1.53.5.1.16
lcsStatusVcCllMngrCallsEntryTofromcodec OBJECT-TYPE
    SYNTAX     DisplayString (SIZE(0..11))
    MAX-ACCESS read-only
    STATUS     current
    DESCRIPTION
            "-- empty --"
    ::= { lcsStatusVcCllMngrCallsEntry 16 }

-- {COLUMN} 1.3.6.1.4.1.2356.11.1.53.5.1.17
lcsStatusVcCllMngrCallsEntryConnect OBJECT-TYPE
    SYNTAX     Gauge32
    MAX-ACCESS read-only
    STATUS     current
    DESCRIPTION
            "-- empty --"
    ::= { lcsStatusVcCllMngrCallsEntry 17 }

-- {COLUMN} 1.3.6.1.4.1.2356.11.1.53.5.1.18
lcsStatusVcCllMngrCallsEntryCfMethod OBJECT-TYPE
    SYNTAX     DisplayString (SIZE(0..11))
    MAX-ACCESS read-only
    STATUS     current
    DESCRIPTION
            "-- empty --"
    ::= { lcsStatusVcCllMngrCallsEntry 18 }

-- {COLUMN} 1.3.6.1.4.1.2356.11.1.53.5.1.19
lcsStatusVcCllMngrCallsEntryFaxDetected OBJECT-TYPE
    SYNTAX     INTEGER {
                  eNo (0),
                  eYes (1)
            }
    MAX-ACCESS read-only
    STATUS     current
    DESCRIPTION
            "-- empty --"
    ::= { lcsStatusVcCllMngrCallsEntry 19 }

-- {COLUMN} 1.3.6.1.4.1.2356.11.1.53.5.1.20
lcsStatusVcCllMngrCallsEntryJitterUnderrun OBJECT-TYPE
    SYNTAX     Integer32 (0..2147483647)
    MAX-ACCESS read-only
    STATUS     current
    DESCRIPTION
            "-- empty --"
    ::= { lcsStatusVcCllMngrCallsEntry 20 }

-- {COLUMN} 1.3.6.1.4.1.2356.11.1.53.5.1.21
lcsStatusVcCllMngrCallsEntryJitterOverrun OBJECT-TYPE
    SYNTAX     Integer32 (0..2147483647)
    MAX-ACCESS read-only
    STATUS     current
    DESCRIPTION
            "-- empty --"
    ::= { lcsStatusVcCllMngrCallsEntry 21 }

-- {COLUMN} 1.3.6.1.4.1.2356.11.1.53.5.1.22
lcsStatusVcCllMngrCallsEntryMissingPackets OBJECT-TYPE
    SYNTAX     Integer32 (0..2147483647)
    MAX-ACCESS read-only
    STATUS     current
    DESCRIPTION
            "-- empty --"
    ::= { lcsStatusVcCllMngrCallsEntry 22 }

-- {COLUMN} 1.3.6.1.4.1.2356.11.1.53.5.1.23
lcsStatusVcCllMngrCallsEntryWrongOrderPackets OBJECT-TYPE
    SYNTAX     Integer32 (0..2147483647)
    MAX-ACCESS read-only
    STATUS     current
    DESCRIPTION
            "-- empty --"
    ::= { lcsStatusVcCllMngrCallsEntry 23 }

-- {COLUMN} 1.3.6.1.4.1.2356.11.1.53.5.1.24
lcsStatusVcCllMngrCallsEntryCallRef OBJECT-TYPE
    SYNTAX     Integer32 (0..2147483647)
    MAX-ACCESS read-only
    STATUS     current
    DESCRIPTION
            "-- empty --"
    ::= { lcsStatusVcCllMngrCallsEntry 24 }

-- {COLUMN} 1.3.6.1.4.1.2356.11.1.53.5.1.25
lcsStatusVcCllMngrCallsEntryFromSrtp OBJECT-TYPE
    SYNTAX     INTEGER {
                  eUnknown (0),
                  eF8128HmacSha180 (1),
                  eAesCm128HmacSha132 (2),
                  eAesCm128HmacSha180 (3),
                  eAes192CmHmacSha132 (4),
                  eAes192CmHmacSha180 (5),
                  eAes256CmHmacSha132 (6),
                  eAes256CmHmacSha180 (7),
                  eNotApplicable (200),
                  eLocalProposed (201),
                  eRemoteIgnored (202),
                  eLocalIgnored (203),
                  eLocalRejected (204),
                  eRemoteAcceptedNone (205),
                  eNoLocalProposal (206),
                  eNoRemoteProposal (207),
                  eMissingRemoteProposal (208),
                  eRtpFallbackAfterError (209)
            }
    MAX-ACCESS read-only
    STATUS     current
    DESCRIPTION
            "-- empty --"
    ::= { lcsStatusVcCllMngrCallsEntry 25 }

-- {COLUMN} 1.3.6.1.4.1.2356.11.1.53.5.1.26
lcsStatusVcCllMngrCallsEntryDestSrtp OBJECT-TYPE
    SYNTAX     INTEGER {
                  eUnknown (0),
                  eF8128HmacSha180 (1),
                  eAesCm128HmacSha132 (2),
                  eAesCm128HmacSha180 (3),
                  eAes192CmHmacSha132 (4),
                  eAes192CmHmacSha180 (5),
                  eAes256CmHmacSha132 (6),
                  eAes256CmHmacSha180 (7),
                  eNotApplicable (200),
                  eLocalProposed (201),
                  eRemoteIgnored (202),
                  eLocalIgnored (203),
                  eLocalRejected (204),
                  eRemoteAcceptedNone (205),
                  eNoLocalProposal (206),
                  eNoRemoteProposal (207),
                  eMissingRemoteProposal (208),
                  eRtpFallbackAfterError (209)
            }
    MAX-ACCESS read-only
    STATUS     current
    DESCRIPTION
            "-- empty --"
    ::= { lcsStatusVcCllMngrCallsEntry 26 }

-- {SCALAR} 1.3.6.1.4.1.2356.11.1.53.6
lcsStatusVcCllMngrUserCounter OBJECT-TYPE
    SYNTAX     Integer32 (0..2147483647)
    MAX-ACCESS read-only
    STATUS     current
    DESCRIPTION
            "-- empty --"
    ::= { lcsStatusVcCllMngr 6 }

-- {SCALAR} 1.3.6.1.4.1.2356.11.1.53.7
lcsStatusVcCllMngrLineCounter OBJECT-TYPE
    SYNTAX     Integer32 (0..2147483647)
    MAX-ACCESS read-only
    STATUS     current
    DESCRIPTION
            "-- empty --"
    ::= { lcsStatusVcCllMngr 7 }

-- {SCALAR} 1.3.6.1.4.1.2356.11.1.53.8
lcsStatusVcCllMngrCallCounter OBJECT-TYPE
    SYNTAX     Integer32 (0..2147483647)
    MAX-ACCESS read-only
    STATUS     current
    DESCRIPTION
            "-- empty --"
    ::= { lcsStatusVcCllMngr 8 }

-- {SCALAR} 1.3.6.1.4.1.2356.11.1.53.9
lcsStatusVcCllMngrDomain OBJECT-TYPE
    SYNTAX     DisplayString (SIZE(0..63))
    MAX-ACCESS read-only
    STATUS     current
    DESCRIPTION
            "-- empty --"
    ::= { lcsStatusVcCllMngr 9 }

-- {SCALAR} 1.3.6.1.4.1.2356.11.1.53.10
lcsStatusVcCllMngrClearCallStatus OBJECT-TYPE
    SYNTAX     DisplayString
    MAX-ACCESS read-write
    STATUS     current
    DESCRIPTION
            "-- empty --"
    ::= { lcsStatusVcCllMngr 10 }

-- {TABLE} 1.3.6.1.4.1.2356.11.1.53.11
lcsStatusVcCllMngrSubscriptionsTable OBJECT-TYPE
    SYNTAX     SEQUENCE OF LcsStatusVcCllMngrSubscriptionsEntry
    MAX-ACCESS not-accessible
    STATUS     current
    DESCRIPTION
            "-- empty --"
    ::= { lcsStatusVcCllMngr 11 }

-- {ROW} 1.3.6.1.4.1.2356.11.1.53.11.1
lcsStatusVcCllMngrSubscriptionsEntry OBJECT-TYPE
    SYNTAX     LcsStatusVcCllMngrSubscriptionsEntry
    MAX-ACCESS not-accessible
    STATUS     current
    DESCRIPTION
            ""
    INDEX {
            lcsStatusVcCllMngrSubscriptionsEntryIndex
          }
    ::= { lcsStatusVcCllMngrSubscriptionsTable 1 }

LcsStatusVcCllMngrSubscriptionsEntry ::= SEQUENCE {
            lcsStatusVcCllMngrSubscriptionsEntryIndex Integer32,
            lcsStatusVcCllMngrSubscriptionsEntryEvent DisplayString,
            lcsStatusVcCllMngrSubscriptionsEntrySource DisplayString,
            lcsStatusVcCllMngrSubscriptionsEntryTarget DisplayString,
            lcsStatusVcCllMngrSubscriptionsEntryRemaining Gauge32
    }

-- {COLUMN} 1.3.6.1.4.1.2356.11.1.53.11.1.1
lcsStatusVcCllMngrSubscriptionsEntryIndex OBJECT-TYPE
    SYNTAX     Integer32 (0..2147483647)
    MAX-ACCESS read-only
    STATUS     current
    DESCRIPTION
            "-- empty --"
    ::= { lcsStatusVcCllMngrSubscriptionsEntry 1 }

-- {COLUMN} 1.3.6.1.4.1.2356.11.1.53.11.1.2
lcsStatusVcCllMngrSubscriptionsEntryEvent OBJECT-TYPE
    SYNTAX     DisplayString (SIZE(0..255))
    MAX-ACCESS read-only
    STATUS     current
    DESCRIPTION
            "-- empty --"
    ::= { lcsStatusVcCllMngrSubscriptionsEntry 2 }

-- {COLUMN} 1.3.6.1.4.1.2356.11.1.53.11.1.3
lcsStatusVcCllMngrSubscriptionsEntrySource OBJECT-TYPE
    SYNTAX     DisplayString (SIZE(0..255))
    MAX-ACCESS read-only
    STATUS     current
    DESCRIPTION
            "-- empty --"
    ::= { lcsStatusVcCllMngrSubscriptionsEntry 3 }

-- {COLUMN} 1.3.6.1.4.1.2356.11.1.53.11.1.4
lcsStatusVcCllMngrSubscriptionsEntryTarget OBJECT-TYPE
    SYNTAX     DisplayString (SIZE(0..255))
    MAX-ACCESS read-only
    STATUS     current
    DESCRIPTION
            "-- empty --"
    ::= { lcsStatusVcCllMngrSubscriptionsEntry 4 }

-- {COLUMN} 1.3.6.1.4.1.2356.11.1.53.11.1.5
lcsStatusVcCllMngrSubscriptionsEntryRemaining OBJECT-TYPE
    SYNTAX     Gauge32
    MAX-ACCESS read-only
    STATUS     current
    DESCRIPTION
            "-- empty --"
    ::= { lcsStatusVcCllMngrSubscriptionsEntry 5 }

-- {NODE} 1.3.6.1.4.1.2356.11.1.54
lcsStatusUsb OBJECT IDENTIFIER ::= { lcsStatus 54 }

-- {TABLE} 1.3.6.1.4.1.2356.11.1.54.1
lcsStatusUsbDevicesTable OBJECT-TYPE
    SYNTAX     SEQUENCE OF LcsStatusUsbDevicesEntry
    MAX-ACCESS not-accessible
    STATUS     current
    DESCRIPTION
            ""
    ::= { lcsStatusUsb 1 }

-- {ROW} 1.3.6.1.4.1.2356.11.1.54.1.1
lcsStatusUsbDevicesEntry OBJECT-TYPE
    SYNTAX     LcsStatusUsbDevicesEntry
    MAX-ACCESS not-accessible
    STATUS     current
    DESCRIPTION
            ""
    INDEX {
            lcsStatusUsbDevicesEntryBus,
            lcsStatusUsbDevicesEntryAddress
          }
    ::= { lcsStatusUsbDevicesTable 1 }

LcsStatusUsbDevicesEntry ::= SEQUENCE {
            lcsStatusUsbDevicesEntryBus DisplayString,
            lcsStatusUsbDevicesEntryAddress Integer32,
            lcsStatusUsbDevicesEntryVendor DisplayString,
            lcsStatusUsbDevicesEntryVendorId Integer32,
            lcsStatusUsbDevicesEntryProduct DisplayString,
            lcsStatusUsbDevicesEntryProductId Integer32,
            lcsStatusUsbDevicesEntryDepth Integer32,
            lcsStatusUsbDevicesEntrySpeed Integer32,
            lcsStatusUsbDevicesEntryInterfaces Integer32,
            lcsStatusUsbDevicesEntryPower Integer32,
            lcsStatusUsbDevicesEntryDriver DisplayString,
            lcsStatusUsbDevicesEntryParent DisplayString
    }

-- {COLUMN} 1.3.6.1.4.1.2356.11.1.54.1.1.1
lcsStatusUsbDevicesEntryBus OBJECT-TYPE
    SYNTAX     DisplayString (SIZE(0..255))
    MAX-ACCESS read-only
    STATUS     current
    DESCRIPTION
            ""
    ::= { lcsStatusUsbDevicesEntry 1 }

-- {COLUMN} 1.3.6.1.4.1.2356.11.1.54.1.1.2
lcsStatusUsbDevicesEntryAddress OBJECT-TYPE
    SYNTAX     Integer32 (0..255)
    MAX-ACCESS read-only
    STATUS     current
    DESCRIPTION
            ""
    ::= { lcsStatusUsbDevicesEntry 2 }

-- {COLUMN} 1.3.6.1.4.1.2356.11.1.54.1.1.3
lcsStatusUsbDevicesEntryVendor OBJECT-TYPE
    SYNTAX     DisplayString (SIZE(0..255))
    MAX-ACCESS read-only
    STATUS     current
    DESCRIPTION
            ""
    ::= { lcsStatusUsbDevicesEntry 3 }

-- {COLUMN} 1.3.6.1.4.1.2356.11.1.54.1.1.4
lcsStatusUsbDevicesEntryVendorId OBJECT-TYPE
    SYNTAX     Integer32 (0..65535)
    MAX-ACCESS read-only
    STATUS     current
    DESCRIPTION
            ""
    ::= { lcsStatusUsbDevicesEntry 4 }

-- {COLUMN} 1.3.6.1.4.1.2356.11.1.54.1.1.5
lcsStatusUsbDevicesEntryProduct OBJECT-TYPE
    SYNTAX     DisplayString (SIZE(0..255))
    MAX-ACCESS read-only
    STATUS     current
    DESCRIPTION
            ""
    ::= { lcsStatusUsbDevicesEntry 5 }

-- {COLUMN} 1.3.6.1.4.1.2356.11.1.54.1.1.6
lcsStatusUsbDevicesEntryProductId OBJECT-TYPE
    SYNTAX     Integer32 (0..65535)
    MAX-ACCESS read-only
    STATUS     current
    DESCRIPTION
            ""
    ::= { lcsStatusUsbDevicesEntry 6 }

-- {COLUMN} 1.3.6.1.4.1.2356.11.1.54.1.1.8
lcsStatusUsbDevicesEntryDepth OBJECT-TYPE
    SYNTAX     Integer32 (0..255)
    MAX-ACCESS read-only
    STATUS     current
    DESCRIPTION
            ""
    ::= { lcsStatusUsbDevicesEntry 8 }

-- {COLUMN} 1.3.6.1.4.1.2356.11.1.54.1.1.9
lcsStatusUsbDevicesEntrySpeed OBJECT-TYPE
    SYNTAX     Integer32 (0..255)
    MAX-ACCESS read-only
    STATUS     current
    DESCRIPTION
            ""
    ::= { lcsStatusUsbDevicesEntry 9 }

-- {COLUMN} 1.3.6.1.4.1.2356.11.1.54.1.1.10
lcsStatusUsbDevicesEntryInterfaces OBJECT-TYPE
    SYNTAX     Integer32 (0..255)
    MAX-ACCESS read-only
    STATUS     current
    DESCRIPTION
            ""
    ::= { lcsStatusUsbDevicesEntry 10 }

-- {COLUMN} 1.3.6.1.4.1.2356.11.1.54.1.1.11
lcsStatusUsbDevicesEntryPower OBJECT-TYPE
    SYNTAX     Integer32 (0..2147483647)
    MAX-ACCESS read-only
    STATUS     current
    DESCRIPTION
            ""
    ::= { lcsStatusUsbDevicesEntry 11 }

-- {COLUMN} 1.3.6.1.4.1.2356.11.1.54.1.1.12
lcsStatusUsbDevicesEntryDriver OBJECT-TYPE
    SYNTAX     DisplayString (SIZE(0..255))
    MAX-ACCESS read-only
    STATUS     current
    DESCRIPTION
            ""
    ::= { lcsStatusUsbDevicesEntry 12 }

-- {COLUMN} 1.3.6.1.4.1.2356.11.1.54.1.1.13
lcsStatusUsbDevicesEntryParent OBJECT-TYPE
    SYNTAX     DisplayString (SIZE(0..255))
    MAX-ACCESS read-only
    STATUS     current
    DESCRIPTION
            ""
    ::= { lcsStatusUsbDevicesEntry 13 }

-- {SCALAR} 1.3.6.1.4.1.2356.11.1.54.2
lcsStatusUsbReinit OBJECT-TYPE
    SYNTAX     DisplayString
    MAX-ACCESS read-write
    STATUS     current
    DESCRIPTION
            ""
    ::= { lcsStatusUsb 2 }

-- {TABLE} 1.3.6.1.4.1.2356.11.1.54.3
lcsStatusUsbStatisticsTable OBJECT-TYPE
    SYNTAX     SEQUENCE OF LcsStatusUsbStatisticsEntry
    MAX-ACCESS not-accessible
    STATUS     current
    DESCRIPTION
            ""
    ::= { lcsStatusUsb 3 }

-- {ROW} 1.3.6.1.4.1.2356.11.1.54.3.1
lcsStatusUsbStatisticsEntry OBJECT-TYPE
    SYNTAX     LcsStatusUsbStatisticsEntry
    MAX-ACCESS not-accessible
    STATUS     current
    DESCRIPTION
            ""
    INDEX {
            lcsStatusUsbStatisticsEntryBus
          }
    ::= { lcsStatusUsbStatisticsTable 1 }

LcsStatusUsbStatisticsEntry ::= SEQUENCE {
            lcsStatusUsbStatisticsEntryBus DisplayString,
            lcsStatusUsbStatisticsEntryProduct DisplayString,
            lcsStatusUsbStatisticsEntryTransactions Integer32,
            lcsStatusUsbStatisticsEntryInRetransmissions Integer32,
            lcsStatusUsbStatisticsEntryInBabbles Integer32,
            lcsStatusUsbStatisticsEntryInBufferErrors Integer32,
            lcsStatusUsbStatisticsEntryOutRetransmissions Integer32,
            lcsStatusUsbStatisticsEntryOutBabbles Integer32,
            lcsStatusUsbStatisticsEntryOutBufferErrors Integer32
    }

-- {COLUMN} 1.3.6.1.4.1.2356.11.1.54.3.1.1
lcsStatusUsbStatisticsEntryBus OBJECT-TYPE
    SYNTAX     DisplayString (SIZE(0..255))
    MAX-ACCESS read-only
    STATUS     current
    DESCRIPTION
            ""
    ::= { lcsStatusUsbStatisticsEntry 1 }

-- {COLUMN} 1.3.6.1.4.1.2356.11.1.54.3.1.2
lcsStatusUsbStatisticsEntryProduct OBJECT-TYPE
    SYNTAX     DisplayString (SIZE(0..255))
    MAX-ACCESS read-only
    STATUS     current
    DESCRIPTION
            ""
    ::= { lcsStatusUsbStatisticsEntry 2 }

-- {COLUMN} 1.3.6.1.4.1.2356.11.1.54.3.1.3
lcsStatusUsbStatisticsEntryTransactions OBJECT-TYPE
    SYNTAX     Integer32 (-2147483648..2147483647)
    MAX-ACCESS read-only
    STATUS     current
    DESCRIPTION
            ""
    ::= { lcsStatusUsbStatisticsEntry 3 }

-- {COLUMN} 1.3.6.1.4.1.2356.11.1.54.3.1.10
lcsStatusUsbStatisticsEntryInRetransmissions OBJECT-TYPE
    SYNTAX     Integer32 (-2147483648..2147483647)
    MAX-ACCESS read-only
    STATUS     current
    DESCRIPTION
            ""
    ::= { lcsStatusUsbStatisticsEntry 10 }

-- {COLUMN} 1.3.6.1.4.1.2356.11.1.54.3.1.11
lcsStatusUsbStatisticsEntryInBabbles OBJECT-TYPE
    SYNTAX     Integer32 (-2147483648..2147483647)
    MAX-ACCESS read-only
    STATUS     current
    DESCRIPTION
            ""
    ::= { lcsStatusUsbStatisticsEntry 11 }

-- {COLUMN} 1.3.6.1.4.1.2356.11.1.54.3.1.12
lcsStatusUsbStatisticsEntryInBufferErrors OBJECT-TYPE
    SYNTAX     Integer32 (-2147483648..2147483647)
    MAX-ACCESS read-only
    STATUS     current
    DESCRIPTION
            ""
    ::= { lcsStatusUsbStatisticsEntry 12 }

-- {COLUMN} 1.3.6.1.4.1.2356.11.1.54.3.1.20
lcsStatusUsbStatisticsEntryOutRetransmissions OBJECT-TYPE
    SYNTAX     Integer32 (-2147483648..2147483647)
    MAX-ACCESS read-only
    STATUS     current
    DESCRIPTION
            ""
    ::= { lcsStatusUsbStatisticsEntry 20 }

-- {COLUMN} 1.3.6.1.4.1.2356.11.1.54.3.1.21
lcsStatusUsbStatisticsEntryOutBabbles OBJECT-TYPE
    SYNTAX     Integer32 (-2147483648..2147483647)
    MAX-ACCESS read-only
    STATUS     current
    DESCRIPTION
            ""
    ::= { lcsStatusUsbStatisticsEntry 21 }

-- {COLUMN} 1.3.6.1.4.1.2356.11.1.54.3.1.22
lcsStatusUsbStatisticsEntryOutBufferErrors OBJECT-TYPE
    SYNTAX     Integer32 (-2147483648..2147483647)
    MAX-ACCESS read-only
    STATUS     current
    DESCRIPTION
            ""
    ::= { lcsStatusUsbStatisticsEntry 22 }

-- {SCALAR} 1.3.6.1.4.1.2356.11.1.54.4
lcsStatusUsbClearStatistics OBJECT-TYPE
    SYNTAX     DisplayString
    MAX-ACCESS read-write
    STATUS     current
    DESCRIPTION
            ""
    ::= { lcsStatusUsb 4 }

-- {SCALAR} 1.3.6.1.4.1.2356.11.1.54.5
lcsStatusUsbQueryHubStatus OBJECT-TYPE
    SYNTAX     DisplayString
    MAX-ACCESS read-write
    STATUS     current
    DESCRIPTION
            ""
    ::= { lcsStatusUsb 5 }

-- {NODE} 1.3.6.1.4.1.2356.11.1.56
lcsStatusAccounting OBJECT IDENTIFIER ::= { lcsStatus 56 }

-- {TABLE} 1.3.6.1.4.1.2356.11.1.56.1
lcsStatusAccountingCurrentUserTable OBJECT-TYPE
    SYNTAX     SEQUENCE OF LcsStatusAccountingCurrentUserEntry
    MAX-ACCESS not-accessible
    STATUS     current
    DESCRIPTION
            ""
    ::= { lcsStatusAccounting 1 }

-- {ROW} 1.3.6.1.4.1.2356.11.1.56.1.1
lcsStatusAccountingCurrentUserEntry OBJECT-TYPE
    SYNTAX     LcsStatusAccountingCurrentUserEntry
    MAX-ACCESS not-accessible
    STATUS     current
    DESCRIPTION
            ""
    INDEX {
            lcsStatusAccountingCurrentUserEntryUsername,
            lcsStatusAccountingCurrentUserEntryMacAddress,
            lcsStatusAccountingCurrentUserEntryPeer,
            lcsStatusAccountingCurrentUserEntryConnType
          }
    ::= { lcsStatusAccountingCurrentUserTable 1 }

LcsStatusAccountingCurrentUserEntry ::= SEQUENCE {
            lcsStatusAccountingCurrentUserEntryUsername DisplayString,
            lcsStatusAccountingCurrentUserEntryMacAddress DisplayString,
            lcsStatusAccountingCurrentUserEntryPeer DisplayString,
            lcsStatusAccountingCurrentUserEntryConnType INTEGER,
            lcsStatusAccountingCurrentUserEntryRxKbytes Integer32,
            lcsStatusAccountingCurrentUserEntryTxKbytes Integer32,
            lcsStatusAccountingCurrentUserEntryTotalTime Gauge32,
            lcsStatusAccountingCurrentUserEntryConnections Integer32
    }

-- {COLUMN} 1.3.6.1.4.1.2356.11.1.56.1.1.1
lcsStatusAccountingCurrentUserEntryUsername OBJECT-TYPE
    SYNTAX     DisplayString (SIZE(0..28))
    MAX-ACCESS read-only
    STATUS     current
    DESCRIPTION
            ""
    ::= { lcsStatusAccountingCurrentUserEntry 1 }

-- {COLUMN} 1.3.6.1.4.1.2356.11.1.56.1.1.2
lcsStatusAccountingCurrentUserEntryMacAddress OBJECT-TYPE
    SYNTAX     DisplayString (SIZE(0..255))
    MAX-ACCESS read-only
    STATUS     current
    DESCRIPTION
            ""
    ::= { lcsStatusAccountingCurrentUserEntry 2 }

-- {COLUMN} 1.3.6.1.4.1.2356.11.1.56.1.1.3
lcsStatusAccountingCurrentUserEntryPeer OBJECT-TYPE
    SYNTAX     DisplayString (SIZE(0..16))
    MAX-ACCESS read-only
    STATUS     current
    DESCRIPTION
            ""
    ::= { lcsStatusAccountingCurrentUserEntry 3 }

-- {COLUMN} 1.3.6.1.4.1.2356.11.1.56.1.1.4
lcsStatusAccountingCurrentUserEntryConnType OBJECT-TYPE
    SYNTAX     INTEGER {
                  eUnknown (0),
                  eDialUp (1),
                  eLeasedLine (2),
                  eDslLine (4),
                  eVpnConn (7),
                  ePptpConn (8),
                  eL2tpConn (9),
                  eDsLiteConn (10),
                  eGreConn (11),
                  eLispConn (12)
            }
    MAX-ACCESS read-only
    STATUS     current
    DESCRIPTION
            ""
    ::= { lcsStatusAccountingCurrentUserEntry 4 }

-- {COLUMN} 1.3.6.1.4.1.2356.11.1.56.1.1.5
lcsStatusAccountingCurrentUserEntryRxKbytes OBJECT-TYPE
    SYNTAX     Integer32 (0..2147483647)
    MAX-ACCESS read-only
    STATUS     current
    DESCRIPTION
            ""
    ::= { lcsStatusAccountingCurrentUserEntry 5 }

-- {COLUMN} 1.3.6.1.4.1.2356.11.1.56.1.1.6
lcsStatusAccountingCurrentUserEntryTxKbytes OBJECT-TYPE
    SYNTAX     Integer32 (0..2147483647)
    MAX-ACCESS read-only
    STATUS     current
    DESCRIPTION
            ""
    ::= { lcsStatusAccountingCurrentUserEntry 6 }

-- {COLUMN} 1.3.6.1.4.1.2356.11.1.56.1.1.8
lcsStatusAccountingCurrentUserEntryTotalTime OBJECT-TYPE
    SYNTAX     Gauge32
    MAX-ACCESS read-only
    STATUS     current
    DESCRIPTION
            ""
    ::= { lcsStatusAccountingCurrentUserEntry 8 }

-- {COLUMN} 1.3.6.1.4.1.2356.11.1.56.1.1.9
lcsStatusAccountingCurrentUserEntryConnections OBJECT-TYPE
    SYNTAX     Integer32 (0..2147483647)
    MAX-ACCESS read-only
    STATUS     current
    DESCRIPTION
            ""
    ::= { lcsStatusAccountingCurrentUserEntry 9 }

-- {TABLE} 1.3.6.1.4.1.2356.11.1.56.2
lcsStatusAccountingAccountingListTable OBJECT-TYPE
    SYNTAX     SEQUENCE OF LcsStatusAccountingAccountingListEntry
    MAX-ACCESS not-accessible
    STATUS     current
    DESCRIPTION
            ""
    ::= { lcsStatusAccounting 2 }

-- {ROW} 1.3.6.1.4.1.2356.11.1.56.2.1
lcsStatusAccountingAccountingListEntry OBJECT-TYPE
    SYNTAX     LcsStatusAccountingAccountingListEntry
    MAX-ACCESS not-accessible
    STATUS     current
    DESCRIPTION
            ""
    INDEX {
            lcsStatusAccountingAccountingListEntryUsername,
            lcsStatusAccountingAccountingListEntryMacAddress,
            lcsStatusAccountingAccountingListEntryPeer,
            lcsStatusAccountingAccountingListEntryConnType
          }
    ::= { lcsStatusAccountingAccountingListTable 1 }

LcsStatusAccountingAccountingListEntry ::= SEQUENCE {
            lcsStatusAccountingAccountingListEntryUsername DisplayString,
            lcsStatusAccountingAccountingListEntryMacAddress DisplayString,
            lcsStatusAccountingAccountingListEntryPeer DisplayString,
            lcsStatusAccountingAccountingListEntryConnType INTEGER,
            lcsStatusAccountingAccountingListEntryRxKbytes Integer32,
            lcsStatusAccountingAccountingListEntryTxKbytes Integer32,
            lcsStatusAccountingAccountingListEntryTotalTime Gauge32,
            lcsStatusAccountingAccountingListEntryConnections Integer32
    }

-- {COLUMN} 1.3.6.1.4.1.2356.11.1.56.2.1.1
lcsStatusAccountingAccountingListEntryUsername OBJECT-TYPE
    SYNTAX     DisplayString (SIZE(0..28))
    MAX-ACCESS read-only
    STATUS     current
    DESCRIPTION
            ""
    ::= { lcsStatusAccountingAccountingListEntry 1 }

-- {COLUMN} 1.3.6.1.4.1.2356.11.1.56.2.1.2
lcsStatusAccountingAccountingListEntryMacAddress OBJECT-TYPE
    SYNTAX     DisplayString (SIZE(0..255))
    MAX-ACCESS read-only
    STATUS     current
    DESCRIPTION
            ""
    ::= { lcsStatusAccountingAccountingListEntry 2 }

-- {COLUMN} 1.3.6.1.4.1.2356.11.1.56.2.1.3
lcsStatusAccountingAccountingListEntryPeer OBJECT-TYPE
    SYNTAX     DisplayString (SIZE(0..16))
    MAX-ACCESS read-only
    STATUS     current
    DESCRIPTION
            ""
    ::= { lcsStatusAccountingAccountingListEntry 3 }

-- {COLUMN} 1.3.6.1.4.1.2356.11.1.56.2.1.4
lcsStatusAccountingAccountingListEntryConnType OBJECT-TYPE
    SYNTAX     INTEGER {
                  eUnknown (0),
                  eDialUp (1),
                  eLeasedLine (2),
                  eDslLine (4),
                  eVpnConn (7),
                  ePptpConn (8),
                  eL2tpConn (9),
                  eDsLiteConn (10),
                  eGreConn (11),
                  eLispConn (12)
            }
    MAX-ACCESS read-only
    STATUS     current
    DESCRIPTION
            ""
    ::= { lcsStatusAccountingAccountingListEntry 4 }

-- {COLUMN} 1.3.6.1.4.1.2356.11.1.56.2.1.5
lcsStatusAccountingAccountingListEntryRxKbytes OBJECT-TYPE
    SYNTAX     Integer32 (0..2147483647)
    MAX-ACCESS read-only
    STATUS     current
    DESCRIPTION
            ""
    ::= { lcsStatusAccountingAccountingListEntry 5 }

-- {COLUMN} 1.3.6.1.4.1.2356.11.1.56.2.1.6
lcsStatusAccountingAccountingListEntryTxKbytes OBJECT-TYPE
    SYNTAX     Integer32 (0..2147483647)
    MAX-ACCESS read-only
    STATUS     current
    DESCRIPTION
            ""
    ::= { lcsStatusAccountingAccountingListEntry 6 }

-- {COLUMN} 1.3.6.1.4.1.2356.11.1.56.2.1.8
lcsStatusAccountingAccountingListEntryTotalTime OBJECT-TYPE
    SYNTAX     Gauge32
    MAX-ACCESS read-only
    STATUS     current
    DESCRIPTION
            ""
    ::= { lcsStatusAccountingAccountingListEntry 8 }

-- {COLUMN} 1.3.6.1.4.1.2356.11.1.56.2.1.9
lcsStatusAccountingAccountingListEntryConnections OBJECT-TYPE
    SYNTAX     Integer32 (0..2147483647)
    MAX-ACCESS read-only
    STATUS     current
    DESCRIPTION
            ""
    ::= { lcsStatusAccountingAccountingListEntry 9 }

-- {TABLE} 1.3.6.1.4.1.2356.11.1.56.3
lcsStatusAccountingLastSnapshotTable OBJECT-TYPE
    SYNTAX     SEQUENCE OF LcsStatusAccountingLastSnapshotEntry
    MAX-ACCESS not-accessible
    STATUS     current
    DESCRIPTION
            ""
    ::= { lcsStatusAccounting 3 }

-- {ROW} 1.3.6.1.4.1.2356.11.1.56.3.1
lcsStatusAccountingLastSnapshotEntry OBJECT-TYPE
    SYNTAX     LcsStatusAccountingLastSnapshotEntry
    MAX-ACCESS not-accessible
    STATUS     current
    DESCRIPTION
            ""
    INDEX {
            lcsStatusAccountingLastSnapshotEntryUsername,
            lcsStatusAccountingLastSnapshotEntryMacAddress,
            lcsStatusAccountingLastSnapshotEntryPeer,
            lcsStatusAccountingLastSnapshotEntryConnType
          }
    ::= { lcsStatusAccountingLastSnapshotTable 1 }

LcsStatusAccountingLastSnapshotEntry ::= SEQUENCE {
            lcsStatusAccountingLastSnapshotEntryUsername DisplayString,
            lcsStatusAccountingLastSnapshotEntryMacAddress DisplayString,
            lcsStatusAccountingLastSnapshotEntryPeer DisplayString,
            lcsStatusAccountingLastSnapshotEntryConnType INTEGER,
            lcsStatusAccountingLastSnapshotEntryRxKbytes Integer32,
            lcsStatusAccountingLastSnapshotEntryTxKbytes Integer32,
            lcsStatusAccountingLastSnapshotEntryTotalTime Gauge32,
            lcsStatusAccountingLastSnapshotEntryConnections Integer32
    }

-- {COLUMN} 1.3.6.1.4.1.2356.11.1.56.3.1.1
lcsStatusAccountingLastSnapshotEntryUsername OBJECT-TYPE
    SYNTAX     DisplayString (SIZE(0..28))
    MAX-ACCESS read-only
    STATUS     current
    DESCRIPTION
            ""
    ::= { lcsStatusAccountingLastSnapshotEntry 1 }

-- {COLUMN} 1.3.6.1.4.1.2356.11.1.56.3.1.2
lcsStatusAccountingLastSnapshotEntryMacAddress OBJECT-TYPE
    SYNTAX     DisplayString (SIZE(0..255))
    MAX-ACCESS read-only
    STATUS     current
    DESCRIPTION
            ""
    ::= { lcsStatusAccountingLastSnapshotEntry 2 }

-- {COLUMN} 1.3.6.1.4.1.2356.11.1.56.3.1.3
lcsStatusAccountingLastSnapshotEntryPeer OBJECT-TYPE
    SYNTAX     DisplayString (SIZE(0..16))
    MAX-ACCESS read-only
    STATUS     current
    DESCRIPTION
            ""
    ::= { lcsStatusAccountingLastSnapshotEntry 3 }

-- {COLUMN} 1.3.6.1.4.1.2356.11.1.56.3.1.4
lcsStatusAccountingLastSnapshotEntryConnType OBJECT-TYPE
    SYNTAX     INTEGER {
                  eUnknown (0),
                  eDialUp (1),
                  eLeasedLine (2),
                  eDslLine (4),
                  eVpnConn (7),
                  ePptpConn (8),
                  eL2tpConn (9),
                  eDsLiteConn (10),
                  eGreConn (11),
                  eLispConn (12)
            }
    MAX-ACCESS read-only
    STATUS     current
    DESCRIPTION
            ""
    ::= { lcsStatusAccountingLastSnapshotEntry 4 }

-- {COLUMN} 1.3.6.1.4.1.2356.11.1.56.3.1.5
lcsStatusAccountingLastSnapshotEntryRxKbytes OBJECT-TYPE
    SYNTAX     Integer32 (0..2147483647)
    MAX-ACCESS read-only
    STATUS     current
    DESCRIPTION
            ""
    ::= { lcsStatusAccountingLastSnapshotEntry 5 }

-- {COLUMN} 1.3.6.1.4.1.2356.11.1.56.3.1.6
lcsStatusAccountingLastSnapshotEntryTxKbytes OBJECT-TYPE
    SYNTAX     Integer32 (0..2147483647)
    MAX-ACCESS read-only
    STATUS     current
    DESCRIPTION
            ""
    ::= { lcsStatusAccountingLastSnapshotEntry 6 }

-- {COLUMN} 1.3.6.1.4.1.2356.11.1.56.3.1.8
lcsStatusAccountingLastSnapshotEntryTotalTime OBJECT-TYPE
    SYNTAX     Gauge32
    MAX-ACCESS read-only
    STATUS     current
    DESCRIPTION
            ""
    ::= { lcsStatusAccountingLastSnapshotEntry 8 }

-- {COLUMN} 1.3.6.1.4.1.2356.11.1.56.3.1.9
lcsStatusAccountingLastSnapshotEntryConnections OBJECT-TYPE
    SYNTAX     Integer32 (0..2147483647)
    MAX-ACCESS read-only
    STATUS     current
    DESCRIPTION
            ""
    ::= { lcsStatusAccountingLastSnapshotEntry 9 }

-- {SCALAR} 1.3.6.1.4.1.2356.11.1.56.4
lcsStatusAccountingDeleteValues OBJECT-TYPE
    SYNTAX     DisplayString
    MAX-ACCESS read-write
    STATUS     current
    DESCRIPTION
            ""
    ::= { lcsStatusAccounting 4 }

-- {TABLE} 1.3.6.1.4.1.2356.11.1.56.5
lcsStatusAccountingTimeLastSnapshotTable OBJECT-TYPE
    SYNTAX     SEQUENCE OF LcsStatusAccountingTimeLastSnapshotEntry
    MAX-ACCESS not-accessible
    STATUS     current
    DESCRIPTION
            ""
    ::= { lcsStatusAccounting 5 }

-- {ROW} 1.3.6.1.4.1.2356.11.1.56.5.1
lcsStatusAccountingTimeLastSnapshotEntry OBJECT-TYPE
    SYNTAX     LcsStatusAccountingTimeLastSnapshotEntry
    MAX-ACCESS not-accessible
    STATUS     current
    DESCRIPTION
            ""
    INDEX {
            lcsStatusAccountingTimeLastSnapshotEntrySystemTime
          }
    ::= { lcsStatusAccountingTimeLastSnapshotTable 1 }

LcsStatusAccountingTimeLastSnapshotEntry ::= SEQUENCE {
            lcsStatusAccountingTimeLastSnapshotEntrySystemTime Counter32
    }

-- {COLUMN} 1.3.6.1.4.1.2356.11.1.56.5.1.1
lcsStatusAccountingTimeLastSnapshotEntrySystemTime OBJECT-TYPE
    SYNTAX     Counter32
    MAX-ACCESS read-only
    STATUS     current
    DESCRIPTION
            ""
    ::= { lcsStatusAccountingTimeLastSnapshotEntry 1 }

-- {NODE} 1.3.6.1.4.1.2356.11.1.58
lcsStatusAnalog OBJECT IDENTIFIER ::= { lcsStatus 58 }

-- {TABLE} 1.3.6.1.4.1.2356.11.1.58.1
lcsStatusAnalogOperatingTable OBJECT-TYPE
    SYNTAX     SEQUENCE OF LcsStatusAnalogOperatingEntry
    MAX-ACCESS not-accessible
    STATUS     current
    DESCRIPTION
            "-- empty --"
    ::= { lcsStatusAnalog 1 }

-- {ROW} 1.3.6.1.4.1.2356.11.1.58.1.1
lcsStatusAnalogOperatingEntry OBJECT-TYPE
    SYNTAX     LcsStatusAnalogOperatingEntry
    MAX-ACCESS not-accessible
    STATUS     current
    DESCRIPTION
            ""
    INDEX {
            lcsStatusAnalogOperatingEntryIfc
          }
    ::= { lcsStatusAnalogOperatingTable 1 }

LcsStatusAnalogOperatingEntry ::= SEQUENCE {
            lcsStatusAnalogOperatingEntryIfc INTEGER,
            lcsStatusAnalogOperatingEntryActive INTEGER,
            lcsStatusAnalogOperatingEntrySignaling INTEGER,
            lcsStatusAnalogOperatingEntryLine INTEGER
    }

-- {COLUMN} 1.3.6.1.4.1.2356.11.1.58.1.1.1
lcsStatusAnalogOperatingEntryIfc OBJECT-TYPE
    SYNTAX     INTEGER {
                  eLine1 (1),
                  eAnalog1 (16),
                  eAnalog2 (17),
                  eAnalog3 (18),
                  eAnalog4 (19)
            }
    MAX-ACCESS read-only
    STATUS     current
    DESCRIPTION
            "-- empty --"
    ::= { lcsStatusAnalogOperatingEntry 1 }

-- {COLUMN} 1.3.6.1.4.1.2356.11.1.58.1.1.2
lcsStatusAnalogOperatingEntryActive OBJECT-TYPE
    SYNTAX     INTEGER {
                  eNo (0),
                  eYes (1)
            }
    MAX-ACCESS read-only
    STATUS     current
    DESCRIPTION
            "-- empty --"
    ::= { lcsStatusAnalogOperatingEntry 2 }

-- {COLUMN} 1.3.6.1.4.1.2356.11.1.58.1.1.3
lcsStatusAnalogOperatingEntrySignaling OBJECT-TYPE
    SYNTAX     INTEGER {
                  eIdle (0),
                  eCallinitiated (1),
                  eOverlapsending (2),
                  eOutgcallproc (3),
                  eCalldelivered (4),
                  eCallpresent (6),
                  eCallreceived (7),
                  eInccallproc (9),
                  eActive (10),
                  eDiscreq (11),
                  eDiscind (12),
                  eReleasereq (19)
            }
    MAX-ACCESS read-only
    STATUS     current
    DESCRIPTION
            "-- empty --"
    ::= { lcsStatusAnalogOperatingEntry 3 }

-- {COLUMN} 1.3.6.1.4.1.2356.11.1.58.1.1.4
lcsStatusAnalogOperatingEntryLine OBJECT-TYPE
    SYNTAX     INTEGER {
                  eOnHook (0),
                  eOffHook (1),
                  eRinging (2)
            }
    MAX-ACCESS read-only
    STATUS     current
    DESCRIPTION
            "-- empty --"
    ::= { lcsStatusAnalogOperatingEntry 4 }

-- {TABLE} 1.3.6.1.4.1.2356.11.1.58.2
lcsStatusAnalogStatisticsTable OBJECT-TYPE
    SYNTAX     SEQUENCE OF LcsStatusAnalogStatisticsEntry
    MAX-ACCESS not-accessible
    STATUS     current
    DESCRIPTION
            "-- empty --"
    ::= { lcsStatusAnalog 2 }

-- {ROW} 1.3.6.1.4.1.2356.11.1.58.2.1
lcsStatusAnalogStatisticsEntry OBJECT-TYPE
    SYNTAX     LcsStatusAnalogStatisticsEntry
    MAX-ACCESS not-accessible
    STATUS     current
    DESCRIPTION
            ""
    INDEX {
            lcsStatusAnalogStatisticsEntryIfc
          }
    ::= { lcsStatusAnalogStatisticsTable 1 }

LcsStatusAnalogStatisticsEntry ::= SEQUENCE {
            lcsStatusAnalogStatisticsEntryIfc INTEGER,
            lcsStatusAnalogStatisticsEntryOffHookEvents Integer32,
            lcsStatusAnalogStatisticsEntryRingTripEvents Integer32,
            lcsStatusAnalogStatisticsEntryRingTripFixup Integer32,
            lcsStatusAnalogStatisticsEntrySquelchFixup Integer32
    }

-- {COLUMN} 1.3.6.1.4.1.2356.11.1.58.2.1.1
lcsStatusAnalogStatisticsEntryIfc OBJECT-TYPE
    SYNTAX     INTEGER {
                  eAnalog1 (16),
                  eAnalog2 (17),
                  eAnalog3 (18),
                  eAnalog4 (19)
            }
    MAX-ACCESS read-only
    STATUS     current
    DESCRIPTION
            "-- empty --"
    ::= { lcsStatusAnalogStatisticsEntry 1 }

-- {COLUMN} 1.3.6.1.4.1.2356.11.1.58.2.1.2
lcsStatusAnalogStatisticsEntryOffHookEvents OBJECT-TYPE
    SYNTAX     Integer32 (0..2147483647)
    MAX-ACCESS read-only
    STATUS     current
    DESCRIPTION
            "-- empty --"
    ::= { lcsStatusAnalogStatisticsEntry 2 }

-- {COLUMN} 1.3.6.1.4.1.2356.11.1.58.2.1.3
lcsStatusAnalogStatisticsEntryRingTripEvents OBJECT-TYPE
    SYNTAX     Integer32 (0..2147483647)
    MAX-ACCESS read-only
    STATUS     current
    DESCRIPTION
            "-- empty --"
    ::= { lcsStatusAnalogStatisticsEntry 3 }

-- {COLUMN} 1.3.6.1.4.1.2356.11.1.58.2.1.4
lcsStatusAnalogStatisticsEntryRingTripFixup OBJECT-TYPE
    SYNTAX     Integer32 (0..2147483647)
    MAX-ACCESS read-only
    STATUS     current
    DESCRIPTION
            "-- empty --"
    ::= { lcsStatusAnalogStatisticsEntry 4 }

-- {COLUMN} 1.3.6.1.4.1.2356.11.1.58.2.1.5
lcsStatusAnalogStatisticsEntrySquelchFixup OBJECT-TYPE
    SYNTAX     Integer32 (0..2147483647)
    MAX-ACCESS read-only
    STATUS     current
    DESCRIPTION
            "-- empty --"
    ::= { lcsStatusAnalogStatisticsEntry 5 }

-- {TABLE} 1.3.6.1.4.1.2356.11.1.58.3
lcsStatusAnalogMonitoringTable OBJECT-TYPE
    SYNTAX     SEQUENCE OF LcsStatusAnalogMonitoringEntry
    MAX-ACCESS not-accessible
    STATUS     current
    DESCRIPTION
            "-- empty --"
    ::= { lcsStatusAnalog 3 }

-- {ROW} 1.3.6.1.4.1.2356.11.1.58.3.1
lcsStatusAnalogMonitoringEntry OBJECT-TYPE
    SYNTAX     LcsStatusAnalogMonitoringEntry
    MAX-ACCESS not-accessible
    STATUS     current
    DESCRIPTION
            ""
    INDEX {
            lcsStatusAnalogMonitoringEntryIfc
          }
    ::= { lcsStatusAnalogMonitoringTable 1 }

LcsStatusAnalogMonitoringEntry ::= SEQUENCE {
            lcsStatusAnalogMonitoringEntryIfc INTEGER,
            lcsStatusAnalogMonitoringEntryIloopUa Integer32,
            lcsStatusAnalogMonitoringEntryIlongUa Integer32,
            lcsStatusAnalogMonitoringEntryItipUa Integer32,
            lcsStatusAnalogMonitoringEntryIringUa Integer32,
            lcsStatusAnalogMonitoringEntryVdcMv Integer32,
            lcsStatusAnalogMonitoringEntryVbatMv Integer32,
            lcsStatusAnalogMonitoringEntryVdiffMv Integer32,
            lcsStatusAnalogMonitoringEntryVlongMv Integer32,
            lcsStatusAnalogMonitoringEntryVtipMv Integer32,
            lcsStatusAnalogMonitoringEntryVringMv Integer32
    }

-- {COLUMN} 1.3.6.1.4.1.2356.11.1.58.3.1.1
lcsStatusAnalogMonitoringEntryIfc OBJECT-TYPE
    SYNTAX     INTEGER {
                  eAnalog1 (16),
                  eAnalog2 (17),
                  eAnalog3 (18),
                  eAnalog4 (19)
            }
    MAX-ACCESS read-only
    STATUS     current
    DESCRIPTION
            "-- empty --"
    ::= { lcsStatusAnalogMonitoringEntry 1 }

-- {COLUMN} 1.3.6.1.4.1.2356.11.1.58.3.1.2
lcsStatusAnalogMonitoringEntryIloopUa OBJECT-TYPE
    SYNTAX     Integer32 (-2147483648..2147483647)
    MAX-ACCESS read-only
    STATUS     current
    DESCRIPTION
            "-- empty --"
    ::= { lcsStatusAnalogMonitoringEntry 2 }

-- {COLUMN} 1.3.6.1.4.1.2356.11.1.58.3.1.3
lcsStatusAnalogMonitoringEntryIlongUa OBJECT-TYPE
    SYNTAX     Integer32 (-2147483648..2147483647)
    MAX-ACCESS read-only
    STATUS     current
    DESCRIPTION
            "-- empty --"
    ::= { lcsStatusAnalogMonitoringEntry 3 }

-- {COLUMN} 1.3.6.1.4.1.2356.11.1.58.3.1.4
lcsStatusAnalogMonitoringEntryItipUa OBJECT-TYPE
    SYNTAX     Integer32 (-2147483648..2147483647)
    MAX-ACCESS read-only
    STATUS     current
    DESCRIPTION
            "-- empty --"
    ::= { lcsStatusAnalogMonitoringEntry 4 }

-- {COLUMN} 1.3.6.1.4.1.2356.11.1.58.3.1.5
lcsStatusAnalogMonitoringEntryIringUa OBJECT-TYPE
    SYNTAX     Integer32 (-2147483648..2147483647)
    MAX-ACCESS read-only
    STATUS     current
    DESCRIPTION
            "-- empty --"
    ::= { lcsStatusAnalogMonitoringEntry 5 }

-- {COLUMN} 1.3.6.1.4.1.2356.11.1.58.3.1.6
lcsStatusAnalogMonitoringEntryVdcMv OBJECT-TYPE
    SYNTAX     Integer32 (-2147483648..2147483647)
    MAX-ACCESS read-only
    STATUS     current
    DESCRIPTION
            "-- empty --"
    ::= { lcsStatusAnalogMonitoringEntry 6 }

-- {COLUMN} 1.3.6.1.4.1.2356.11.1.58.3.1.7
lcsStatusAnalogMonitoringEntryVbatMv OBJECT-TYPE
    SYNTAX     Integer32 (-2147483648..2147483647)
    MAX-ACCESS read-only
    STATUS     current
    DESCRIPTION
            "-- empty --"
    ::= { lcsStatusAnalogMonitoringEntry 7 }

-- {COLUMN} 1.3.6.1.4.1.2356.11.1.58.3.1.8
lcsStatusAnalogMonitoringEntryVdiffMv OBJECT-TYPE
    SYNTAX     Integer32 (-2147483648..2147483647)
    MAX-ACCESS read-only
    STATUS     current
    DESCRIPTION
            "-- empty --"
    ::= { lcsStatusAnalogMonitoringEntry 8 }

-- {COLUMN} 1.3.6.1.4.1.2356.11.1.58.3.1.9
lcsStatusAnalogMonitoringEntryVlongMv OBJECT-TYPE
    SYNTAX     Integer32 (-2147483648..2147483647)
    MAX-ACCESS read-only
    STATUS     current
    DESCRIPTION
            "-- empty --"
    ::= { lcsStatusAnalogMonitoringEntry 9 }

-- {COLUMN} 1.3.6.1.4.1.2356.11.1.58.3.1.10
lcsStatusAnalogMonitoringEntryVtipMv OBJECT-TYPE
    SYNTAX     Integer32 (-2147483648..2147483647)
    MAX-ACCESS read-only
    STATUS     current
    DESCRIPTION
            "-- empty --"
    ::= { lcsStatusAnalogMonitoringEntry 10 }

-- {COLUMN} 1.3.6.1.4.1.2356.11.1.58.3.1.11
lcsStatusAnalogMonitoringEntryVringMv OBJECT-TYPE
    SYNTAX     Integer32 (-2147483648..2147483647)
    MAX-ACCESS read-only
    STATUS     current
    DESCRIPTION
            "-- empty --"
    ::= { lcsStatusAnalogMonitoringEntry 11 }

-- {NODE} 1.3.6.1.4.1.2356.11.1.59
lcsStatusWtpMngmt OBJECT IDENTIFIER ::= { lcsStatus 59 }

-- {TABLE} 1.3.6.1.4.1.2356.11.1.59.1
lcsStatusWtpMngmtApConnectionsTable OBJECT-TYPE
    SYNTAX     SEQUENCE OF LcsStatusWtpMngmtApConnectionsEntry
    MAX-ACCESS not-accessible
    STATUS     current
    DESCRIPTION
            ""
    ::= { lcsStatusWtpMngmt 1 }

-- {ROW} 1.3.6.1.4.1.2356.11.1.59.1.1
lcsStatusWtpMngmtApConnectionsEntry OBJECT-TYPE
    SYNTAX     LcsStatusWtpMngmtApConnectionsEntry
    MAX-ACCESS not-accessible
    STATUS     current
    DESCRIPTION
            ""
    INDEX {
            lcsStatusWtpMngmtApConnectionsEntryConnId
          }
    ::= { lcsStatusWtpMngmtApConnectionsTable 1 }

LcsStatusWtpMngmtApConnectionsEntry ::= SEQUENCE {
            lcsStatusWtpMngmtApConnectionsEntryConnId Integer32,
            lcsStatusWtpMngmtApConnectionsEntryIpAddress IpAddress,
            lcsStatusWtpMngmtApConnectionsEntryPort Integer32,
            lcsStatusWtpMngmtApConnectionsEntryResptime Integer32,
            lcsStatusWtpMngmtApConnectionsEntryName DisplayString,
            lcsStatusWtpMngmtApConnectionsEntryState INTEGER,
            lcsStatusWtpMngmtApConnectionsEntryResult INTEGER,
            lcsStatusWtpMngmtApConnectionsEntryPriority INTEGER,
            lcsStatusWtpMngmtApConnectionsEntryUtilisation DisplayString,
            lcsStatusWtpMngmtApConnectionsEntryFirmwareVersion DisplayString,
            lcsStatusWtpMngmtApConnectionsEntryPmtu Integer32,
            lcsStatusWtpMngmtApConnectionsEntryDscpForControlPackets INTEGER,
            lcsStatusWtpMngmtApConnectionsEntryDscpForDataPackets INTEGER,
            lcsStatusWtpMngmtApConnectionsEntryPreference Integer32,
            lcsStatusWtpMngmtApConnectionsEntryCpuLoad300sPercent DisplayString,
            lcsStatusWtpMngmtApConnectionsEntryRetransmissions Integer32
    }

-- {COLUMN} 1.3.6.1.4.1.2356.11.1.59.1.1.1
lcsStatusWtpMngmtApConnectionsEntryConnId OBJECT-TYPE
    SYNTAX     Integer32 (0..2147483647)
    MAX-ACCESS read-only
    STATUS     current
    DESCRIPTION
            ""
    ::= { lcsStatusWtpMngmtApConnectionsEntry 1 }

-- {COLUMN} 1.3.6.1.4.1.2356.11.1.59.1.1.2
lcsStatusWtpMngmtApConnectionsEntryIpAddress OBJECT-TYPE
    SYNTAX     IpAddress
    MAX-ACCESS read-only
    STATUS     current
    DESCRIPTION
            ""
    ::= { lcsStatusWtpMngmtApConnectionsEntry 2 }

-- {COLUMN} 1.3.6.1.4.1.2356.11.1.59.1.1.3
lcsStatusWtpMngmtApConnectionsEntryPort OBJECT-TYPE
    SYNTAX     Integer32 (0..65535)
    MAX-ACCESS read-only
    STATUS     current
    DESCRIPTION
            ""
    ::= { lcsStatusWtpMngmtApConnectionsEntry 3 }

-- {COLUMN} 1.3.6.1.4.1.2356.11.1.59.1.1.4
lcsStatusWtpMngmtApConnectionsEntryResptime OBJECT-TYPE
    SYNTAX     Integer32 (0..2147483647)
    MAX-ACCESS read-only
    STATUS     current
    DESCRIPTION
            ""
    ::= { lcsStatusWtpMngmtApConnectionsEntry 4 }

-- {COLUMN} 1.3.6.1.4.1.2356.11.1.59.1.1.5
lcsStatusWtpMngmtApConnectionsEntryName OBJECT-TYPE
    SYNTAX     DisplayString (SIZE(0..31))
    MAX-ACCESS read-only
    STATUS     current
    DESCRIPTION
            ""
    ::= { lcsStatusWtpMngmtApConnectionsEntry 5 }

-- {COLUMN} 1.3.6.1.4.1.2356.11.1.59.1.1.6
lcsStatusWtpMngmtApConnectionsEntryState OBJECT-TYPE
    SYNTAX     INTEGER {
                  eUnknown (0),
                  eIdle (5),
                  eDiscovery (10),
                  eDtlsSetup (15),
                  eJoin (20),
                  eConfigure (25),
                  eImageData (30),
                  eReset (35),
                  eDtlsTeardown (40),
                  eSulking (45),
                  eRun (100)
            }
    MAX-ACCESS read-only
    STATUS     current
    DESCRIPTION
            ""
    ::= { lcsStatusWtpMngmtApConnectionsEntry 6 }

-- {COLUMN} 1.3.6.1.4.1.2356.11.1.59.1.1.7
lcsStatusWtpMngmtApConnectionsEntryResult OBJECT-TYPE
    SYNTAX     INTEGER {
                  eSuccess (0),
                  eFailure (1),
                  eSuccessNat (2),
                  eJoinFailUnspecified (3),
                  eJoinFailResourceDepletion (4),
                  eJoinFailUnknwnSrc (5),
                  eJoinFailIncorrectData (6),
                  eJoinFailSessionIdInUse (7),
                  eJoinFailWtpNotSupported (8),
                  eJoinFailBindingNotSupp (9),
                  eResetFailUnableToReset (10),
                  eResetFailFirmwWriteErr (11),
                  eConfigurationErrorServProvAnyhow (12),
                  eConfigurationErrorServNotProv (13),
                  eImageDataErrorChecksum (14),
                  eImageDataErrorLength (15),
                  eImageDataErrorOther (16),
                  eImageDataErrorAlrPresent (17),
                  eMessageUnexpectedInvalid (18),
                  eMessageUnexpectedUnrecognized (19),
                  eFailMissingMandMsgElem (20),
                  eFailUnrecognizedMsgElem (21),
                  eUnsupportedLoaderVersion (300),
                  eUnsupportedFirmwareVersion (301),
                  eUnknown (302),
                  eJoinFailAlreadyConnected (303)
            }
    MAX-ACCESS read-only
    STATUS     current
    DESCRIPTION
            ""
    ::= { lcsStatusWtpMngmtApConnectionsEntry 7 }

-- {COLUMN} 1.3.6.1.4.1.2356.11.1.59.1.1.8
lcsStatusWtpMngmtApConnectionsEntryPriority OBJECT-TYPE
    SYNTAX     INTEGER {
                  eUnspec (0),
                  ePrimary (1),
                  eSecondary (2)
            }
    MAX-ACCESS read-only
    STATUS     current
    DESCRIPTION
            ""
    ::= { lcsStatusWtpMngmtApConnectionsEntry 8 }

-- {COLUMN} 1.3.6.1.4.1.2356.11.1.59.1.1.9
lcsStatusWtpMngmtApConnectionsEntryUtilisation OBJECT-TYPE
    SYNTAX     DisplayString (SIZE(0..6))
    MAX-ACCESS read-only
    STATUS     current
    DESCRIPTION
            ""
    ::= { lcsStatusWtpMngmtApConnectionsEntry 9 }

-- {COLUMN} 1.3.6.1.4.1.2356.11.1.59.1.1.10
lcsStatusWtpMngmtApConnectionsEntryFirmwareVersion OBJECT-TYPE
    SYNTAX     DisplayString (SIZE(0..31))
    MAX-ACCESS read-only
    STATUS     current
    DESCRIPTION
            ""
    ::= { lcsStatusWtpMngmtApConnectionsEntry 10 }

-- {COLUMN} 1.3.6.1.4.1.2356.11.1.59.1.1.11
lcsStatusWtpMngmtApConnectionsEntryPmtu OBJECT-TYPE
    SYNTAX     Integer32 (0..2147483647)
    MAX-ACCESS read-only
    STATUS     current
    DESCRIPTION
            ""
    ::= { lcsStatusWtpMngmtApConnectionsEntry 11 }

-- {COLUMN} 1.3.6.1.4.1.2356.11.1.59.1.1.12
lcsStatusWtpMngmtApConnectionsEntryDscpForControlPackets OBJECT-TYPE
    SYNTAX     INTEGER {
                  eBestEffort (0),
                  eAssuredForwarding11 (40),
                  eAssuredForwarding12 (48),
                  eAssuredForwarding13 (56),
                  eAssuredForwarding21 (72),
                  eAssuredForwarding22 (80),
                  eAssuredForwarding23 (88),
                  eAssuredForwarding31 (104),
                  eAssuredForwarding32 (112),
                  eAssuredForwarding33 (120),
                  eAssuredForwarding41 (136),
                  eAssuredForwarding42 (144),
                  eAssuredForwarding43 (152),
                  eExpeditedForwarding (184)
            }
    MAX-ACCESS read-only
    STATUS     current
    DESCRIPTION
            ""
    ::= { lcsStatusWtpMngmtApConnectionsEntry 12 }

-- {COLUMN} 1.3.6.1.4.1.2356.11.1.59.1.1.13
lcsStatusWtpMngmtApConnectionsEntryDscpForDataPackets OBJECT-TYPE
    SYNTAX     INTEGER {
                  eBestEffort (0),
                  eAssuredForwarding11 (40),
                  eAssuredForwarding12 (48),
                  eAssuredForwarding13 (56),
                  eAssuredForwarding21 (72),
                  eAssuredForwarding22 (80),
                  eAssuredForwarding23 (88),
                  eAssuredForwarding31 (104),
                  eAssuredForwarding32 (112),
                  eAssuredForwarding33 (120),
                  eAssuredForwarding41 (136),
                  eAssuredForwarding42 (144),
                  eAssuredForwarding43 (152),
                  eExpeditedForwarding (184)
            }
    MAX-ACCESS read-only
    STATUS     current
    DESCRIPTION
            ""
    ::= { lcsStatusWtpMngmtApConnectionsEntry 13 }

-- {COLUMN} 1.3.6.1.4.1.2356.11.1.59.1.1.14
lcsStatusWtpMngmtApConnectionsEntryPreference OBJECT-TYPE
    SYNTAX     Integer32 (0..255)
    MAX-ACCESS read-only
    STATUS     current
    DESCRIPTION
            "-- empty --"
    ::= { lcsStatusWtpMngmtApConnectionsEntry 14 }

-- {COLUMN} 1.3.6.1.4.1.2356.11.1.59.1.1.15
lcsStatusWtpMngmtApConnectionsEntryCpuLoad300sPercent OBJECT-TYPE
    SYNTAX     DisplayString (SIZE(0..7))
    MAX-ACCESS read-only
    STATUS     current
    DESCRIPTION
            "-- empty --"
    ::= { lcsStatusWtpMngmtApConnectionsEntry 15 }

-- {COLUMN} 1.3.6.1.4.1.2356.11.1.59.1.1.16
lcsStatusWtpMngmtApConnectionsEntryRetransmissions OBJECT-TYPE
    SYNTAX     Integer32 (0..2147483647)
    MAX-ACCESS read-only
    STATUS     current
    DESCRIPTION
            "-- empty --"
    ::= { lcsStatusWtpMngmtApConnectionsEntry 16 }

-- {TABLE} 1.3.6.1.4.1.2356.11.1.59.99
lcsStatusWtpMngmtGlobalconfigTable OBJECT-TYPE
    SYNTAX     SEQUENCE OF LcsStatusWtpMngmtGlobalconfigEntry
    MAX-ACCESS not-accessible
    STATUS     current
    DESCRIPTION
            ""
    ::= { lcsStatusWtpMngmt 99 }

-- {ROW} 1.3.6.1.4.1.2356.11.1.59.99.1
lcsStatusWtpMngmtGlobalconfigEntry OBJECT-TYPE
    SYNTAX     LcsStatusWtpMngmtGlobalconfigEntry
    MAX-ACCESS not-accessible
    STATUS     current
    DESCRIPTION
            ""
    INDEX {
            lcsStatusWtpMngmtGlobalconfigEntryVersion
          }
    ::= { lcsStatusWtpMngmtGlobalconfigTable 1 }

LcsStatusWtpMngmtGlobalconfigEntry ::= SEQUENCE {
            lcsStatusWtpMngmtGlobalconfigEntryVersion Integer32,
            lcsStatusWtpMngmtGlobalconfigEntryIpAddress IpAddress,
            lcsStatusWtpMngmtGlobalconfigEntryNetMask IpAddress,
            lcsStatusWtpMngmtGlobalconfigEntryGateway IpAddress,
            lcsStatusWtpMngmtGlobalconfigEntryDns1 IpAddress,
            lcsStatusWtpMngmtGlobalconfigEntryDns2 IpAddress,
            lcsStatusWtpMngmtGlobalconfigEntryMgmtVlanid Integer32,
            lcsStatusWtpMngmtGlobalconfigEntryMgmtVlantrunk Integer32,
            lcsStatusWtpMngmtGlobalconfigEntryDnsSuffix DisplayString
    }

-- {COLUMN} 1.3.6.1.4.1.2356.11.1.59.99.1.1
lcsStatusWtpMngmtGlobalconfigEntryVersion OBJECT-TYPE
    SYNTAX     Integer32 (0..2147483647)
    MAX-ACCESS read-only
    STATUS     current
    DESCRIPTION
            ""
    ::= { lcsStatusWtpMngmtGlobalconfigEntry 1 }

-- {COLUMN} 1.3.6.1.4.1.2356.11.1.59.99.1.2
lcsStatusWtpMngmtGlobalconfigEntryIpAddress OBJECT-TYPE
    SYNTAX     IpAddress
    MAX-ACCESS read-only
    STATUS     current
    DESCRIPTION
            ""
    ::= { lcsStatusWtpMngmtGlobalconfigEntry 2 }

-- {COLUMN} 1.3.6.1.4.1.2356.11.1.59.99.1.3
lcsStatusWtpMngmtGlobalconfigEntryNetMask OBJECT-TYPE
    SYNTAX     IpAddress
    MAX-ACCESS read-only
    STATUS     current
    DESCRIPTION
            ""
    ::= { lcsStatusWtpMngmtGlobalconfigEntry 3 }

-- {COLUMN} 1.3.6.1.4.1.2356.11.1.59.99.1.4
lcsStatusWtpMngmtGlobalconfigEntryGateway OBJECT-TYPE
    SYNTAX     IpAddress
    MAX-ACCESS read-only
    STATUS     current
    DESCRIPTION
            ""
    ::= { lcsStatusWtpMngmtGlobalconfigEntry 4 }

-- {COLUMN} 1.3.6.1.4.1.2356.11.1.59.99.1.5
lcsStatusWtpMngmtGlobalconfigEntryDns1 OBJECT-TYPE
    SYNTAX     IpAddress
    MAX-ACCESS read-only
    STATUS     current
    DESCRIPTION
            ""
    ::= { lcsStatusWtpMngmtGlobalconfigEntry 5 }

-- {COLUMN} 1.3.6.1.4.1.2356.11.1.59.99.1.6
lcsStatusWtpMngmtGlobalconfigEntryDns2 OBJECT-TYPE
    SYNTAX     IpAddress
    MAX-ACCESS read-only
    STATUS     current
    DESCRIPTION
            ""
    ::= { lcsStatusWtpMngmtGlobalconfigEntry 6 }

-- {COLUMN} 1.3.6.1.4.1.2356.11.1.59.99.1.8
lcsStatusWtpMngmtGlobalconfigEntryMgmtVlanid OBJECT-TYPE
    SYNTAX     Integer32 (0..65535)
    MAX-ACCESS read-only
    STATUS     current
    DESCRIPTION
            ""
    ::= { lcsStatusWtpMngmtGlobalconfigEntry 8 }

-- {COLUMN} 1.3.6.1.4.1.2356.11.1.59.99.1.9
lcsStatusWtpMngmtGlobalconfigEntryMgmtVlantrunk OBJECT-TYPE
    SYNTAX     Integer32 (0..65535)
    MAX-ACCESS read-only
    STATUS     current
    DESCRIPTION
            ""
    ::= { lcsStatusWtpMngmtGlobalconfigEntry 9 }

-- {COLUMN} 1.3.6.1.4.1.2356.11.1.59.99.1.14
lcsStatusWtpMngmtGlobalconfigEntryDnsSuffix OBJECT-TYPE
    SYNTAX     DisplayString (SIZE(0..63))
    MAX-ACCESS read-only
    STATUS     current
    DESCRIPTION
            ""
    ::= { lcsStatusWtpMngmtGlobalconfigEntry 14 }

-- {TABLE} 1.3.6.1.4.1.2356.11.1.59.100
lcsStatusWtpMngmtLastWlcTable OBJECT-TYPE
    SYNTAX     SEQUENCE OF LcsStatusWtpMngmtLastWlcEntry
    MAX-ACCESS not-accessible
    STATUS     current
    DESCRIPTION
            ""
    ::= { lcsStatusWtpMngmt 100 }

-- {ROW} 1.3.6.1.4.1.2356.11.1.59.100.1
lcsStatusWtpMngmtLastWlcEntry OBJECT-TYPE
    SYNTAX     LcsStatusWtpMngmtLastWlcEntry
    MAX-ACCESS not-accessible
    STATUS     current
    DESCRIPTION
            ""
    INDEX {
            lcsStatusWtpMngmtLastWlcEntryIpAddress
          }
    ::= { lcsStatusWtpMngmtLastWlcTable 1 }

LcsStatusWtpMngmtLastWlcEntry ::= SEQUENCE {
            lcsStatusWtpMngmtLastWlcEntryIpAddress IpAddress,
            lcsStatusWtpMngmtLastWlcEntryPort Integer32,
            lcsStatusWtpMngmtLastWlcEntryName DisplayString,
            lcsStatusWtpMngmtLastWlcEntryRoutetag Integer32,
            lcsStatusWtpMngmtLastWlcEntryType Integer32,
            lcsStatusWtpMngmtLastWlcEntryMgmtVlanId Integer32
    }

-- {COLUMN} 1.3.6.1.4.1.2356.11.1.59.100.1.1
lcsStatusWtpMngmtLastWlcEntryIpAddress OBJECT-TYPE
    SYNTAX     IpAddress
    MAX-ACCESS read-only
    STATUS     current
    DESCRIPTION
            ""
    ::= { lcsStatusWtpMngmtLastWlcEntry 1 }

-- {COLUMN} 1.3.6.1.4.1.2356.11.1.59.100.1.2
lcsStatusWtpMngmtLastWlcEntryPort OBJECT-TYPE
    SYNTAX     Integer32 (0..65535)
    MAX-ACCESS read-only
    STATUS     current
    DESCRIPTION
            ""
    ::= { lcsStatusWtpMngmtLastWlcEntry 2 }

-- {COLUMN} 1.3.6.1.4.1.2356.11.1.59.100.1.3
lcsStatusWtpMngmtLastWlcEntryName OBJECT-TYPE
    SYNTAX     DisplayString (SIZE(0..31))
    MAX-ACCESS read-only
    STATUS     current
    DESCRIPTION
            ""
    ::= { lcsStatusWtpMngmtLastWlcEntry 3 }

-- {COLUMN} 1.3.6.1.4.1.2356.11.1.59.100.1.4
lcsStatusWtpMngmtLastWlcEntryRoutetag OBJECT-TYPE
    SYNTAX     Integer32 (0..65535)
    MAX-ACCESS read-only
    STATUS     current
    DESCRIPTION
            ""
    ::= { lcsStatusWtpMngmtLastWlcEntry 4 }

-- {COLUMN} 1.3.6.1.4.1.2356.11.1.59.100.1.5
lcsStatusWtpMngmtLastWlcEntryType OBJECT-TYPE
    SYNTAX     Integer32 (0..255)
    MAX-ACCESS read-only
    STATUS     current
    DESCRIPTION
            ""
    ::= { lcsStatusWtpMngmtLastWlcEntry 5 }

-- {COLUMN} 1.3.6.1.4.1.2356.11.1.59.100.1.6
lcsStatusWtpMngmtLastWlcEntryMgmtVlanId OBJECT-TYPE
    SYNTAX     Integer32 (0..65535)
    MAX-ACCESS read-only
    STATUS     current
    DESCRIPTION
            ""
    ::= { lcsStatusWtpMngmtLastWlcEntry 6 }

-- {TABLE} 1.3.6.1.4.1.2356.11.1.59.101
lcsStatusWtpMngmtRadioprofilsTable OBJECT-TYPE
    SYNTAX     SEQUENCE OF LcsStatusWtpMngmtRadioprofilsEntry
    MAX-ACCESS not-accessible
    STATUS     current
    DESCRIPTION
            ""
    ::= { lcsStatusWtpMngmt 101 }

-- {ROW} 1.3.6.1.4.1.2356.11.1.59.101.1
lcsStatusWtpMngmtRadioprofilsEntry OBJECT-TYPE
    SYNTAX     LcsStatusWtpMngmtRadioprofilsEntry
    MAX-ACCESS not-accessible
    STATUS     current
    DESCRIPTION
            ""
    INDEX {
            lcsStatusWtpMngmtRadioprofilsEntryName
          }
    ::= { lcsStatusWtpMngmtRadioprofilsTable 1 }

LcsStatusWtpMngmtRadioprofilsEntry ::= SEQUENCE {
            lcsStatusWtpMngmtRadioprofilsEntryName DisplayString,
            lcsStatusWtpMngmtRadioprofilsEntryCountry INTEGER,
            lcsStatusWtpMngmtRadioprofilsEntry24ghzMode INTEGER,
            lcsStatusWtpMngmtRadioprofilsEntry5ghzMode INTEGER,
            lcsStatusWtpMngmtRadioprofilsEntrySubbands INTEGER,
            lcsStatusWtpMngmtRadioprofilsEntryQos INTEGER,
            lcsStatusWtpMngmtRadioprofilsEntryDtimPeriod Integer32,
            lcsStatusWtpMngmtRadioprofilsEntryBackgroundScan Integer32,
            lcsStatusWtpMngmtRadioprofilsEntryAntennaGain Integer32,
            lcsStatusWtpMngmtRadioprofilsEntryTxPowerReduction Integer32,
            lcsStatusWtpMngmtRadioprofilsEntryMgmtVLANId Integer32,
            lcsStatusWtpMngmtRadioprofilsEntryMgmtVlanTrunk Integer32,
            lcsStatusWtpMngmtRadioprofilsEntryIndoorOnlyOperation INTEGER,
            lcsStatusWtpMngmtRadioprofilsEntryMgmtVLANIdnew Integer32,
            lcsStatusWtpMngmtRadioprofilsEntryReportSeenClients INTEGER,
            lcsStatusWtpMngmtRadioprofilsEntryClientSteering INTEGER,
            lcsStatusWtpMngmtRadioprofilsEntryPreferredBand INTEGER,
            lcsStatusWtpMngmtRadioprofilsEntryPrReqAgeO Integer32,
            lcsStatusWtpMngmtRadioprofilsEntryAdaptiveRfOptimization INTEGER,
            lcsStatusWtpMngmtRadioprofilsEntryRxPacketSensReduction Integer32
    }

-- {COLUMN} 1.3.6.1.4.1.2356.11.1.59.101.1.1
lcsStatusWtpMngmtRadioprofilsEntryName OBJECT-TYPE
    SYNTAX     DisplayString (SIZE(0..31))
    MAX-ACCESS read-only
    STATUS     current
    DESCRIPTION
            ""
    ::= { lcsStatusWtpMngmtRadioprofilsEntry 1 }

-- {COLUMN} 1.3.6.1.4.1.2356.11.1.59.101.1.4
lcsStatusWtpMngmtRadioprofilsEntryCountry OBJECT-TYPE
    SYNTAX     INTEGER {
                  eDefault (0),
                  eAlbania (8),
                  eAlgeria (12),
                  eArgentina (32),
                  eAustralia (36),
                  eAustria (40),
                  eBahrain (48),
                  eBangladesh (50),
                  eBelgium (56),
                  eBosniaHerzegovina (70),
                  eBrazil (76),
                  eBruneiDarussalam (96),
                  eBulgaria (100),
                  eBelarus (112),
                  eCanada (124),
                  eChile (152),
                  eChina (156),
                  eTaiwan (158),
                  eColombia (170),
                  eCostaRica (188),
                  eCroatia (191),
                  eCyprus (196),
                  eCzech (203),
                  eDenmark (208),
                  eEcuador (218),
                  eEstonia (233),
                  eFinland (246),
                  eFrance (250),
                  eGermany (276),
                  eGhana (288),
                  eGreece (300),
                  eGuatemala (320),
                  eHonduras (340),
                  eHongKong (344),
                  eHungary (348),
                  eIceland (352),
                  eIndia (356),
                  eIndonesia (360),
                  eIreland (372),
                  eIsrael (376),
                  eItaly (380),
                  eJapan (392),
                  eJordan (400),
                  eSouthKorea (410),
                  eKuwait (414),
                  eLebanon (422),
                  eLatvia (428),
                  eLiechtenstein (438),
                  eLithuania (440),
                  eLuxembourg (442),
                  eMacau (446),
                  eMalaysia (458),
                  eMalta (470),
                  eMexico (484),
                  eMoldavia (498),
                  eMorocco (504),
                  eOman (512),
                  eNetherlands (528),
                  eNewZealand (554),
                  eNicaragua (558),
                  eNorway (578),
                  ePakistan (586),
                  ePanama (591),
                  eParaguay (600),
                  ePeru (604),
                  ePhilippines (608),
                  ePoland (616),
                  ePortugal (620),
                  ePuertoRico (630),
                  eQatar (634),
                  eRomania (642),
                  eRussia (643),
                  eSaudiArabia (682),
                  eSingapore (702),
                  eSlovak (703),
                  eSlovenia (705),
                  eSouthAfrica (710),
                  eSpain (724),
                  eSweden (752),
                  eSwitzerland (756),
                  eThailand (764),
                  eUnitedArabEmirates (784),
                  eTunisia (788),
                  eTurkey (792),
                  eUganda (800),
                  eUkraine (804),
                  eMacedonia (807),
                  eEgypt (818),
                  eUnitedKingdom (826),
                  eTanzania (834),
                  eUnitedStatesFcc (840),
                  eUruguay (858),
                  eVenezuela (862),
                  eEurope (998),
                  eEgalistan (999)
            }
    MAX-ACCESS read-only
    STATUS     current
    DESCRIPTION
            ""
    ::= { lcsStatusWtpMngmtRadioprofilsEntry 4 }

-- {COLUMN} 1.3.6.1.4.1.2356.11.1.59.101.1.6
lcsStatusWtpMngmtRadioprofilsEntry24ghzMode OBJECT-TYPE
    SYNTAX     INTEGER {
                  e11bgMixed (0),
                  e11gOnly (1),
                  e11bOnly (2),
                  e11bgnMixed (4),
                  e11gnMixed (5),
                  eGreenfield (6),
                  eAuto (255)
            }
    MAX-ACCESS read-only
    STATUS     current
    DESCRIPTION
            ""
    ::= { lcsStatusWtpMngmtRadioprofilsEntry 6 }

-- {COLUMN} 1.3.6.1.4.1.2356.11.1.59.101.1.7
lcsStatusWtpMngmtRadioprofilsEntry5ghzMode OBJECT-TYPE
    SYNTAX     INTEGER {
                  eNormal (0),
                  e11anMixed (4),
                  eGreenfield (5),
                  e11anacMixed (6),
                  e11nacMixed (7),
                  e11acOnly (8),
                  eAuto (255)
            }
    MAX-ACCESS read-only
    STATUS     current
    DESCRIPTION
            ""
    ::= { lcsStatusWtpMngmtRadioprofilsEntry 7 }

-- {COLUMN} 1.3.6.1.4.1.2356.11.1.59.101.1.8
lcsStatusWtpMngmtRadioprofilsEntrySubbands OBJECT-TYPE
    SYNTAX     INTEGER {
                  eBand1Plus2Plus3 (0),
                  eBand1 (1),
                  eBand2 (2),
                  eBand3 (3),
                  eBand1Plus2 (4),
                  eBand1Plus3 (5),
                  eBand2Plus3 (6)
            }
    MAX-ACCESS read-only
    STATUS     current
    DESCRIPTION
            ""
    ::= { lcsStatusWtpMngmtRadioprofilsEntry 8 }

-- {COLUMN} 1.3.6.1.4.1.2356.11.1.59.101.1.9
lcsStatusWtpMngmtRadioprofilsEntryQos OBJECT-TYPE
    SYNTAX     INTEGER {
                  eNo (0),
                  eYes (1)
            }
    MAX-ACCESS read-only
    STATUS     current
    DESCRIPTION
            ""
    ::= { lcsStatusWtpMngmtRadioprofilsEntry 9 }

-- {COLUMN} 1.3.6.1.4.1.2356.11.1.59.101.1.10
lcsStatusWtpMngmtRadioprofilsEntryDtimPeriod OBJECT-TYPE
    SYNTAX     Integer32 (0..255)
    MAX-ACCESS read-only
    STATUS     current
    DESCRIPTION
            ""
    ::= { lcsStatusWtpMngmtRadioprofilsEntry 10 }

-- {COLUMN} 1.3.6.1.4.1.2356.11.1.59.101.1.11
lcsStatusWtpMngmtRadioprofilsEntryBackgroundScan OBJECT-TYPE
    SYNTAX     Integer32 (0..2147483647)
    MAX-ACCESS read-only
    STATUS     current
    DESCRIPTION
            ""
    ::= { lcsStatusWtpMngmtRadioprofilsEntry 11 }

-- {COLUMN} 1.3.6.1.4.1.2356.11.1.59.101.1.12
lcsStatusWtpMngmtRadioprofilsEntryAntennaGain OBJECT-TYPE
    SYNTAX     Integer32 (-128..127)
    MAX-ACCESS read-only
    STATUS     current
    DESCRIPTION
            ""
    ::= { lcsStatusWtpMngmtRadioprofilsEntry 12 }

-- {COLUMN} 1.3.6.1.4.1.2356.11.1.59.101.1.13
lcsStatusWtpMngmtRadioprofilsEntryTxPowerReduction OBJECT-TYPE
    SYNTAX     Integer32 (0..255)
    MAX-ACCESS read-only
    STATUS     current
    DESCRIPTION
            ""
    ::= { lcsStatusWtpMngmtRadioprofilsEntry 13 }

-- {COLUMN} 1.3.6.1.4.1.2356.11.1.59.101.1.14
lcsStatusWtpMngmtRadioprofilsEntryMgmtVLANId OBJECT-TYPE
    SYNTAX     Integer32 (0..65535)
    MAX-ACCESS read-only
    STATUS     obsolete
    DESCRIPTION
            ""
    ::= { lcsStatusWtpMngmtRadioprofilsEntry 14 }

-- {COLUMN} 1.3.6.1.4.1.2356.11.1.59.101.1.15
lcsStatusWtpMngmtRadioprofilsEntryMgmtVlanTrunk OBJECT-TYPE
    SYNTAX     Integer32 (0..65535)
    MAX-ACCESS read-only
    STATUS     current
    DESCRIPTION
            ""
    ::= { lcsStatusWtpMngmtRadioprofilsEntry 15 }

-- {COLUMN} 1.3.6.1.4.1.2356.11.1.59.101.1.16
lcsStatusWtpMngmtRadioprofilsEntryIndoorOnlyOperation OBJECT-TYPE
    SYNTAX     INTEGER {
                  eNo (0),
                  eYes (1)
            }
    MAX-ACCESS read-only
    STATUS     current
    DESCRIPTION
            ""
    ::= { lcsStatusWtpMngmtRadioprofilsEntry 16 }

-- {COLUMN} 1.3.6.1.4.1.2356.11.1.59.101.1.19
lcsStatusWtpMngmtRadioprofilsEntryMgmtVLANIdnew OBJECT-TYPE
    SYNTAX     Integer32 (0..65535)
    MAX-ACCESS read-only
    STATUS     current
    DESCRIPTION
            ""
    ::= { lcsStatusWtpMngmtRadioprofilsEntry 19 }

-- {COLUMN} 1.3.6.1.4.1.2356.11.1.59.101.1.20
lcsStatusWtpMngmtRadioprofilsEntryReportSeenClients OBJECT-TYPE
    SYNTAX     INTEGER {
                  eNo (0),
                  eYes (1)
            }
    MAX-ACCESS read-only
    STATUS     current
    DESCRIPTION
            ""
    ::= { lcsStatusWtpMngmtRadioprofilsEntry 20 }

-- {COLUMN} 1.3.6.1.4.1.2356.11.1.59.101.1.21
lcsStatusWtpMngmtRadioprofilsEntryClientSteering OBJECT-TYPE
    SYNTAX     INTEGER {
                  eOff (0),
                  eYes (1),
                  eOn (2),
                  eClientManagement (3)
            }
    MAX-ACCESS read-only
    STATUS     current
    DESCRIPTION
            "-- empty --"
    ::= { lcsStatusWtpMngmtRadioprofilsEntry 21 }

-- {COLUMN} 1.3.6.1.4.1.2356.11.1.59.101.1.22
lcsStatusWtpMngmtRadioprofilsEntryPreferredBand OBJECT-TYPE
    SYNTAX     INTEGER {
                  e24ghz (1),
                  e5ghz (2)
            }
    MAX-ACCESS read-only
    STATUS     current
    DESCRIPTION
            "-- empty --"
    ::= { lcsStatusWtpMngmtRadioprofilsEntry 22 }

-- {COLUMN} 1.3.6.1.4.1.2356.11.1.59.101.1.23
lcsStatusWtpMngmtRadioprofilsEntryPrReqAgeO OBJECT-TYPE
    SYNTAX     Integer32 (0..2147483647)
    MAX-ACCESS read-only
    STATUS     current
    DESCRIPTION
            ""
    ::= { lcsStatusWtpMngmtRadioprofilsEntry 23 }

-- {COLUMN} 1.3.6.1.4.1.2356.11.1.59.101.1.24
lcsStatusWtpMngmtRadioprofilsEntryAdaptiveRfOptimization OBJECT-TYPE
    SYNTAX     INTEGER {
                  eNo (0),
                  eYes (1)
            }
    MAX-ACCESS read-only
    STATUS     current
    DESCRIPTION
            "-- empty --"
    ::= { lcsStatusWtpMngmtRadioprofilsEntry 24 }

-- {COLUMN} 1.3.6.1.4.1.2356.11.1.59.101.1.25
lcsStatusWtpMngmtRadioprofilsEntryRxPacketSensReduction OBJECT-TYPE
    SYNTAX     Integer32 (0..255)
    MAX-ACCESS read-only
    STATUS     current
    DESCRIPTION
            "-- empty --"
    ::= { lcsStatusWtpMngmtRadioprofilsEntry 25 }

-- {TABLE} 1.3.6.1.4.1.2356.11.1.59.102
lcsStatusWtpMngmtRadioModeTable OBJECT-TYPE
    SYNTAX     SEQUENCE OF LcsStatusWtpMngmtRadioModeEntry
    MAX-ACCESS not-accessible
    STATUS     current
    DESCRIPTION
            ""
    ::= { lcsStatusWtpMngmt 102 }

-- {ROW} 1.3.6.1.4.1.2356.11.1.59.102.1
lcsStatusWtpMngmtRadioModeEntry OBJECT-TYPE
    SYNTAX     LcsStatusWtpMngmtRadioModeEntry
    MAX-ACCESS not-accessible
    STATUS     current
    DESCRIPTION
            ""
    INDEX {
            lcsStatusWtpMngmtRadioModeEntryIndex
          }
    ::= { lcsStatusWtpMngmtRadioModeTable 1 }

LcsStatusWtpMngmtRadioModeEntry ::= SEQUENCE {
            lcsStatusWtpMngmtRadioModeEntryIndex Integer32,
            lcsStatusWtpMngmtRadioModeEntryRadioMode INTEGER,
            lcsStatusWtpMngmtRadioModeEntryOperating INTEGER,
            lcsStatusWtpMngmtRadioModeEntryChannelList DisplayString,
            lcsStatusWtpMngmtRadioModeEntryRadioChannel INTEGER,
            lcsStatusWtpMngmtRadioModeEntryAllow40mhz INTEGER,
            lcsStatusWtpMngmtRadioModeEntryAntennaMask INTEGER,
            lcsStatusWtpMngmtRadioModeEntryAntennaGain Integer32,
            lcsStatusWtpMngmtRadioModeEntryTxPowerReduction Integer32,
            lcsStatusWtpMngmtRadioModeEntryMaxChannelBandwidth INTEGER,
            lcsStatusWtpMngmtRadioModeEntryRxPacketSensReduction Integer32
    }

-- {COLUMN} 1.3.6.1.4.1.2356.11.1.59.102.1.1
lcsStatusWtpMngmtRadioModeEntryIndex OBJECT-TYPE
    SYNTAX     Integer32 (0..255)
    MAX-ACCESS read-only
    STATUS     current
    DESCRIPTION
            ""
    ::= { lcsStatusWtpMngmtRadioModeEntry 1 }

-- {COLUMN} 1.3.6.1.4.1.2356.11.1.59.102.1.2
lcsStatusWtpMngmtRadioModeEntryRadioMode OBJECT-TYPE
    SYNTAX     INTEGER {
                  eDefault (0),
                  e24ghz (1),
                  e5ghz (2),
                  eOff (3),
                  eAuto (255)
            }
    MAX-ACCESS read-only
    STATUS     current
    DESCRIPTION
            ""
    ::= { lcsStatusWtpMngmtRadioModeEntry 2 }

-- {COLUMN} 1.3.6.1.4.1.2356.11.1.59.102.1.3
lcsStatusWtpMngmtRadioModeEntryOperating OBJECT-TYPE
    SYNTAX     INTEGER {
                  eYes (0),
                  eNo (1)
            }
    MAX-ACCESS read-only
    STATUS     current
    DESCRIPTION
            ""
    ::= { lcsStatusWtpMngmtRadioModeEntry 3 }

-- {COLUMN} 1.3.6.1.4.1.2356.11.1.59.102.1.4
lcsStatusWtpMngmtRadioModeEntryChannelList OBJECT-TYPE
    SYNTAX     DisplayString (SIZE(0..48))
    MAX-ACCESS read-only
    STATUS     current
    DESCRIPTION
            ""
    ::= { lcsStatusWtpMngmtRadioModeEntry 4 }

-- {COLUMN} 1.3.6.1.4.1.2356.11.1.59.102.1.5
lcsStatusWtpMngmtRadioModeEntryRadioChannel OBJECT-TYPE
    SYNTAX     INTEGER {
                  eAuto (0)
            }
    MAX-ACCESS read-only
    STATUS     current
    DESCRIPTION
            ""
    ::= { lcsStatusWtpMngmtRadioModeEntry 5 }

-- {COLUMN} 1.3.6.1.4.1.2356.11.1.59.102.1.6
lcsStatusWtpMngmtRadioModeEntryAllow40mhz OBJECT-TYPE
    SYNTAX     INTEGER {
                  eAuto (0),
                  eNo (1)
            }
    MAX-ACCESS read-only
    STATUS     current
    DESCRIPTION
            ""
    ::= { lcsStatusWtpMngmtRadioModeEntry 6 }

-- {COLUMN} 1.3.6.1.4.1.2356.11.1.59.102.1.7
lcsStatusWtpMngmtRadioModeEntryAntennaMask OBJECT-TYPE
    SYNTAX     INTEGER {
                  eAuto (0),
                  eAntenna1 (1),
                  eAntenna1Plus2 (3),
                  eAntenna1Plus3 (5),
                  eAntenna1Plus2Plus3 (7),
                  eAntenna1Plus2Plus3Plus4 (15)
            }
    MAX-ACCESS read-only
    STATUS     current
    DESCRIPTION
            ""
    ::= { lcsStatusWtpMngmtRadioModeEntry 7 }

-- {COLUMN} 1.3.6.1.4.1.2356.11.1.59.102.1.8
lcsStatusWtpMngmtRadioModeEntryAntennaGain OBJECT-TYPE
    SYNTAX     Integer32 (-128..127)
    MAX-ACCESS read-only
    STATUS     current
    DESCRIPTION
            ""
    ::= { lcsStatusWtpMngmtRadioModeEntry 8 }

-- {COLUMN} 1.3.6.1.4.1.2356.11.1.59.102.1.9
lcsStatusWtpMngmtRadioModeEntryTxPowerReduction OBJECT-TYPE
    SYNTAX     Integer32 (0..255)
    MAX-ACCESS read-only
    STATUS     current
    DESCRIPTION
            ""
    ::= { lcsStatusWtpMngmtRadioModeEntry 9 }

-- {COLUMN} 1.3.6.1.4.1.2356.11.1.59.102.1.10
lcsStatusWtpMngmtRadioModeEntryMaxChannelBandwidth OBJECT-TYPE
    SYNTAX     INTEGER {
                  e20mhz (0),
                  e40mhz (1),
                  e80mhz (2),
                  e160mhz (3),
                  e80Plus80mhz (4),
                  eAuto (255)
            }
    MAX-ACCESS read-only
    STATUS     current
    DESCRIPTION
            "-- empty --"
    ::= { lcsStatusWtpMngmtRadioModeEntry 10 }

-- {COLUMN} 1.3.6.1.4.1.2356.11.1.59.102.1.11
lcsStatusWtpMngmtRadioModeEntryRxPacketSensReduction OBJECT-TYPE
    SYNTAX     Integer32 (0..255)
    MAX-ACCESS read-only
    STATUS     current
    DESCRIPTION
            "-- empty --"
    ::= { lcsStatusWtpMngmtRadioModeEntry 11 }

-- {TABLE} 1.3.6.1.4.1.2356.11.1.59.103
lcsStatusWtpMngmtNetwprofilsTable OBJECT-TYPE
    SYNTAX     SEQUENCE OF LcsStatusWtpMngmtNetwprofilsEntry
    MAX-ACCESS not-accessible
    STATUS     current
    DESCRIPTION
            "network profiles"
    ::= { lcsStatusWtpMngmt 103 }

-- {ROW} 1.3.6.1.4.1.2356.11.1.59.103.1
lcsStatusWtpMngmtNetwprofilsEntry OBJECT-TYPE
    SYNTAX     LcsStatusWtpMngmtNetwprofilsEntry
    MAX-ACCESS not-accessible
    STATUS     current
    DESCRIPTION
            ""
    INDEX {
            lcsStatusWtpMngmtNetwprofilsEntryName
          }
    ::= { lcsStatusWtpMngmtNetwprofilsTable 1 }

LcsStatusWtpMngmtNetwprofilsEntry ::= SEQUENCE {
            lcsStatusWtpMngmtNetwprofilsEntryName DisplayString,
            lcsStatusWtpMngmtNetwprofilsEntryOperating INTEGER,
            lcsStatusWtpMngmtNetwprofilsEntryVlanId Integer32,
            lcsStatusWtpMngmtNetwprofilsEntryEncryption INTEGER,
            lcsStatusWtpMngmtNetwprofilsEntryWpa1SessionKeytypes INTEGER,
            lcsStatusWtpMngmtNetwprofilsEntryWpaVersion INTEGER,
            lcsStatusWtpMngmtNetwprofilsEntryKey DisplayString,
            lcsStatusWtpMngmtNetwprofilsEntryRadioBand INTEGER,
            lcsStatusWtpMngmtNetwprofilsEntryContinuation Integer32,
            lcsStatusWtpMngmtNetwprofilsEntryMinTxRate INTEGER,
            lcsStatusWtpMngmtNetwprofilsEntryMaxTxRate INTEGER,
            lcsStatusWtpMngmtNetwprofilsEntryBasicRate INTEGER,
            lcsStatusWtpMngmtNetwprofilsEntry11bPreamble INTEGER,
            lcsStatusWtpMngmtNetwprofilsEntryMacFilter INTEGER,
            lcsStatusWtpMngmtNetwprofilsEntryClBrgSupport INTEGER,
            lcsStatusWtpMngmtNetwprofilsEntryMaxStations Integer32,
            lcsStatusWtpMngmtNetwprofilsEntrySsidBroadcast INTEGER,
            lcsStatusWtpMngmtNetwprofilsEntryVlanTrunk Integer32,
            lcsStatusWtpMngmtNetwprofilsEntrySsid DisplayString,
            lcsStatusWtpMngmtNetwprofilsEntryMinHtMcs INTEGER,
            lcsStatusWtpMngmtNetwprofilsEntryMaxHtMcs INTEGER,
            lcsStatusWtpMngmtNetwprofilsEntryShortGuardInterval INTEGER,
            lcsStatusWtpMngmtNetwprofilsEntryMaxSpatialStreams INTEGER,
            lcsStatusWtpMngmtNetwprofilsEntrySendAggregates INTEGER,
            lcsStatusWtpMngmtNetwprofilsEntryWpa2SessionKeytypes INTEGER,
            lcsStatusWtpMngmtNetwprofilsEntryRadiusAccounting INTEGER,
            lcsStatusWtpMngmtNetwprofilsEntryVlanMode INTEGER,
            lcsStatusWtpMngmtNetwprofilsEntryConnectSsidTo INTEGER,
            lcsStatusWtpMngmtNetwprofilsEntryInterStationTraffic INTEGER,
            lcsStatusWtpMngmtNetwprofilsEntryVlanIdnew Integer32,
            lcsStatusWtpMngmtNetwprofilsEntryRadiusProfile DisplayString,
            lcsStatusWtpMngmtNetwprofilsEntryStbcActivated INTEGER,
            lcsStatusWtpMngmtNetwprofilsEntryLdpcActivated INTEGER,
            lcsStatusWtpMngmtNetwprofilsEntryMinClientStrength Integer32,
            lcsStatusWtpMngmtNetwprofilsEntryIeee80211uNetworkProfile DisplayString,
            lcsStatusWtpMngmtNetwprofilsEntryOkc INTEGER,
            lcsStatusWtpMngmtNetwprofilsEntryWpa2KeyManagement BITS,
            lcsStatusWtpMngmtNetwprofilsEntryApsd INTEGER,
            lcsStatusWtpMngmtNetwprofilsEntryProtMgmtFrames INTEGER,
            lcsStatusWtpMngmtNetwprofilsEntryTxLimit Integer32,
            lcsStatusWtpMngmtNetwprofilsEntryRxLimit Integer32,
            lcsStatusWtpMngmtNetwprofilsEntryLbsTracking INTEGER,
            lcsStatusWtpMngmtNetwprofilsEntryLbsTrackingList DisplayString,
            lcsStatusWtpMngmtNetwprofilsEntry11acBeamforming INTEGER,
            lcsStatusWtpMngmtNetwprofilsEntryConvertToUnicast BITS,
            lcsStatusWtpMngmtNetwprofilsEntryTransmitOnlyUnicasts INTEGER,
            lcsStatusWtpMngmtNetwprofilsEntryWpa23SessionKeytypes BITS,
            lcsStatusWtpMngmtNetwprofilsEntryWpa8021xSecurityLevel INTEGER,
            lcsStatusWtpMngmtNetwprofilsEntryPerClientTxLimit Integer32,
            lcsStatusWtpMngmtNetwprofilsEntryPerClientRxLimit Integer32,
            lcsStatusWtpMngmtNetwprofilsEntryTimeframe DisplayString,
            lcsStatusWtpMngmtNetwprofilsEntryMinClDisStr Integer32
    }

-- {COLUMN} 1.3.6.1.4.1.2356.11.1.59.103.1.1
lcsStatusWtpMngmtNetwprofilsEntryName OBJECT-TYPE
    SYNTAX     DisplayString (SIZE(0..31))
    MAX-ACCESS read-only
    STATUS     current
    DESCRIPTION
            ""
    ::= { lcsStatusWtpMngmtNetwprofilsEntry 1 }

-- {COLUMN} 1.3.6.1.4.1.2356.11.1.59.103.1.4
lcsStatusWtpMngmtNetwprofilsEntryOperating OBJECT-TYPE
    SYNTAX     INTEGER {
                  eYes (0),
                  eNo (1)
            }
    MAX-ACCESS read-only
    STATUS     current
    DESCRIPTION
            ""
    ::= { lcsStatusWtpMngmtNetwprofilsEntry 4 }

-- {COLUMN} 1.3.6.1.4.1.2356.11.1.59.103.1.5
lcsStatusWtpMngmtNetwprofilsEntryVlanId OBJECT-TYPE
    SYNTAX     Integer32 (0..65535)
    MAX-ACCESS read-only
    STATUS     obsolete
    DESCRIPTION
            ""
    ::= { lcsStatusWtpMngmtNetwprofilsEntry 5 }

-- {COLUMN} 1.3.6.1.4.1.2356.11.1.59.103.1.6
lcsStatusWtpMngmtNetwprofilsEntryEncryption OBJECT-TYPE
    SYNTAX     INTEGER {
                  e80211iWpaPsk (0),
                  e80211iWpa8021x (1),
                  eWep104Bits (2),
                  eWep40Bits (3),
                  eWep104Bits8021x (4),
                  eWep40Bits8021x (5),
                  eNone (6),
                  eWPA-OWE (7),
                  eEnhancedOpenTransitional (8)
            }
    MAX-ACCESS read-only
    STATUS     current
    DESCRIPTION
            ""
    ::= { lcsStatusWtpMngmtNetwprofilsEntry 6 }

-- {COLUMN} 1.3.6.1.4.1.2356.11.1.59.103.1.7
lcsStatusWtpMngmtNetwprofilsEntryWpa1SessionKeytypes OBJECT-TYPE
    SYNTAX     INTEGER {
                  eTkipAes (0),
                  eAes (1),
                  eTkip (2)
            }
    MAX-ACCESS read-only
    STATUS     current
    DESCRIPTION
            ""
    ::= { lcsStatusWtpMngmtNetwprofilsEntry 7 }

-- {COLUMN} 1.3.6.1.4.1.2356.11.1.59.103.1.8
lcsStatusWtpMngmtNetwprofilsEntryWpaVersion OBJECT-TYPE
    SYNTAX     INTEGER {
                  eWpa12 (0),
                  eWpa1 (1),
                  eWpa2 (2),
                  eWpa3 (3),
                  eWpa23 (4),
                  eWpa123 (5)
            }
    MAX-ACCESS read-only
    STATUS     current
    DESCRIPTION
            ""
    ::= { lcsStatusWtpMngmtNetwprofilsEntry 8 }

-- {COLUMN} 1.3.6.1.4.1.2356.11.1.59.103.1.9
lcsStatusWtpMngmtNetwprofilsEntryKey OBJECT-TYPE
    SYNTAX     DisplayString (SIZE(0..63))
    MAX-ACCESS read-only
    STATUS     current
    DESCRIPTION
            ""
    ::= { lcsStatusWtpMngmtNetwprofilsEntry 9 }

-- {COLUMN} 1.3.6.1.4.1.2356.11.1.59.103.1.10
lcsStatusWtpMngmtNetwprofilsEntryRadioBand OBJECT-TYPE
    SYNTAX     INTEGER {
                  e24ghz5ghz (0),
                  e24ghz (1),
                  e5ghz (2)
            }
    MAX-ACCESS read-only
    STATUS     current
    DESCRIPTION
            ""
    ::= { lcsStatusWtpMngmtNetwprofilsEntry 10 }

-- {COLUMN} 1.3.6.1.4.1.2356.11.1.59.103.1.11
lcsStatusWtpMngmtNetwprofilsEntryContinuation OBJECT-TYPE
    SYNTAX     Integer32 (0..65535)
    MAX-ACCESS read-only
    STATUS     current
    DESCRIPTION
            ""
    ::= { lcsStatusWtpMngmtNetwprofilsEntry 11 }

-- {COLUMN} 1.3.6.1.4.1.2356.11.1.59.103.1.12
lcsStatusWtpMngmtNetwprofilsEntryMinTxRate OBJECT-TYPE
    SYNTAX     INTEGER {
                  eAuto (0),
                  e1M (1),
                  e2M (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-only
    STATUS     current
    DESCRIPTION
            ""
    ::= { lcsStatusWtpMngmtNetwprofilsEntry 12 }

-- {COLUMN} 1.3.6.1.4.1.2356.11.1.59.103.1.13
lcsStatusWtpMngmtNetwprofilsEntryMaxTxRate OBJECT-TYPE
    SYNTAX     INTEGER {
                  eAuto (0),
                  e1M (1),
                  e2M (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-only
    STATUS     current
    DESCRIPTION
            ""
    ::= { lcsStatusWtpMngmtNetwprofilsEntry 13 }

-- {COLUMN} 1.3.6.1.4.1.2356.11.1.59.103.1.14
lcsStatusWtpMngmtNetwprofilsEntryBasicRate OBJECT-TYPE
    SYNTAX     INTEGER {
                  e2M (0),
                  e1M (1),
                  eAuto (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-only
    STATUS     current
    DESCRIPTION
            ""
    ::= { lcsStatusWtpMngmtNetwprofilsEntry 14 }

-- {COLUMN} 1.3.6.1.4.1.2356.11.1.59.103.1.15
lcsStatusWtpMngmtNetwprofilsEntry11bPreamble OBJECT-TYPE
    SYNTAX     INTEGER {
                  eAuto (0),
                  eLong (1)
            }
    MAX-ACCESS read-only
    STATUS     current
    DESCRIPTION
            ""
    ::= { lcsStatusWtpMngmtNetwprofilsEntry 15 }

-- {COLUMN} 1.3.6.1.4.1.2356.11.1.59.103.1.16
lcsStatusWtpMngmtNetwprofilsEntryMacFilter OBJECT-TYPE
    SYNTAX     INTEGER {
                  eNo (0),
                  eYes (1)
            }
    MAX-ACCESS read-only
    STATUS     current
    DESCRIPTION
            ""
    ::= { lcsStatusWtpMngmtNetwprofilsEntry 16 }

-- {COLUMN} 1.3.6.1.4.1.2356.11.1.59.103.1.17
lcsStatusWtpMngmtNetwprofilsEntryClBrgSupport OBJECT-TYPE
    SYNTAX     INTEGER {
                  eNo (0),
                  eYes (1),
                  eExclusive (2)
            }
    MAX-ACCESS read-only
    STATUS     current
    DESCRIPTION
            ""
    ::= { lcsStatusWtpMngmtNetwprofilsEntry 17 }

-- {COLUMN} 1.3.6.1.4.1.2356.11.1.59.103.1.18
lcsStatusWtpMngmtNetwprofilsEntryMaxStations OBJECT-TYPE
    SYNTAX     Integer32 (0..65535)
    MAX-ACCESS read-only
    STATUS     current
    DESCRIPTION
            ""
    ::= { lcsStatusWtpMngmtNetwprofilsEntry 18 }

-- {COLUMN} 1.3.6.1.4.1.2356.11.1.59.103.1.19
lcsStatusWtpMngmtNetwprofilsEntrySsidBroadcast OBJECT-TYPE
    SYNTAX     INTEGER {
                  eYes (0),
                  eNo (1),
                  eTightened (2)
            }
    MAX-ACCESS read-only
    STATUS     current
    DESCRIPTION
            ""
    ::= { lcsStatusWtpMngmtNetwprofilsEntry 19 }

-- {COLUMN} 1.3.6.1.4.1.2356.11.1.59.103.1.20
lcsStatusWtpMngmtNetwprofilsEntryVlanTrunk OBJECT-TYPE
    SYNTAX     Integer32 (0..65535)
    MAX-ACCESS read-only
    STATUS     current
    DESCRIPTION
            ""
    ::= { lcsStatusWtpMngmtNetwprofilsEntry 20 }

-- {COLUMN} 1.3.6.1.4.1.2356.11.1.59.103.1.21
lcsStatusWtpMngmtNetwprofilsEntrySsid OBJECT-TYPE
    SYNTAX     DisplayString (SIZE(0..32))
    MAX-ACCESS read-only
    STATUS     current
    DESCRIPTION
            ""
    ::= { lcsStatusWtpMngmtNetwprofilsEntry 21 }

-- {COLUMN} 1.3.6.1.4.1.2356.11.1.59.103.1.22
lcsStatusWtpMngmtNetwprofilsEntryMinHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-only
    STATUS     current
    DESCRIPTION
            ""
    ::= { lcsStatusWtpMngmtNetwprofilsEntry 22 }

-- {COLUMN} 1.3.6.1.4.1.2356.11.1.59.103.1.23
lcsStatusWtpMngmtNetwprofilsEntryMaxHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-only
    STATUS     current
    DESCRIPTION
            ""
    ::= { lcsStatusWtpMngmtNetwprofilsEntry 23 }

-- {COLUMN} 1.3.6.1.4.1.2356.11.1.59.103.1.24
lcsStatusWtpMngmtNetwprofilsEntryShortGuardInterval OBJECT-TYPE
    SYNTAX     INTEGER {
                  eAuto (0),
                  eNo (1)
            }
    MAX-ACCESS read-only
    STATUS     current
    DESCRIPTION
            ""
    ::= { lcsStatusWtpMngmtNetwprofilsEntry 24 }

-- {COLUMN} 1.3.6.1.4.1.2356.11.1.59.103.1.25
lcsStatusWtpMngmtNetwprofilsEntryMaxSpatialStreams OBJECT-TYPE
    SYNTAX     INTEGER {
                  eAuto (0),
                  eOne (1),
                  eTwo (2),
                  eThree (3),
                  eFour (4)
            }
    MAX-ACCESS read-only
    STATUS     current
    DESCRIPTION
            ""
    ::= { lcsStatusWtpMngmtNetwprofilsEntry 25 }

-- {COLUMN} 1.3.6.1.4.1.2356.11.1.59.103.1.26
lcsStatusWtpMngmtNetwprofilsEntrySendAggregates OBJECT-TYPE
    SYNTAX     INTEGER {
                  eNo (0),
                  eYes (1)
            }
    MAX-ACCESS read-only
    STATUS     current
    DESCRIPTION
            ""
    ::= { lcsStatusWtpMngmtNetwprofilsEntry 26 }

-- {COLUMN} 1.3.6.1.4.1.2356.11.1.59.103.1.27
lcsStatusWtpMngmtNetwprofilsEntryWpa2SessionKeytypes OBJECT-TYPE
    SYNTAX     INTEGER {
                  eTkipAes (0),
                  eAes (1),
                  eTkip (2)
            }
    MAX-ACCESS read-only
    STATUS     current
    DESCRIPTION
            ""
    ::= { lcsStatusWtpMngmtNetwprofilsEntry 27 }

-- {COLUMN} 1.3.6.1.4.1.2356.11.1.59.103.1.28
lcsStatusWtpMngmtNetwprofilsEntryRadiusAccounting OBJECT-TYPE
    SYNTAX     INTEGER {
                  eNo (0),
                  eYes (1)
            }
    MAX-ACCESS read-only
    STATUS     current
    DESCRIPTION
            ""
    ::= { lcsStatusWtpMngmtNetwprofilsEntry 28 }

-- {COLUMN} 1.3.6.1.4.1.2356.11.1.59.103.1.30
lcsStatusWtpMngmtNetwprofilsEntryVlanMode OBJECT-TYPE
    SYNTAX     INTEGER {
                  eUntagged (0),
                  eTagged (1)
            }
    MAX-ACCESS read-only
    STATUS     current
    DESCRIPTION
            ""
    ::= { lcsStatusWtpMngmtNetwprofilsEntry 30 }

-- {COLUMN} 1.3.6.1.4.1.2356.11.1.59.103.1.32
lcsStatusWtpMngmtNetwprofilsEntryConnectSsidTo OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-only
    STATUS     current
    DESCRIPTION
            ""
    ::= { lcsStatusWtpMngmtNetwprofilsEntry 32 }

-- {COLUMN} 1.3.6.1.4.1.2356.11.1.59.103.1.33
lcsStatusWtpMngmtNetwprofilsEntryInterStationTraffic OBJECT-TYPE
    SYNTAX     INTEGER {
                  eNo (0),
                  eYes (1)
            }
    MAX-ACCESS read-only
    STATUS     current
    DESCRIPTION
            ""
    ::= { lcsStatusWtpMngmtNetwprofilsEntry 33 }

-- {COLUMN} 1.3.6.1.4.1.2356.11.1.59.103.1.34
lcsStatusWtpMngmtNetwprofilsEntryVlanIdnew OBJECT-TYPE
    SYNTAX     Integer32 (0..65535)
    MAX-ACCESS read-only
    STATUS     current
    DESCRIPTION
            ""
    ::= { lcsStatusWtpMngmtNetwprofilsEntry 34 }

-- {COLUMN} 1.3.6.1.4.1.2356.11.1.59.103.1.35
lcsStatusWtpMngmtNetwprofilsEntryRadiusProfile OBJECT-TYPE
    SYNTAX     DisplayString (SIZE(0..16))
    MAX-ACCESS read-only
    STATUS     current
    DESCRIPTION
            "-- empty --"
    ::= { lcsStatusWtpMngmtNetwprofilsEntry 35 }

-- {COLUMN} 1.3.6.1.4.1.2356.11.1.59.103.1.36
lcsStatusWtpMngmtNetwprofilsEntryStbcActivated OBJECT-TYPE
    SYNTAX     INTEGER {
                  eNo (0),
                  eYes (1)
            }
    MAX-ACCESS read-only
    STATUS     current
    DESCRIPTION
            "-- empty --"
    ::= { lcsStatusWtpMngmtNetwprofilsEntry 36 }

-- {COLUMN} 1.3.6.1.4.1.2356.11.1.59.103.1.37
lcsStatusWtpMngmtNetwprofilsEntryLdpcActivated OBJECT-TYPE
    SYNTAX     INTEGER {
                  eNo (0),
                  eYes (1)
            }
    MAX-ACCESS read-only
    STATUS     current
    DESCRIPTION
            "-- empty --"
    ::= { lcsStatusWtpMngmtNetwprofilsEntry 37 }

-- {COLUMN} 1.3.6.1.4.1.2356.11.1.59.103.1.38
lcsStatusWtpMngmtNetwprofilsEntryMinClientStrength OBJECT-TYPE
    SYNTAX     Integer32 (0..255)
    MAX-ACCESS read-only
    STATUS     current
    DESCRIPTION
            "-- empty --"
    ::= { lcsStatusWtpMngmtNetwprofilsEntry 38 }

-- {COLUMN} 1.3.6.1.4.1.2356.11.1.59.103.1.39
lcsStatusWtpMngmtNetwprofilsEntryIeee80211uNetworkProfile OBJECT-TYPE
    SYNTAX     DisplayString (SIZE(0..32))
    MAX-ACCESS read-only
    STATUS     current
    DESCRIPTION
            "-- empty --"
    ::= { lcsStatusWtpMngmtNetwprofilsEntry 39 }

-- {COLUMN} 1.3.6.1.4.1.2356.11.1.59.103.1.40
lcsStatusWtpMngmtNetwprofilsEntryOkc OBJECT-TYPE
    SYNTAX     INTEGER {
                  eNo (0),
                  eYes (1)
            }
    MAX-ACCESS read-only
    STATUS     current
    DESCRIPTION
            "-- empty --"
    ::= { lcsStatusWtpMngmtNetwprofilsEntry 40 }

-- {COLUMN} 1.3.6.1.4.1.2356.11.1.59.103.1.41
lcsStatusWtpMngmtNetwprofilsEntryWpa2KeyManagement OBJECT-TYPE
    SYNTAX     BITS {
                  eSha256 (5),
                  eFastRoaming (6),
                  eStandard (7)
            }
    MAX-ACCESS read-only
    STATUS     current
    DESCRIPTION
            "-- empty --"
    ::= { lcsStatusWtpMngmtNetwprofilsEntry 41 }

-- {COLUMN} 1.3.6.1.4.1.2356.11.1.59.103.1.42
lcsStatusWtpMngmtNetwprofilsEntryApsd OBJECT-TYPE
    SYNTAX     INTEGER {
                  eNo (0),
                  eYes (1)
            }
    MAX-ACCESS read-only
    STATUS     current
    DESCRIPTION
            "-- empty --"
    ::= { lcsStatusWtpMngmtNetwprofilsEntry 42 }

-- {COLUMN} 1.3.6.1.4.1.2356.11.1.59.103.1.43
lcsStatusWtpMngmtNetwprofilsEntryProtMgmtFrames OBJECT-TYPE
    SYNTAX     INTEGER {
                  eNo (0),
                  eOptional (1),
                  eMandatory (2)
            }
    MAX-ACCESS read-only
    STATUS     current
    DESCRIPTION
            "-- empty --"
    ::= { lcsStatusWtpMngmtNetwprofilsEntry 43 }

-- {COLUMN} 1.3.6.1.4.1.2356.11.1.59.103.1.44
lcsStatusWtpMngmtNetwprofilsEntryTxLimit OBJECT-TYPE
    SYNTAX     Integer32 (0..2147483647)
    MAX-ACCESS read-only
    STATUS     current
    DESCRIPTION
            "-- empty --"
    ::= { lcsStatusWtpMngmtNetwprofilsEntry 44 }

-- {COLUMN} 1.3.6.1.4.1.2356.11.1.59.103.1.45
lcsStatusWtpMngmtNetwprofilsEntryRxLimit OBJECT-TYPE
    SYNTAX     Integer32 (0..2147483647)
    MAX-ACCESS read-only
    STATUS     current
    DESCRIPTION
            "-- empty --"
    ::= { lcsStatusWtpMngmtNetwprofilsEntry 45 }

-- {COLUMN} 1.3.6.1.4.1.2356.11.1.59.103.1.46
lcsStatusWtpMngmtNetwprofilsEntryLbsTracking OBJECT-TYPE
    SYNTAX     INTEGER {
                  eNo (0),
                  eYes (1)
            }
    MAX-ACCESS read-only
    STATUS     current
    DESCRIPTION
            "-- empty --"
    ::= { lcsStatusWtpMngmtNetwprofilsEntry 46 }

-- {COLUMN} 1.3.6.1.4.1.2356.11.1.59.103.1.47
lcsStatusWtpMngmtNetwprofilsEntryLbsTrackingList OBJECT-TYPE
    SYNTAX     DisplayString (SIZE(0..32))
    MAX-ACCESS read-only
    STATUS     current
    DESCRIPTION
            "-- empty --"
    ::= { lcsStatusWtpMngmtNetwprofilsEntry 47 }

-- {COLUMN} 1.3.6.1.4.1.2356.11.1.59.103.1.49
lcsStatusWtpMngmtNetwprofilsEntry11acBeamforming OBJECT-TYPE
    SYNTAX     INTEGER {
                  eAuto (0),
                  eNo (1),
                  eSuMimo (2),
                  eMuMimo (3)
            }
    MAX-ACCESS read-only
    STATUS     current
    DESCRIPTION
            "-- empty --"
    ::= { lcsStatusWtpMngmtNetwprofilsEntry 49 }

-- {COLUMN} 1.3.6.1.4.1.2356.11.1.59.103.1.50
lcsStatusWtpMngmtNetwprofilsEntryConvertToUnicast OBJECT-TYPE
    SYNTAX     BITS {
                  eMulticast (14),
                  eDhcp (15)
            }
    MAX-ACCESS read-only
    STATUS     current
    DESCRIPTION
            "-- empty --"
    ::= { lcsStatusWtpMngmtNetwprofilsEntry 50 }

-- {COLUMN} 1.3.6.1.4.1.2356.11.1.59.103.1.51
lcsStatusWtpMngmtNetwprofilsEntryTransmitOnlyUnicasts OBJECT-TYPE
    SYNTAX     INTEGER {
                  eNo (0),
                  eYes (1)
            }
    MAX-ACCESS read-only
    STATUS     current
    DESCRIPTION
            "-- empty --"
    ::= { lcsStatusWtpMngmtNetwprofilsEntry 51 }

-- {COLUMN} 1.3.6.1.4.1.2356.11.1.59.103.1.53
lcsStatusWtpMngmtNetwprofilsEntryWpa23SessionKeytypes OBJECT-TYPE
    SYNTAX     BITS {
                  eAesGcmp256 (2),
                  eAesGcmp128 (3),
                  eAesCcmp256 (4),
                  eAesCcm (5),
                  eTkip (6)
            }
    MAX-ACCESS read-only
    STATUS     current
    DESCRIPTION
            "-- empty --"
    ::= { lcsStatusWtpMngmtNetwprofilsEntry 53 }

-- {COLUMN} 1.3.6.1.4.1.2356.11.1.59.103.1.54
lcsStatusWtpMngmtNetwprofilsEntryWpa8021xSecurityLevel OBJECT-TYPE
    SYNTAX     INTEGER {
                  eStandard (0),
                  eSuiteB128Bits (1),
                  eSuiteB192Bits (2)
            }
    MAX-ACCESS read-only
    STATUS     current
    DESCRIPTION
            "-- empty --"
    ::= { lcsStatusWtpMngmtNetwprofilsEntry 54 }

-- {COLUMN} 1.3.6.1.4.1.2356.11.1.59.103.1.55
lcsStatusWtpMngmtNetwprofilsEntryPerClientTxLimit OBJECT-TYPE
    SYNTAX     Integer32 (0..2147483647)
    MAX-ACCESS read-only
    STATUS     current
    DESCRIPTION
            "-- empty --"
    ::= { lcsStatusWtpMngmtNetwprofilsEntry 55 }

-- {COLUMN} 1.3.6.1.4.1.2356.11.1.59.103.1.56
lcsStatusWtpMngmtNetwprofilsEntryPerClientRxLimit OBJECT-TYPE
    SYNTAX     Integer32 (0..2147483647)
    MAX-ACCESS read-only
    STATUS     current
    DESCRIPTION
            "-- empty --"
    ::= { lcsStatusWtpMngmtNetwprofilsEntry 56 }

-- {COLUMN} 1.3.6.1.4.1.2356.11.1.59.103.1.57
lcsStatusWtpMngmtNetwprofilsEntryTimeframe OBJECT-TYPE
    SYNTAX     DisplayString (SIZE(0..31))
    MAX-ACCESS read-only
    STATUS     current
    DESCRIPTION
            "-- empty --"
    ::= { lcsStatusWtpMngmtNetwprofilsEntry 57 }

-- {COLUMN} 1.3.6.1.4.1.2356.11.1.59.103.1.58
lcsStatusWtpMngmtNetwprofilsEntryMinClDisStr OBJECT-TYPE
    SYNTAX     Integer32 (0..255)
    MAX-ACCESS read-only
    STATUS     current
    DESCRIPTION
            ""
    ::= { lcsStatusWtpMngmtNetwprofilsEntry 58 }

-- {TABLE} 1.3.6.1.4.1.2356.11.1.59.104
lcsStatusWtpMngmtApBridgeInterfacesTable OBJECT-TYPE
    SYNTAX     SEQUENCE OF LcsStatusWtpMngmtApBridgeInterfacesEntry
    MAX-ACCESS not-accessible
    STATUS     current
    DESCRIPTION
            ""
    ::= { lcsStatusWtpMngmt 104 }

-- {ROW} 1.3.6.1.4.1.2356.11.1.59.104.1
lcsStatusWtpMngmtApBridgeInterfacesEntry OBJECT-TYPE
    SYNTAX     LcsStatusWtpMngmtApBridgeInterfacesEntry
    MAX-ACCESS not-accessible
    STATUS     current
    DESCRIPTION
            ""
    INDEX {
            lcsStatusWtpMngmtApBridgeInterfacesEntryBridgeInterface
          }
    ::= { lcsStatusWtpMngmtApBridgeInterfacesTable 1 }

LcsStatusWtpMngmtApBridgeInterfacesEntry ::= SEQUENCE {
            lcsStatusWtpMngmtApBridgeInterfacesEntryBridgeInterface INTEGER,
            lcsStatusWtpMngmtApBridgeInterfacesEntryRegisteredConnections Integer32,
            lcsStatusWtpMngmtApBridgeInterfacesEntryRecvUnicasts Integer32,
            lcsStatusWtpMngmtApBridgeInterfacesEntryRecvMulticasts Integer32,
            lcsStatusWtpMngmtApBridgeInterfacesEntryRecvBroadcasts Integer32,
            lcsStatusWtpMngmtApBridgeInterfacesEntryTransUnicastPackets Integer32,
            lcsStatusWtpMngmtApBridgeInterfacesEntryTransMultiBroadPckts Integer32,
            lcsStatusWtpMngmtApBridgeInterfacesEntryDroppedPackets Integer32,
            lcsStatusWtpMngmtApBridgeInterfacesEntryTxBytes Counter64,
            lcsStatusWtpMngmtApBridgeInterfacesEntryRxBytes Counter64,
            lcsStatusWtpMngmtApBridgeInterfacesEntryThroughput DisplayString,
            lcsStatusWtpMngmtApBridgeInterfacesEntryMaxThroughput DisplayString
    }

-- {COLUMN} 1.3.6.1.4.1.2356.11.1.59.104.1.1
lcsStatusWtpMngmtApBridgeInterfacesEntryBridgeInterface OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-only
    STATUS     current
    DESCRIPTION
            ""
    ::= { lcsStatusWtpMngmtApBridgeInterfacesEntry 1 }

-- {COLUMN} 1.3.6.1.4.1.2356.11.1.59.104.1.2
lcsStatusWtpMngmtApBridgeInterfacesEntryRegisteredConnections OBJECT-TYPE
    SYNTAX     Integer32 (0..2147483647)
    MAX-ACCESS read-only
    STATUS     current
    DESCRIPTION
            ""
    ::= { lcsStatusWtpMngmtApBridgeInterfacesEntry 2 }

-- {COLUMN} 1.3.6.1.4.1.2356.11.1.59.104.1.3
lcsStatusWtpMngmtApBridgeInterfacesEntryRecvUnicasts OBJECT-TYPE
    SYNTAX     Integer32 (0..2147483647)
    MAX-ACCESS read-only
    STATUS     current
    DESCRIPTION
            ""
    ::= { lcsStatusWtpMngmtApBridgeInterfacesEntry 3 }

-- {COLUMN} 1.3.6.1.4.1.2356.11.1.59.104.1.4
lcsStatusWtpMngmtApBridgeInterfacesEntryRecvMulticasts OBJECT-TYPE
    SYNTAX     Integer32 (0..2147483647)
    MAX-ACCESS read-only
    STATUS     current
    DESCRIPTION
            ""
    ::= { lcsStatusWtpMngmtApBridgeInterfacesEntry 4 }

-- {COLUMN} 1.3.6.1.4.1.2356.11.1.59.104.1.5
lcsStatusWtpMngmtApBridgeInterfacesEntryRecvBroadcasts OBJECT-TYPE
    SYNTAX     Integer32 (0..2147483647)
    MAX-ACCESS read-only
    STATUS     current
    DESCRIPTION
            ""
    ::= { lcsStatusWtpMngmtApBridgeInterfacesEntry 5 }

-- {COLUMN} 1.3.6.1.4.1.2356.11.1.59.104.1.6
lcsStatusWtpMngmtApBridgeInterfacesEntryTransUnicastPackets OBJECT-TYPE
    SYNTAX     Integer32 (0..2147483647)
    MAX-ACCESS read-only
    STATUS     current
    DESCRIPTION
            ""
    ::= { lcsStatusWtpMngmtApBridgeInterfacesEntry 6 }

-- {COLUMN} 1.3.6.1.4.1.2356.11.1.59.104.1.7
lcsStatusWtpMngmtApBridgeInterfacesEntryTransMultiBroadPckts OBJECT-TYPE
    SYNTAX     Integer32 (0..2147483647)
    MAX-ACCESS read-only
    STATUS     current
    DESCRIPTION
            ""
    ::= { lcsStatusWtpMngmtApBridgeInterfacesEntry 7 }

-- {COLUMN} 1.3.6.1.4.1.2356.11.1.59.104.1.8
lcsStatusWtpMngmtApBridgeInterfacesEntryDroppedPackets OBJECT-TYPE
    SYNTAX     Integer32 (0..2147483647)
    MAX-ACCESS read-only
    STATUS     current
    DESCRIPTION
            ""
    ::= { lcsStatusWtpMngmtApBridgeInterfacesEntry 8 }

-- {COLUMN} 1.3.6.1.4.1.2356.11.1.59.104.1.10
lcsStatusWtpMngmtApBridgeInterfacesEntryTxBytes OBJECT-TYPE
    SYNTAX     Counter64
    MAX-ACCESS read-only
    STATUS     current
    DESCRIPTION
            "-- empty --"
    ::= { lcsStatusWtpMngmtApBridgeInterfacesEntry 10 }

-- {COLUMN} 1.3.6.1.4.1.2356.11.1.59.104.1.11
lcsStatusWtpMngmtApBridgeInterfacesEntryRxBytes OBJECT-TYPE
    SYNTAX     Counter64
    MAX-ACCESS read-only
    STATUS     current
    DESCRIPTION
            "-- empty --"
    ::= { lcsStatusWtpMngmtApBridgeInterfacesEntry 11 }

-- {COLUMN} 1.3.6.1.4.1.2356.11.1.59.104.1.12
lcsStatusWtpMngmtApBridgeInterfacesEntryThroughput OBJECT-TYPE
    SYNTAX     DisplayString (SIZE(0..255))
    MAX-ACCESS read-only
    STATUS     current
    DESCRIPTION
            "-- empty --"
    ::= { lcsStatusWtpMngmtApBridgeInterfacesEntry 12 }

-- {COLUMN} 1.3.6.1.4.1.2356.11.1.59.104.1.13
lcsStatusWtpMngmtApBridgeInterfacesEntryMaxThroughput OBJECT-TYPE
    SYNTAX     DisplayString (SIZE(0..255))
    MAX-ACCESS read-only
    STATUS     current
    DESCRIPTION
            "-- empty --"
    ::= { lcsStatusWtpMngmtApBridgeInterfacesEntry 13 }

-- {TABLE} 1.3.6.1.4.1.2356.11.1.59.105
lcsStatusWtpMngmtRadiusServerProfilesTable OBJECT-TYPE
    SYNTAX     SEQUENCE OF LcsStatusWtpMngmtRadiusServerProfilesEntry
    MAX-ACCESS not-accessible
    STATUS     current
    DESCRIPTION
            "-- empty --"
    ::= { lcsStatusWtpMngmt 105 }

-- {ROW} 1.3.6.1.4.1.2356.11.1.59.105.1
lcsStatusWtpMngmtRadiusServerProfilesEntry OBJECT-TYPE
    SYNTAX     LcsStatusWtpMngmtRadiusServerProfilesEntry
    MAX-ACCESS not-accessible
    STATUS     current
    DESCRIPTION
            ""
    INDEX {
            lcsStatusWtpMngmtRadiusServerProfilesEntryName
          }
    ::= { lcsStatusWtpMngmtRadiusServerProfilesTable 1 }

LcsStatusWtpMngmtRadiusServerProfilesEntry ::= SEQUENCE {
            lcsStatusWtpMngmtRadiusServerProfilesEntryName DisplayString,
            lcsStatusWtpMngmtRadiusServerProfilesEntryAccountIp IpAddress,
            lcsStatusWtpMngmtRadiusServerProfilesEntryAccountPort Integer32,
            lcsStatusWtpMngmtRadiusServerProfilesEntryAccountSecret DisplayString,
            lcsStatusWtpMngmtRadiusServerProfilesEntryAccountLoopback DisplayString,
            lcsStatusWtpMngmtRadiusServerProfilesEntryAccountProtocol INTEGER,
            lcsStatusWtpMngmtRadiusServerProfilesEntryAccessIp IpAddress,
            lcsStatusWtpMngmtRadiusServerProfilesEntryAccessPort Integer32,
            lcsStatusWtpMngmtRadiusServerProfilesEntryAccessSecret DisplayString,
            lcsStatusWtpMngmtRadiusServerProfilesEntryAccessLoopback DisplayString,
            lcsStatusWtpMngmtRadiusServerProfilesEntryAccessProtocol INTEGER,
            lcsStatusWtpMngmtRadiusServerProfilesEntryBackup DisplayString
    }

-- {COLUMN} 1.3.6.1.4.1.2356.11.1.59.105.1.1
lcsStatusWtpMngmtRadiusServerProfilesEntryName OBJECT-TYPE
    SYNTAX     DisplayString (SIZE(0..16))
    MAX-ACCESS read-only
    STATUS     current
    DESCRIPTION
            "-- empty --"
    ::= { lcsStatusWtpMngmtRadiusServerProfilesEntry 1 }

-- {COLUMN} 1.3.6.1.4.1.2356.11.1.59.105.1.2
lcsStatusWtpMngmtRadiusServerProfilesEntryAccountIp OBJECT-TYPE
    SYNTAX     IpAddress
    MAX-ACCESS read-only
    STATUS     current
    DESCRIPTION
            "-- empty --"
    ::= { lcsStatusWtpMngmtRadiusServerProfilesEntry 2 }

-- {COLUMN} 1.3.6.1.4.1.2356.11.1.59.105.1.3
lcsStatusWtpMngmtRadiusServerProfilesEntryAccountPort OBJECT-TYPE
    SYNTAX     Integer32 (0..65535)
    MAX-ACCESS read-only
    STATUS     current
    DESCRIPTION
            "-- empty --"
    ::= { lcsStatusWtpMngmtRadiusServerProfilesEntry 3 }

-- {COLUMN} 1.3.6.1.4.1.2356.11.1.59.105.1.4
lcsStatusWtpMngmtRadiusServerProfilesEntryAccountSecret OBJECT-TYPE
    SYNTAX     DisplayString (SIZE(0..64))
    MAX-ACCESS read-only
    STATUS     current
    DESCRIPTION
            "-- empty --"
    ::= { lcsStatusWtpMngmtRadiusServerProfilesEntry 4 }

-- {COLUMN} 1.3.6.1.4.1.2356.11.1.59.105.1.5
lcsStatusWtpMngmtRadiusServerProfilesEntryAccountLoopback OBJECT-TYPE
    SYNTAX     DisplayString (SIZE(0..16))
    MAX-ACCESS read-only
    STATUS     current
    DESCRIPTION
            "-- empty --"
    ::= { lcsStatusWtpMngmtRadiusServerProfilesEntry 5 }

-- {COLUMN} 1.3.6.1.4.1.2356.11.1.59.105.1.6
lcsStatusWtpMngmtRadiusServerProfilesEntryAccountProtocol OBJECT-TYPE
    SYNTAX     INTEGER {
                  eRadius (0),
                  eRadsec (1)
            }
    MAX-ACCESS read-only
    STATUS     current
    DESCRIPTION
            "-- empty --"
    ::= { lcsStatusWtpMngmtRadiusServerProfilesEntry 6 }

-- {COLUMN} 1.3.6.1.4.1.2356.11.1.59.105.1.7
lcsStatusWtpMngmtRadiusServerProfilesEntryAccessIp OBJECT-TYPE
    SYNTAX     IpAddress
    MAX-ACCESS read-only
    STATUS     current
    DESCRIPTION
            "-- empty --"
    ::= { lcsStatusWtpMngmtRadiusServerProfilesEntry 7 }

-- {COLUMN} 1.3.6.1.4.1.2356.11.1.59.105.1.8
lcsStatusWtpMngmtRadiusServerProfilesEntryAccessPort OBJECT-TYPE
    SYNTAX     Integer32 (0..65535)
    MAX-ACCESS read-only
    STATUS     current
    DESCRIPTION
            "-- empty --"
    ::= { lcsStatusWtpMngmtRadiusServerProfilesEntry 8 }

-- {COLUMN} 1.3.6.1.4.1.2356.11.1.59.105.1.9
lcsStatusWtpMngmtRadiusServerProfilesEntryAccessSecret OBJECT-TYPE
    SYNTAX     DisplayString (SIZE(0..64))
    MAX-ACCESS read-only
    STATUS     current
    DESCRIPTION
            "-- empty --"
    ::= { lcsStatusWtpMngmtRadiusServerProfilesEntry 9 }

-- {COLUMN} 1.3.6.1.4.1.2356.11.1.59.105.1.10
lcsStatusWtpMngmtRadiusServerProfilesEntryAccessLoopback OBJECT-TYPE
    SYNTAX     DisplayString (SIZE(0..16))
    MAX-ACCESS read-only
    STATUS     current
    DESCRIPTION
            "-- empty --"
    ::= { lcsStatusWtpMngmtRadiusServerProfilesEntry 10 }

-- {COLUMN} 1.3.6.1.4.1.2356.11.1.59.105.1.11
lcsStatusWtpMngmtRadiusServerProfilesEntryAccessProtocol OBJECT-TYPE
    SYNTAX     INTEGER {
                  eRadius (0),
                  eRadsec (1)
            }
    MAX-ACCESS read-only
    STATUS     current
    DESCRIPTION
            "-- empty --"
    ::= { lcsStatusWtpMngmtRadiusServerProfilesEntry 11 }

-- {COLUMN} 1.3.6.1.4.1.2356.11.1.59.105.1.12
lcsStatusWtpMngmtRadiusServerProfilesEntryBackup OBJECT-TYPE
    SYNTAX     DisplayString (SIZE(0..16))
    MAX-ACCESS read-only
    STATUS     current
    DESCRIPTION
            "-- empty --"
    ::= { lcsStatusWtpMngmtRadiusServerProfilesEntry 12 }

-- {TABLE} 1.3.6.1.4.1.2356.11.1.59.106
lcsStatusWtpMngmtAutowdsProfileTable OBJECT-TYPE
    SYNTAX     SEQUENCE OF LcsStatusWtpMngmtAutowdsProfileEntry
    MAX-ACCESS not-accessible
    STATUS     current
    DESCRIPTION
            "-- empty --"
    ::= { lcsStatusWtpMngmt 106 }

-- {ROW} 1.3.6.1.4.1.2356.11.1.59.106.1
lcsStatusWtpMngmtAutowdsProfileEntry OBJECT-TYPE
    SYNTAX     LcsStatusWtpMngmtAutowdsProfileEntry
    MAX-ACCESS not-accessible
    STATUS     current
    DESCRIPTION
            ""
    INDEX {
            lcsStatusWtpMngmtAutowdsProfileEntryName
          }
    ::= { lcsStatusWtpMngmtAutowdsProfileTable 1 }

LcsStatusWtpMngmtAutowdsProfileEntry ::= SEQUENCE {
            lcsStatusWtpMngmtAutowdsProfileEntryName DisplayString,
            lcsStatusWtpMngmtAutowdsProfileEntrySsid DisplayString,
            lcsStatusWtpMngmtAutowdsProfileEntryKey DisplayString,
            lcsStatusWtpMngmtAutowdsProfileEntryEnabled INTEGER,
            lcsStatusWtpMngmtAutowdsProfileEntryAllowExprInt INTEGER,
            lcsStatusWtpMngmtAutowdsProfileEntryTimeTillPreconfScan Integer32,
            lcsStatusWtpMngmtAutowdsProfileEntryTimeTillExpressScan Integer32,
            lcsStatusWtpMngmtAutowdsProfileEntryInterfacePairing INTEGER,
            lcsStatusWtpMngmtAutowdsProfileEntrySlaveRadioMultiHop INTEGER
    }

-- {COLUMN} 1.3.6.1.4.1.2356.11.1.59.106.1.1
lcsStatusWtpMngmtAutowdsProfileEntryName OBJECT-TYPE
    SYNTAX     DisplayString (SIZE(0..15))
    MAX-ACCESS read-only
    STATUS     current
    DESCRIPTION
            "-- empty --"
    ::= { lcsStatusWtpMngmtAutowdsProfileEntry 1 }

-- {COLUMN} 1.3.6.1.4.1.2356.11.1.59.106.1.3
lcsStatusWtpMngmtAutowdsProfileEntrySsid OBJECT-TYPE
    SYNTAX     DisplayString (SIZE(0..32))
    MAX-ACCESS read-only
    STATUS     current
    DESCRIPTION
            "-- empty --"
    ::= { lcsStatusWtpMngmtAutowdsProfileEntry 3 }

-- {COLUMN} 1.3.6.1.4.1.2356.11.1.59.106.1.4
lcsStatusWtpMngmtAutowdsProfileEntryKey OBJECT-TYPE
    SYNTAX     DisplayString (SIZE(0..63))
    MAX-ACCESS read-only
    STATUS     current
    DESCRIPTION
            "-- empty --"
    ::= { lcsStatusWtpMngmtAutowdsProfileEntry 4 }

-- {COLUMN} 1.3.6.1.4.1.2356.11.1.59.106.1.6
lcsStatusWtpMngmtAutowdsProfileEntryEnabled OBJECT-TYPE
    SYNTAX     INTEGER {
                  eNo (0),
                  eYes (1)
            }
    MAX-ACCESS read-only
    STATUS     current
    DESCRIPTION
            "-- empty --"
    ::= { lcsStatusWtpMngmtAutowdsProfileEntry 6 }

-- {COLUMN} 1.3.6.1.4.1.2356.11.1.59.106.1.7
lcsStatusWtpMngmtAutowdsProfileEntryAllowExprInt OBJECT-TYPE
    SYNTAX     INTEGER {
                  eNo (0),
                  eYes (1)
            }
    MAX-ACCESS read-only
    STATUS     current
    DESCRIPTION
            "Allow-Express-Integration"
    ::= { lcsStatusWtpMngmtAutowdsProfileEntry 7 }

-- {COLUMN} 1.3.6.1.4.1.2356.11.1.59.106.1.15
lcsStatusWtpMngmtAutowdsProfileEntryTimeTillPreconfScan OBJECT-TYPE
    SYNTAX     Integer32 (0..2147483647)
    MAX-ACCESS read-only
    STATUS     current
    DESCRIPTION
            "-- empty --"
    ::= { lcsStatusWtpMngmtAutowdsProfileEntry 15 }

-- {COLUMN} 1.3.6.1.4.1.2356.11.1.59.106.1.16
lcsStatusWtpMngmtAutowdsProfileEntryTimeTillExpressScan OBJECT-TYPE
    SYNTAX     Integer32 (0..2147483647)
    MAX-ACCESS read-only
    STATUS     current
    DESCRIPTION
            "-- empty --"
    ::= { lcsStatusWtpMngmtAutowdsProfileEntry 16 }

-- {COLUMN} 1.3.6.1.4.1.2356.11.1.59.106.1.17
lcsStatusWtpMngmtAutowdsProfileEntryInterfacePairing OBJECT-TYPE
    SYNTAX     INTEGER {
                  eAutomatic (0),
                  eStrict (1),
                  eMixed (2)
            }
    MAX-ACCESS read-only
    STATUS     current
    DESCRIPTION
            "-- empty --"
    ::= { lcsStatusWtpMngmtAutowdsProfileEntry 17 }

-- {COLUMN} 1.3.6.1.4.1.2356.11.1.59.106.1.18
lcsStatusWtpMngmtAutowdsProfileEntrySlaveRadioMultiHop OBJECT-TYPE
    SYNTAX     INTEGER {
                  eNo (0),
                  eYes (1),
                  eSingleRadioApOnly (2)
            }
    MAX-ACCESS read-only
    STATUS     current
    DESCRIPTION
            "-- empty --"
    ::= { lcsStatusWtpMngmtAutowdsProfileEntry 18 }

-- {TABLE} 1.3.6.1.4.1.2356.11.1.59.107
lcsStatusWtpMngmtAutowdsTopologyTable OBJECT-TYPE
    SYNTAX     SEQUENCE OF LcsStatusWtpMngmtAutowdsTopologyEntry
    MAX-ACCESS not-accessible
    STATUS     current
    DESCRIPTION
            "-- empty --"
    ::= { lcsStatusWtpMngmt 107 }

-- {ROW} 1.3.6.1.4.1.2356.11.1.59.107.1
lcsStatusWtpMngmtAutowdsTopologyEntry OBJECT-TYPE
    SYNTAX     LcsStatusWtpMngmtAutowdsTopologyEntry
    MAX-ACCESS not-accessible
    STATUS     current
    DESCRIPTION
            ""
    INDEX {
            lcsStatusWtpMngmtAutowdsTopologyEntryAutowdsProfile,
            lcsStatusWtpMngmtAutowdsTopologyEntryPriority,
            lcsStatusWtpMngmtAutowdsTopologyEntrySlaveApName,
            lcsStatusWtpMngmtAutowdsTopologyEntrySlaveApWlanIfc,
            lcsStatusWtpMngmtAutowdsTopologyEntrySlaveApWlanMac
          }
    ::= { lcsStatusWtpMngmtAutowdsTopologyTable 1 }

LcsStatusWtpMngmtAutowdsTopologyEntry ::= SEQUENCE {
            lcsStatusWtpMngmtAutowdsTopologyEntryAutowdsProfile DisplayString,
            lcsStatusWtpMngmtAutowdsTopologyEntryPriority Integer32,
            lcsStatusWtpMngmtAutowdsTopologyEntrySlaveApName DisplayString,
            lcsStatusWtpMngmtAutowdsTopologyEntrySlaveApWlanIfc INTEGER,
            lcsStatusWtpMngmtAutowdsTopologyEntrySlaveApWlanMac DisplayString,
            lcsStatusWtpMngmtAutowdsTopologyEntryMasterApName DisplayString,
            lcsStatusWtpMngmtAutowdsTopologyEntryMasterApWlanIfc INTEGER,
            lcsStatusWtpMngmtAutowdsTopologyEntryMasterApWlanMac DisplayString,
            lcsStatusWtpMngmtAutowdsTopologyEntryKey DisplayString,
            lcsStatusWtpMngmtAutowdsTopologyEntryEnabled INTEGER,
            lcsStatusWtpMngmtAutowdsTopologyEntrySlaveTxLimit Integer32,
            lcsStatusWtpMngmtAutowdsTopologyEntryMasterTxLimit Integer32,
            lcsStatusWtpMngmtAutowdsTopologyEntryLinkLossTimeout Integer32,
            lcsStatusWtpMngmtAutowdsTopologyEntryContinuation Integer32,
            lcsStatusWtpMngmtAutowdsTopologyEntryGenerated INTEGER,
            lcsStatusWtpMngmtAutowdsTopologyEntryP2pIndex Integer32,
            lcsStatusWtpMngmtAutowdsTopologyEntryP2pRole INTEGER
    }

-- {COLUMN} 1.3.6.1.4.1.2356.11.1.59.107.1.1
lcsStatusWtpMngmtAutowdsTopologyEntryAutowdsProfile OBJECT-TYPE
    SYNTAX     DisplayString (SIZE(0..15))
    MAX-ACCESS read-only
    STATUS     current
    DESCRIPTION
            "-- empty --"
    ::= { lcsStatusWtpMngmtAutowdsTopologyEntry 1 }

-- {COLUMN} 1.3.6.1.4.1.2356.11.1.59.107.1.2
lcsStatusWtpMngmtAutowdsTopologyEntryPriority OBJECT-TYPE
    SYNTAX     Integer32 (0..65535)
    MAX-ACCESS read-only
    STATUS     current
    DESCRIPTION
            "-- empty --"
    ::= { lcsStatusWtpMngmtAutowdsTopologyEntry 2 }

-- {COLUMN} 1.3.6.1.4.1.2356.11.1.59.107.1.3
lcsStatusWtpMngmtAutowdsTopologyEntrySlaveApName OBJECT-TYPE
    SYNTAX     DisplayString (SIZE(0..64))
    MAX-ACCESS read-only
    STATUS     current
    DESCRIPTION
            "-- empty --"
    ::= { lcsStatusWtpMngmtAutowdsTopologyEntry 3 }

-- {COLUMN} 1.3.6.1.4.1.2356.11.1.59.107.1.4
lcsStatusWtpMngmtAutowdsTopologyEntrySlaveApWlanIfc OBJECT-TYPE
    SYNTAX     INTEGER {
                  eWlan1 (1),
                  eWlan2 (2)
            }
    MAX-ACCESS read-only
    STATUS     current
    DESCRIPTION
            "-- empty --"
    ::= { lcsStatusWtpMngmtAutowdsTopologyEntry 4 }

-- {COLUMN} 1.3.6.1.4.1.2356.11.1.59.107.1.5
lcsStatusWtpMngmtAutowdsTopologyEntrySlaveApWlanMac OBJECT-TYPE
    SYNTAX     DisplayString (SIZE(0..12))
    MAX-ACCESS read-only
    STATUS     current
    DESCRIPTION
            "-- empty --"
    ::= { lcsStatusWtpMngmtAutowdsTopologyEntry 5 }

-- {COLUMN} 1.3.6.1.4.1.2356.11.1.59.107.1.6
lcsStatusWtpMngmtAutowdsTopologyEntryMasterApName OBJECT-TYPE
    SYNTAX     DisplayString (SIZE(0..64))
    MAX-ACCESS read-only
    STATUS     current
    DESCRIPTION
            "-- empty --"
    ::= { lcsStatusWtpMngmtAutowdsTopologyEntry 6 }

-- {COLUMN} 1.3.6.1.4.1.2356.11.1.59.107.1.7
lcsStatusWtpMngmtAutowdsTopologyEntryMasterApWlanIfc OBJECT-TYPE
    SYNTAX     INTEGER {
                  eWlan1 (1),
                  eWlan2 (2)
            }
    MAX-ACCESS read-only
    STATUS     current
    DESCRIPTION
            "-- empty --"
    ::= { lcsStatusWtpMngmtAutowdsTopologyEntry 7 }

-- {COLUMN} 1.3.6.1.4.1.2356.11.1.59.107.1.8
lcsStatusWtpMngmtAutowdsTopologyEntryMasterApWlanMac OBJECT-TYPE
    SYNTAX     DisplayString (SIZE(0..12))
    MAX-ACCESS read-only
    STATUS     current
    DESCRIPTION
            "-- empty --"
    ::= { lcsStatusWtpMngmtAutowdsTopologyEntry 8 }

-- {COLUMN} 1.3.6.1.4.1.2356.11.1.59.107.1.9
lcsStatusWtpMngmtAutowdsTopologyEntryKey OBJECT-TYPE
    SYNTAX     DisplayString (SIZE(0..63))
    MAX-ACCESS read-only
    STATUS     current
    DESCRIPTION
            "-- empty --"
    ::= { lcsStatusWtpMngmtAutowdsTopologyEntry 9 }

-- {COLUMN} 1.3.6.1.4.1.2356.11.1.59.107.1.10
lcsStatusWtpMngmtAutowdsTopologyEntryEnabled OBJECT-TYPE
    SYNTAX     INTEGER {
                  eNo (0),
                  eYes (1)
            }
    MAX-ACCESS read-only
    STATUS     current
    DESCRIPTION
            "-- empty --"
    ::= { lcsStatusWtpMngmtAutowdsTopologyEntry 10 }

-- {COLUMN} 1.3.6.1.4.1.2356.11.1.59.107.1.12
lcsStatusWtpMngmtAutowdsTopologyEntrySlaveTxLimit OBJECT-TYPE
    SYNTAX     Integer32 (0..2147483647)
    MAX-ACCESS read-only
    STATUS     current
    DESCRIPTION
            "-- empty --"
    ::= { lcsStatusWtpMngmtAutowdsTopologyEntry 12 }

-- {COLUMN} 1.3.6.1.4.1.2356.11.1.59.107.1.13
lcsStatusWtpMngmtAutowdsTopologyEntryMasterTxLimit OBJECT-TYPE
    SYNTAX     Integer32 (0..2147483647)
    MAX-ACCESS read-only
    STATUS     current
    DESCRIPTION
            "-- empty --"
    ::= { lcsStatusWtpMngmtAutowdsTopologyEntry 13 }

-- {COLUMN} 1.3.6.1.4.1.2356.11.1.59.107.1.14
lcsStatusWtpMngmtAutowdsTopologyEntryLinkLossTimeout OBJECT-TYPE
    SYNTAX     Integer32 (0..2147483647)
    MAX-ACCESS read-only
    STATUS     current
    DESCRIPTION
            "-- empty --"
    ::= { lcsStatusWtpMngmtAutowdsTopologyEntry 14 }

-- {COLUMN} 1.3.6.1.4.1.2356.11.1.59.107.1.16
lcsStatusWtpMngmtAutowdsTopologyEntryContinuation OBJECT-TYPE
    SYNTAX     Integer32 (0..65535)
    MAX-ACCESS read-only
    STATUS     current
    DESCRIPTION
            ""
    ::= { lcsStatusWtpMngmtAutowdsTopologyEntry 16 }

-- {COLUMN} 1.3.6.1.4.1.2356.11.1.59.107.1.17
lcsStatusWtpMngmtAutowdsTopologyEntryGenerated OBJECT-TYPE
    SYNTAX     INTEGER {
                  eNo (0),
                  eYes (1)
            }
    MAX-ACCESS read-only
    STATUS     current
    DESCRIPTION
            "-- empty --"
    ::= { lcsStatusWtpMngmtAutowdsTopologyEntry 17 }

-- {COLUMN} 1.3.6.1.4.1.2356.11.1.59.107.1.19
lcsStatusWtpMngmtAutowdsTopologyEntryP2pIndex OBJECT-TYPE
    SYNTAX     Integer32 (0..65535)
    MAX-ACCESS read-only
    STATUS     current
    DESCRIPTION
            "-- empty --"
    ::= { lcsStatusWtpMngmtAutowdsTopologyEntry 19 }

-- {COLUMN} 1.3.6.1.4.1.2356.11.1.59.107.1.20
lcsStatusWtpMngmtAutowdsTopologyEntryP2pRole OBJECT-TYPE
    SYNTAX     INTEGER {
                  eNone (0),
                  eSlave (1),
                  eMaster (2)
            }
    MAX-ACCESS read-only
    STATUS     current
    DESCRIPTION
            "-- empty --"
    ::= { lcsStatusWtpMngmtAutowdsTopologyEntry 20 }

-- {NODE} 1.3.6.1.4.1.2356.11.1.59.108
lcsStatusWtpMngmt11u OBJECT IDENTIFIER ::= { lcsStatusWtpMngmt 108 }

-- {TABLE} 1.3.6.1.4.1.2356.11.1.59.108.1
lcsStatusWtpMngmt11u11u-NwTable OBJECT-TYPE
    SYNTAX     SEQUENCE OF LcsStatusWtpMngmt11u11u-NwEntry
    MAX-ACCESS not-accessible
    STATUS     current
    DESCRIPTION
            "IEEE802.11u-Networks"
    ::= { lcsStatusWtpMngmt11u 1 }

-- {ROW} 1.3.6.1.4.1.2356.11.1.59.108.1.1
lcsStatusWtpMngmt11u11u-NwEntry OBJECT-TYPE
    SYNTAX     LcsStatusWtpMngmt11u11u-NwEntry
    MAX-ACCESS not-accessible
    STATUS     current
    DESCRIPTION
            ""
    INDEX {
            lcsStatusWtpMngmt11u11u-NwEntryName
          }
    ::= { lcsStatusWtpMngmt11u11u-NwTable 1 }

LcsStatusWtpMngmt11u11u-NwEntry ::= SEQUENCE {
            lcsStatusWtpMngmt11u11u-NwEntryName DisplayString,
            lcsStatusWtpMngmt11u11u-NwEntryOper INTEGER,
            lcsStatusWtpMngmt11u11u-NwEntryHs20 INTEGER,
            lcsStatusWtpMngmt11u11u-NwEntryInet INTEGER,
            lcsStatusWtpMngmt11u11u-NwEntryNwType INTEGER,
            lcsStatusWtpMngmt11u11u-NwEntryAsra INTEGER,
            lcsStatusWtpMngmt11u11u-NwEntryHESSIDT INTEGER,
            lcsStatusWtpMngmt11u11u-NwEntryHESSIDM MacAddress,
            lcsStatusWtpMngmt11u11u-NwEntryANQP-Prof DisplayString,
            lcsStatusWtpMngmt11u11u-NwEntryHs20-Prof DisplayString
    }

-- {COLUMN} 1.3.6.1.4.1.2356.11.1.59.108.1.1.1
lcsStatusWtpMngmt11u11u-NwEntryName OBJECT-TYPE
    SYNTAX     DisplayString (SIZE(0..32))
    MAX-ACCESS read-only
    STATUS     current
    DESCRIPTION
            "-- empty --"
    ::= { lcsStatusWtpMngmt11u11u-NwEntry 1 }

-- {COLUMN} 1.3.6.1.4.1.2356.11.1.59.108.1.1.2
lcsStatusWtpMngmt11u11u-NwEntryOper OBJECT-TYPE
    SYNTAX     INTEGER {
                  eNo (0),
                  eYes (1)
            }
    MAX-ACCESS read-only
    STATUS     current
    DESCRIPTION
            "Operating"
    ::= { lcsStatusWtpMngmt11u11u-NwEntry 2 }

-- {COLUMN} 1.3.6.1.4.1.2356.11.1.59.108.1.1.3
lcsStatusWtpMngmt11u11u-NwEntryHs20 OBJECT-TYPE
    SYNTAX     INTEGER {
                  eNo (0),
                  eYes (1)
            }
    MAX-ACCESS read-only
    STATUS     current
    DESCRIPTION
            "Hotspot2.0"
    ::= { lcsStatusWtpMngmt11u11u-NwEntry 3 }

-- {COLUMN} 1.3.6.1.4.1.2356.11.1.59.108.1.1.4
lcsStatusWtpMngmt11u11u-NwEntryInet OBJECT-TYPE
    SYNTAX     INTEGER {
                  eNo (0),
                  eYes (1)
            }
    MAX-ACCESS read-only
    STATUS     current
    DESCRIPTION
            "Internet"
    ::= { lcsStatusWtpMngmt11u11u-NwEntry 4 }

-- {COLUMN} 1.3.6.1.4.1.2356.11.1.59.108.1.1.5
lcsStatusWtpMngmt11u11u-NwEntryNwType OBJECT-TYPE
    SYNTAX     INTEGER {
                  ePrivate (0),
                  ePrivateGuestacc (1),
                  ePublicCharge (2),
                  ePublicFree (3),
                  ePersonalDev (4),
                  eEmergency (5),
                  eExperimental (14),
                  eWildcard (15)
            }
    MAX-ACCESS read-only
    STATUS     current
    DESCRIPTION
            "Network-Type"
    ::= { lcsStatusWtpMngmt11u11u-NwEntry 5 }

-- {COLUMN} 1.3.6.1.4.1.2356.11.1.59.108.1.1.6
lcsStatusWtpMngmt11u11u-NwEntryAsra OBJECT-TYPE
    SYNTAX     INTEGER {
                  eNo (0),
                  eYes (1)
            }
    MAX-ACCESS read-only
    STATUS     current
    DESCRIPTION
            "Asra"
    ::= { lcsStatusWtpMngmt11u11u-NwEntry 6 }

-- {COLUMN} 1.3.6.1.4.1.2356.11.1.59.108.1.1.7
lcsStatusWtpMngmt11u11u-NwEntryHESSIDT OBJECT-TYPE
    SYNTAX     INTEGER {
                  eAuto (0),
                  eUser (1),
                  eNone (2)
            }
    MAX-ACCESS read-only
    STATUS     current
    DESCRIPTION
            "HESSID-Type"
    ::= { lcsStatusWtpMngmt11u11u-NwEntry 7 }

-- {COLUMN} 1.3.6.1.4.1.2356.11.1.59.108.1.1.8
lcsStatusWtpMngmt11u11u-NwEntryHESSIDM OBJECT-TYPE
    SYNTAX     MacAddress
    MAX-ACCESS read-only
    STATUS     current
    DESCRIPTION
            "HESSID-MAC"
    ::= { lcsStatusWtpMngmt11u11u-NwEntry 8 }

-- {COLUMN} 1.3.6.1.4.1.2356.11.1.59.108.1.1.10
lcsStatusWtpMngmt11u11u-NwEntryANQP-Prof OBJECT-TYPE
    SYNTAX     DisplayString (SIZE(0..32))
    MAX-ACCESS read-only
    STATUS     current
    DESCRIPTION
            "ANQP-Profile"
    ::= { lcsStatusWtpMngmt11u11u-NwEntry 10 }

-- {COLUMN} 1.3.6.1.4.1.2356.11.1.59.108.1.1.12
lcsStatusWtpMngmt11u11u-NwEntryHs20-Prof OBJECT-TYPE
    SYNTAX     DisplayString (SIZE(0..32))
    MAX-ACCESS read-only
    STATUS     current
    DESCRIPTION
            "HS20-Profile"
    ::= { lcsStatusWtpMngmt11u11u-NwEntry 12 }

-- {TABLE} 1.3.6.1.4.1.2356.11.1.59.108.2
lcsStatusWtpMngmt11uANQP-ProfsTable OBJECT-TYPE
    SYNTAX     SEQUENCE OF LcsStatusWtpMngmt11uANQP-ProfsEntry
    MAX-ACCESS not-accessible
    STATUS     current
    DESCRIPTION
            "ANQP-Profiles"
    ::= { lcsStatusWtpMngmt11u 2 }

-- {ROW} 1.3.6.1.4.1.2356.11.1.59.108.2.1
lcsStatusWtpMngmt11uANQP-ProfsEntry OBJECT-TYPE
    SYNTAX     LcsStatusWtpMngmt11uANQP-ProfsEntry
    MAX-ACCESS not-accessible
    STATUS     current
    DESCRIPTION
            ""
    INDEX {
            lcsStatusWtpMngmt11uANQP-ProfsEntryName
          }
    ::= { lcsStatusWtpMngmt11uANQP-ProfsTable 1 }

LcsStatusWtpMngmt11uANQP-ProfsEntry ::= SEQUENCE {
            lcsStatusWtpMngmt11uANQP-ProfsEntryName DisplayString,
            lcsStatusWtpMngmt11uANQP-ProfsEntryIncOUI DisplayString,
            lcsStatusWtpMngmt11uANQP-ProfsEntryAddOUI DisplayString,
            lcsStatusWtpMngmt11uANQP-ProfsEntryDomainList DisplayString,
            lcsStatusWtpMngmt11uANQP-ProfsEntryNaiRealmList DisplayString,
            lcsStatusWtpMngmt11uANQP-ProfsEntryCellularList DisplayString,
            lcsStatusWtpMngmt11uANQP-ProfsEntryNetList DisplayString
    }

-- {COLUMN} 1.3.6.1.4.1.2356.11.1.59.108.2.1.1
lcsStatusWtpMngmt11uANQP-ProfsEntryName OBJECT-TYPE
    SYNTAX     DisplayString (SIZE(0..32))
    MAX-ACCESS read-only
    STATUS     current
    DESCRIPTION
            "-- empty --"
    ::= { lcsStatusWtpMngmt11uANQP-ProfsEntry 1 }

-- {COLUMN} 1.3.6.1.4.1.2356.11.1.59.108.2.1.2
lcsStatusWtpMngmt11uANQP-ProfsEntryIncOUI OBJECT-TYPE
    SYNTAX     DisplayString (SIZE(0..65))
    MAX-ACCESS read-only
    STATUS     current
    DESCRIPTION
            "Include-in-Beacon-OUI"
    ::= { lcsStatusWtpMngmt11uANQP-ProfsEntry 2 }

-- {COLUMN} 1.3.6.1.4.1.2356.11.1.59.108.2.1.3
lcsStatusWtpMngmt11uANQP-ProfsEntryAddOUI OBJECT-TYPE
    SYNTAX     DisplayString (SIZE(0..65))
    MAX-ACCESS read-only
    STATUS     current
    DESCRIPTION
            "Additional-OUI"
    ::= { lcsStatusWtpMngmt11uANQP-ProfsEntry 3 }

-- {COLUMN} 1.3.6.1.4.1.2356.11.1.59.108.2.1.4
lcsStatusWtpMngmt11uANQP-ProfsEntryDomainList OBJECT-TYPE
    SYNTAX     DisplayString (SIZE(0..65))
    MAX-ACCESS read-only
    STATUS     current
    DESCRIPTION
            "-- empty --"
    ::= { lcsStatusWtpMngmt11uANQP-ProfsEntry 4 }

-- {COLUMN} 1.3.6.1.4.1.2356.11.1.59.108.2.1.5
lcsStatusWtpMngmt11uANQP-ProfsEntryNaiRealmList OBJECT-TYPE
    SYNTAX     DisplayString (SIZE(0..65))
    MAX-ACCESS read-only
    STATUS     current
    DESCRIPTION
            "-- empty --"
    ::= { lcsStatusWtpMngmt11uANQP-ProfsEntry 5 }

-- {COLUMN} 1.3.6.1.4.1.2356.11.1.59.108.2.1.6
lcsStatusWtpMngmt11uANQP-ProfsEntryCellularList OBJECT-TYPE
    SYNTAX     DisplayString (SIZE(0..65))
    MAX-ACCESS read-only
    STATUS     current
    DESCRIPTION
            "-- empty --"
    ::= { lcsStatusWtpMngmt11uANQP-ProfsEntry 6 }

-- {COLUMN} 1.3.6.1.4.1.2356.11.1.59.108.2.1.7
lcsStatusWtpMngmt11uANQP-ProfsEntryNetList OBJECT-TYPE
    SYNTAX     DisplayString (SIZE(0..65))
    MAX-ACCESS read-only
    STATUS     current
    DESCRIPTION
            "Network-Auth-Type-List"
    ::= { lcsStatusWtpMngmt11uANQP-ProfsEntry 7 }

-- {TABLE} 1.3.6.1.4.1.2356.11.1.59.108.3
lcsStatusWtpMngmt11uHs20-ProfsTable OBJECT-TYPE
    SYNTAX     SEQUENCE OF LcsStatusWtpMngmt11uHs20-ProfsEntry
    MAX-ACCESS not-accessible
    STATUS     current
    DESCRIPTION
            "Hotspot2.0-Profiles"
    ::= { lcsStatusWtpMngmt11u 3 }

-- {ROW} 1.3.6.1.4.1.2356.11.1.59.108.3.1
lcsStatusWtpMngmt11uHs20-ProfsEntry OBJECT-TYPE
    SYNTAX     LcsStatusWtpMngmt11uHs20-ProfsEntry
    MAX-ACCESS not-accessible
    STATUS     current
    DESCRIPTION
            ""
    INDEX {
            lcsStatusWtpMngmt11uHs20-ProfsEntryName
          }
    ::= { lcsStatusWtpMngmt11uHs20-ProfsTable 1 }

LcsStatusWtpMngmt11uHs20-ProfsEntry ::= SEQUENCE {
            lcsStatusWtpMngmt11uHs20-ProfsEntryName DisplayString,
            lcsStatusWtpMngmt11uHs20-ProfsEntryOperatorName DisplayString,
            lcsStatusWtpMngmt11uHs20-ProfsEntryConnCaps DisplayString,
            lcsStatusWtpMngmt11uHs20-ProfsEntryOpClass DisplayString
    }

-- {COLUMN} 1.3.6.1.4.1.2356.11.1.59.108.3.1.1
lcsStatusWtpMngmt11uHs20-ProfsEntryName OBJECT-TYPE
    SYNTAX     DisplayString (SIZE(0..32))
    MAX-ACCESS read-only
    STATUS     current
    DESCRIPTION
            "-- empty --"
    ::= { lcsStatusWtpMngmt11uHs20-ProfsEntry 1 }

-- {COLUMN} 1.3.6.1.4.1.2356.11.1.59.108.3.1.2
lcsStatusWtpMngmt11uHs20-ProfsEntryOperatorName OBJECT-TYPE
    SYNTAX     DisplayString (SIZE(0..65))
    MAX-ACCESS read-only
    STATUS     current
    DESCRIPTION
            "-- empty --"
    ::= { lcsStatusWtpMngmt11uHs20-ProfsEntry 2 }

-- {COLUMN} 1.3.6.1.4.1.2356.11.1.59.108.3.1.3
lcsStatusWtpMngmt11uHs20-ProfsEntryConnCaps OBJECT-TYPE
    SYNTAX     DisplayString (SIZE(0..250))
    MAX-ACCESS read-only
    STATUS     current
    DESCRIPTION
            "Connection-Capabilities"
    ::= { lcsStatusWtpMngmt11uHs20-ProfsEntry 3 }

-- {COLUMN} 1.3.6.1.4.1.2356.11.1.59.108.3.1.4
lcsStatusWtpMngmt11uHs20-ProfsEntryOpClass OBJECT-TYPE
    SYNTAX     DisplayString (SIZE(0..32))
    MAX-ACCESS read-only
    STATUS     current
    DESCRIPTION
            "Operating-Class"
    ::= { lcsStatusWtpMngmt11uHs20-ProfsEntry 4 }

-- {TABLE} 1.3.6.1.4.1.2356.11.1.59.108.4
lcsStatusWtpMngmt11uNetAuthTable OBJECT-TYPE
    SYNTAX     SEQUENCE OF LcsStatusWtpMngmt11uNetAuthEntry
    MAX-ACCESS not-accessible
    STATUS     current
    DESCRIPTION
            "Network-Authentication-Type"
    ::= { lcsStatusWtpMngmt11u 4 }

-- {ROW} 1.3.6.1.4.1.2356.11.1.59.108.4.1
lcsStatusWtpMngmt11uNetAuthEntry OBJECT-TYPE
    SYNTAX     LcsStatusWtpMngmt11uNetAuthEntry
    MAX-ACCESS not-accessible
    STATUS     current
    DESCRIPTION
            ""
    INDEX {
            lcsStatusWtpMngmt11uNetAuthEntryName
          }
    ::= { lcsStatusWtpMngmt11uNetAuthTable 1 }

LcsStatusWtpMngmt11uNetAuthEntry ::= SEQUENCE {
            lcsStatusWtpMngmt11uNetAuthEntryName DisplayString,
            lcsStatusWtpMngmt11uNetAuthEntryNetType INTEGER,
            lcsStatusWtpMngmt11uNetAuthEntryReUrl DisplayString
    }

-- {COLUMN} 1.3.6.1.4.1.2356.11.1.59.108.4.1.1
lcsStatusWtpMngmt11uNetAuthEntryName OBJECT-TYPE
    SYNTAX     DisplayString (SIZE(0..32))
    MAX-ACCESS read-only
    STATUS     current
    DESCRIPTION
            "-- empty --"
    ::= { lcsStatusWtpMngmt11uNetAuthEntry 1 }

-- {COLUMN} 1.3.6.1.4.1.2356.11.1.59.108.4.1.2
lcsStatusWtpMngmt11uNetAuthEntryNetType OBJECT-TYPE
    SYNTAX     INTEGER {
                  eAcceptTermsCond (0),
                  eOnlineEnrollment (1),
                  eHttpRedirection (2),
                  eDnsRedirection (3)
            }
    MAX-ACCESS read-only
    STATUS     current
    DESCRIPTION
            "Network-Auth-Type"
    ::= { lcsStatusWtpMngmt11uNetAuthEntry 2 }

-- {COLUMN} 1.3.6.1.4.1.2356.11.1.59.108.4.1.3
lcsStatusWtpMngmt11uNetAuthEntryReUrl OBJECT-TYPE
    SYNTAX     DisplayString (SIZE(0..65))
    MAX-ACCESS read-only
    STATUS     current
    DESCRIPTION
            "Redirect-URL"
    ::= { lcsStatusWtpMngmt11uNetAuthEntry 3 }

-- {TABLE} 1.3.6.1.4.1.2356.11.1.59.108.5
lcsStatusWtpMngmt11uCellListTable OBJECT-TYPE
    SYNTAX     SEQUENCE OF LcsStatusWtpMngmt11uCellListEntry
    MAX-ACCESS not-accessible
    STATUS     current
    DESCRIPTION
            "Cellular-Network-Information-List"
    ::= { lcsStatusWtpMngmt11u 5 }

-- {ROW} 1.3.6.1.4.1.2356.11.1.59.108.5.1
lcsStatusWtpMngmt11uCellListEntry OBJECT-TYPE
    SYNTAX     LcsStatusWtpMngmt11uCellListEntry
    MAX-ACCESS not-accessible
    STATUS     current
    DESCRIPTION
            ""
    INDEX {
            lcsStatusWtpMngmt11uCellListEntryName
          }
    ::= { lcsStatusWtpMngmt11uCellListTable 1 }

LcsStatusWtpMngmt11uCellListEntry ::= SEQUENCE {
            lcsStatusWtpMngmt11uCellListEntryName DisplayString,
            lcsStatusWtpMngmt11uCellListEntryCountry DisplayString,
            lcsStatusWtpMngmt11uCellListEntryNetwork DisplayString
    }

-- {COLUMN} 1.3.6.1.4.1.2356.11.1.59.108.5.1.1
lcsStatusWtpMngmt11uCellListEntryName OBJECT-TYPE
    SYNTAX     DisplayString (SIZE(0..32))
    MAX-ACCESS read-only
    STATUS     current
    DESCRIPTION
            "-- empty --"
    ::= { lcsStatusWtpMngmt11uCellListEntry 1 }

-- {COLUMN} 1.3.6.1.4.1.2356.11.1.59.108.5.1.2
lcsStatusWtpMngmt11uCellListEntryCountry OBJECT-TYPE
    SYNTAX     DisplayString (SIZE(0..3))
    MAX-ACCESS read-only
    STATUS     current
    DESCRIPTION
            "Country-Code"
    ::= { lcsStatusWtpMngmt11uCellListEntry 2 }

-- {COLUMN} 1.3.6.1.4.1.2356.11.1.59.108.5.1.3
lcsStatusWtpMngmt11uCellListEntryNetwork OBJECT-TYPE
    SYNTAX     DisplayString (SIZE(0..3))
    MAX-ACCESS read-only
    STATUS     current
    DESCRIPTION
            "Network-Code"
    ::= { lcsStatusWtpMngmt11uCellListEntry 3 }

-- {TABLE} 1.3.6.1.4.1.2356.11.1.59.108.6
lcsStatusWtpMngmt11uVenueNameTable OBJECT-TYPE
    SYNTAX     SEQUENCE OF LcsStatusWtpMngmt11uVenueNameEntry
    MAX-ACCESS not-accessible
    STATUS     current
    DESCRIPTION
            "-- empty --"
    ::= { lcsStatusWtpMngmt11u 6 }

-- {ROW} 1.3.6.1.4.1.2356.11.1.59.108.6.1
lcsStatusWtpMngmt11uVenueNameEntry OBJECT-TYPE
    SYNTAX     LcsStatusWtpMngmt11uVenueNameEntry
    MAX-ACCESS not-accessible
    STATUS     current
    DESCRIPTION
            ""
    INDEX {
            lcsStatusWtpMngmt11uVenueNameEntryName,
            lcsStatusWtpMngmt11uVenueNameEntryLanguage
          }
    ::= { lcsStatusWtpMngmt11uVenueNameTable 1 }

LcsStatusWtpMngmt11uVenueNameEntry ::= SEQUENCE {
            lcsStatusWtpMngmt11uVenueNameEntryName DisplayString,
            lcsStatusWtpMngmt11uVenueNameEntryLanguage INTEGER,
            lcsStatusWtpMngmt11uVenueNameEntryVenueName DisplayString
    }

-- {COLUMN} 1.3.6.1.4.1.2356.11.1.59.108.6.1.1
lcsStatusWtpMngmt11uVenueNameEntryName OBJECT-TYPE
    SYNTAX     DisplayString (SIZE(0..32))
    MAX-ACCESS read-only
    STATUS     current
    DESCRIPTION
            "-- empty --"
    ::= { lcsStatusWtpMngmt11uVenueNameEntry 1 }

-- {COLUMN} 1.3.6.1.4.1.2356.11.1.59.108.6.1.2
lcsStatusWtpMngmt11uVenueNameEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13)
            }
    MAX-ACCESS read-only
    STATUS     current
    DESCRIPTION
            "-- empty --"
    ::= { lcsStatusWtpMngmt11uVenueNameEntry 2 }

-- {COLUMN} 1.3.6.1.4.1.2356.11.1.59.108.6.1.3
lcsStatusWtpMngmt11uVenueNameEntryVenueName OBJECT-TYPE
    SYNTAX     DisplayString (SIZE(0..65))
    MAX-ACCESS read-only
    STATUS     current
    DESCRIPTION
            "-- empty --"
    ::= { lcsStatusWtpMngmt11uVenueNameEntry 3 }

-- {TABLE} 1.3.6.1.4.1.2356.11.1.59.108.7
lcsStatusWtpMngmt11uNAIsTable OBJECT-TYPE
    SYNTAX     SEQUENCE OF LcsStatusWtpMngmt11uNAIsEntry
    MAX-ACCESS not-accessible
    STATUS     current
    DESCRIPTION
            "NAI-Realms"
    ::= { lcsStatusWtpMngmt11u 7 }

-- {ROW} 1.3.6.1.4.1.2356.11.1.59.108.7.1
lcsStatusWtpMngmt11uNAIsEntry OBJECT-TYPE
    SYNTAX     LcsStatusWtpMngmt11uNAIsEntry
    MAX-ACCESS not-accessible
    STATUS     current
    DESCRIPTION
            ""
    INDEX {
            lcsStatusWtpMngmt11uNAIsEntryName
          }
    ::= { lcsStatusWtpMngmt11uNAIsTable 1 }

LcsStatusWtpMngmt11uNAIsEntry ::= SEQUENCE {
            lcsStatusWtpMngmt11uNAIsEntryName DisplayString,
            lcsStatusWtpMngmt11uNAIsEntryNaiRealm DisplayString,
            lcsStatusWtpMngmt11uNAIsEntryEapMethod INTEGER,
            lcsStatusWtpMngmt11uNAIsEntryAuthPar DisplayString
    }

-- {COLUMN} 1.3.6.1.4.1.2356.11.1.59.108.7.1.1
lcsStatusWtpMngmt11uNAIsEntryName OBJECT-TYPE
    SYNTAX     DisplayString (SIZE(0..32))
    MAX-ACCESS read-only
    STATUS     current
    DESCRIPTION
            "-- empty --"
    ::= { lcsStatusWtpMngmt11uNAIsEntry 1 }

-- {COLUMN} 1.3.6.1.4.1.2356.11.1.59.108.7.1.2
lcsStatusWtpMngmt11uNAIsEntryNaiRealm OBJECT-TYPE
    SYNTAX     DisplayString (SIZE(0..32))
    MAX-ACCESS read-only
    STATUS     current
    DESCRIPTION
            "-- empty --"
    ::= { lcsStatusWtpMngmt11uNAIsEntry 2 }

-- {COLUMN} 1.3.6.1.4.1.2356.11.1.59.108.7.1.3
lcsStatusWtpMngmt11uNAIsEntryEapMethod OBJECT-TYPE
    SYNTAX     INTEGER {
                  eNone (0),
                  eEapTls (13),
                  eEapSim (18),
                  eEapTtls (21),
                  eEapAka (23)
            }
    MAX-ACCESS read-only
    STATUS     current
    DESCRIPTION
            "-- empty --"
    ::= { lcsStatusWtpMngmt11uNAIsEntry 3 }

-- {COLUMN} 1.3.6.1.4.1.2356.11.1.59.108.7.1.4
lcsStatusWtpMngmt11uNAIsEntryAuthPar OBJECT-TYPE
    SYNTAX     DisplayString (SIZE(0..65))
    MAX-ACCESS read-only
    STATUS     current
    DESCRIPTION
            "Auth-Parameter-List"
    ::= { lcsStatusWtpMngmt11uNAIsEntry 4 }

-- {TABLE} 1.3.6.1.4.1.2356.11.1.59.108.8
lcsStatusWtpMngmt11uOperatorListTable OBJECT-TYPE
    SYNTAX     SEQUENCE OF LcsStatusWtpMngmt11uOperatorListEntry
    MAX-ACCESS not-accessible
    STATUS     current
    DESCRIPTION
            "-- empty --"
    ::= { lcsStatusWtpMngmt11u 8 }

-- {ROW} 1.3.6.1.4.1.2356.11.1.59.108.8.1
lcsStatusWtpMngmt11uOperatorListEntry OBJECT-TYPE
    SYNTAX     LcsStatusWtpMngmt11uOperatorListEntry
    MAX-ACCESS not-accessible
    STATUS     current
    DESCRIPTION
            ""
    INDEX {
            lcsStatusWtpMngmt11uOperatorListEntryName,
            lcsStatusWtpMngmt11uOperatorListEntryLanguage
          }
    ::= { lcsStatusWtpMngmt11uOperatorListTable 1 }

LcsStatusWtpMngmt11uOperatorListEntry ::= SEQUENCE {
            lcsStatusWtpMngmt11uOperatorListEntryName DisplayString,
            lcsStatusWtpMngmt11uOperatorListEntryLanguage INTEGER,
            lcsStatusWtpMngmt11uOperatorListEntryOperatorName DisplayString
    }

-- {COLUMN} 1.3.6.1.4.1.2356.11.1.59.108.8.1.1
lcsStatusWtpMngmt11uOperatorListEntryName OBJECT-TYPE
    SYNTAX     DisplayString (SIZE(0..32))
    MAX-ACCESS read-only
    STATUS     current
    DESCRIPTION
            "-- empty --"
    ::= { lcsStatusWtpMngmt11uOperatorListEntry 1 }

-- {COLUMN} 1.3.6.1.4.1.2356.11.1.59.108.8.1.2
lcsStatusWtpMngmt11uOperatorListEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13)
            }
    MAX-ACCESS read-only
    STATUS     current
    DESCRIPTION
            "-- empty --"
    ::= { lcsStatusWtpMngmt11uOperatorListEntry 2 }

-- {COLUMN} 1.3.6.1.4.1.2356.11.1.59.108.8.1.3
lcsStatusWtpMngmt11uOperatorListEntryOperatorName OBJECT-TYPE
    SYNTAX     DisplayString (SIZE(0..65))
    MAX-ACCESS read-only
    STATUS     current
    DESCRIPTION
            "-- empty --"
    ::= { lcsStatusWtpMngmt11uOperatorListEntry 3 }

-- {TABLE} 1.3.6.1.4.1.2356.11.1.59.108.9
lcsStatusWtpMngmt11uGeneralTable OBJECT-TYPE
    SYNTAX     SEQUENCE OF LcsStatusWtpMngmt11uGeneralEntry
    MAX-ACCESS not-accessible
    STATUS     current
    DESCRIPTION
            "-- empty --"
    ::= { lcsStatusWtpMngmt11u 9 }

-- {ROW} 1.3.6.1.4.1.2356.11.1.59.108.9.1
lcsStatusWtpMngmt11uGeneralEntry OBJECT-TYPE
    SYNTAX     LcsStatusWtpMngmt11uGeneralEntry
    MAX-ACCESS not-accessible
    STATUS     current
    DESCRIPTION
            ""
    INDEX {
            lcsStatusWtpMngmt11uGeneralEntryName
          }
    ::= { lcsStatusWtpMngmt11uGeneralTable 1 }

LcsStatusWtpMngmt11uGeneralEntry ::= SEQUENCE {
            lcsStatusWtpMngmt11uGeneralEntryName DisplayString,
            lcsStatusWtpMngmt11uGeneralEntryLinkStatus INTEGER,
            lcsStatusWtpMngmt11uGeneralEntryDownlinkSpeed Integer32,
            lcsStatusWtpMngmt11uGeneralEntryUplinkSpeed Integer32,
            lcsStatusWtpMngmt11uGeneralEntryIpv4AddrType INTEGER,
            lcsStatusWtpMngmt11uGeneralEntryIpv6AddrType INTEGER,
            lcsStatusWtpMngmt11uGeneralEntryVenueGroup INTEGER,
            lcsStatusWtpMngmt11uGeneralEntryVenueType Integer32,
            lcsStatusWtpMngmt11uGeneralEntryVenueName DisplayString
    }

-- {COLUMN} 1.3.6.1.4.1.2356.11.1.59.108.9.1.1
lcsStatusWtpMngmt11uGeneralEntryName OBJECT-TYPE
    SYNTAX     DisplayString (SIZE(0..32))
    MAX-ACCESS read-only
    STATUS     current
    DESCRIPTION
            "-- empty --"
    ::= { lcsStatusWtpMngmt11uGeneralEntry 1 }

-- {COLUMN} 1.3.6.1.4.1.2356.11.1.59.108.9.1.2
lcsStatusWtpMngmt11uGeneralEntryLinkStatus OBJECT-TYPE
    SYNTAX     INTEGER {
                  eAuto (0),
                  eLinkUp (1),
                  eLinkDown (2),
                  eLinkTest (3)
            }
    MAX-ACCESS read-only
    STATUS     current
    DESCRIPTION
            "-- empty --"
    ::= { lcsStatusWtpMngmt11uGeneralEntry 2 }

-- {COLUMN} 1.3.6.1.4.1.2356.11.1.59.108.9.1.3
lcsStatusWtpMngmt11uGeneralEntryDownlinkSpeed OBJECT-TYPE
    SYNTAX     Integer32 (0..2147483647)
    MAX-ACCESS read-only
    STATUS     current
    DESCRIPTION
            "-- empty --"
    ::= { lcsStatusWtpMngmt11uGeneralEntry 3 }

-- {COLUMN} 1.3.6.1.4.1.2356.11.1.59.108.9.1.4
lcsStatusWtpMngmt11uGeneralEntryUplinkSpeed OBJECT-TYPE
    SYNTAX     Integer32 (0..2147483647)
    MAX-ACCESS read-only
    STATUS     current
    DESCRIPTION
            "-- empty --"
    ::= { lcsStatusWtpMngmt11uGeneralEntry 4 }

-- {COLUMN} 1.3.6.1.4.1.2356.11.1.59.108.9.1.5
lcsStatusWtpMngmt11uGeneralEntryIpv4AddrType OBJECT-TYPE
    SYNTAX     INTEGER {
                  eNotAvailable (0),
                  ePublicAddrAvailable (1),
                  ePortRestrAddrAvail (2),
                  eSingleNatPrivAddrAvail (3),
                  eDoubleNatPrivAddrAvail (4),
                  ePortRestrSingleNatAddrAvail (5),
                  ePortRestrDoubleNatAddrAvail (6),
                  eAvailabilityNotKnown (7)
            }
    MAX-ACCESS read-only
    STATUS     current
    DESCRIPTION
            "-- empty --"
    ::= { lcsStatusWtpMngmt11uGeneralEntry 5 }

-- {COLUMN} 1.3.6.1.4.1.2356.11.1.59.108.9.1.6
lcsStatusWtpMngmt11uGeneralEntryIpv6AddrType OBJECT-TYPE
    SYNTAX     INTEGER {
                  eNotAvailable (0),
                  eAvailable (1),
                  eAvailabilityNotKnown (2)
            }
    MAX-ACCESS read-only
    STATUS     current
    DESCRIPTION
            "-- empty --"
    ::= { lcsStatusWtpMngmt11uGeneralEntry 6 }

-- {COLUMN} 1.3.6.1.4.1.2356.11.1.59.108.9.1.7
lcsStatusWtpMngmt11uGeneralEntryVenueGroup OBJECT-TYPE
    SYNTAX     INTEGER {
                  eUnspecified (0),
                  eAssembly (1),
                  eBusiness (2),
                  eEducational (3),
                  eFactoryAndIndustrial (4),
                  eInstitutional (5),
                  eMercantile (6),
                  eResindential (7),
                  eStorage (8),
                  eUtilityAndMiscellaneous (9),
                  eVehicular (10),
                  eOutdoor (11)
            }
    MAX-ACCESS read-only
    STATUS     current
    DESCRIPTION
            "-- empty --"
    ::= { lcsStatusWtpMngmt11uGeneralEntry 7 }

-- {COLUMN} 1.3.6.1.4.1.2356.11.1.59.108.9.1.8
lcsStatusWtpMngmt11uGeneralEntryVenueType OBJECT-TYPE
    SYNTAX     Integer32 (0..255)
    MAX-ACCESS read-only
    STATUS     current
    DESCRIPTION
            "-- empty --"
    ::= { lcsStatusWtpMngmt11uGeneralEntry 8 }

-- {COLUMN} 1.3.6.1.4.1.2356.11.1.59.108.9.1.9
lcsStatusWtpMngmt11uGeneralEntryVenueName OBJECT-TYPE
    SYNTAX     DisplayString (SIZE(0..32))
    MAX-ACCESS read-only
    STATUS     current
    DESCRIPTION
            "-- empty --"
    ::= { lcsStatusWtpMngmt11uGeneralEntry 9 }

-- {NODE} 1.3.6.1.4.1.2356.11.1.59.109
lcsStatusWtpMngmtAutowdsOperation OBJECT IDENTIFIER ::= { lcsStatusWtpMngmt 109 }

-- {SCALAR} 1.3.6.1.4.1.2356.11.1.59.109.1
lcsStatusWtpMngmtAutowdsOperationActiveScanMode OBJECT-TYPE
    SYNTAX     INTEGER {
                  eNone (0),
                  eExpress (1),
                  ePreconfigured (2)
            }
    MAX-ACCESS read-only
    STATUS     current
    DESCRIPTION
            "-- empty --"
    ::= { lcsStatusWtpMngmtAutowdsOperation 1 }

-- {SCALAR} 1.3.6.1.4.1.2356.11.1.59.109.2
lcsStatusWtpMngmtAutowdsOperationCapwapUp OBJECT-TYPE
    SYNTAX     INTEGER {
                  eNo (0),
                  eYes (1)
            }
    MAX-ACCESS read-only
    STATUS     current
    DESCRIPTION
            "-- empty --"
    ::= { lcsStatusWtpMngmtAutowdsOperation 2 }

-- {SCALAR} 1.3.6.1.4.1.2356.11.1.59.109.3
lcsStatusWtpMngmtAutowdsOperationCapwapUpAgainAfterConfig OBJECT-TYPE
    SYNTAX     INTEGER {
                  eNo (0),
                  eYes (1)
            }
    MAX-ACCESS read-only
    STATUS     current
    DESCRIPTION
            "-- empty --"
    ::= { lcsStatusWtpMngmtAutowdsOperation 3 }

-- {SCALAR} 1.3.6.1.4.1.2356.11.1.59.109.4
lcsStatusWtpMngmtAutowdsOperationAutowdsFallbackTimer OBJECT-TYPE
    SYNTAX     Integer32 (0..2147483647)
    MAX-ACCESS read-only
    STATUS     current
    DESCRIPTION
            "-- empty --"
    ::= { lcsStatusWtpMngmtAutowdsOperation 4 }

-- {SCALAR} 1.3.6.1.4.1.2356.11.1.59.109.5
lcsStatusWtpMngmtAutowdsOperationAutowdsFallbForceDeassocTimer OBJECT-TYPE
    SYNTAX     Integer32 (0..2147483647)
    MAX-ACCESS read-only
    STATUS     current
    DESCRIPTION
            ""
    ::= { lcsStatusWtpMngmtAutowdsOperation 5 }

-- {SCALAR} 1.3.6.1.4.1.2356.11.1.59.109.6
lcsStatusWtpMngmtAutowdsOperationCapwapContinuationTimer OBJECT-TYPE
    SYNTAX     Integer32 (0..2147483647)
    MAX-ACCESS read-only
    STATUS     current
    DESCRIPTION
            "-- empty --"
    ::= { lcsStatusWtpMngmtAutowdsOperation 6 }

-- {SCALAR} 1.3.6.1.4.1.2356.11.1.59.109.7
lcsStatusWtpMngmtAutowdsOperationCapwapSilentTimer OBJECT-TYPE
    SYNTAX     Integer32 (0..2147483647)
    MAX-ACCESS read-only
    STATUS     current
    DESCRIPTION
            "-- empty --"
    ::= { lcsStatusWtpMngmtAutowdsOperation 7 }

-- {TABLE} 1.3.6.1.4.1.2356.11.1.59.110
lcsStatusWtpMngmtLedProfilesTable OBJECT-TYPE
    SYNTAX     SEQUENCE OF LcsStatusWtpMngmtLedProfilesEntry
    MAX-ACCESS not-accessible
    STATUS     current
    DESCRIPTION
            "-- empty --"
    ::= { lcsStatusWtpMngmt 110 }

-- {ROW} 1.3.6.1.4.1.2356.11.1.59.110.1
lcsStatusWtpMngmtLedProfilesEntry OBJECT-TYPE
    SYNTAX     LcsStatusWtpMngmtLedProfilesEntry
    MAX-ACCESS not-accessible
    STATUS     current
    DESCRIPTION
            ""
    INDEX {
            lcsStatusWtpMngmtLedProfilesEntryName
          }
    ::= { lcsStatusWtpMngmtLedProfilesTable 1 }

LcsStatusWtpMngmtLedProfilesEntry ::= SEQUENCE {
            lcsStatusWtpMngmtLedProfilesEntryName DisplayString,
            lcsStatusWtpMngmtLedProfilesEntryLedMode INTEGER,
            lcsStatusWtpMngmtLedProfilesEntryLedOffSeconds Integer32
    }

-- {COLUMN} 1.3.6.1.4.1.2356.11.1.59.110.1.1
lcsStatusWtpMngmtLedProfilesEntryName OBJECT-TYPE
    SYNTAX     DisplayString (SIZE(0..31))
    MAX-ACCESS read-only
    STATUS     current
    DESCRIPTION
            "-- empty --"
    ::= { lcsStatusWtpMngmtLedProfilesEntry 1 }

-- {COLUMN} 1.3.6.1.4.1.2356.11.1.59.110.1.4
lcsStatusWtpMngmtLedProfilesEntryLedMode OBJECT-TYPE
    SYNTAX     INTEGER {
                  eOn (0),
                  eOff (1),
                  eTimedOff (2)
            }
    MAX-ACCESS read-only
    STATUS     current
    DESCRIPTION
            "-- empty --"
    ::= { lcsStatusWtpMngmtLedProfilesEntry 4 }

-- {COLUMN} 1.3.6.1.4.1.2356.11.1.59.110.1.5
lcsStatusWtpMngmtLedProfilesEntryLedOffSeconds OBJECT-TYPE
    SYNTAX     Integer32 (0..2147483647)
    MAX-ACCESS read-only
    STATUS     current
    DESCRIPTION
            "-- empty --"
    ::= { lcsStatusWtpMngmtLedProfilesEntry 5 }

-- {NODE} 1.3.6.1.4.1.2356.11.1.59.111
lcsStatusWtpMngmtLbs OBJECT IDENTIFIER ::= { lcsStatusWtpMngmt 111 }

-- {TABLE} 1.3.6.1.4.1.2356.11.1.59.111.1
lcsStatusWtpMngmtLbsGeneralTable OBJECT-TYPE
    SYNTAX     SEQUENCE OF LcsStatusWtpMngmtLbsGeneralEntry
    MAX-ACCESS not-accessible
    STATUS     current
    DESCRIPTION
            "-- empty --"
    ::= { lcsStatusWtpMngmtLbs 1 }

-- {ROW} 1.3.6.1.4.1.2356.11.1.59.111.1.1
lcsStatusWtpMngmtLbsGeneralEntry OBJECT-TYPE
    SYNTAX     LcsStatusWtpMngmtLbsGeneralEntry
    MAX-ACCESS not-accessible
    STATUS     current
    DESCRIPTION
            ""
    INDEX {
            lcsStatusWtpMngmtLbsGeneralEntryName
          }
    ::= { lcsStatusWtpMngmtLbsGeneralTable 1 }

LcsStatusWtpMngmtLbsGeneralEntry ::= SEQUENCE {
            lcsStatusWtpMngmtLbsGeneralEntryName DisplayString,
            lcsStatusWtpMngmtLbsGeneralEntryOperating INTEGER,
            lcsStatusWtpMngmtLbsGeneralEntryUseTlsConnection INTEGER,
            lcsStatusWtpMngmtLbsGeneralEntryLbsServerAddress DisplayString,
            lcsStatusWtpMngmtLbsGeneralEntryLbsServerPort Integer32,
            lcsStatusWtpMngmtLbsGeneralEntryUserName DisplayString,
            lcsStatusWtpMngmtLbsGeneralEntryPassword DisplayString,
            lcsStatusWtpMngmtLbsGeneralEntryAggregation INTEGER,
            lcsStatusWtpMngmtLbsGeneralEntrySequenceNumberTransmit INTEGER,
            lcsStatusWtpMngmtLbsGeneralEntrySsidTransmit INTEGER,
            lcsStatusWtpMngmtLbsGeneralEntryIfcTrans INTEGER,
            lcsStatusWtpMngmtLbsGeneralEntryBssidTransmit INTEGER,
            lcsStatusWtpMngmtLbsGeneralEntrySignalLevelTransmit INTEGER,
            lcsStatusWtpMngmtLbsGeneralEntryFrequencyTransmit INTEGER,
            lcsStatusWtpMngmtLbsGeneralEntryNoiseTransmit INTEGER,
            lcsStatusWtpMngmtLbsGeneralEntryWlanFrameTypeTransmit INTEGER
    }

-- {COLUMN} 1.3.6.1.4.1.2356.11.1.59.111.1.1.1
lcsStatusWtpMngmtLbsGeneralEntryName OBJECT-TYPE
    SYNTAX     DisplayString (SIZE(0..31))
    MAX-ACCESS read-only
    STATUS     current
    DESCRIPTION
            "-- empty --"
    ::= { lcsStatusWtpMngmtLbsGeneralEntry 1 }

-- {COLUMN} 1.3.6.1.4.1.2356.11.1.59.111.1.1.2
lcsStatusWtpMngmtLbsGeneralEntryOperating OBJECT-TYPE
    SYNTAX     INTEGER {
                  eNo (0),
                  eYes (1)
            }
    MAX-ACCESS read-only
    STATUS     current
    DESCRIPTION
            "-- empty --"
    ::= { lcsStatusWtpMngmtLbsGeneralEntry 2 }

-- {COLUMN} 1.3.6.1.4.1.2356.11.1.59.111.1.1.3
lcsStatusWtpMngmtLbsGeneralEntryUseTlsConnection OBJECT-TYPE
    SYNTAX     INTEGER {
                  eNo (0),
                  eYes (1)
            }
    MAX-ACCESS read-only
    STATUS     current
    DESCRIPTION
            "-- empty --"
    ::= { lcsStatusWtpMngmtLbsGeneralEntry 3 }

-- {COLUMN} 1.3.6.1.4.1.2356.11.1.59.111.1.1.4
lcsStatusWtpMngmtLbsGeneralEntryLbsServerAddress OBJECT-TYPE
    SYNTAX     DisplayString (SIZE(0..64))
    MAX-ACCESS read-only
    STATUS     current
    DESCRIPTION
            "-- empty --"
    ::= { lcsStatusWtpMngmtLbsGeneralEntry 4 }

-- {COLUMN} 1.3.6.1.4.1.2356.11.1.59.111.1.1.5
lcsStatusWtpMngmtLbsGeneralEntryLbsServerPort OBJECT-TYPE
    SYNTAX     Integer32 (0..65535)
    MAX-ACCESS read-only
    STATUS     current
    DESCRIPTION
            "-- empty --"
    ::= { lcsStatusWtpMngmtLbsGeneralEntry 5 }

-- {COLUMN} 1.3.6.1.4.1.2356.11.1.59.111.1.1.6
lcsStatusWtpMngmtLbsGeneralEntryUserName OBJECT-TYPE
    SYNTAX     DisplayString (SIZE(0..64))
    MAX-ACCESS read-only
    STATUS     current
    DESCRIPTION
            "-- empty --"
    ::= { lcsStatusWtpMngmtLbsGeneralEntry 6 }

-- {COLUMN} 1.3.6.1.4.1.2356.11.1.59.111.1.1.7
lcsStatusWtpMngmtLbsGeneralEntryPassword OBJECT-TYPE
    SYNTAX     DisplayString (SIZE(0..32))
    MAX-ACCESS read-only
    STATUS     current
    DESCRIPTION
            "-- empty --"
    ::= { lcsStatusWtpMngmtLbsGeneralEntry 7 }

-- {COLUMN} 1.3.6.1.4.1.2356.11.1.59.111.1.1.8
lcsStatusWtpMngmtLbsGeneralEntryAggregation OBJECT-TYPE
    SYNTAX     INTEGER {
                  eNo (0),
                  eYes (1)
            }
    MAX-ACCESS read-only
    STATUS     current
    DESCRIPTION
            "-- empty --"
    ::= { lcsStatusWtpMngmtLbsGeneralEntry 8 }

-- {COLUMN} 1.3.6.1.4.1.2356.11.1.59.111.1.1.9
lcsStatusWtpMngmtLbsGeneralEntrySequenceNumberTransmit OBJECT-TYPE
    SYNTAX     INTEGER {
                  eNo (0),
                  eYes (1)
            }
    MAX-ACCESS read-only
    STATUS     current
    DESCRIPTION
            "-- empty --"
    ::= { lcsStatusWtpMngmtLbsGeneralEntry 9 }

-- {COLUMN} 1.3.6.1.4.1.2356.11.1.59.111.1.1.10
lcsStatusWtpMngmtLbsGeneralEntrySsidTransmit OBJECT-TYPE
    SYNTAX     INTEGER {
                  eNo (0),
                  eYes (1)
            }
    MAX-ACCESS read-only
    STATUS     current
    DESCRIPTION
            "-- empty --"
    ::= { lcsStatusWtpMngmtLbsGeneralEntry 10 }

-- {COLUMN} 1.3.6.1.4.1.2356.11.1.59.111.1.1.11
lcsStatusWtpMngmtLbsGeneralEntryIfcTrans OBJECT-TYPE
    SYNTAX     INTEGER {
                  eNo (0),
                  eYes (1)
            }
    MAX-ACCESS read-only
    STATUS     current
    DESCRIPTION
            ""
    ::= { lcsStatusWtpMngmtLbsGeneralEntry 11 }

-- {COLUMN} 1.3.6.1.4.1.2356.11.1.59.111.1.1.12
lcsStatusWtpMngmtLbsGeneralEntryBssidTransmit OBJECT-TYPE
    SYNTAX     INTEGER {
                  eNo (0),
                  eYes (1)
            }
    MAX-ACCESS read-only
    STATUS     current
    DESCRIPTION
            "-- empty --"
    ::= { lcsStatusWtpMngmtLbsGeneralEntry 12 }

-- {COLUMN} 1.3.6.1.4.1.2356.11.1.59.111.1.1.13
lcsStatusWtpMngmtLbsGeneralEntrySignalLevelTransmit OBJECT-TYPE
    SYNTAX     INTEGER {
                  eNo (0),
                  eYes (1)
            }
    MAX-ACCESS read-only
    STATUS     current
    DESCRIPTION
            "-- empty --"
    ::= { lcsStatusWtpMngmtLbsGeneralEntry 13 }

-- {COLUMN} 1.3.6.1.4.1.2356.11.1.59.111.1.1.14
lcsStatusWtpMngmtLbsGeneralEntryFrequencyTransmit OBJECT-TYPE
    SYNTAX     INTEGER {
                  eNo (0),
                  eYes (1)
            }
    MAX-ACCESS read-only
    STATUS     current
    DESCRIPTION
            "-- empty --"
    ::= { lcsStatusWtpMngmtLbsGeneralEntry 14 }

-- {COLUMN} 1.3.6.1.4.1.2356.11.1.59.111.1.1.15
lcsStatusWtpMngmtLbsGeneralEntryNoiseTransmit OBJECT-TYPE
    SYNTAX     INTEGER {
                  eNo (0),
                  eYes (1)
            }
    MAX-ACCESS read-only
    STATUS     current
    DESCRIPTION
            "-- empty --"
    ::= { lcsStatusWtpMngmtLbsGeneralEntry 15 }

-- {COLUMN} 1.3.6.1.4.1.2356.11.1.59.111.1.1.16
lcsStatusWtpMngmtLbsGeneralEntryWlanFrameTypeTransmit OBJECT-TYPE
    SYNTAX     INTEGER {
                  eNo (0),
                  eYes (1)
            }
    MAX-ACCESS read-only
    STATUS     current
    DESCRIPTION
            "-- empty --"
    ::= { lcsStatusWtpMngmtLbsGeneralEntry 16 }

-- {TABLE} 1.3.6.1.4.1.2356.11.1.59.111.2
lcsStatusWtpMngmtLbsDevLocTable OBJECT-TYPE
    SYNTAX     SEQUENCE OF LcsStatusWtpMngmtLbsDevLocEntry
    MAX-ACCESS not-accessible
    STATUS     current
    DESCRIPTION
            ""
    ::= { lcsStatusWtpMngmtLbs 2 }

-- {ROW} 1.3.6.1.4.1.2356.11.1.59.111.2.1
lcsStatusWtpMngmtLbsDevLocEntry OBJECT-TYPE
    SYNTAX     LcsStatusWtpMngmtLbsDevLocEntry
    MAX-ACCESS not-accessible
    STATUS     current
    DESCRIPTION
            ""
    INDEX {
            lcsStatusWtpMngmtLbsDevLocEntryName
          }
    ::= { lcsStatusWtpMngmtLbsDevLocTable 1 }

LcsStatusWtpMngmtLbsDevLocEntry ::= SEQUENCE {
            lcsStatusWtpMngmtLbsDevLocEntryName DisplayString,
            lcsStatusWtpMngmtLbsDevLocEntryFloor Integer32,
            lcsStatusWtpMngmtLbsDevLocEntryHeight Integer32,
            lcsStatusWtpMngmtLbsDevLocEntryLatDeg Integer32,
            lcsStatusWtpMngmtLbsDevLocEntryLatMin Integer32,
            lcsStatusWtpMngmtLbsDevLocEntryLatSec Integer32,
            lcsStatusWtpMngmtLbsDevLocEntryLatHemi INTEGER,
            lcsStatusWtpMngmtLbsDevLocEntryLongDeg Integer32,
            lcsStatusWtpMngmtLbsDevLocEntryLongMin Integer32,
            lcsStatusWtpMngmtLbsDevLocEntryLongSec Integer32,
            lcsStatusWtpMngmtLbsDevLocEntryLongHemi INTEGER,
            lcsStatusWtpMngmtLbsDevLocEntryDescription DisplayString,
            lcsStatusWtpMngmtLbsDevLocEntryLatDecDeg DisplayString,
            lcsStatusWtpMngmtLbsDevLocEntryLongDecDeg DisplayString
    }

-- {COLUMN} 1.3.6.1.4.1.2356.11.1.59.111.2.1.1
lcsStatusWtpMngmtLbsDevLocEntryName OBJECT-TYPE
    SYNTAX     DisplayString (SIZE(0..31))
    MAX-ACCESS read-only
    STATUS     current
    DESCRIPTION
            "-- empty --"
    ::= { lcsStatusWtpMngmtLbsDevLocEntry 1 }

-- {COLUMN} 1.3.6.1.4.1.2356.11.1.59.111.2.1.2
lcsStatusWtpMngmtLbsDevLocEntryFloor OBJECT-TYPE
    SYNTAX     Integer32 (-32768..32767)
    MAX-ACCESS read-only
    STATUS     current
    DESCRIPTION
            "-- empty --"
    ::= { lcsStatusWtpMngmtLbsDevLocEntry 2 }

-- {COLUMN} 1.3.6.1.4.1.2356.11.1.59.111.2.1.3
lcsStatusWtpMngmtLbsDevLocEntryHeight OBJECT-TYPE
    SYNTAX     Integer32 (-32768..32767)
    MAX-ACCESS read-only
    STATUS     current
    DESCRIPTION
            "-- empty --"
    ::= { lcsStatusWtpMngmtLbsDevLocEntry 3 }

-- {COLUMN} 1.3.6.1.4.1.2356.11.1.59.111.2.1.4
lcsStatusWtpMngmtLbsDevLocEntryLatDeg OBJECT-TYPE
    SYNTAX     Integer32 (0..255)
    MAX-ACCESS read-only
    STATUS     current
    DESCRIPTION
            ""
    ::= { lcsStatusWtpMngmtLbsDevLocEntry 4 }

-- {COLUMN} 1.3.6.1.4.1.2356.11.1.59.111.2.1.5
lcsStatusWtpMngmtLbsDevLocEntryLatMin OBJECT-TYPE
    SYNTAX     Integer32 (0..255)
    MAX-ACCESS read-only
    STATUS     current
    DESCRIPTION
            ""
    ::= { lcsStatusWtpMngmtLbsDevLocEntry 5 }

-- {COLUMN} 1.3.6.1.4.1.2356.11.1.59.111.2.1.6
lcsStatusWtpMngmtLbsDevLocEntryLatSec OBJECT-TYPE
    SYNTAX     Integer32 (0..2147483647)
    MAX-ACCESS read-only
    STATUS     current
    DESCRIPTION
            ""
    ::= { lcsStatusWtpMngmtLbsDevLocEntry 6 }

-- {COLUMN} 1.3.6.1.4.1.2356.11.1.59.111.2.1.7
lcsStatusWtpMngmtLbsDevLocEntryLatHemi OBJECT-TYPE
    SYNTAX     INTEGER {
                  eN (0),
                  eS (1)
            }
    MAX-ACCESS read-only
    STATUS     current
    DESCRIPTION
            ""
    ::= { lcsStatusWtpMngmtLbsDevLocEntry 7 }

-- {COLUMN} 1.3.6.1.4.1.2356.11.1.59.111.2.1.8
lcsStatusWtpMngmtLbsDevLocEntryLongDeg OBJECT-TYPE
    SYNTAX     Integer32 (0..255)
    MAX-ACCESS read-only
    STATUS     current
    DESCRIPTION
            ""
    ::= { lcsStatusWtpMngmtLbsDevLocEntry 8 }

-- {COLUMN} 1.3.6.1.4.1.2356.11.1.59.111.2.1.9
lcsStatusWtpMngmtLbsDevLocEntryLongMin OBJECT-TYPE
    SYNTAX     Integer32 (0..255)
    MAX-ACCESS read-only
    STATUS     current
    DESCRIPTION
            ""
    ::= { lcsStatusWtpMngmtLbsDevLocEntry 9 }

-- {COLUMN} 1.3.6.1.4.1.2356.11.1.59.111.2.1.10
lcsStatusWtpMngmtLbsDevLocEntryLongSec OBJECT-TYPE
    SYNTAX     Integer32 (0..2147483647)
    MAX-ACCESS read-only
    STATUS     current
    DESCRIPTION
            ""
    ::= { lcsStatusWtpMngmtLbsDevLocEntry 10 }

-- {COLUMN} 1.3.6.1.4.1.2356.11.1.59.111.2.1.11
lcsStatusWtpMngmtLbsDevLocEntryLongHemi OBJECT-TYPE
    SYNTAX     INTEGER {
                  eE (0),
                  eW (1)
            }
    MAX-ACCESS read-only
    STATUS     current
    DESCRIPTION
            ""
    ::= { lcsStatusWtpMngmtLbsDevLocEntry 11 }

-- {COLUMN} 1.3.6.1.4.1.2356.11.1.59.111.2.1.12
lcsStatusWtpMngmtLbsDevLocEntryDescription OBJECT-TYPE
    SYNTAX     DisplayString (SIZE(0..31))
    MAX-ACCESS read-only
    STATUS     current
    DESCRIPTION
            "-- empty --"
    ::= { lcsStatusWtpMngmtLbsDevLocEntry 12 }

-- {COLUMN} 1.3.6.1.4.1.2356.11.1.59.111.2.1.13
lcsStatusWtpMngmtLbsDevLocEntryLatDecDeg OBJECT-TYPE
    SYNTAX     DisplayString (SIZE(0..12))
    MAX-ACCESS read-only
    STATUS     current
    DESCRIPTION
            ""
    ::= { lcsStatusWtpMngmtLbsDevLocEntry 13 }

-- {COLUMN} 1.3.6.1.4.1.2356.11.1.59.111.2.1.14
lcsStatusWtpMngmtLbsDevLocEntryLongDecDeg OBJECT-TYPE
    SYNTAX     DisplayString (SIZE(0..12))
    MAX-ACCESS read-only
    STATUS     current
    DESCRIPTION
            ""
    ::= { lcsStatusWtpMngmtLbsDevLocEntry 14 }

-- {NODE} 1.3.6.1.4.1.2356.11.1.59.112
lcsStatusWtpMngmtLepsU OBJECT IDENTIFIER ::= { lcsStatusWtpMngmt 112 }

-- {TABLE} 1.3.6.1.4.1.2356.11.1.59.112.1
lcsStatusWtpMngmtLepsUProfilesTable OBJECT-TYPE
    SYNTAX     SEQUENCE OF LcsStatusWtpMngmtLepsUProfilesEntry
    MAX-ACCESS not-accessible
    STATUS     current
    DESCRIPTION
            "-- empty --"
    ::= { lcsStatusWtpMngmtLepsU 1 }

-- {ROW} 1.3.6.1.4.1.2356.11.1.59.112.1.1
lcsStatusWtpMngmtLepsUProfilesEntry OBJECT-TYPE
    SYNTAX     LcsStatusWtpMngmtLepsUProfilesEntry
    MAX-ACCESS not-accessible
    STATUS     current
    DESCRIPTION
            ""
    INDEX {
            lcsStatusWtpMngmtLepsUProfilesEntryName
          }
    ::= { lcsStatusWtpMngmtLepsUProfilesTable 1 }

LcsStatusWtpMngmtLepsUProfilesEntry ::= SEQUENCE {
            lcsStatusWtpMngmtLepsUProfilesEntryName DisplayString,
            lcsStatusWtpMngmtLepsUProfilesEntryNetworkprofile DisplayString
    }

-- {COLUMN} 1.3.6.1.4.1.2356.11.1.59.112.1.1.1
lcsStatusWtpMngmtLepsUProfilesEntryName OBJECT-TYPE
    SYNTAX     DisplayString (SIZE(0..32))
    MAX-ACCESS read-only
    STATUS     current
    DESCRIPTION
            "-- empty --"
    ::= { lcsStatusWtpMngmtLepsUProfilesEntry 1 }

-- {COLUMN} 1.3.6.1.4.1.2356.11.1.59.112.1.1.2
lcsStatusWtpMngmtLepsUProfilesEntryNetworkprofile OBJECT-TYPE
    SYNTAX     DisplayString (SIZE(0..31))
    MAX-ACCESS read-only
    STATUS     current
    DESCRIPTION
            "-- empty --"
    ::= { lcsStatusWtpMngmtLepsUProfilesEntry 2 }

-- {TABLE} 1.3.6.1.4.1.2356.11.1.59.112.2
lcsStatusWtpMngmtLepsUUsersTable OBJECT-TYPE
    SYNTAX     SEQUENCE OF LcsStatusWtpMngmtLepsUUsersEntry
    MAX-ACCESS not-accessible
    STATUS     current
    DESCRIPTION
            "-- empty --"
    ::= { lcsStatusWtpMngmtLepsU 2 }

-- {ROW} 1.3.6.1.4.1.2356.11.1.59.112.2.1
lcsStatusWtpMngmtLepsUUsersEntry OBJECT-TYPE
    SYNTAX     LcsStatusWtpMngmtLepsUUsersEntry
    MAX-ACCESS not-accessible
    STATUS     current
    DESCRIPTION
            ""
    INDEX {
            lcsStatusWtpMngmtLepsUUsersEntryName
          }
    ::= { lcsStatusWtpMngmtLepsUUsersTable 1 }

LcsStatusWtpMngmtLepsUUsersEntry ::= SEQUENCE {
            lcsStatusWtpMngmtLepsUUsersEntryName DisplayString,
            lcsStatusWtpMngmtLepsUUsersEntryProfile DisplayString,
            lcsStatusWtpMngmtLepsUUsersEntryWpaPassphrase DisplayString,
            lcsStatusWtpMngmtLepsUUsersEntryPerClientTxLimit Integer32,
            lcsStatusWtpMngmtLepsUUsersEntryPerClientRxLimit Integer32,
            lcsStatusWtpMngmtLepsUUsersEntryVlanIdnew Integer32
    }

-- {COLUMN} 1.3.6.1.4.1.2356.11.1.59.112.2.1.1
lcsStatusWtpMngmtLepsUUsersEntryName OBJECT-TYPE
    SYNTAX     DisplayString (SIZE(0..32))
    MAX-ACCESS read-only
    STATUS     current
    DESCRIPTION
            "-- empty --"
    ::= { lcsStatusWtpMngmtLepsUUsersEntry 1 }

-- {COLUMN} 1.3.6.1.4.1.2356.11.1.59.112.2.1.2
lcsStatusWtpMngmtLepsUUsersEntryProfile OBJECT-TYPE
    SYNTAX     DisplayString (SIZE(0..32))
    MAX-ACCESS read-only
    STATUS     current
    DESCRIPTION
            "-- empty --"
    ::= { lcsStatusWtpMngmtLepsUUsersEntry 2 }

-- {COLUMN} 1.3.6.1.4.1.2356.11.1.59.112.2.1.3
lcsStatusWtpMngmtLepsUUsersEntryWpaPassphrase OBJECT-TYPE
    SYNTAX     DisplayString (SIZE(0..63))
    MAX-ACCESS read-only
    STATUS     current
    DESCRIPTION
            "-- empty --"
    ::= { lcsStatusWtpMngmtLepsUUsersEntry 3 }

-- {COLUMN} 1.3.6.1.4.1.2356.11.1.59.112.2.1.4
lcsStatusWtpMngmtLepsUUsersEntryPerClientTxLimit OBJECT-TYPE
    SYNTAX     Integer32 (0..2147483647)
    MAX-ACCESS read-only
    STATUS     current
    DESCRIPTION
            "-- empty --"
    ::= { lcsStatusWtpMngmtLepsUUsersEntry 4 }

-- {COLUMN} 1.3.6.1.4.1.2356.11.1.59.112.2.1.5
lcsStatusWtpMngmtLepsUUsersEntryPerClientRxLimit OBJECT-TYPE
    SYNTAX     Integer32 (0..2147483647)
    MAX-ACCESS read-only
    STATUS     current
    DESCRIPTION
            "-- empty --"
    ::= { lcsStatusWtpMngmtLepsUUsersEntry 5 }

-- {COLUMN} 1.3.6.1.4.1.2356.11.1.59.112.2.1.6
lcsStatusWtpMngmtLepsUUsersEntryVlanIdnew OBJECT-TYPE
    SYNTAX     Integer32 (0..65535)
    MAX-ACCESS read-only
    STATUS     current
    DESCRIPTION
            ""
    ::= { lcsStatusWtpMngmtLepsUUsersEntry 6 }

-- {TABLE} 1.3.6.1.4.1.2356.11.1.59.120
lcsStatusWtpMngmtLogTableTable OBJECT-TYPE
    SYNTAX     SEQUENCE OF LcsStatusWtpMngmtLogTableEntry
    MAX-ACCESS not-accessible
    STATUS     current
    DESCRIPTION
            ""
    ::= { lcsStatusWtpMngmt 120 }

-- {ROW} 1.3.6.1.4.1.2356.11.1.59.120.1
lcsStatusWtpMngmtLogTableEntry OBJECT-TYPE
    SYNTAX     LcsStatusWtpMngmtLogTableEntry
    MAX-ACCESS not-accessible
    STATUS     current
    DESCRIPTION
            ""
    INDEX {
            lcsStatusWtpMngmtLogTableEntryIndex
          }
    ::= { lcsStatusWtpMngmtLogTableTable 1 }

LcsStatusWtpMngmtLogTableEntry ::= SEQUENCE {
            lcsStatusWtpMngmtLogTableEntryIndex Integer32,
            lcsStatusWtpMngmtLogTableEntryTime DisplayString,
            lcsStatusWtpMngmtLogTableEntryLevel INTEGER,
            lcsStatusWtpMngmtLogTableEntryEvent DisplayString
    }

-- {COLUMN} 1.3.6.1.4.1.2356.11.1.59.120.1.1
lcsStatusWtpMngmtLogTableEntryIndex OBJECT-TYPE
    SYNTAX     Integer32 (0..2147483647)
    MAX-ACCESS read-only
    STATUS     current
    DESCRIPTION
            ""
    ::= { lcsStatusWtpMngmtLogTableEntry 1 }

-- {COLUMN} 1.3.6.1.4.1.2356.11.1.59.120.1.2
lcsStatusWtpMngmtLogTableEntryTime OBJECT-TYPE
    SYNTAX     DisplayString (SIZE(0..19))
    MAX-ACCESS read-only
    STATUS     current
    DESCRIPTION
            ""
    ::= { lcsStatusWtpMngmtLogTableEntry 2 }

-- {COLUMN} 1.3.6.1.4.1.2356.11.1.59.120.1.3
lcsStatusWtpMngmtLogTableEntryLevel OBJECT-TYPE
    SYNTAX     INTEGER {
                  eDebug (1),
                  eInfo (2),
                  eWarning (4),
                  eError (8),
                  eStatechange (16),
                  eAutowds (32)
            }
    MAX-ACCESS read-only
    STATUS     current
    DESCRIPTION
            "-- empty --"
    ::= { lcsStatusWtpMngmtLogTableEntry 3 }

-- {COLUMN} 1.3.6.1.4.1.2356.11.1.59.120.1.6
lcsStatusWtpMngmtLogTableEntryEvent OBJECT-TYPE
    SYNTAX     DisplayString (SIZE(0..80))
    MAX-ACCESS read-only
    STATUS     current
    DESCRIPTION
            ""
    ::= { lcsStatusWtpMngmtLogTableEntry 6 }

-- {NODE} 1.3.6.1.4.1.2356.11.1.59.121
lcsStatusWtpMngmtWirelessEpaperProfile OBJECT IDENTIFIER ::= { lcsStatusWtpMngmt 121 }

-- {SCALAR} 1.3.6.1.4.1.2356.11.1.59.121.1
lcsStatusWtpMngmtWirelessEpaperProfileOperating OBJECT-TYPE
    SYNTAX     INTEGER {
                  eNo (0),
                  eYes (1)
            }
    MAX-ACCESS read-only
    STATUS     current
    DESCRIPTION
            "-- empty --"
    ::= { lcsStatusWtpMngmtWirelessEpaperProfile 1 }

-- {SCALAR} 1.3.6.1.4.1.2356.11.1.59.121.2
lcsStatusWtpMngmtWirelessEpaperProfilePort OBJECT-TYPE
    SYNTAX     Integer32 (0..65535)
    MAX-ACCESS read-only
    STATUS     current
    DESCRIPTION
            "-- empty --"
    ::= { lcsStatusWtpMngmtWirelessEpaperProfile 2 }

-- {SCALAR} 1.3.6.1.4.1.2356.11.1.59.121.3
lcsStatusWtpMngmtWirelessEpaperProfileCurrentChannel OBJECT-TYPE
    SYNTAX     INTEGER {
                  e2404mhz (0),
                  e2410mhz (1),
                  e2422mhz (2),
                  e2425mhz (3),
                  e2442mhz (4),
                  e2450mhz (5),
                  e2462mhz (6),
                  e2470mhz (7),
                  e2474mhz (8),
                  e2477mhz (9),
                  e2480mhz (10),
                  eAuto (255)
            }
    MAX-ACCESS read-only
    STATUS     current
    DESCRIPTION
            "-- empty --"
    ::= { lcsStatusWtpMngmtWirelessEpaperProfile 3 }

-- {NODE} 1.3.6.1.4.1.2356.11.1.59.122
lcsStatusWtpMngmtIbeaconProfile OBJECT IDENTIFIER ::= { lcsStatusWtpMngmt 122 }

-- {SCALAR} 1.3.6.1.4.1.2356.11.1.59.122.1
lcsStatusWtpMngmtIbeaconProfileOperating OBJECT-TYPE
    SYNTAX     INTEGER {
                  eNo (0),
                  eYes (1)
            }
    MAX-ACCESS read-only
    STATUS     current
    DESCRIPTION
            "-- empty --"
    ::= { lcsStatusWtpMngmtIbeaconProfile 1 }

-- {SCALAR} 1.3.6.1.4.1.2356.11.1.59.122.2
lcsStatusWtpMngmtIbeaconProfileUuid OBJECT-TYPE
    SYNTAX     DisplayString (SIZE(0..36))
    MAX-ACCESS read-only
    STATUS     current
    DESCRIPTION
            "-- empty --"
    ::= { lcsStatusWtpMngmtIbeaconProfile 2 }

-- {SCALAR} 1.3.6.1.4.1.2356.11.1.59.122.3
lcsStatusWtpMngmtIbeaconProfileMajor OBJECT-TYPE
    SYNTAX     Integer32 (0..65535)
    MAX-ACCESS read-only
    STATUS     current
    DESCRIPTION
            "-- empty --"
    ::= { lcsStatusWtpMngmtIbeaconProfile 3 }

-- {SCALAR} 1.3.6.1.4.1.2356.11.1.59.122.4
lcsStatusWtpMngmtIbeaconProfileMinor OBJECT-TYPE
    SYNTAX     Integer32 (0..65535)
    MAX-ACCESS read-only
    STATUS     current
    DESCRIPTION
            "-- empty --"
    ::= { lcsStatusWtpMngmtIbeaconProfile 4 }

-- {SCALAR} 1.3.6.1.4.1.2356.11.1.59.122.5
lcsStatusWtpMngmtIbeaconProfileTransmitPower OBJECT-TYPE
    SYNTAX     INTEGER {
                  eLow (0),
                  eMedium (1),
                  eHigh (2),
                  eNotSet (254)
            }
    MAX-ACCESS read-only
    STATUS     current
    DESCRIPTION
            "-- empty --"
    ::= { lcsStatusWtpMngmtIbeaconProfile 5 }

-- {SCALAR} 1.3.6.1.4.1.2356.11.1.59.122.6
lcsStatusWtpMngmtIbeaconProfileChannelS OBJECT-TYPE
    SYNTAX     BITS {
                  e2480mhz (5),
                  e2426mhz (6),
                  e2402mhz (7)
            }
    MAX-ACCESS read-only
    STATUS     current
    DESCRIPTION
            "-- empty --"
    ::= { lcsStatusWtpMngmtIbeaconProfile 6 }

-- {TABLE} 1.3.6.1.4.1.2356.11.1.59.248
lcsStatusWtpMngmtWIdsTable OBJECT-TYPE
    SYNTAX     SEQUENCE OF LcsStatusWtpMngmtWIdsEntry
    MAX-ACCESS not-accessible
    STATUS     current
    DESCRIPTION
            ""
    ::= { lcsStatusWtpMngmt 248 }

-- {ROW} 1.3.6.1.4.1.2356.11.1.59.248.1
lcsStatusWtpMngmtWIdsEntry OBJECT-TYPE
    SYNTAX     LcsStatusWtpMngmtWIdsEntry
    MAX-ACCESS not-accessible
    STATUS     current
    DESCRIPTION
            ""
    INDEX {
            lcsStatusWtpMngmtWIdsEntryName
          }
    ::= { lcsStatusWtpMngmtWIdsTable 1 }

LcsStatusWtpMngmtWIdsEntry ::= SEQUENCE {
            lcsStatusWtpMngmtWIdsEntryName DisplayString,
            lcsStatusWtpMngmtWIdsEntryOperating INTEGER,
            lcsStatusWtpMngmtWIdsEntryEapolstartcounterlimit Integer32,
            lcsStatusWtpMngmtWIdsEntryEapolstartcounterinterval Integer32,
            lcsStatusWtpMngmtWIdsEntryProbebroadcounterlimit Integer32,
            lcsStatusWtpMngmtWIdsEntryProbebroadcounterinterval Integer32,
            lcsStatusWtpMngmtWIdsEntryDeauthenticatebroadcounterlimit Integer32,
            lcsStatusWtpMngmtWIdsEntryDeauthBroadCtrInt Integer32,
            lcsStatusWtpMngmtWIdsEntryDeauthenticatecounterlimit Integer32,
            lcsStatusWtpMngmtWIdsEntryDeauthenticatecounterinterval Integer32,
            lcsStatusWtpMngmtWIdsEntryAssociatereqcounterlimit Integer32,
            lcsStatusWtpMngmtWIdsEntryAssociatereqcounterinterval Integer32,
            lcsStatusWtpMngmtWIdsEntryReassociatereqcounterlimit Integer32,
            lcsStatusWtpMngmtWIdsEntryReassociatereqcounterinterval Integer32,
            lcsStatusWtpMngmtWIdsEntryAuthenticatecounterlimit Integer32,
            lcsStatusWtpMngmtWIdsEntryAuthenticatecounterinterval Integer32,
            lcsStatusWtpMngmtWIdsEntryDisassociatecounterlimit Integer32,
            lcsStatusWtpMngmtWIdsEntryDisassociatecounterinterval Integer32,
            lcsStatusWtpMngmtWIdsEntryIdsOperational INTEGER,
            lcsStatusWtpMngmtWIdsEntrySyslogOperational INTEGER,
            lcsStatusWtpMngmtWIdsEntrySnmptrapsOperational INTEGER,
            lcsStatusWtpMngmtWIdsEntryEMail INTEGER,
            lcsStatusWtpMngmtWIdsEntryEMailReceiver DisplayString,
            lcsStatusWtpMngmtWIdsEntryEMailAggregateInterval Integer32,
            lcsStatusWtpMngmtWIdsEntryBlockackOutOfWindowCounter Integer32,
            lcsStatusWtpMngmtWIdsEntryBlockackOutOfWindowCounterTime Integer32,
            lcsStatusWtpMngmtWIdsEntryBARxAfterDelBACtr Integer32,
            lcsStatusWtpMngmtWIdsEntryBARxAfterDelBAInt Integer32,
            lcsStatusWtpMngmtWIdsEntryNullDataDosCounter Integer32,
            lcsStatusWtpMngmtWIdsEntryNullDataDosCounterTime Integer32,
            lcsStatusWtpMngmtWIdsEntryNullDataPSBufferOverflowCounter Integer32,
            lcsStatusWtpMngmtWIdsEntryNullDataPSOverflowCtr Integer32,
            lcsStatusWtpMngmtWIdsEntryPSPollTIMIntervalDiff Integer32,
            lcsStatusWtpMngmtWIdsEntryPSPollTIMIntervalDiffCounter Integer32,
            lcsStatusWtpMngmtWIdsEntryPSPollTIMIntervalDiffCounterTime Integer32,
            lcsStatusWtpMngmtWIdsEntrySMPSMulStreamFrameCounter Integer32,
            lcsStatusWtpMngmtWIdsEntrySMPSMulStreamFrameCounterTime Integer32,
            lcsStatusWtpMngmtWIdsEntryDisassociatebroadcounterlimit Integer32,
            lcsStatusWtpMngmtWIdsEntryDisassociatebroadcounterinterval Integer32,
            lcsStatusWtpMngmtWIdsEntryEapolsuccesscounterlimit Integer32,
            lcsStatusWtpMngmtWIdsEntryEapolsuccesscounterinterval Integer32,
            lcsStatusWtpMngmtWIdsEntryEapolfailurecounterlimit Integer32,
            lcsStatusWtpMngmtWIdsEntryEapolfailurecounterinterval Integer32,
            lcsStatusWtpMngmtWIdsEntryPromiscuousMode INTEGER
    }

-- {COLUMN} 1.3.6.1.4.1.2356.11.1.59.248.1.1
lcsStatusWtpMngmtWIdsEntryName OBJECT-TYPE
    SYNTAX     DisplayString (SIZE(0..31))
    MAX-ACCESS read-only
    STATUS     current
    DESCRIPTION
            "-- empty --"
    ::= { lcsStatusWtpMngmtWIdsEntry 1 }

-- {COLUMN} 1.3.6.1.4.1.2356.11.1.59.248.1.2
lcsStatusWtpMngmtWIdsEntryOperating OBJECT-TYPE
    SYNTAX     INTEGER {
                  eNo (0),
                  eYes (1)
            }
    MAX-ACCESS read-only
    STATUS     current
    DESCRIPTION
            "-- empty --"
    ::= { lcsStatusWtpMngmtWIdsEntry 2 }

-- {COLUMN} 1.3.6.1.4.1.2356.11.1.59.248.1.3
lcsStatusWtpMngmtWIdsEntryEapolstartcounterlimit OBJECT-TYPE
    SYNTAX     Integer32 (0..2147483647)
    MAX-ACCESS read-only
    STATUS     current
    DESCRIPTION
            "-- empty --"
    ::= { lcsStatusWtpMngmtWIdsEntry 3 }

-- {COLUMN} 1.3.6.1.4.1.2356.11.1.59.248.1.4
lcsStatusWtpMngmtWIdsEntryEapolstartcounterinterval OBJECT-TYPE
    SYNTAX     Integer32 (0..2147483647)
    MAX-ACCESS read-only
    STATUS     current
    DESCRIPTION
            "-- empty --"
    ::= { lcsStatusWtpMngmtWIdsEntry 4 }

-- {COLUMN} 1.3.6.1.4.1.2356.11.1.59.248.1.5
lcsStatusWtpMngmtWIdsEntryProbebroadcounterlimit OBJECT-TYPE
    SYNTAX     Integer32 (0..2147483647)
    MAX-ACCESS read-only
    STATUS     current
    DESCRIPTION
            "-- empty --"
    ::= { lcsStatusWtpMngmtWIdsEntry 5 }

-- {COLUMN} 1.3.6.1.4.1.2356.11.1.59.248.1.6
lcsStatusWtpMngmtWIdsEntryProbebroadcounterinterval OBJECT-TYPE
    SYNTAX     Integer32 (0..2147483647)
    MAX-ACCESS read-only
    STATUS     current
    DESCRIPTION
            "-- empty --"
    ::= { lcsStatusWtpMngmtWIdsEntry 6 }

-- {COLUMN} 1.3.6.1.4.1.2356.11.1.59.248.1.7
lcsStatusWtpMngmtWIdsEntryDeauthenticatebroadcounterlimit OBJECT-TYPE
    SYNTAX     Integer32 (0..2147483647)
    MAX-ACCESS read-only
    STATUS     current
    DESCRIPTION
            "-- empty --"
    ::= { lcsStatusWtpMngmtWIdsEntry 7 }

-- {COLUMN} 1.3.6.1.4.1.2356.11.1.59.248.1.8
lcsStatusWtpMngmtWIdsEntryDeauthBroadCtrInt OBJECT-TYPE
    SYNTAX     Integer32 (0..2147483647)
    MAX-ACCESS read-only
    STATUS     current
    DESCRIPTION
            ""
    ::= { lcsStatusWtpMngmtWIdsEntry 8 }

-- {COLUMN} 1.3.6.1.4.1.2356.11.1.59.248.1.9
lcsStatusWtpMngmtWIdsEntryDeauthenticatecounterlimit OBJECT-TYPE
    SYNTAX     Integer32 (0..2147483647)
    MAX-ACCESS read-only
    STATUS     current
    DESCRIPTION
            "-- empty --"
    ::= { lcsStatusWtpMngmtWIdsEntry 9 }

-- {COLUMN} 1.3.6.1.4.1.2356.11.1.59.248.1.10
lcsStatusWtpMngmtWIdsEntryDeauthenticatecounterinterval OBJECT-TYPE
    SYNTAX     Integer32 (0..2147483647)
    MAX-ACCESS read-only
    STATUS     current
    DESCRIPTION
            "-- empty --"
    ::= { lcsStatusWtpMngmtWIdsEntry 10 }

-- {COLUMN} 1.3.6.1.4.1.2356.11.1.59.248.1.11
lcsStatusWtpMngmtWIdsEntryAssociatereqcounterlimit OBJECT-TYPE
    SYNTAX     Integer32 (0..2147483647)
    MAX-ACCESS read-only
    STATUS     current
    DESCRIPTION
            "-- empty --"
    ::= { lcsStatusWtpMngmtWIdsEntry 11 }

-- {COLUMN} 1.3.6.1.4.1.2356.11.1.59.248.1.12
lcsStatusWtpMngmtWIdsEntryAssociatereqcounterinterval OBJECT-TYPE
    SYNTAX     Integer32 (0..2147483647)
    MAX-ACCESS read-only
    STATUS     current
    DESCRIPTION
            "-- empty --"
    ::= { lcsStatusWtpMngmtWIdsEntry 12 }

-- {COLUMN} 1.3.6.1.4.1.2356.11.1.59.248.1.13
lcsStatusWtpMngmtWIdsEntryReassociatereqcounterlimit OBJECT-TYPE
    SYNTAX     Integer32 (0..2147483647)
    MAX-ACCESS read-only
    STATUS     current
    DESCRIPTION
            "-- empty --"
    ::= { lcsStatusWtpMngmtWIdsEntry 13 }

-- {COLUMN} 1.3.6.1.4.1.2356.11.1.59.248.1.14
lcsStatusWtpMngmtWIdsEntryReassociatereqcounterinterval OBJECT-TYPE
    SYNTAX     Integer32 (0..2147483647)
    MAX-ACCESS read-only
    STATUS     current
    DESCRIPTION
            "-- empty --"
    ::= { lcsStatusWtpMngmtWIdsEntry 14 }

-- {COLUMN} 1.3.6.1.4.1.2356.11.1.59.248.1.15
lcsStatusWtpMngmtWIdsEntryAuthenticatecounterlimit OBJECT-TYPE
    SYNTAX     Integer32 (0..2147483647)
    MAX-ACCESS read-only
    STATUS     current
    DESCRIPTION
            "-- empty --"
    ::= { lcsStatusWtpMngmtWIdsEntry 15 }

-- {COLUMN} 1.3.6.1.4.1.2356.11.1.59.248.1.16
lcsStatusWtpMngmtWIdsEntryAuthenticatecounterinterval OBJECT-TYPE
    SYNTAX     Integer32 (0..2147483647)
    MAX-ACCESS read-only
    STATUS     current
    DESCRIPTION
            "-- empty --"
    ::= { lcsStatusWtpMngmtWIdsEntry 16 }

-- {COLUMN} 1.3.6.1.4.1.2356.11.1.59.248.1.17
lcsStatusWtpMngmtWIdsEntryDisassociatecounterlimit OBJECT-TYPE
    SYNTAX     Integer32 (0..2147483647)
    MAX-ACCESS read-only
    STATUS     current
    DESCRIPTION
            "-- empty --"
    ::= { lcsStatusWtpMngmtWIdsEntry 17 }

-- {COLUMN} 1.3.6.1.4.1.2356.11.1.59.248.1.18
lcsStatusWtpMngmtWIdsEntryDisassociatecounterinterval OBJECT-TYPE
    SYNTAX     Integer32 (0..2147483647)
    MAX-ACCESS read-only
    STATUS     current
    DESCRIPTION
            "-- empty --"
    ::= { lcsStatusWtpMngmtWIdsEntry 18 }

-- {COLUMN} 1.3.6.1.4.1.2356.11.1.59.248.1.19
lcsStatusWtpMngmtWIdsEntryIdsOperational OBJECT-TYPE
    SYNTAX     INTEGER {
                  eNo (0),
                  eYes (1)
            }
    MAX-ACCESS read-only
    STATUS     current
    DESCRIPTION
            "-- empty --"
    ::= { lcsStatusWtpMngmtWIdsEntry 19 }

-- {COLUMN} 1.3.6.1.4.1.2356.11.1.59.248.1.20
lcsStatusWtpMngmtWIdsEntrySyslogOperational OBJECT-TYPE
    SYNTAX     INTEGER {
                  eNo (0),
                  eYes (1)
            }
    MAX-ACCESS read-only
    STATUS     current
    DESCRIPTION
            "-- empty --"
    ::= { lcsStatusWtpMngmtWIdsEntry 20 }

-- {COLUMN} 1.3.6.1.4.1.2356.11.1.59.248.1.21
lcsStatusWtpMngmtWIdsEntrySnmptrapsOperational OBJECT-TYPE
    SYNTAX     INTEGER {
                  eNo (0),
                  eYes (1)
            }
    MAX-ACCESS read-only
    STATUS     current
    DESCRIPTION
            "-- empty --"
    ::= { lcsStatusWtpMngmtWIdsEntry 21 }

-- {COLUMN} 1.3.6.1.4.1.2356.11.1.59.248.1.22
lcsStatusWtpMngmtWIdsEntryEMail OBJECT-TYPE
    SYNTAX     INTEGER {
                  eNo (0),
                  eYes (1)
            }
    MAX-ACCESS read-only
    STATUS     current
    DESCRIPTION
            "-- empty --"
    ::= { lcsStatusWtpMngmtWIdsEntry 22 }

-- {COLUMN} 1.3.6.1.4.1.2356.11.1.59.248.1.23
lcsStatusWtpMngmtWIdsEntryEMailReceiver OBJECT-TYPE
    SYNTAX     DisplayString (SIZE(0..64))
    MAX-ACCESS read-only
    STATUS     current
    DESCRIPTION
            "-- empty --"
    ::= { lcsStatusWtpMngmtWIdsEntry 23 }

-- {COLUMN} 1.3.6.1.4.1.2356.11.1.59.248.1.24
lcsStatusWtpMngmtWIdsEntryEMailAggregateInterval OBJECT-TYPE
    SYNTAX     Integer32 (0..2147483647)
    MAX-ACCESS read-only
    STATUS     current
    DESCRIPTION
            "-- empty --"
    ::= { lcsStatusWtpMngmtWIdsEntry 24 }

-- {COLUMN} 1.3.6.1.4.1.2356.11.1.59.248.1.26
lcsStatusWtpMngmtWIdsEntryBlockackOutOfWindowCounter OBJECT-TYPE
    SYNTAX     Integer32 (0..2147483647)
    MAX-ACCESS read-only
    STATUS     current
    DESCRIPTION
            "-- empty --"
    ::= { lcsStatusWtpMngmtWIdsEntry 26 }

-- {COLUMN} 1.3.6.1.4.1.2356.11.1.59.248.1.27
lcsStatusWtpMngmtWIdsEntryBlockackOutOfWindowCounterTime OBJECT-TYPE
    SYNTAX     Integer32 (0..2147483647)
    MAX-ACCESS read-only
    STATUS     current
    DESCRIPTION
            "-- empty --"
    ::= { lcsStatusWtpMngmtWIdsEntry 27 }

-- {COLUMN} 1.3.6.1.4.1.2356.11.1.59.248.1.28
lcsStatusWtpMngmtWIdsEntryBARxAfterDelBACtr OBJECT-TYPE
    SYNTAX     Integer32 (0..2147483647)
    MAX-ACCESS read-only
    STATUS     current
    DESCRIPTION
            ""
    ::= { lcsStatusWtpMngmtWIdsEntry 28 }

-- {COLUMN} 1.3.6.1.4.1.2356.11.1.59.248.1.29
lcsStatusWtpMngmtWIdsEntryBARxAfterDelBAInt OBJECT-TYPE
    SYNTAX     Integer32 (0..2147483647)
    MAX-ACCESS read-only
    STATUS     current
    DESCRIPTION
            ""
    ::= { lcsStatusWtpMngmtWIdsEntry 29 }

-- {COLUMN} 1.3.6.1.4.1.2356.11.1.59.248.1.31
lcsStatusWtpMngmtWIdsEntryNullDataDosCounter OBJECT-TYPE
    SYNTAX     Integer32 (0..2147483647)
    MAX-ACCESS read-only
    STATUS     current
    DESCRIPTION
            "-- empty --"
    ::= { lcsStatusWtpMngmtWIdsEntry 31 }

-- {COLUMN} 1.3.6.1.4.1.2356.11.1.59.248.1.32
lcsStatusWtpMngmtWIdsEntryNullDataDosCounterTime OBJECT-TYPE
    SYNTAX     Integer32 (0..2147483647)
    MAX-ACCESS read-only
    STATUS     current
    DESCRIPTION
            "-- empty --"
    ::= { lcsStatusWtpMngmtWIdsEntry 32 }

-- {COLUMN} 1.3.6.1.4.1.2356.11.1.59.248.1.34
lcsStatusWtpMngmtWIdsEntryNullDataPSBufferOverflowCounter OBJECT-TYPE
    SYNTAX     Integer32 (0..2147483647)
    MAX-ACCESS read-only
    STATUS     current
    DESCRIPTION
            "-- empty --"
    ::= { lcsStatusWtpMngmtWIdsEntry 34 }

-- {COLUMN} 1.3.6.1.4.1.2356.11.1.59.248.1.35
lcsStatusWtpMngmtWIdsEntryNullDataPSOverflowCtr OBJECT-TYPE
    SYNTAX     Integer32 (0..2147483647)
    MAX-ACCESS read-only
    STATUS     current
    DESCRIPTION
            ""
    ::= { lcsStatusWtpMngmtWIdsEntry 35 }

-- {COLUMN} 1.3.6.1.4.1.2356.11.1.59.248.1.37
lcsStatusWtpMngmtWIdsEntryPSPollTIMIntervalDiff OBJECT-TYPE
    SYNTAX     Integer32 (0..2147483647)
    MAX-ACCESS read-only
    STATUS     current
    DESCRIPTION
            "-- empty --"
    ::= { lcsStatusWtpMngmtWIdsEntry 37 }

-- {COLUMN} 1.3.6.1.4.1.2356.11.1.59.248.1.38
lcsStatusWtpMngmtWIdsEntryPSPollTIMIntervalDiffCounter OBJECT-TYPE
    SYNTAX     Integer32 (0..2147483647)
    MAX-ACCESS read-only
    STATUS     current
    DESCRIPTION
            "-- empty --"
    ::= { lcsStatusWtpMngmtWIdsEntry 38 }

-- {COLUMN} 1.3.6.1.4.1.2356.11.1.59.248.1.39
lcsStatusWtpMngmtWIdsEntryPSPollTIMIntervalDiffCounterTime OBJECT-TYPE
    SYNTAX     Integer32 (0..2147483647)
    MAX-ACCESS read-only
    STATUS     current
    DESCRIPTION
            "-- empty --"
    ::= { lcsStatusWtpMngmtWIdsEntry 39 }

-- {COLUMN} 1.3.6.1.4.1.2356.11.1.59.248.1.41
lcsStatusWtpMngmtWIdsEntrySMPSMulStreamFrameCounter OBJECT-TYPE
    SYNTAX     Integer32 (0..2147483647)
    MAX-ACCESS read-only
    STATUS     current
    DESCRIPTION
            "-- empty --"
    ::= { lcsStatusWtpMngmtWIdsEntry 41 }

-- {COLUMN} 1.3.6.1.4.1.2356.11.1.59.248.1.42
lcsStatusWtpMngmtWIdsEntrySMPSMulStreamFrameCounterTime OBJECT-TYPE
    SYNTAX     Integer32 (0..2147483647)
    MAX-ACCESS read-only
    STATUS     current
    DESCRIPTION
            "-- empty --"
    ::= { lcsStatusWtpMngmtWIdsEntry 42 }

-- {COLUMN} 1.3.6.1.4.1.2356.11.1.59.248.1.45
lcsStatusWtpMngmtWIdsEntryDisassociatebroadcounterlimit OBJECT-TYPE
    SYNTAX     Integer32 (0..2147483647)
    MAX-ACCESS read-only
    STATUS     current
    DESCRIPTION
            "-- empty --"
    ::= { lcsStatusWtpMngmtWIdsEntry 45 }

-- {COLUMN} 1.3.6.1.4.1.2356.11.1.59.248.1.46
lcsStatusWtpMngmtWIdsEntryDisassociatebroadcounterinterval OBJECT-TYPE
    SYNTAX     Integer32 (0..2147483647)
    MAX-ACCESS read-only
    STATUS     current
    DESCRIPTION
            "-- empty --"
    ::= { lcsStatusWtpMngmtWIdsEntry 46 }

-- {COLUMN} 1.3.6.1.4.1.2356.11.1.59.248.1.47
lcsStatusWtpMngmtWIdsEntryEapolsuccesscounterlimit OBJECT-TYPE
    SYNTAX     Integer32 (0..2147483647)
    MAX-ACCESS read-only
    STATUS     current
    DESCRIPTION
            "-- empty --"
    ::= { lcsStatusWtpMngmtWIdsEntry 47 }

-- {COLUMN} 1.3.6.1.4.1.2356.11.1.59.248.1.48
lcsStatusWtpMngmtWIdsEntryEapolsuccesscounterinterval OBJECT-TYPE
    SYNTAX     Integer32 (0..2147483647)
    MAX-ACCESS read-only
    STATUS     current
    DESCRIPTION
            "-- empty --"
    ::= { lcsStatusWtpMngmtWIdsEntry 48 }

-- {COLUMN} 1.3.6.1.4.1.2356.11.1.59.248.1.49
lcsStatusWtpMngmtWIdsEntryEapolfailurecounterlimit OBJECT-TYPE
    SYNTAX     Integer32 (0..2147483647)
    MAX-ACCESS read-only
    STATUS     current
    DESCRIPTION
            "-- empty --"
    ::= { lcsStatusWtpMngmtWIdsEntry 49 }

-- {COLUMN} 1.3.6.1.4.1.2356.11.1.59.248.1.50
lcsStatusWtpMngmtWIdsEntryEapolfailurecounterinterval OBJECT-TYPE
    SYNTAX     Integer32 (0..2147483647)
    MAX-ACCESS read-only
    STATUS     current
    DESCRIPTION
            "-- empty --"
    ::= { lcsStatusWtpMngmtWIdsEntry 50 }

-- {COLUMN} 1.3.6.1.4.1.2356.11.1.59.248.1.51
lcsStatusWtpMngmtWIdsEntryPromiscuousMode OBJECT-TYPE
    SYNTAX     INTEGER {
                  eNo (0),
                  eYes (1)
            }
    MAX-ACCESS read-only
    STATUS     current
    DESCRIPTION
            "-- empty --"
    ::= { lcsStatusWtpMngmtWIdsEntry 51 }

-- {NODE} 1.3.6.1.4.1.2356.11.1.60
lcsStatusLldp OBJECT IDENTIFIER ::= { lcsStatus 60 }

-- {SCALAR} 1.3.6.1.4.1.2356.11.1.60.1
lcsStatusLldpRemoteTablesLastChange OBJECT-TYPE
    SYNTAX     DisplayString (SIZE(0..21))
    MAX-ACCESS read-only
    STATUS     current
    DESCRIPTION
            "-- empty --"
    ::= { lcsStatusLldp 1 }

-- {SCALAR} 1.3.6.1.4.1.2356.11.1.60.2
lcsStatusLldpRemoteTablesInserts OBJECT-TYPE
    SYNTAX     Counter32
    MAX-ACCESS read-only
    STATUS     current
    DESCRIPTION
            "-- empty --"
    ::= { lcsStatusLldp 2 }

-- {SCALAR} 1.3.6.1.4.1.2356.11.1.60.3
lcsStatusLldpRemoteTablesDeletes OBJECT-TYPE
    SYNTAX     Counter32
    MAX-ACCESS read-only
    STATUS     current
    DESCRIPTION
            "-- empty --"
    ::= { lcsStatusLldp 3 }

-- {SCALAR} 1.3.6.1.4.1.2356.11.1.60.4
lcsStatusLldpRemoteTablesDrops OBJECT-TYPE
    SYNTAX     Counter32
    MAX-ACCESS read-only
    STATUS     current
    DESCRIPTION
            "-- empty --"
    ::= { lcsStatusLldp 4 }

-- {SCALAR} 1.3.6.1.4.1.2356.11.1.60.5
lcsStatusLldpRemoteTablesAgeouts OBJECT-TYPE
    SYNTAX     Counter32
    MAX-ACCESS read-only
    STATUS     current
    DESCRIPTION
            "-- empty --"
    ::= { lcsStatusLldp 5 }

-- {TABLE} 1.3.6.1.4.1.2356.11.1.60.7
lcsStatusLldpPortsTable OBJECT-TYPE
    SYNTAX     SEQUENCE OF LcsStatusLldpPortsEntry
    MAX-ACCESS not-accessible
    STATUS     current
    DESCRIPTION
            "-- empty --"
    ::= { lcsStatusLldp 7 }

-- {ROW} 1.3.6.1.4.1.2356.11.1.60.7.1
lcsStatusLldpPortsEntry OBJECT-TYPE
    SYNTAX     LcsStatusLldpPortsEntry
    MAX-ACCESS not-accessible
    STATUS     current
    DESCRIPTION
            ""
    INDEX {
            lcsStatusLldpPortsEntryName
          }
    ::= { lcsStatusLldpPortsTable 1 }

LcsStatusLldpPortsEntry ::= SEQUENCE {
            lcsStatusLldpPortsEntryName DisplayString,
            lcsStatusLldpPortsEntryTxFrames Counter32,
            lcsStatusLldpPortsEntryRxFrames Counter32,
            lcsStatusLldpPortsEntryFramesDiscarded Counter32,
            lcsStatusLldpPortsEntryFramesErrors Counter32,
            lcsStatusLldpPortsEntryTlvsDiscarded Counter32,
            lcsStatusLldpPortsEntryTlvsUnrecognized Counter32,
            lcsStatusLldpPortsEntryAgeouts Counter32,
            lcsStatusLldpPortsEntryTotalEntries Gauge32,
            lcsStatusLldpPortsEntryFdbTotalEntries Gauge32,
            lcsStatusLldpPortsEntryLldpEntries Gauge32,
            lcsStatusLldpPortsEntryOtherEntries Gauge32
    }

-- {COLUMN} 1.3.6.1.4.1.2356.11.1.60.7.1.1
lcsStatusLldpPortsEntryName OBJECT-TYPE
    SYNTAX     DisplayString (SIZE(0..255))
    MAX-ACCESS read-only
    STATUS     current
    DESCRIPTION
            "-- empty --"
    ::= { lcsStatusLldpPortsEntry 1 }

-- {COLUMN} 1.3.6.1.4.1.2356.11.1.60.7.1.2
lcsStatusLldpPortsEntryTxFrames OBJECT-TYPE
    SYNTAX     Counter32
    MAX-ACCESS read-only
    STATUS     current
    DESCRIPTION
            "-- empty --"
    ::= { lcsStatusLldpPortsEntry 2 }

-- {COLUMN} 1.3.6.1.4.1.2356.11.1.60.7.1.3
lcsStatusLldpPortsEntryRxFrames OBJECT-TYPE
    SYNTAX     Counter32
    MAX-ACCESS read-only
    STATUS     current
    DESCRIPTION
            "-- empty --"
    ::= { lcsStatusLldpPortsEntry 3 }

-- {COLUMN} 1.3.6.1.4.1.2356.11.1.60.7.1.4
lcsStatusLldpPortsEntryFramesDiscarded OBJECT-TYPE
    SYNTAX     Counter32
    MAX-ACCESS read-only
    STATUS     current
    DESCRIPTION
            "-- empty --"
    ::= { lcsStatusLldpPortsEntry 4 }

-- {COLUMN} 1.3.6.1.4.1.2356.11.1.60.7.1.5
lcsStatusLldpPortsEntryFramesErrors OBJECT-TYPE
    SYNTAX     Counter32
    MAX-ACCESS read-only
    STATUS     current
    DESCRIPTION
            "-- empty --"
    ::= { lcsStatusLldpPortsEntry 5 }

-- {COLUMN} 1.3.6.1.4.1.2356.11.1.60.7.1.6
lcsStatusLldpPortsEntryTlvsDiscarded OBJECT-TYPE
    SYNTAX     Counter32
    MAX-ACCESS read-only
    STATUS     current
    DESCRIPTION
            "-- empty --"
    ::= { lcsStatusLldpPortsEntry 6 }

-- {COLUMN} 1.3.6.1.4.1.2356.11.1.60.7.1.7
lcsStatusLldpPortsEntryTlvsUnrecognized OBJECT-TYPE
    SYNTAX     Counter32
    MAX-ACCESS read-only
    STATUS     current
    DESCRIPTION
            "-- empty --"
    ::= { lcsStatusLldpPortsEntry 7 }

-- {COLUMN} 1.3.6.1.4.1.2356.11.1.60.7.1.8
lcsStatusLldpPortsEntryAgeouts OBJECT-TYPE
    SYNTAX     Counter32
    MAX-ACCESS read-only
    STATUS     current
    DESCRIPTION
            "-- empty --"
    ::= { lcsStatusLldpPortsEntry 8 }

-- {COLUMN} 1.3.6.1.4.1.2356.11.1.60.7.1.9
lcsStatusLldpPortsEntryTotalEntries OBJECT-TYPE
    SYNTAX     Gauge32
    MAX-ACCESS read-only
    STATUS     current
    DESCRIPTION
            "-- empty --"
    ::= { lcsStatusLldpPortsEntry 9 }

-- {COLUMN} 1.3.6.1.4.1.2356.11.1.60.7.1.10
lcsStatusLldpPortsEntryFdbTotalEntries OBJECT-TYPE
    SYNTAX     Gauge32
    MAX-ACCESS read-only
    STATUS     current
    DESCRIPTION
            "-- empty --"
    ::= { lcsStatusLldpPortsEntry 10 }

-- {COLUMN} 1.3.6.1.4.1.2356.11.1.60.7.1.11
lcsStatusLldpPortsEntryLldpEntries OBJECT-TYPE
    SYNTAX     Gauge32
    MAX-ACCESS read-only
    STATUS     current
    DESCRIPTION
            "-- empty --"
    ::= { lcsStatusLldpPortsEntry 11 }

-- {COLUMN} 1.3.6.1.4.1.2356.11.1.60.7.1.12
lcsStatusLldpPortsEntryOtherEntries OBJECT-TYPE
    SYNTAX     Gauge32
    MAX-ACCESS read-only
    STATUS     current
    DESCRIPTION
            "-- empty --"
    ::= { lcsStatusLldpPortsEntry 12 }

-- {TABLE} 1.3.6.1.4.1.2356.11.1.60.8
lcsStatusLldpRemoteTableTable OBJECT-TYPE
    SYNTAX     SEQUENCE OF LcsStatusLldpRemoteTableEntry
    MAX-ACCESS not-accessible
    STATUS     current
    DESCRIPTION
            "-- empty --"
    ::= { lcsStatusLldp 8 }

-- {ROW} 1.3.6.1.4.1.2356.11.1.60.8.1
lcsStatusLldpRemoteTableEntry OBJECT-TYPE
    SYNTAX     LcsStatusLldpRemoteTableEntry
    MAX-ACCESS not-accessible
    STATUS     current
    DESCRIPTION
            ""
    INDEX {
            lcsStatusLldpRemoteTableEntryIndex
          }
    ::= { lcsStatusLldpRemoteTableTable 1 }

LcsStatusLldpRemoteTableEntry ::= SEQUENCE {
            lcsStatusLldpRemoteTableEntryIndex Integer32,
            lcsStatusLldpRemoteTableEntryLastUpdate DisplayString,
            lcsStatusLldpRemoteTableEntryChassisIdType INTEGER,
            lcsStatusLldpRemoteTableEntryChassisId DisplayString,
            lcsStatusLldpRemoteTableEntryPortIdType INTEGER,
            lcsStatusLldpRemoteTableEntryPortId DisplayString,
            lcsStatusLldpRemoteTableEntryTtl Integer32,
            lcsStatusLldpRemoteTableEntryTtlRemaining Integer32,
            lcsStatusLldpRemoteTableEntryPortDescriptor DisplayString,
            lcsStatusLldpRemoteTableEntrySystemName DisplayString,
            lcsStatusLldpRemoteTableEntrySystemDescriptor DisplayString,
            lcsStatusLldpRemoteTableEntryCapabilitiesSupported BITS,
            lcsStatusLldpRemoteTableEntryCapabilitiesEnabled BITS,
            lcsStatusLldpRemoteTableEntryPortVlanId Integer32,
            lcsStatusLldpRemoteTableEntrySource INTEGER,
            lcsStatusLldpRemoteTableEntryPort DisplayString
    }

-- {COLUMN} 1.3.6.1.4.1.2356.11.1.60.8.1.1
lcsStatusLldpRemoteTableEntryIndex OBJECT-TYPE
    SYNTAX     Integer32 (0..2147483647)
    MAX-ACCESS read-only
    STATUS     current
    DESCRIPTION
            "-- empty --"
    ::= { lcsStatusLldpRemoteTableEntry 1 }

-- {COLUMN} 1.3.6.1.4.1.2356.11.1.60.8.1.2
lcsStatusLldpRemoteTableEntryLastUpdate OBJECT-TYPE
    SYNTAX     DisplayString (SIZE(0..19))
    MAX-ACCESS read-only
    STATUS     current
    DESCRIPTION
            "-- empty --"
    ::= { lcsStatusLldpRemoteTableEntry 2 }

-- {COLUMN} 1.3.6.1.4.1.2356.11.1.60.8.1.4
lcsStatusLldpRemoteTableEntryChassisIdType OBJECT-TYPE
    SYNTAX     INTEGER {
                  eChassisComponent (1),
                  eInterfaceAlias (2),
                  ePortComponent (3),
                  eMacAddress (4),
                  eNetworkAddress (5),
                  eInterfaceName (6),
                  eLocallyAssigned (7)
            }
    MAX-ACCESS read-only
    STATUS     current
    DESCRIPTION
            "-- empty --"
    ::= { lcsStatusLldpRemoteTableEntry 4 }

-- {COLUMN} 1.3.6.1.4.1.2356.11.1.60.8.1.5
lcsStatusLldpRemoteTableEntryChassisId OBJECT-TYPE
    SYNTAX     DisplayString (SIZE(0..255))
    MAX-ACCESS read-only
    STATUS     current
    DESCRIPTION
            "-- empty --"
    ::= { lcsStatusLldpRemoteTableEntry 5 }

-- {COLUMN} 1.3.6.1.4.1.2356.11.1.60.8.1.6
lcsStatusLldpRemoteTableEntryPortIdType OBJECT-TYPE
    SYNTAX     INTEGER {
                  eInterfaceAlias (1),
                  ePortComponent (2),
                  eMacAddress (3),
                  eNetworkAddress (4),
                  eInterfaceName (5),
                  eCircuitId (6),
                  eLocallyAssigned (7)
            }
    MAX-ACCESS read-only
    STATUS     current
    DESCRIPTION
            "-- empty --"
    ::= { lcsStatusLldpRemoteTableEntry 6 }

-- {COLUMN} 1.3.6.1.4.1.2356.11.1.60.8.1.7
lcsStatusLldpRemoteTableEntryPortId OBJECT-TYPE
    SYNTAX     DisplayString (SIZE(0..255))
    MAX-ACCESS read-only
    STATUS     current
    DESCRIPTION
            "-- empty --"
    ::= { lcsStatusLldpRemoteTableEntry 7 }

-- {COLUMN} 1.3.6.1.4.1.2356.11.1.60.8.1.8
lcsStatusLldpRemoteTableEntryTtl OBJECT-TYPE
    SYNTAX     Integer32 (0..65535)
    MAX-ACCESS read-only
    STATUS     current
    DESCRIPTION
            "-- empty --"
    ::= { lcsStatusLldpRemoteTableEntry 8 }

-- {COLUMN} 1.3.6.1.4.1.2356.11.1.60.8.1.9
lcsStatusLldpRemoteTableEntryTtlRemaining OBJECT-TYPE
    SYNTAX     Integer32 (0..65535)
    MAX-ACCESS read-only
    STATUS     current
    DESCRIPTION
            "-- empty --"
    ::= { lcsStatusLldpRemoteTableEntry 9 }

-- {COLUMN} 1.3.6.1.4.1.2356.11.1.60.8.1.10
lcsStatusLldpRemoteTableEntryPortDescriptor OBJECT-TYPE
    SYNTAX     DisplayString (SIZE(0..255))
    MAX-ACCESS read-only
    STATUS     current
    DESCRIPTION
            "-- empty --"
    ::= { lcsStatusLldpRemoteTableEntry 10 }

-- {COLUMN} 1.3.6.1.4.1.2356.11.1.60.8.1.11
lcsStatusLldpRemoteTableEntrySystemName OBJECT-TYPE
    SYNTAX     DisplayString (SIZE(0..255))
    MAX-ACCESS read-only
    STATUS     current
    DESCRIPTION
            "-- empty --"
    ::= { lcsStatusLldpRemoteTableEntry 11 }

-- {COLUMN} 1.3.6.1.4.1.2356.11.1.60.8.1.12
lcsStatusLldpRemoteTableEntrySystemDescriptor OBJECT-TYPE
    SYNTAX     DisplayString (SIZE(0..255))
    MAX-ACCESS read-only
    STATUS     current
    DESCRIPTION
            "-- empty --"
    ::= { lcsStatusLldpRemoteTableEntry 12 }

-- {COLUMN} 1.3.6.1.4.1.2356.11.1.60.8.1.13
lcsStatusLldpRemoteTableEntryCapabilitiesSupported OBJECT-TYPE
    SYNTAX     BITS {
                  eStationOnly (0),
                  eDocsisCable (1),
                  eTelephone (2),
                  eRouter (3),
                  eWlanAp (4),
                  eBridge (5),
                  eRepeater (6),
                  eOther (7)
            }
    MAX-ACCESS read-only
    STATUS     current
    DESCRIPTION
            "-- empty --"
    ::= { lcsStatusLldpRemoteTableEntry 13 }

-- {COLUMN} 1.3.6.1.4.1.2356.11.1.60.8.1.14
lcsStatusLldpRemoteTableEntryCapabilitiesEnabled OBJECT-TYPE
    SYNTAX     BITS {
                  eStationOnly (0),
                  eDocsisCable (1),
                  eTelephone (2),
                  eRouter (3),
                  eWlanAp (4),
                  eBridge (5),
                  eRepeater (6),
                  eOther (7)
            }
    MAX-ACCESS read-only
    STATUS     current
    DESCRIPTION
            "-- empty --"
    ::= { lcsStatusLldpRemoteTableEntry 14 }

-- {COLUMN} 1.3.6.1.4.1.2356.11.1.60.8.1.15
lcsStatusLldpRemoteTableEntryPortVlanId OBJECT-TYPE
    SYNTAX     Integer32 (0..65535)
    MAX-ACCESS read-only
    STATUS     current
    DESCRIPTION
            "-- empty --"
    ::= { lcsStatusLldpRemoteTableEntry 15 }

-- {COLUMN} 1.3.6.1.4.1.2356.11.1.60.8.1.16
lcsStatusLldpRemoteTableEntrySource OBJECT-TYPE
    SYNTAX     INTEGER {
                  eLldp (1),
                  eCdp (2),
                  eWlan (3),
                  eFdb (4)
            }
    MAX-ACCESS read-only
    STATUS     current
    DESCRIPTION
            "-- empty --"
    ::= { lcsStatusLldpRemoteTableEntry 16 }

-- {COLUMN} 1.3.6.1.4.1.2356.11.1.60.8.1.17
lcsStatusLldpRemoteTableEntryPort OBJECT-TYPE
    SYNTAX     DisplayString (SIZE(0..255))
    MAX-ACCESS read-only
    STATUS     current
    DESCRIPTION
            "-- empty --"
    ::= { lcsStatusLldpRemoteTableEntry 17 }

-- {TABLE} 1.3.6.1.4.1.2356.11.1.60.9
lcsStatusLldpRemoteManagementAddressesTable OBJECT-TYPE
    SYNTAX     SEQUENCE OF LcsStatusLldpRemoteManagementAddressesEntry
    MAX-ACCESS not-accessible
    STATUS     current
    DESCRIPTION
            "-- empty --"
    ::= { lcsStatusLldp 9 }

-- {ROW} 1.3.6.1.4.1.2356.11.1.60.9.1
lcsStatusLldpRemoteManagementAddressesEntry OBJECT-TYPE
    SYNTAX     LcsStatusLldpRemoteManagementAddressesEntry
    MAX-ACCESS not-accessible
    STATUS     current
    DESCRIPTION
            ""
    INDEX {
            lcsStatusLldpRemoteManagementAddressesEntryIndex,
            lcsStatusLldpRemoteManagementAddressesEntryAddressType,
            lcsStatusLldpRemoteManagementAddressesEntryAddress
          }
    ::= { lcsStatusLldpRemoteManagementAddressesTable 1 }

LcsStatusLldpRemoteManagementAddressesEntry ::= SEQUENCE {
            lcsStatusLldpRemoteManagementAddressesEntryIndex Integer32,
            lcsStatusLldpRemoteManagementAddressesEntryAddressType INTEGER,
            lcsStatusLldpRemoteManagementAddressesEntryAddress DisplayString,
            lcsStatusLldpRemoteManagementAddressesEntryIfcSubtype INTEGER,
            lcsStatusLldpRemoteManagementAddressesEntryIfcId Integer32
    }

-- {COLUMN} 1.3.6.1.4.1.2356.11.1.60.9.1.1
lcsStatusLldpRemoteManagementAddressesEntryIndex OBJECT-TYPE
    SYNTAX     Integer32 (0..2147483647)
    MAX-ACCESS read-only
    STATUS     current
    DESCRIPTION
            "-- empty --"
    ::= { lcsStatusLldpRemoteManagementAddressesEntry 1 }

-- {COLUMN} 1.3.6.1.4.1.2356.11.1.60.9.1.2
lcsStatusLldpRemoteManagementAddressesEntryAddressType OBJECT-TYPE
    SYNTAX     INTEGER {
                  eIpv4 (1),
                  eIpv6 (2),
                  e802 (6),
                  eIpx (11)
            }
    MAX-ACCESS read-only
    STATUS     current
    DESCRIPTION
            "-- empty --"
    ::= { lcsStatusLldpRemoteManagementAddressesEntry 2 }

-- {COLUMN} 1.3.6.1.4.1.2356.11.1.60.9.1.3
lcsStatusLldpRemoteManagementAddressesEntryAddress OBJECT-TYPE
    SYNTAX     DisplayString (SIZE(0..255))
    MAX-ACCESS read-only
    STATUS     current
    DESCRIPTION
            "-- empty --"
    ::= { lcsStatusLldpRemoteManagementAddressesEntry 3 }

-- {COLUMN} 1.3.6.1.4.1.2356.11.1.60.9.1.4
lcsStatusLldpRemoteManagementAddressesEntryIfcSubtype OBJECT-TYPE
    SYNTAX     INTEGER {
                  eUnknown (1),
                  eIfindex (2),
                  eSystemPortNum (3)
            }
    MAX-ACCESS read-only
    STATUS     current
    DESCRIPTION
            "-- empty --"
    ::= { lcsStatusLldpRemoteManagementAddressesEntry 4 }

-- {COLUMN} 1.3.6.1.4.1.2356.11.1.60.9.1.5
lcsStatusLldpRemoteManagementAddressesEntryIfcId OBJECT-TYPE
    SYNTAX     Integer32 (0..2147483647)
    MAX-ACCESS read-only
    STATUS     current
    DESCRIPTION
            "-- empty --"
    ::= { lcsStatusLldpRemoteManagementAddressesEntry 5 }

-- {TABLE} 1.3.6.1.4.1.2356.11.1.60.10
lcsStatusLldpRemote8023TableTable OBJECT-TYPE
    SYNTAX     SEQUENCE OF LcsStatusLldpRemote8023TableEntry
    MAX-ACCESS not-accessible
    STATUS     current
    DESCRIPTION
            "-- empty --"
    ::= { lcsStatusLldp 10 }

-- {ROW} 1.3.6.1.4.1.2356.11.1.60.10.1
lcsStatusLldpRemote8023TableEntry OBJECT-TYPE
    SYNTAX     LcsStatusLldpRemote8023TableEntry
    MAX-ACCESS not-accessible
    STATUS     current
    DESCRIPTION
            ""
    INDEX {
            lcsStatusLldpRemote8023TableEntryIndex
          }
    ::= { lcsStatusLldpRemote8023TableTable 1 }

LcsStatusLldpRemote8023TableEntry ::= SEQUENCE {
            lcsStatusLldpRemote8023TableEntryIndex Integer32,
            lcsStatusLldpRemote8023TableEntryAutoNegotiationSupported INTEGER,
            lcsStatusLldpRemote8023TableEntryAutoNegotiationEnabled INTEGER,
            lcsStatusLldpRemote8023TableEntryAutoNegotiationCapabilities BITS,
            lcsStatusLldpRemote8023TableEntryMauOperationalType INTEGER,
            lcsStatusLldpRemote8023TableEntryPortPowerType INTEGER,
            lcsStatusLldpRemote8023TableEntryPsePowerSupport INTEGER,
            lcsStatusLldpRemote8023TableEntryPsePowerEnabled INTEGER,
            lcsStatusLldpRemote8023TableEntryPsePowerPairControl INTEGER,
            lcsStatusLldpRemote8023TableEntryPsePowerPair INTEGER,
            lcsStatusLldpRemote8023TableEntryPowerClass INTEGER,
            lcsStatusLldpRemote8023TableEntryAggregationCapable INTEGER,
            lcsStatusLldpRemote8023TableEntryAggregationEnabled INTEGER,
            lcsStatusLldpRemote8023TableEntryAggregationPortId Integer32,
            lcsStatusLldpRemote8023TableEntryMaxFrameSize Integer32,
            lcsStatusLldpRemote8023TableEntryPdRequestedPower Integer32,
            lcsStatusLldpRemote8023TableEntryPseAllocatedPower Integer32
    }

-- {COLUMN} 1.3.6.1.4.1.2356.11.1.60.10.1.1
lcsStatusLldpRemote8023TableEntryIndex OBJECT-TYPE
    SYNTAX     Integer32 (0..2147483647)
    MAX-ACCESS read-only
    STATUS     current
    DESCRIPTION
            "-- empty --"
    ::= { lcsStatusLldpRemote8023TableEntry 1 }

-- {COLUMN} 1.3.6.1.4.1.2356.11.1.60.10.1.2
lcsStatusLldpRemote8023TableEntryAutoNegotiationSupported OBJECT-TYPE
    SYNTAX     INTEGER {
                  eNo (0),
                  eYes (1)
            }
    MAX-ACCESS read-only
    STATUS     current
    DESCRIPTION
            "-- empty --"
    ::= { lcsStatusLldpRemote8023TableEntry 2 }

-- {COLUMN} 1.3.6.1.4.1.2356.11.1.60.10.1.3
lcsStatusLldpRemote8023TableEntryAutoNegotiationEnabled OBJECT-TYPE
    SYNTAX     INTEGER {
                  eNo (0),
                  eYes (1)
            }
    MAX-ACCESS read-only
    STATUS     current
    DESCRIPTION
            "-- empty --"
    ::= { lcsStatusLldpRemote8023TableEntry 3 }

-- {COLUMN} 1.3.6.1.4.1.2356.11.1.60.10.1.4
lcsStatusLldpRemote8023TableEntryAutoNegotiationCapabilities OBJECT-TYPE
    SYNTAX     BITS {
                  eOther (0),
                  e10baset (1),
                  e10basetFd (2),
                  e100baset4 (3),
                  e100basetx (4),
                  e100basetxFd (5),
                  e100baset2 (6),
                  e100baset2Fd (7),
                  ePause (8),
                  eAsymmetricPause (9),
                  eSymmetricPause (10),
                  eAsymmetricSymmetricPause (11),
                  e1000basex (12),
                  e1000basexFd (13),
                  e1000baset (14),
                  e1000basetFd (15)
            }
    MAX-ACCESS read-only
    STATUS     current
    DESCRIPTION
            "-- empty --"
    ::= { lcsStatusLldpRemote8023TableEntry 4 }

-- {COLUMN} 1.3.6.1.4.1.2356.11.1.60.10.1.5
lcsStatusLldpRemote8023TableEntryMauOperationalType OBJECT-TYPE
    SYNTAX     INTEGER {
                  eUnknown (0),
                  e10baseaui (1),
                  e10base2 (4),
                  e10basetHd (10),
                  e10basetFd (11),
                  e100basetxHd (15),
                  e100basetxFd (16),
                  e1000basexHd (21),
                  e1000basexFd (22),
                  e1000baselxHd (23),
                  e1000baselxFd (24),
                  e1000basesxHd (25),
                  e1000basesxFd (26),
                  e1000basetxFd (30),
                  e1000basebx10d (44),
                  e1000basebx10u (45)
            }
    MAX-ACCESS read-only
    STATUS     current
    DESCRIPTION
            "-- empty --"
    ::= { lcsStatusLldpRemote8023TableEntry 5 }

-- {COLUMN} 1.3.6.1.4.1.2356.11.1.60.10.1.6
lcsStatusLldpRemote8023TableEntryPortPowerType OBJECT-TYPE
    SYNTAX     INTEGER {
                  eNone (0),
                  ePse (1),
                  ePd (2)
            }
    MAX-ACCESS read-only
    STATUS     current
    DESCRIPTION
            "-- empty --"
    ::= { lcsStatusLldpRemote8023TableEntry 6 }

-- {COLUMN} 1.3.6.1.4.1.2356.11.1.60.10.1.7
lcsStatusLldpRemote8023TableEntryPsePowerSupport OBJECT-TYPE
    SYNTAX     INTEGER {
                  eNo (0),
                  eYes (1)
            }
    MAX-ACCESS read-only
    STATUS     current
    DESCRIPTION
            "-- empty --"
    ::= { lcsStatusLldpRemote8023TableEntry 7 }

-- {COLUMN} 1.3.6.1.4.1.2356.11.1.60.10.1.8
lcsStatusLldpRemote8023TableEntryPsePowerEnabled OBJECT-TYPE
    SYNTAX     INTEGER {
                  eNo (0),
                  eYes (1)
            }
    MAX-ACCESS read-only
    STATUS     current
    DESCRIPTION
            "-- empty --"
    ::= { lcsStatusLldpRemote8023TableEntry 8 }

-- {COLUMN} 1.3.6.1.4.1.2356.11.1.60.10.1.9
lcsStatusLldpRemote8023TableEntryPsePowerPairControl OBJECT-TYPE
    SYNTAX     INTEGER {
                  eNo (0),
                  eYes (1)
            }
    MAX-ACCESS read-only
    STATUS     current
    DESCRIPTION
            "-- empty --"
    ::= { lcsStatusLldpRemote8023TableEntry 9 }

-- {COLUMN} 1.3.6.1.4.1.2356.11.1.60.10.1.10
lcsStatusLldpRemote8023TableEntryPsePowerPair OBJECT-TYPE
    SYNTAX     INTEGER {
                  eNone (0),
                  eSignal (1),
                  eSpare (2)
            }
    MAX-ACCESS read-only
    STATUS     current
    DESCRIPTION
            "-- empty --"
    ::= { lcsStatusLldpRemote8023TableEntry 10 }

-- {COLUMN} 1.3.6.1.4.1.2356.11.1.60.10.1.11
lcsStatusLldpRemote8023TableEntryPowerClass OBJECT-TYPE
    SYNTAX     INTEGER {
                  eNone (0),
                  eClass0 (1),
                  eClass1 (2),
                  eClass2 (3),
                  eClass3 (4),
                  eClass4 (5)
            }
    MAX-ACCESS read-only
    STATUS     current
    DESCRIPTION
            "-- empty --"
    ::= { lcsStatusLldpRemote8023TableEntry 11 }

-- {COLUMN} 1.3.6.1.4.1.2356.11.1.60.10.1.12
lcsStatusLldpRemote8023TableEntryAggregationCapable OBJECT-TYPE
    SYNTAX     INTEGER {
                  eNo (0),
                  eYes (1)
            }
    MAX-ACCESS read-only
    STATUS     current
    DESCRIPTION
            "-- empty --"
    ::= { lcsStatusLldpRemote8023TableEntry 12 }

-- {COLUMN} 1.3.6.1.4.1.2356.11.1.60.10.1.13
lcsStatusLldpRemote8023TableEntryAggregationEnabled OBJECT-TYPE
    SYNTAX     INTEGER {
                  eNo (0),
                  eYes (1)
            }
    MAX-ACCESS read-only
    STATUS     current
    DESCRIPTION
            "-- empty --"
    ::= { lcsStatusLldpRemote8023TableEntry 13 }

-- {COLUMN} 1.3.6.1.4.1.2356.11.1.60.10.1.14
lcsStatusLldpRemote8023TableEntryAggregationPortId OBJECT-TYPE
    SYNTAX     Integer32 (0..2147483647)
    MAX-ACCESS read-only
    STATUS     current
    DESCRIPTION
            "-- empty --"
    ::= { lcsStatusLldpRemote8023TableEntry 14 }

-- {COLUMN} 1.3.6.1.4.1.2356.11.1.60.10.1.15
lcsStatusLldpRemote8023TableEntryMaxFrameSize OBJECT-TYPE
    SYNTAX     Integer32 (0..65535)
    MAX-ACCESS read-only
    STATUS     current
    DESCRIPTION
            "-- empty --"
    ::= { lcsStatusLldpRemote8023TableEntry 15 }

-- {COLUMN} 1.3.6.1.4.1.2356.11.1.60.10.1.16
lcsStatusLldpRemote8023TableEntryPdRequestedPower OBJECT-TYPE
    SYNTAX     Integer32 (0..65535)
    MAX-ACCESS read-only
    STATUS     current
    DESCRIPTION
            "-- empty --"
    ::= { lcsStatusLldpRemote8023TableEntry 16 }

-- {COLUMN} 1.3.6.1.4.1.2356.11.1.60.10.1.17
lcsStatusLldpRemote8023TableEntryPseAllocatedPower OBJECT-TYPE
    SYNTAX     Integer32 (0..65535)
    MAX-ACCESS read-only
    STATUS     current
    DESCRIPTION
            "-- empty --"
    ::= { lcsStatusLldpRemote8023TableEntry 17 }

-- {TABLE} 1.3.6.1.4.1.2356.11.1.60.11
lcsStatusLldpRemote8021ProtoVlansTable OBJECT-TYPE
    SYNTAX     SEQUENCE OF LcsStatusLldpRemote8021ProtoVlansEntry
    MAX-ACCESS not-accessible
    STATUS     current
    DESCRIPTION
            "-- empty --"
    ::= { lcsStatusLldp 11 }

-- {ROW} 1.3.6.1.4.1.2356.11.1.60.11.1
lcsStatusLldpRemote8021ProtoVlansEntry OBJECT-TYPE
    SYNTAX     LcsStatusLldpRemote8021ProtoVlansEntry
    MAX-ACCESS not-accessible
    STATUS     current
    DESCRIPTION
            ""
    INDEX {
            lcsStatusLldpRemote8021ProtoVlansEntryIndex,
            lcsStatusLldpRemote8021ProtoVlansEntryVlanId
          }
    ::= { lcsStatusLldpRemote8021ProtoVlansTable 1 }

LcsStatusLldpRemote8021ProtoVlansEntry ::= SEQUENCE {
            lcsStatusLldpRemote8021ProtoVlansEntryIndex Integer32,
            lcsStatusLldpRemote8021ProtoVlansEntryVlanId Integer32,
            lcsStatusLldpRemote8021ProtoVlansEntrySupported INTEGER,
            lcsStatusLldpRemote8021ProtoVlansEntryEnabled INTEGER
    }

-- {COLUMN} 1.3.6.1.4.1.2356.11.1.60.11.1.1
lcsStatusLldpRemote8021ProtoVlansEntryIndex OBJECT-TYPE
    SYNTAX     Integer32 (0..2147483647)
    MAX-ACCESS read-only
    STATUS     current
    DESCRIPTION
            "-- empty --"
    ::= { lcsStatusLldpRemote8021ProtoVlansEntry 1 }

-- {COLUMN} 1.3.6.1.4.1.2356.11.1.60.11.1.2
lcsStatusLldpRemote8021ProtoVlansEntryVlanId OBJECT-TYPE
    SYNTAX     Integer32 (0..65535)
    MAX-ACCESS read-only
    STATUS     current
    DESCRIPTION
            "-- empty --"
    ::= { lcsStatusLldpRemote8021ProtoVlansEntry 2 }

-- {COLUMN} 1.3.6.1.4.1.2356.11.1.60.11.1.3
lcsStatusLldpRemote8021ProtoVlansEntrySupported OBJECT-TYPE
    SYNTAX     INTEGER {
                  eNo (0),
                  eYes (1)
            }
    MAX-ACCESS read-only
    STATUS     current
    DESCRIPTION
            "-- empty --"
    ::= { lcsStatusLldpRemote8021ProtoVlansEntry 3 }

-- {COLUMN} 1.3.6.1.4.1.2356.11.1.60.11.1.4
lcsStatusLldpRemote8021ProtoVlansEntryEnabled OBJECT-TYPE
    SYNTAX     INTEGER {
                  eNo (0),
                  eYes (1)
            }
    MAX-ACCESS read-only
    STATUS     current
    DESCRIPTION
            "-- empty --"
    ::= { lcsStatusLldpRemote8021ProtoVlansEntry 4 }

-- {TABLE} 1.3.6.1.4.1.2356.11.1.60.12
lcsStatusLldpRemote8021VlanNamesTable OBJECT-TYPE
    SYNTAX     SEQUENCE OF LcsStatusLldpRemote8021VlanNamesEntry
    MAX-ACCESS not-accessible
    STATUS     current
    DESCRIPTION
            "-- empty --"
    ::= { lcsStatusLldp 12 }

-- {ROW} 1.3.6.1.4.1.2356.11.1.60.12.1
lcsStatusLldpRemote8021VlanNamesEntry OBJECT-TYPE
    SYNTAX     LcsStatusLldpRemote8021VlanNamesEntry
    MAX-ACCESS not-accessible
    STATUS     current
    DESCRIPTION
            ""
    INDEX {
            lcsStatusLldpRemote8021VlanNamesEntryIndex,
            lcsStatusLldpRemote8021VlanNamesEntryVlanId
          }
    ::= { lcsStatusLldpRemote8021VlanNamesTable 1 }

LcsStatusLldpRemote8021VlanNamesEntry ::= SEQUENCE {
            lcsStatusLldpRemote8021VlanNamesEntryIndex Integer32,
            lcsStatusLldpRemote8021VlanNamesEntryVlanId Integer32,
            lcsStatusLldpRemote8021VlanNamesEntryName DisplayString
    }

-- {COLUMN} 1.3.6.1.4.1.2356.11.1.60.12.1.1
lcsStatusLldpRemote8021VlanNamesEntryIndex OBJECT-TYPE
    SYNTAX     Integer32 (0..2147483647)
    MAX-ACCESS read-only
    STATUS     current
    DESCRIPTION
            "-- empty --"
    ::= { lcsStatusLldpRemote8021VlanNamesEntry 1 }

-- {COLUMN} 1.3.6.1.4.1.2356.11.1.60.12.1.2
lcsStatusLldpRemote8021VlanNamesEntryVlanId OBJECT-TYPE
    SYNTAX     Integer32 (0..65535)
    MAX-ACCESS read-only
    STATUS     current
    DESCRIPTION
            "-- empty --"
    ::= { lcsStatusLldpRemote8021VlanNamesEntry 2 }

-- {COLUMN} 1.3.6.1.4.1.2356.11.1.60.12.1.3
lcsStatusLldpRemote8021VlanNamesEntryName OBJECT-TYPE
    SYNTAX     DisplayString (SIZE(0..32))
    MAX-ACCESS read-only
    STATUS     current
    DESCRIPTION
            "-- empty --"
    ::= { lcsStatusLldpRemote8021VlanNamesEntry 3 }

-- {TABLE} 1.3.6.1.4.1.2356.11.1.60.13
lcsStatusLldpRemote8021ProtocolIdsTable OBJECT-TYPE
    SYNTAX     SEQUENCE OF LcsStatusLldpRemote8021ProtocolIdsEntry
    MAX-ACCESS not-accessible
    STATUS     current
    DESCRIPTION
            "-- empty --"
    ::= { lcsStatusLldp 13 }

-- {ROW} 1.3.6.1.4.1.2356.11.1.60.13.1
lcsStatusLldpRemote8021ProtocolIdsEntry OBJECT-TYPE
    SYNTAX     LcsStatusLldpRemote8021ProtocolIdsEntry
    MAX-ACCESS not-accessible
    STATUS     current
    DESCRIPTION
            ""
    INDEX {
            lcsStatusLldpRemote8021ProtocolIdsEntryIndex,
            lcsStatusLldpRemote8021ProtocolIdsEntryProtocol
          }
    ::= { lcsStatusLldpRemote8021ProtocolIdsTable 1 }

LcsStatusLldpRemote8021ProtocolIdsEntry ::= SEQUENCE {
            lcsStatusLldpRemote8021ProtocolIdsEntryIndex Integer32,
            lcsStatusLldpRemote8021ProtocolIdsEntryProtocol DisplayString
    }

-- {COLUMN} 1.3.6.1.4.1.2356.11.1.60.13.1.1
lcsStatusLldpRemote8021ProtocolIdsEntryIndex OBJECT-TYPE
    SYNTAX     Integer32 (0..2147483647)
    MAX-ACCESS read-only
    STATUS     current
    DESCRIPTION
            "-- empty --"
    ::= { lcsStatusLldpRemote8021ProtocolIdsEntry 1 }

-- {COLUMN} 1.3.6.1.4.1.2356.11.1.60.13.1.3
lcsStatusLldpRemote8021ProtocolIdsEntryProtocol OBJECT-TYPE
    SYNTAX     DisplayString (SIZE(0..255))
    MAX-ACCESS read-only
    STATUS     current
    DESCRIPTION
            "-- empty --"
    ::= { lcsStatusLldpRemote8021ProtocolIdsEntry 3 }

-- {TABLE} 1.3.6.1.4.1.2356.11.1.60.14
lcsStatusLldpRemoteUnknownTlvsTable OBJECT-TYPE
    SYNTAX     SEQUENCE OF LcsStatusLldpRemoteUnknownTlvsEntry
    MAX-ACCESS not-accessible
    STATUS     current
    DESCRIPTION
            "-- empty --"
    ::= { lcsStatusLldp 14 }

-- {ROW} 1.3.6.1.4.1.2356.11.1.60.14.1
lcsStatusLldpRemoteUnknownTlvsEntry OBJECT-TYPE
    SYNTAX     LcsStatusLldpRemoteUnknownTlvsEntry
    MAX-ACCESS not-accessible
    STATUS     current
    DESCRIPTION
            ""
    INDEX {
            lcsStatusLldpRemoteUnknownTlvsEntryIndex,
            lcsStatusLldpRemoteUnknownTlvsEntryType
          }
    ::= { lcsStatusLldpRemoteUnknownTlvsTable 1 }

LcsStatusLldpRemoteUnknownTlvsEntry ::= SEQUENCE {
            lcsStatusLldpRemoteUnknownTlvsEntryIndex Integer32,
            lcsStatusLldpRemoteUnknownTlvsEntryType Integer32,
            lcsStatusLldpRemoteUnknownTlvsEntryData DisplayString
    }

-- {COLUMN} 1.3.6.1.4.1.2356.11.1.60.14.1.1
lcsStatusLldpRemoteUnknownTlvsEntryIndex OBJECT-TYPE
    SYNTAX     Integer32 (0..2147483647)
    MAX-ACCESS read-only
    STATUS     current
    DESCRIPTION
            "-- empty --"
    ::= { lcsStatusLldpRemoteUnknownTlvsEntry 1 }

-- {COLUMN} 1.3.6.1.4.1.2356.11.1.60.14.1.2
lcsStatusLldpRemoteUnknownTlvsEntryType OBJECT-TYPE
    SYNTAX     Integer32 (0..255)
    MAX-ACCESS read-only
    STATUS     current
    DESCRIPTION
            "-- empty --"
    ::= { lcsStatusLldpRemoteUnknownTlvsEntry 2 }

-- {COLUMN} 1.3.6.1.4.1.2356.11.1.60.14.1.3
lcsStatusLldpRemoteUnknownTlvsEntryData OBJECT-TYPE
    SYNTAX     DisplayString (SIZE(0..255))
    MAX-ACCESS read-only
    STATUS     current
    DESCRIPTION
            "-- empty --"
    ::= { lcsStatusLldpRemoteUnknownTlvsEntry 3 }

-- {TABLE} 1.3.6.1.4.1.2356.11.1.60.15
lcsStatusLldpRemoteOrgDefaultInfosTable OBJECT-TYPE
    SYNTAX     SEQUENCE OF LcsStatusLldpRemoteOrgDefaultInfosEntry
    MAX-ACCESS not-accessible
    STATUS     current
    DESCRIPTION
            "-- empty --"
    ::= { lcsStatusLldp 15 }

-- {ROW} 1.3.6.1.4.1.2356.11.1.60.15.1
lcsStatusLldpRemoteOrgDefaultInfosEntry OBJECT-TYPE
    SYNTAX     LcsStatusLldpRemoteOrgDefaultInfosEntry
    MAX-ACCESS not-accessible
    STATUS     current
    DESCRIPTION
            ""
    INDEX {
            lcsStatusLldpRemoteOrgDefaultInfosEntryIndex,
            lcsStatusLldpRemoteOrgDefaultInfosEntryOid,
            lcsStatusLldpRemoteOrgDefaultInfosEntrySubtype,
            lcsStatusLldpRemoteOrgDefaultInfosEntryTlvIndex
          }
    ::= { lcsStatusLldpRemoteOrgDefaultInfosTable 1 }

LcsStatusLldpRemoteOrgDefaultInfosEntry ::= SEQUENCE {
            lcsStatusLldpRemoteOrgDefaultInfosEntryIndex Integer32,
            lcsStatusLldpRemoteOrgDefaultInfosEntryOid Integer32,
            lcsStatusLldpRemoteOrgDefaultInfosEntrySubtype Integer32,
            lcsStatusLldpRemoteOrgDefaultInfosEntryTlvIndex Integer32,
            lcsStatusLldpRemoteOrgDefaultInfosEntryData DisplayString
    }

-- {COLUMN} 1.3.6.1.4.1.2356.11.1.60.15.1.1
lcsStatusLldpRemoteOrgDefaultInfosEntryIndex OBJECT-TYPE
    SYNTAX     Integer32 (0..2147483647)
    MAX-ACCESS read-only
    STATUS     current
    DESCRIPTION
            "-- empty --"
    ::= { lcsStatusLldpRemoteOrgDefaultInfosEntry 1 }

-- {COLUMN} 1.3.6.1.4.1.2356.11.1.60.15.1.2
lcsStatusLldpRemoteOrgDefaultInfosEntryOid OBJECT-TYPE
    SYNTAX     Integer32 (0..2147483647)
    MAX-ACCESS read-only
    STATUS     current
    DESCRIPTION
            "-- empty --"
    ::= { lcsStatusLldpRemoteOrgDefaultInfosEntry 2 }

-- {COLUMN} 1.3.6.1.4.1.2356.11.1.60.15.1.3
lcsStatusLldpRemoteOrgDefaultInfosEntrySubtype OBJECT-TYPE
    SYNTAX     Integer32 (0..255)
    MAX-ACCESS read-only
    STATUS     current
    DESCRIPTION
            "-- empty --"
    ::= { lcsStatusLldpRemoteOrgDefaultInfosEntry 3 }

-- {COLUMN} 1.3.6.1.4.1.2356.11.1.60.15.1.4
lcsStatusLldpRemoteOrgDefaultInfosEntryTlvIndex OBJECT-TYPE
    SYNTAX     Integer32 (0..2147483647)
    MAX-ACCESS read-only
    STATUS     current
    DESCRIPTION
            "-- empty --"
    ::= { lcsStatusLldpRemoteOrgDefaultInfosEntry 4 }

-- {COLUMN} 1.3.6.1.4.1.2356.11.1.60.15.1.5
lcsStatusLldpRemoteOrgDefaultInfosEntryData OBJECT-TYPE
    SYNTAX     DisplayString (SIZE(0..255))
    MAX-ACCESS read-only
    STATUS     current
    DESCRIPTION
            "-- empty --"
    ::= { lcsStatusLldpRemoteOrgDefaultInfosEntry 5 }

-- {TABLE} 1.3.6.1.4.1.2356.11.1.60.16
lcsStatusLldpRemote80211TableTable OBJECT-TYPE
    SYNTAX     SEQUENCE OF LcsStatusLldpRemote80211TableEntry
    MAX-ACCESS not-accessible
    STATUS     current
    DESCRIPTION
            "-- empty --"
    ::= { lcsStatusLldp 16 }

-- {ROW} 1.3.6.1.4.1.2356.11.1.60.16.1
lcsStatusLldpRemote80211TableEntry OBJECT-TYPE
    SYNTAX     LcsStatusLldpRemote80211TableEntry
    MAX-ACCESS not-accessible
    STATUS     current
    DESCRIPTION
            ""
    INDEX {
            lcsStatusLldpRemote80211TableEntryIndex
          }
    ::= { lcsStatusLldpRemote80211TableTable 1 }

LcsStatusLldpRemote80211TableEntry ::= SEQUENCE {
            lcsStatusLldpRemote80211TableEntryIndex Integer32,
            lcsStatusLldpRemote80211TableEntrySsid DisplayString,
            lcsStatusLldpRemote80211TableEntryRadioChannel Integer32,
            lcsStatusLldpRemote80211TableEntryPhyType INTEGER
    }

-- {COLUMN} 1.3.6.1.4.1.2356.11.1.60.16.1.1
lcsStatusLldpRemote80211TableEntryIndex OBJECT-TYPE
    SYNTAX     Integer32 (0..2147483647)
    MAX-ACCESS read-only
    STATUS     current
    DESCRIPTION
            "-- empty --"
    ::= { lcsStatusLldpRemote80211TableEntry 1 }

-- {COLUMN} 1.3.6.1.4.1.2356.11.1.60.16.1.3
lcsStatusLldpRemote80211TableEntrySsid OBJECT-TYPE
    SYNTAX     DisplayString (SIZE(0..32))
    MAX-ACCESS read-only
    STATUS     current
    DESCRIPTION
            "-- empty --"
    ::= { lcsStatusLldpRemote80211TableEntry 3 }

-- {COLUMN} 1.3.6.1.4.1.2356.11.1.60.16.1.4
lcsStatusLldpRemote80211TableEntryRadioChannel OBJECT-TYPE
    SYNTAX     Integer32 (0..255)
    MAX-ACCESS read-only
    STATUS     current
    DESCRIPTION
            "-- empty --"
    ::= { lcsStatusLldpRemote80211TableEntry 4 }

-- {COLUMN} 1.3.6.1.4.1.2356.11.1.60.16.1.5
lcsStatusLldpRemote80211TableEntryPhyType OBJECT-TYPE
    SYNTAX     INTEGER {
                  eFhss (1),
                  eDsss (2),
                  eInfrared (3),
                  eOfdm (4),
                  eHrDsss (5),
                  eErp (6),
                  eHt (7),
                  eVht (9),
                  ePbcc (254)
            }
    MAX-ACCESS read-only
    STATUS     current
    DESCRIPTION
            "-- empty --"
    ::= { lcsStatusLldpRemote80211TableEntry 5 }

-- {NODE} 1.3.6.1.4.1.2356.11.1.61
lcsStatusCerts OBJECT IDENTIFIER ::= { lcsStatus 61 }

-- {NODE} 1.3.6.1.4.1.2356.11.1.61.1
lcsStatusCertsScepClnt OBJECT IDENTIFIER ::= { lcsStatusCerts 1 }

-- {TABLE} 1.3.6.1.4.1.2356.11.1.61.1.4
lcsStatusCertsScepClntCasTable OBJECT-TYPE
    SYNTAX     SEQUENCE OF LcsStatusCertsScepClntCasEntry
    MAX-ACCESS not-accessible
    STATUS     current
    DESCRIPTION
            ""
    ::= { lcsStatusCertsScepClnt 4 }

-- {ROW} 1.3.6.1.4.1.2356.11.1.61.1.4.1
lcsStatusCertsScepClntCasEntry OBJECT-TYPE
    SYNTAX     LcsStatusCertsScepClntCasEntry
    MAX-ACCESS not-accessible
    STATUS     current
    DESCRIPTION
            ""
    INDEX {
            lcsStatusCertsScepClntCasEntryIdx
          }
    ::= { lcsStatusCertsScepClntCasTable 1 }

LcsStatusCertsScepClntCasEntry ::= SEQUENCE {
            lcsStatusCertsScepClntCasEntryIdx Integer32,
            lcsStatusCertsScepClntCasEntryName DisplayString,
            lcsStatusCertsScepClntCasEntryExpires DisplayString,
            lcsStatusCertsScepClntCasEntryIssued DisplayString,
            lcsStatusCertsScepClntCasEntryKeyUsage DisplayString,
            lcsStatusCertsScepClntCasEntryIssuer DisplayString,
            lcsStatusCertsScepClntCasEntrySubject DisplayString,
            lcsStatusCertsScepClntCasEntryStatus DisplayString,
            lcsStatusCertsScepClntCasEntryIkeCertificate DisplayString,
            lcsStatusCertsScepClntCasEntryMd5Fingerprint DisplayString,
            lcsStatusCertsScepClntCasEntrySha1Fingerprint DisplayString,
            lcsStatusCertsScepClntCasEntryExpSnmp Counter32,
            lcsStatusCertsScepClntCasEntryIssSnmp Counter32,
            lcsStatusCertsScepClntCasEntrySha256Fingerprint DisplayString
    }

-- {COLUMN} 1.3.6.1.4.1.2356.11.1.61.1.4.1.1
lcsStatusCertsScepClntCasEntryIdx OBJECT-TYPE
    SYNTAX     Integer32 (0..2147483647)
    MAX-ACCESS read-only
    STATUS     current
    DESCRIPTION
            ""
    ::= { lcsStatusCertsScepClntCasEntry 1 }

-- {COLUMN} 1.3.6.1.4.1.2356.11.1.61.1.4.1.2
lcsStatusCertsScepClntCasEntryName OBJECT-TYPE
    SYNTAX     DisplayString (SIZE(0..255))
    MAX-ACCESS read-only
    STATUS     current
    DESCRIPTION
            ""
    ::= { lcsStatusCertsScepClntCasEntry 2 }

-- {COLUMN} 1.3.6.1.4.1.2356.11.1.61.1.4.1.3
lcsStatusCertsScepClntCasEntryExpires OBJECT-TYPE
    SYNTAX     DisplayString (SIZE(0..255))
    MAX-ACCESS read-only
    STATUS     current
    DESCRIPTION
            ""
    ::= { lcsStatusCertsScepClntCasEntry 3 }

-- {COLUMN} 1.3.6.1.4.1.2356.11.1.61.1.4.1.4
lcsStatusCertsScepClntCasEntryIssued OBJECT-TYPE
    SYNTAX     DisplayString (SIZE(0..255))
    MAX-ACCESS read-only
    STATUS     current
    DESCRIPTION
            ""
    ::= { lcsStatusCertsScepClntCasEntry 4 }

-- {COLUMN} 1.3.6.1.4.1.2356.11.1.61.1.4.1.5
lcsStatusCertsScepClntCasEntryKeyUsage OBJECT-TYPE
    SYNTAX     DisplayString (SIZE(0..255))
    MAX-ACCESS read-only
    STATUS     current
    DESCRIPTION
            ""
    ::= { lcsStatusCertsScepClntCasEntry 5 }

-- {COLUMN} 1.3.6.1.4.1.2356.11.1.61.1.4.1.6
lcsStatusCertsScepClntCasEntryIssuer OBJECT-TYPE
    SYNTAX     DisplayString (SIZE(0..255))
    MAX-ACCESS read-only
    STATUS     current
    DESCRIPTION
            ""
    ::= { lcsStatusCertsScepClntCasEntry 6 }

-- {COLUMN} 1.3.6.1.4.1.2356.11.1.61.1.4.1.7
lcsStatusCertsScepClntCasEntrySubject OBJECT-TYPE
    SYNTAX     DisplayString (SIZE(0..255))
    MAX-ACCESS read-only
    STATUS     current
    DESCRIPTION
            ""
    ::= { lcsStatusCertsScepClntCasEntry 7 }

-- {COLUMN} 1.3.6.1.4.1.2356.11.1.61.1.4.1.8
lcsStatusCertsScepClntCasEntryStatus OBJECT-TYPE
    SYNTAX     DisplayString (SIZE(0..255))
    MAX-ACCESS read-only
    STATUS     current
    DESCRIPTION
            ""
    ::= { lcsStatusCertsScepClntCasEntry 8 }

-- {COLUMN} 1.3.6.1.4.1.2356.11.1.61.1.4.1.9
lcsStatusCertsScepClntCasEntryIkeCertificate OBJECT-TYPE
    SYNTAX     DisplayString (SIZE(0..255))
    MAX-ACCESS read-only
    STATUS     current
    DESCRIPTION
            ""
    ::= { lcsStatusCertsScepClntCasEntry 9 }

-- {COLUMN} 1.3.6.1.4.1.2356.11.1.61.1.4.1.10
lcsStatusCertsScepClntCasEntryMd5Fingerprint OBJECT-TYPE
    SYNTAX     DisplayString (SIZE(0..255))
    MAX-ACCESS read-only
    STATUS     current
    DESCRIPTION
            ""
    ::= { lcsStatusCertsScepClntCasEntry 10 }

-- {COLUMN} 1.3.6.1.4.1.2356.11.1.61.1.4.1.11
lcsStatusCertsScepClntCasEntrySha1Fingerprint OBJECT-TYPE
    SYNTAX     DisplayString (SIZE(0..255))
    MAX-ACCESS read-only
    STATUS     current
    DESCRIPTION
            ""
    ::= { lcsStatusCertsScepClntCasEntry 11 }

-- {COLUMN} 1.3.6.1.4.1.2356.11.1.61.1.4.1.12
lcsStatusCertsScepClntCasEntryExpSnmp OBJECT-TYPE
    SYNTAX     Counter32
    MAX-ACCESS read-only
    STATUS     current
    DESCRIPTION
            ""
    ::= { lcsStatusCertsScepClntCasEntry 12 }

-- {COLUMN} 1.3.6.1.4.1.2356.11.1.61.1.4.1.13
lcsStatusCertsScepClntCasEntryIssSnmp OBJECT-TYPE
    SYNTAX     Counter32
    MAX-ACCESS read-only
    STATUS     current
    DESCRIPTION
            ""
    ::= { lcsStatusCertsScepClntCasEntry 13 }

-- {COLUMN} 1.3.6.1.4.1.2356.11.1.61.1.4.1.14
lcsStatusCertsScepClntCasEntrySha256Fingerprint OBJECT-TYPE
    SYNTAX     DisplayString (SIZE(0..255))
    MAX-ACCESS read-only
    STATUS     current
    DESCRIPTION
            "-- empty --"
    ::= { lcsStatusCertsScepClntCasEntry 14 }

-- {TABLE} 1.3.6.1.4.1.2356.11.1.61.1.5
lcsStatusCertsScepClntRasTable OBJECT-TYPE
    SYNTAX     SEQUENCE OF LcsStatusCertsScepClntRasEntry
    MAX-ACCESS not-accessible
    STATUS     current
    DESCRIPTION
            ""
    ::= { lcsStatusCertsScepClnt 5 }

-- {ROW} 1.3.6.1.4.1.2356.11.1.61.1.5.1
lcsStatusCertsScepClntRasEntry OBJECT-TYPE
    SYNTAX     LcsStatusCertsScepClntRasEntry
    MAX-ACCESS not-accessible
    STATUS     current
    DESCRIPTION
            ""
    INDEX {
            lcsStatusCertsScepClntRasEntryIdx
          }
    ::= { lcsStatusCertsScepClntRasTable 1 }

LcsStatusCertsScepClntRasEntry ::= SEQUENCE {
            lcsStatusCertsScepClntRasEntryIdx Integer32,
            lcsStatusCertsScepClntRasEntryName DisplayString,
            lcsStatusCertsScepClntRasEntryExpires DisplayString,
            lcsStatusCertsScepClntRasEntryIssued DisplayString,
            lcsStatusCertsScepClntRasEntryKeyUsage DisplayString,
            lcsStatusCertsScepClntRasEntryIssuer DisplayString,
            lcsStatusCertsScepClntRasEntrySubject DisplayString,
            lcsStatusCertsScepClntRasEntryStatus DisplayString,
            lcsStatusCertsScepClntRasEntryExpSnmp Counter32,
            lcsStatusCertsScepClntRasEntryIssSnmp Counter32
    }

-- {COLUMN} 1.3.6.1.4.1.2356.11.1.61.1.5.1.1
lcsStatusCertsScepClntRasEntryIdx OBJECT-TYPE
    SYNTAX     Integer32 (0..2147483647)
    MAX-ACCESS read-only
    STATUS     current
    DESCRIPTION
            ""
    ::= { lcsStatusCertsScepClntRasEntry 1 }

-- {COLUMN} 1.3.6.1.4.1.2356.11.1.61.1.5.1.2
lcsStatusCertsScepClntRasEntryName OBJECT-TYPE
    SYNTAX     DisplayString (SIZE(0..255))
    MAX-ACCESS read-only
    STATUS     current
    DESCRIPTION
            ""
    ::= { lcsStatusCertsScepClntRasEntry 2 }

-- {COLUMN} 1.3.6.1.4.1.2356.11.1.61.1.5.1.3
lcsStatusCertsScepClntRasEntryExpires OBJECT-TYPE
    SYNTAX     DisplayString (SIZE(0..255))
    MAX-ACCESS read-only
    STATUS     current
    DESCRIPTION
            ""
    ::= { lcsStatusCertsScepClntRasEntry 3 }

-- {COLUMN} 1.3.6.1.4.1.2356.11.1.61.1.5.1.4
lcsStatusCertsScepClntRasEntryIssued OBJECT-TYPE
    SYNTAX     DisplayString (SIZE(0..255))
    MAX-ACCESS read-only
    STATUS     current
    DESCRIPTION
            ""
    ::= { lcsStatusCertsScepClntRasEntry 4 }

-- {COLUMN} 1.3.6.1.4.1.2356.11.1.61.1.5.1.5
lcsStatusCertsScepClntRasEntryKeyUsage OBJECT-TYPE
    SYNTAX     DisplayString (SIZE(0..255))
    MAX-ACCESS read-only
    STATUS     current
    DESCRIPTION
            ""
    ::= { lcsStatusCertsScepClntRasEntry 5 }

-- {COLUMN} 1.3.6.1.4.1.2356.11.1.61.1.5.1.6
lcsStatusCertsScepClntRasEntryIssuer OBJECT-TYPE
    SYNTAX     DisplayString (SIZE(0..255))
    MAX-ACCESS read-only
    STATUS     current
    DESCRIPTION
            ""
    ::= { lcsStatusCertsScepClntRasEntry 6 }

-- {COLUMN} 1.3.6.1.4.1.2356.11.1.61.1.5.1.7
lcsStatusCertsScepClntRasEntrySubject OBJECT-TYPE
    SYNTAX     DisplayString (SIZE(0..255))
    MAX-ACCESS read-only
    STATUS     current
    DESCRIPTION
            ""
    ::= { lcsStatusCertsScepClntRasEntry 7 }

-- {COLUMN} 1.3.6.1.4.1.2356.11.1.61.1.5.1.8
lcsStatusCertsScepClntRasEntryStatus OBJECT-TYPE
    SYNTAX     DisplayString (SIZE(0..255))
    MAX-ACCESS read-only
    STATUS     current
    DESCRIPTION
            ""
    ::= { lcsStatusCertsScepClntRasEntry 8 }

-- {COLUMN} 1.3.6.1.4.1.2356.11.1.61.1.5.1.9
lcsStatusCertsScepClntRasEntryExpSnmp OBJECT-TYPE
    SYNTAX     Counter32
    MAX-ACCESS read-only
    STATUS     current
    DESCRIPTION
            ""
    ::= { lcsStatusCertsScepClntRasEntry 9 }

-- {COLUMN} 1.3.6.1.4.1.2356.11.1.61.1.5.1.10
lcsStatusCertsScepClntRasEntryIssSnmp OBJECT-TYPE
    SYNTAX     Counter32
    MAX-ACCESS read-only
    STATUS     current
    DESCRIPTION
            ""
    ::= { lcsStatusCertsScepClntRasEntry 10 }

-- {TABLE} 1.3.6.1.4.1.2356.11.1.61.1.6
lcsStatusCertsScepClntCertsTable OBJECT-TYPE
    SYNTAX     SEQUENCE OF LcsStatusCertsScepClntCertsEntry
    MAX-ACCESS not-accessible
    STATUS     current
    DESCRIPTION
            ""
    ::= { lcsStatusCertsScepClnt 6 }

-- {ROW} 1.3.6.1.4.1.2356.11.1.61.1.6.1
lcsStatusCertsScepClntCertsEntry OBJECT-TYPE
    SYNTAX     LcsStatusCertsScepClntCertsEntry
    MAX-ACCESS not-accessible
    STATUS     current
    DESCRIPTION
            ""
    INDEX {
            lcsStatusCertsScepClntCertsEntryIdx
          }
    ::= { lcsStatusCertsScepClntCertsTable 1 }

LcsStatusCertsScepClntCertsEntry ::= SEQUENCE {
            lcsStatusCertsScepClntCertsEntryIdx Integer32,
            lcsStatusCertsScepClntCertsEntryName DisplayString,
            lcsStatusCertsScepClntCertsEntryExpires DisplayString,
            lcsStatusCertsScepClntCertsEntryIssued DisplayString,
            lcsStatusCertsScepClntCertsEntryKeyUsage DisplayString,
            lcsStatusCertsScepClntCertsEntrySubjectaltname DisplayString,
            lcsStatusCertsScepClntCertsEntryIssuer DisplayString,
            lcsStatusCertsScepClntCertsEntrySubject DisplayString,
            lcsStatusCertsScepClntCertsEntryStatus DisplayString,
            lcsStatusCertsScepClntCertsEntryExpSnmp Counter32,
            lcsStatusCertsScepClntCertsEntryIssSnmp Counter32,
            lcsStatusCertsScepClntCertsEntryExtendedKeyusage DisplayString,
            lcsStatusCertsScepClntCertsEntryFilename DisplayString
    }

-- {COLUMN} 1.3.6.1.4.1.2356.11.1.61.1.6.1.1
lcsStatusCertsScepClntCertsEntryIdx OBJECT-TYPE
    SYNTAX     Integer32 (0..2147483647)
    MAX-ACCESS read-only
    STATUS     current
    DESCRIPTION
            ""
    ::= { lcsStatusCertsScepClntCertsEntry 1 }

-- {COLUMN} 1.3.6.1.4.1.2356.11.1.61.1.6.1.2
lcsStatusCertsScepClntCertsEntryName OBJECT-TYPE
    SYNTAX     DisplayString (SIZE(0..255))
    MAX-ACCESS read-only
    STATUS     current
    DESCRIPTION
            ""
    ::= { lcsStatusCertsScepClntCertsEntry 2 }

-- {COLUMN} 1.3.6.1.4.1.2356.11.1.61.1.6.1.3
lcsStatusCertsScepClntCertsEntryExpires OBJECT-TYPE
    SYNTAX     DisplayString (SIZE(0..255))
    MAX-ACCESS read-only
    STATUS     current
    DESCRIPTION
            ""
    ::= { lcsStatusCertsScepClntCertsEntry 3 }

-- {COLUMN} 1.3.6.1.4.1.2356.11.1.61.1.6.1.4
lcsStatusCertsScepClntCertsEntryIssued OBJECT-TYPE
    SYNTAX     DisplayString (SIZE(0..255))
    MAX-ACCESS read-only
    STATUS     current
    DESCRIPTION
            ""
    ::= { lcsStatusCertsScepClntCertsEntry 4 }

-- {COLUMN} 1.3.6.1.4.1.2356.11.1.61.1.6.1.5
lcsStatusCertsScepClntCertsEntryKeyUsage OBJECT-TYPE
    SYNTAX     DisplayString (SIZE(0..255))
    MAX-ACCESS read-only
    STATUS     current
    DESCRIPTION
            ""
    ::= { lcsStatusCertsScepClntCertsEntry 5 }

-- {COLUMN} 1.3.6.1.4.1.2356.11.1.61.1.6.1.6
lcsStatusCertsScepClntCertsEntrySubjectaltname OBJECT-TYPE
    SYNTAX     DisplayString (SIZE(0..255))
    MAX-ACCESS read-only
    STATUS     current
    DESCRIPTION
            ""
    ::= { lcsStatusCertsScepClntCertsEntry 6 }

-- {COLUMN} 1.3.6.1.4.1.2356.11.1.61.1.6.1.7
lcsStatusCertsScepClntCertsEntryIssuer OBJECT-TYPE
    SYNTAX     DisplayString (SIZE(0..255))
    MAX-ACCESS read-only
    STATUS     current
    DESCRIPTION
            ""
    ::= { lcsStatusCertsScepClntCertsEntry 7 }

-- {COLUMN} 1.3.6.1.4.1.2356.11.1.61.1.6.1.8
lcsStatusCertsScepClntCertsEntrySubject OBJECT-TYPE
    SYNTAX     DisplayString (SIZE(0..255))
    MAX-ACCESS read-only
    STATUS     current
    DESCRIPTION
            ""
    ::= { lcsStatusCertsScepClntCertsEntry 8 }

-- {COLUMN} 1.3.6.1.4.1.2356.11.1.61.1.6.1.9
lcsStatusCertsScepClntCertsEntryStatus OBJECT-TYPE
    SYNTAX     DisplayString (SIZE(0..255))
    MAX-ACCESS read-only
    STATUS     current
    DESCRIPTION
            ""
    ::= { lcsStatusCertsScepClntCertsEntry 9 }

-- {COLUMN} 1.3.6.1.4.1.2356.11.1.61.1.6.1.10
lcsStatusCertsScepClntCertsEntryExpSnmp OBJECT-TYPE
    SYNTAX     Counter32
    MAX-ACCESS read-only
    STATUS     current
    DESCRIPTION
            ""
    ::= { lcsStatusCertsScepClntCertsEntry 10 }

-- {COLUMN} 1.3.6.1.4.1.2356.11.1.61.1.6.1.11
lcsStatusCertsScepClntCertsEntryIssSnmp OBJECT-TYPE
    SYNTAX     Counter32
    MAX-ACCESS read-only
    STATUS     current
    DESCRIPTION
            ""
    ::= { lcsStatusCertsScepClntCertsEntry 11 }

-- {COLUMN} 1.3.6.1.4.1.2356.11.1.61.1.6.1.12
lcsStatusCertsScepClntCertsEntryExtendedKeyusage OBJECT-TYPE
    SYNTAX     DisplayString (SIZE(0..255))
    MAX-ACCESS read-only
    STATUS     current
    DESCRIPTION
            ""
    ::= { lcsStatusCertsScepClntCertsEntry 12 }

-- {COLUMN} 1.3.6.1.4.1.2356.11.1.61.1.6.1.13
lcsStatusCertsScepClntCertsEntryFilename OBJECT-TYPE
    SYNTAX     DisplayString (SIZE(0..255))
    MAX-ACCESS read-only
    STATUS     current
    DESCRIPTION
            ""
    ::= { lcsStatusCertsScepClntCertsEntry 13 }

-- {SCALAR} 1.3.6.1.4.1.2356.11.1.61.1.8
lcsStatusCertsScepClntScepClientState OBJECT-TYPE
    SYNTAX     DisplayString
    MAX-ACCESS read-only
    STATUS     current
    DESCRIPTION
            ""
    ::= { lcsStatusCertsScepClnt 8 }

-- {NODE} 1.3.6.1.4.1.2356.11.1.61.2
lcsStatusCertsScepCa OBJECT IDENTIFIER ::= { lcsStatusCerts 2 }

-- {NODE} 1.3.6.1.4.1.2356.11.1.61.2.1
lcsStatusCertsScepCaCerts OBJECT IDENTIFIER ::= { lcsStatusCertsScepCa 1 }

-- {TABLE} 1.3.6.1.4.1.2356.11.1.61.2.1.1
lcsStatusCertsScepCaCertsCertsStatusTabTable OBJECT-TYPE
    SYNTAX     SEQUENCE OF LcsStatusCertsScepCaCertsCertsStatusTabEntry
    MAX-ACCESS not-accessible
    STATUS     current
    DESCRIPTION
            "certificates status table"
    ::= { lcsStatusCertsScepCaCerts 1 }

-- {ROW} 1.3.6.1.4.1.2356.11.1.61.2.1.1.1
lcsStatusCertsScepCaCertsCertsStatusTabEntry OBJECT-TYPE
    SYNTAX     LcsStatusCertsScepCaCertsCertsStatusTabEntry
    MAX-ACCESS not-accessible
    STATUS     current
    DESCRIPTION
            ""
    INDEX {
            lcsStatusCertsScepCaCertsCertsStatusTabEntryIndex
          }
    ::= { lcsStatusCertsScepCaCertsCertsStatusTabTable 1 }

LcsStatusCertsScepCaCertsCertsStatusTabEntry ::= SEQUENCE {
            lcsStatusCertsScepCaCertsCertsStatusTabEntryIndex Integer32,
            lcsStatusCertsScepCaCertsCertsStatusTabEntrySerialnumber DisplayString,
            lcsStatusCertsScepCaCertsCertsStatusTabEntryStatus DisplayString,
            lcsStatusCertsScepCaCertsCertsStatusTabEntryCreationDate DisplayString,
            lcsStatusCertsScepCaCertsCertsStatusTabEntryEndTime DisplayString,
            lcsStatusCertsScepCaCertsCertsStatusTabEntryRevTime DisplayString,
            lcsStatusCertsScepCaCertsCertsStatusTabEntryRevReas DisplayString,
            lcsStatusCertsScepCaCertsCertsStatusTabEntryMacAddress DisplayString,
            lcsStatusCertsScepCaCertsCertsStatusTabEntryDn DisplayString,
            lcsStatusCertsScepCaCertsCertsStatusTabEntryProfileName DisplayString
    }

-- {COLUMN} 1.3.6.1.4.1.2356.11.1.61.2.1.1.1.1
lcsStatusCertsScepCaCertsCertsStatusTabEntryIndex OBJECT-TYPE
    SYNTAX     Integer32 (-2147483648..2147483647)
    MAX-ACCESS read-only
    STATUS     current
    DESCRIPTION
            ""
    ::= { lcsStatusCertsScepCaCertsCertsStatusTabEntry 1 }

-- {COLUMN} 1.3.6.1.4.1.2356.11.1.61.2.1.1.1.2
lcsStatusCertsScepCaCertsCertsStatusTabEntrySerialnumber OBJECT-TYPE
    SYNTAX     DisplayString
    MAX-ACCESS read-only
    STATUS     current
    DESCRIPTION
            ""
    ::= { lcsStatusCertsScepCaCertsCertsStatusTabEntry 2 }

-- {COLUMN} 1.3.6.1.4.1.2356.11.1.61.2.1.1.1.3
lcsStatusCertsScepCaCertsCertsStatusTabEntryStatus OBJECT-TYPE
    SYNTAX     DisplayString
    MAX-ACCESS read-only
    STATUS     current
    DESCRIPTION
            ""
    ::= { lcsStatusCertsScepCaCertsCertsStatusTabEntry 3 }

-- {COLUMN} 1.3.6.1.4.1.2356.11.1.61.2.1.1.1.4
lcsStatusCertsScepCaCertsCertsStatusTabEntryCreationDate OBJECT-TYPE
    SYNTAX     DisplayString
    MAX-ACCESS read-only
    STATUS     current
    DESCRIPTION
            ""
    ::= { lcsStatusCertsScepCaCertsCertsStatusTabEntry 4 }

-- {COLUMN} 1.3.6.1.4.1.2356.11.1.61.2.1.1.1.5
lcsStatusCertsScepCaCertsCertsStatusTabEntryEndTime OBJECT-TYPE
    SYNTAX     DisplayString
    MAX-ACCESS read-only
    STATUS     current
    DESCRIPTION
            "ending time"
    ::= { lcsStatusCertsScepCaCertsCertsStatusTabEntry 5 }

-- {COLUMN} 1.3.6.1.4.1.2356.11.1.61.2.1.1.1.6
lcsStatusCertsScepCaCertsCertsStatusTabEntryRevTime OBJECT-TYPE
    SYNTAX     DisplayString
    MAX-ACCESS read-only
    STATUS     current
    DESCRIPTION
            "revocation time"
    ::= { lcsStatusCertsScepCaCertsCertsStatusTabEntry 6 }

-- {COLUMN} 1.3.6.1.4.1.2356.11.1.61.2.1.1.1.7
lcsStatusCertsScepCaCertsCertsStatusTabEntryRevReas OBJECT-TYPE
    SYNTAX     DisplayString
    MAX-ACCESS read-only
    STATUS     current
    DESCRIPTION
            "revoke reason"
    ::= { lcsStatusCertsScepCaCertsCertsStatusTabEntry 7 }

-- {COLUMN} 1.3.6.1.4.1.2356.11.1.61.2.1.1.1.8
lcsStatusCertsScepCaCertsCertsStatusTabEntryMacAddress OBJECT-TYPE
    SYNTAX     DisplayString
    MAX-ACCESS read-only
    STATUS     current
    DESCRIPTION
            ""
    ::= { lcsStatusCertsScepCaCertsCertsStatusTabEntry 8 }

-- {COLUMN} 1.3.6.1.4.1.2356.11.1.61.2.1.1.1.9
lcsStatusCertsScepCaCertsCertsStatusTabEntryDn OBJECT-TYPE
    SYNTAX     DisplayString (SIZE(0..256))
    MAX-ACCESS read-only
    STATUS     current
    DESCRIPTION
            ""
    ::= { lcsStatusCertsScepCaCertsCertsStatusTabEntry 9 }

-- {COLUMN} 1.3.6.1.4.1.2356.11.1.61.2.1.1.1.10
lcsStatusCertsScepCaCertsCertsStatusTabEntryProfileName OBJECT-TYPE
    SYNTAX     DisplayString
    MAX-ACCESS read-only
    STATUS     current
    DESCRIPTION
            "-- empty --"
    ::= { lcsStatusCertsScepCaCertsCertsStatusTabEntry 10 }

-- {SCALAR} 1.3.6.1.4.1.2356.11.1.61.2.1.2
lcsStatusCertsScepCaCertsRevokeCertificate OBJECT-TYPE
    SYNTAX     DisplayString
    MAX-ACCESS read-write
    STATUS     current
    DESCRIPTION
            ""
    ::= { lcsStatusCertsScepCaCerts 2 }

-- {SCALAR} 1.3.6.1.4.1.2356.11.1.61.2.1.3
lcsStatusCertsScepCaCertsSetCertificateOnHold OBJECT-TYPE
    SYNTAX     DisplayString
    MAX-ACCESS read-write
    STATUS     current
    DESCRIPTION
            ""
    ::= { lcsStatusCertsScepCaCerts 3 }

-- {SCALAR} 1.3.6.1.4.1.2356.11.1.61.2.1.4
lcsStatusCertsScepCaCertsDeclCertsValid OBJECT-TYPE
    SYNTAX     DisplayString
    MAX-ACCESS read-write
    STATUS     current
    DESCRIPTION
            "declare certificates as valid again"
    ::= { lcsStatusCertsScepCaCerts 4 }

-- {NODE} 1.3.6.1.4.1.2356.11.1.61.2.2
lcsStatusCertsScepCaRequests OBJECT IDENTIFIER ::= { lcsStatusCertsScepCa 2 }

-- {TABLE} 1.3.6.1.4.1.2356.11.1.61.2.2.1
lcsStatusCertsScepCaRequestsPendReqTable OBJECT-TYPE
    SYNTAX     SEQUENCE OF LcsStatusCertsScepCaRequestsPendReqEntry
    MAX-ACCESS not-accessible
    STATUS     current
    DESCRIPTION
            "pending requests"
    ::= { lcsStatusCertsScepCaRequests 1 }

-- {ROW} 1.3.6.1.4.1.2356.11.1.61.2.2.1.1
lcsStatusCertsScepCaRequestsPendReqEntry OBJECT-TYPE
    SYNTAX     LcsStatusCertsScepCaRequestsPendReqEntry
    MAX-ACCESS not-accessible
    STATUS     current
    DESCRIPTION
            ""
    INDEX {
            lcsStatusCertsScepCaRequestsPendReqEntryIndex
          }
    ::= { lcsStatusCertsScepCaRequestsPendReqTable 1 }

LcsStatusCertsScepCaRequestsPendReqEntry ::= SEQUENCE {
            lcsStatusCertsScepCaRequestsPendReqEntryIndex Integer32,
            lcsStatusCertsScepCaRequestsPendReqEntryTransactionId DisplayString,
            lcsStatusCertsScepCaRequestsPendReqEntryMacAddress DisplayString,
            lcsStatusCertsScepCaRequestsPendReqEntryIpAddress IpAddress,
            lcsStatusCertsScepCaRequestsPendReqEntryPkiStatus DisplayString,
            lcsStatusCertsScepCaRequestsPendReqEntryReason INTEGER,
            lcsStatusCertsScepCaRequestsPendReqEntryRequestFingerprint DisplayString,
            lcsStatusCertsScepCaRequestsPendReqEntryDn DisplayString,
            lcsStatusCertsScepCaRequestsPendReqEntryReceiveDate DisplayString
    }

-- {COLUMN} 1.3.6.1.4.1.2356.11.1.61.2.2.1.1.1
lcsStatusCertsScepCaRequestsPendReqEntryIndex OBJECT-TYPE
    SYNTAX     Integer32 (0..65535)
    MAX-ACCESS read-only
    STATUS     current
    DESCRIPTION
            ""
    ::= { lcsStatusCertsScepCaRequestsPendReqEntry 1 }

-- {COLUMN} 1.3.6.1.4.1.2356.11.1.61.2.2.1.1.2
lcsStatusCertsScepCaRequestsPendReqEntryTransactionId OBJECT-TYPE
    SYNTAX     DisplayString (SIZE(0..64))
    MAX-ACCESS read-only
    STATUS     current
    DESCRIPTION
            ""
    ::= { lcsStatusCertsScepCaRequestsPendReqEntry 2 }

-- {COLUMN} 1.3.6.1.4.1.2356.11.1.61.2.2.1.1.3
lcsStatusCertsScepCaRequestsPendReqEntryMacAddress OBJECT-TYPE
    SYNTAX     DisplayString (SIZE(0..12))
    MAX-ACCESS read-only
    STATUS     current
    DESCRIPTION
            ""
    ::= { lcsStatusCertsScepCaRequestsPendReqEntry 3 }

-- {COLUMN} 1.3.6.1.4.1.2356.11.1.61.2.2.1.1.4
lcsStatusCertsScepCaRequestsPendReqEntryIpAddress OBJECT-TYPE
    SYNTAX     IpAddress
    MAX-ACCESS read-only
    STATUS     current
    DESCRIPTION
            ""
    ::= { lcsStatusCertsScepCaRequestsPendReqEntry 4 }

-- {COLUMN} 1.3.6.1.4.1.2356.11.1.61.2.2.1.1.5
lcsStatusCertsScepCaRequestsPendReqEntryPkiStatus OBJECT-TYPE
    SYNTAX     DisplayString (SIZE(0..7))
    MAX-ACCESS read-only
    STATUS     current
    DESCRIPTION
            ""
    ::= { lcsStatusCertsScepCaRequestsPendReqEntry 5 }

-- {COLUMN} 1.3.6.1.4.1.2356.11.1.61.2.2.1.1.6
lcsStatusCertsScepCaRequestsPendReqEntryReason OBJECT-TYPE
    SYNTAX     INTEGER {
                  eUnknownReason (0),
                  eManuallyDeclined (1),
                  eManuallyGranted (2),
                  eAutoapproveNotAllowed (3),
                  eClientCertificateIsNotValid (4),
                  eClientCertificateIsNotOldEnoughForRenewal (5),
                  eClientRequestContainsNoChallengePassword (6),
                  eNoGeneralChallengePasswordAvailableForClients (7),
                  eRequestContainsBrokenChallengePasswordAttribute (8),
                  eChallengePasswordDoesNotMatch (9),
                  eInternalProcessingError (10),
                  eRequestSignatureVerificationFailed (11),
                  eNoCertificateRequestAvailable (12),
                  eRequestSubjectNameDoesNotMatchCertificateSubjectName (13),
                  eMaximalSizeOfCertificateListReached (14)
            }
    MAX-ACCESS read-only
    STATUS     current
    DESCRIPTION
            ""
    ::= { lcsStatusCertsScepCaRequestsPendReqEntry 6 }

-- {COLUMN} 1.3.6.1.4.1.2356.11.1.61.2.2.1.1.7
lcsStatusCertsScepCaRequestsPendReqEntryRequestFingerprint OBJECT-TYPE
    SYNTAX     DisplayString (SIZE(0..128))
    MAX-ACCESS read-only
    STATUS     current
    DESCRIPTION
            ""
    ::= { lcsStatusCertsScepCaRequestsPendReqEntry 7 }

-- {COLUMN} 1.3.6.1.4.1.2356.11.1.61.2.2.1.1.8
lcsStatusCertsScepCaRequestsPendReqEntryDn OBJECT-TYPE
    SYNTAX     DisplayString (SIZE(0..251))
    MAX-ACCESS read-only
    STATUS     current
    DESCRIPTION
            ""
    ::= { lcsStatusCertsScepCaRequestsPendReqEntry 8 }

-- {COLUMN} 1.3.6.1.4.1.2356.11.1.61.2.2.1.1.9
lcsStatusCertsScepCaRequestsPendReqEntryReceiveDate OBJECT-TYPE
    SYNTAX     DisplayString (SIZE(0..63))
    MAX-ACCESS read-only
    STATUS     current
    DESCRIPTION
            ""
    ::= { lcsStatusCertsScepCaRequestsPendReqEntry 9 }

-- {SCALAR} 1.3.6.1.4.1.2356.11.1.61.2.2.2
lcsStatusCertsScepCaRequestsIssueCertificate OBJECT-TYPE
    SYNTAX     DisplayString
    MAX-ACCESS read-write
    STATUS     current
    DESCRIPTION
            ""
    ::= { lcsStatusCertsScepCaRequests 2 }

-- {SCALAR} 1.3.6.1.4.1.2356.11.1.61.2.2.3
lcsStatusCertsScepCaRequestsGrantAllCertificates OBJECT-TYPE
    SYNTAX     DisplayString
    MAX-ACCESS read-write
    STATUS     current
    DESCRIPTION
            ""
    ::= { lcsStatusCertsScepCaRequests 3 }

-- {SCALAR} 1.3.6.1.4.1.2356.11.1.61.2.2.4
lcsStatusCertsScepCaRequestsDeclineRequest OBJECT-TYPE
    SYNTAX     DisplayString
    MAX-ACCESS read-write
    STATUS     current
    DESCRIPTION
            ""
    ::= { lcsStatusCertsScepCaRequests 4 }

-- {SCALAR} 1.3.6.1.4.1.2356.11.1.61.2.2.5
lcsStatusCertsScepCaRequestsDenyAllRequests OBJECT-TYPE
    SYNTAX     DisplayString
    MAX-ACCESS read-write
    STATUS     current
    DESCRIPTION
            ""
    ::= { lcsStatusCertsScepCaRequests 5 }

-- {SCALAR} 1.3.6.1.4.1.2356.11.1.61.2.2.6
lcsStatusCertsScepCaRequestsDeletePendingRequest OBJECT-TYPE
    SYNTAX     DisplayString
    MAX-ACCESS read-write
    STATUS     current
    DESCRIPTION
            ""
    ::= { lcsStatusCertsScepCaRequests 6 }

-- {SCALAR} 1.3.6.1.4.1.2356.11.1.61.2.2.7
lcsStatusCertsScepCaRequestsDeleteAllPendingRequests OBJECT-TYPE
    SYNTAX     DisplayString
    MAX-ACCESS read-write
    STATUS     current
    DESCRIPTION
            ""
    ::= { lcsStatusCertsScepCaRequests 7 }

-- {NODE} 1.3.6.1.4.1.2356.11.1.61.2.3
lcsStatusCertsScepCaCaStatus OBJECT IDENTIFIER ::= { lcsStatusCertsScepCa 3 }

-- {SCALAR} 1.3.6.1.4.1.2356.11.1.61.2.3.1
lcsStatusCertsScepCaCaStatusCaStatus OBJECT-TYPE
    SYNTAX     INTEGER {
                  eDisabled (0),
                  eActive (1),
                  eInitializing (2),
                  eInitializationError (3)
            }
    MAX-ACCESS read-only
    STATUS     current
    DESCRIPTION
            ""
    ::= { lcsStatusCertsScepCaCaStatus 1 }

-- {SCALAR} 1.3.6.1.4.1.2356.11.1.61.2.3.2
lcsStatusCertsScepCaCaStatusError OBJECT-TYPE
    SYNTAX     INTEGER {
                  eNoError (0),
                  eNoValidCadn (1),
                  eNoValidRadn (2),
                  eNoValidKeyUsageForCaCertificate (3),
                  eNoValidKeyUsageForRaCertificate (4),
                  eNoUtcAvailable (6),
                  eConfiguredKeyLengthDoesNotMatchSavedKeys (7),
                  eNoGeneralChallengePasswordSet (8),
                  eValidityPeriodForCaRaIsZero (9),
                  eValidityPeriodForClientsIsZero (10),
                  eCouldNotCreateNewCaRaCertificates (11),
                  eCaRaCertificatesAreNotValid (12),
                  eSavedKeysDoNotMatchCertificates (13),
                  eRaCertKeyUsageMismatch (14),
                  eCaCertKeyUsageMismatch (15),
                  eCaCertDigestMismatch (16),
                  eRaCertDigestMismatch (17),
                  eCadnDoesNotMatchCertificate (18),
                  eRadnDoesNotMatchCertificate (19),
                  eNoMemoryAvailable (20),
                  eRandomPoolNotSeeded (21),
                  eMaximalSizeOfCertificateListReached (23),
                  eValidityPeriodForClientsIsTooLong (24),
                  eConfigCheckLimitReached (25)
            }
    MAX-ACCESS read-only
    STATUS     current
    DESCRIPTION
            ""
    ::= { lcsStatusCertsScepCaCaStatus 2 }

-- {SCALAR} 1.3.6.1.4.1.2356.11.1.61.2.3.3
lcsStatusCertsScepCaCaStatusAdditonalErrorInformation OBJECT-TYPE
    SYNTAX     DisplayString
    MAX-ACCESS read-only
    STATUS     current
    DESCRIPTION
            ""
    ::= { lcsStatusCertsScepCaCaStatus 3 }

-- {SCALAR} 1.3.6.1.4.1.2356.11.1.61.2.3.4
lcsStatusCertsScepCaCaStatusFingerprintAlgorithm OBJECT-TYPE
    SYNTAX     INTEGER {
                  eMd5 (0),
                  eSha1 (1),
                  eSha256 (2),
                  eSha384 (3),
                  eSha512 (4)
            }
    MAX-ACCESS read-only
    STATUS     current
    DESCRIPTION
            ""
    ::= { lcsStatusCertsScepCaCaStatus 4 }

-- {SCALAR} 1.3.6.1.4.1.2356.11.1.61.2.3.5
lcsStatusCertsScepCaCaStatusCaCertificateFingerprint OBJECT-TYPE
    SYNTAX     DisplayString
    MAX-ACCESS read-only
    STATUS     current
    DESCRIPTION
            ""
    ::= { lcsStatusCertsScepCaCaStatus 5 }

-- {SCALAR} 1.3.6.1.4.1.2356.11.1.61.2.3.6
lcsStatusCertsScepCaCaStatusRaCertificateFingerprint OBJECT-TYPE
    SYNTAX     DisplayString
    MAX-ACCESS read-only
    STATUS     current
    DESCRIPTION
            ""
    ::= { lcsStatusCertsScepCaCaStatus 6 }

-- {TABLE} 1.3.6.1.4.1.2356.11.1.61.2.3.7
lcsStatusCertsScepCaCaStatusLogTableTable OBJECT-TYPE
    SYNTAX     SEQUENCE OF LcsStatusCertsScepCaCaStatusLogTableEntry
    MAX-ACCESS not-accessible
    STATUS     current
    DESCRIPTION
            "-- empty --"
    ::= { lcsStatusCertsScepCaCaStatus 7 }

-- {ROW} 1.3.6.1.4.1.2356.11.1.61.2.3.7.1
lcsStatusCertsScepCaCaStatusLogTableEntry OBJECT-TYPE
    SYNTAX     LcsStatusCertsScepCaCaStatusLogTableEntry
    MAX-ACCESS not-accessible
    STATUS     current
    DESCRIPTION
            ""
    INDEX {
            lcsStatusCertsScepCaCaStatusLogTableEntryIndex
          }
    ::= { lcsStatusCertsScepCaCaStatusLogTableTable 1 }

LcsStatusCertsScepCaCaStatusLogTableEntry ::= SEQUENCE {
            lcsStatusCertsScepCaCaStatusLogTableEntryIndex Integer32,
            lcsStatusCertsScepCaCaStatusLogTableEntryTime DisplayString,
            lcsStatusCertsScepCaCaStatusLogTableEntryEvent DisplayString
    }

-- {COLUMN} 1.3.6.1.4.1.2356.11.1.61.2.3.7.1.1
lcsStatusCertsScepCaCaStatusLogTableEntryIndex OBJECT-TYPE
    SYNTAX     Integer32 (0..2147483647)
    MAX-ACCESS read-only
    STATUS     current
    DESCRIPTION
            "-- empty --"
    ::= { lcsStatusCertsScepCaCaStatusLogTableEntry 1 }

-- {COLUMN} 1.3.6.1.4.1.2356.11.1.61.2.3.7.1.2
lcsStatusCertsScepCaCaStatusLogTableEntryTime OBJECT-TYPE
    SYNTAX     DisplayString (SIZE(0..19))
    MAX-ACCESS read-only
    STATUS     current
    DESCRIPTION
            "-- empty --"
    ::= { lcsStatusCertsScepCaCaStatusLogTableEntry 2 }

-- {COLUMN} 1.3.6.1.4.1.2356.11.1.61.2.3.7.1.6
lcsStatusCertsScepCaCaStatusLogTableEntryEvent OBJECT-TYPE
    SYNTAX     DisplayString (SIZE(0..80))
    MAX-ACCESS read-only
    STATUS     current
    DESCRIPTION
            "-- empty --"
    ::= { lcsStatusCertsScepCaCaStatusLogTableEntry 6 }

-- {NODE} 1.3.6.1.4.1.2356.11.1.61.2.4
lcsStatusCertsScepCaWebIfc OBJECT IDENTIFIER ::= { lcsStatusCertsScepCa 4 }

-- {TABLE} 1.3.6.1.4.1.2356.11.1.61.2.4.1
lcsStatusCertsScepCaWebIfcProfilesTable OBJECT-TYPE
    SYNTAX     SEQUENCE OF LcsStatusCertsScepCaWebIfcProfilesEntry
    MAX-ACCESS not-accessible
    STATUS     current
    DESCRIPTION
            "-- empty --"
    ::= { lcsStatusCertsScepCaWebIfc 1 }

-- {ROW} 1.3.6.1.4.1.2356.11.1.61.2.4.1.1
lcsStatusCertsScepCaWebIfcProfilesEntry OBJECT-TYPE
    SYNTAX     LcsStatusCertsScepCaWebIfcProfilesEntry
    MAX-ACCESS not-accessible
    STATUS     current
    DESCRIPTION
            ""
    INDEX {
            lcsStatusCertsScepCaWebIfcProfilesEntryProfileName,
            lcsStatusCertsScepCaWebIfcProfilesEntryTemplate
          }
    ::= { lcsStatusCertsScepCaWebIfcProfilesTable 1 }

LcsStatusCertsScepCaWebIfcProfilesEntry ::= SEQUENCE {
            lcsStatusCertsScepCaWebIfcProfilesEntryProfileName DisplayString,
            lcsStatusCertsScepCaWebIfcProfilesEntryKeyUsage DisplayString,
            lcsStatusCertsScepCaWebIfcProfilesEntryExtendedKeyUsage DisplayString,
            lcsStatusCertsScepCaWebIfcProfilesEntryRsaKeyLength INTEGER,
            lcsStatusCertsScepCaWebIfcProfilesEntryValidityPeriod Integer32,
            lcsStatusCertsScepCaWebIfcProfilesEntryCa INTEGER,
            lcsStatusCertsScepCaWebIfcProfilesEntryPassword DisplayString,
            lcsStatusCertsScepCaWebIfcProfilesEntryCountryName DisplayString,
            lcsStatusCertsScepCaWebIfcProfilesEntryLocalityName DisplayString,
            lcsStatusCertsScepCaWebIfcProfilesEntryOrganizationName DisplayString,
            lcsStatusCertsScepCaWebIfcProfilesEntryOrganizationUnitName DisplayString,
            lcsStatusCertsScepCaWebIfcProfilesEntryStateOrProvince DisplayString,
            lcsStatusCertsScepCaWebIfcProfilesEntryEMail DisplayString,
            lcsStatusCertsScepCaWebIfcProfilesEntrySurname DisplayString,
            lcsStatusCertsScepCaWebIfcProfilesEntrySerialNumber DisplayString,
            lcsStatusCertsScepCaWebIfcProfilesEntryPostalCode DisplayString,
            lcsStatusCertsScepCaWebIfcProfilesEntryTemplate DisplayString,
            lcsStatusCertsScepCaWebIfcProfilesEntrySubjectAlternativeName DisplayString,
            lcsStatusCertsScepCaWebIfcProfilesEntryOcspAia DisplayString
    }

-- {COLUMN} 1.3.6.1.4.1.2356.11.1.61.2.4.1.1.1
lcsStatusCertsScepCaWebIfcProfilesEntryProfileName OBJECT-TYPE
    SYNTAX     DisplayString (SIZE(0..32))
    MAX-ACCESS read-only
    STATUS     current
    DESCRIPTION
            "-- empty --"
    ::= { lcsStatusCertsScepCaWebIfcProfilesEntry 1 }

-- {COLUMN} 1.3.6.1.4.1.2356.11.1.61.2.4.1.1.2
lcsStatusCertsScepCaWebIfcProfilesEntryKeyUsage OBJECT-TYPE
    SYNTAX     DisplayString (SIZE(0..251))
    MAX-ACCESS read-only
    STATUS     current
    DESCRIPTION
            "-- empty --"
    ::= { lcsStatusCertsScepCaWebIfcProfilesEntry 2 }

-- {COLUMN} 1.3.6.1.4.1.2356.11.1.61.2.4.1.1.3
lcsStatusCertsScepCaWebIfcProfilesEntryExtendedKeyUsage OBJECT-TYPE
    SYNTAX     DisplayString (SIZE(0..251))
    MAX-ACCESS read-only
    STATUS     current
    DESCRIPTION
            "-- empty --"
    ::= { lcsStatusCertsScepCaWebIfcProfilesEntry 3 }

-- {COLUMN} 1.3.6.1.4.1.2356.11.1.61.2.4.1.1.4
lcsStatusCertsScepCaWebIfcProfilesEntryRsaKeyLength OBJECT-TYPE
    SYNTAX     INTEGER {
                  e1024 (1024),
                  e2048 (2048),
                  e3072 (3072),
                  e4096 (4096),
                  e8192 (8192)
            }
    MAX-ACCESS read-only
    STATUS     current
    DESCRIPTION
            "-- empty --"
    ::= { lcsStatusCertsScepCaWebIfcProfilesEntry 4 }

-- {COLUMN} 1.3.6.1.4.1.2356.11.1.61.2.4.1.1.5
lcsStatusCertsScepCaWebIfcProfilesEntryValidityPeriod OBJECT-TYPE
    SYNTAX     Integer32 (0..2147483647)
    MAX-ACCESS read-only
    STATUS     current
    DESCRIPTION
            "-- empty --"
    ::= { lcsStatusCertsScepCaWebIfcProfilesEntry 5 }

-- {COLUMN} 1.3.6.1.4.1.2356.11.1.61.2.4.1.1.6
lcsStatusCertsScepCaWebIfcProfilesEntryCa OBJECT-TYPE
    SYNTAX     INTEGER {
                  eNo (0),
                  eYes (1)
            }
    MAX-ACCESS read-only
    STATUS     current
    DESCRIPTION
            "-- empty --"
    ::= { lcsStatusCertsScepCaWebIfcProfilesEntry 6 }

-- {COLUMN} 1.3.6.1.4.1.2356.11.1.61.2.4.1.1.7
lcsStatusCertsScepCaWebIfcProfilesEntryPassword OBJECT-TYPE
    SYNTAX     DisplayString (SIZE(0..32))
    MAX-ACCESS read-only
    STATUS     current
    DESCRIPTION
            "-- empty --"
    ::= { lcsStatusCertsScepCaWebIfcProfilesEntry 7 }

-- {COLUMN} 1.3.6.1.4.1.2356.11.1.61.2.4.1.1.8
lcsStatusCertsScepCaWebIfcProfilesEntryCountryName OBJECT-TYPE
    SYNTAX     DisplayString (SIZE(0..2))
    MAX-ACCESS read-only
    STATUS     current
    DESCRIPTION
            "-- empty --"
    ::= { lcsStatusCertsScepCaWebIfcProfilesEntry 8 }

-- {COLUMN} 1.3.6.1.4.1.2356.11.1.61.2.4.1.1.9
lcsStatusCertsScepCaWebIfcProfilesEntryLocalityName OBJECT-TYPE
    SYNTAX     DisplayString (SIZE(0..32))
    MAX-ACCESS read-only
    STATUS     current
    DESCRIPTION
            "-- empty --"
    ::= { lcsStatusCertsScepCaWebIfcProfilesEntry 9 }

-- {COLUMN} 1.3.6.1.4.1.2356.11.1.61.2.4.1.1.10
lcsStatusCertsScepCaWebIfcProfilesEntryOrganizationName OBJECT-TYPE
    SYNTAX     DisplayString (SIZE(0..32))
    MAX-ACCESS read-only
    STATUS     current
    DESCRIPTION
            "-- empty --"
    ::= { lcsStatusCertsScepCaWebIfcProfilesEntry 10 }

-- {COLUMN} 1.3.6.1.4.1.2356.11.1.61.2.4.1.1.11
lcsStatusCertsScepCaWebIfcProfilesEntryOrganizationUnitName OBJECT-TYPE
    SYNTAX     DisplayString (SIZE(0..32))
    MAX-ACCESS read-only
    STATUS     current
    DESCRIPTION
            "-- empty --"
    ::= { lcsStatusCertsScepCaWebIfcProfilesEntry 11 }

-- {COLUMN} 1.3.6.1.4.1.2356.11.1.61.2.4.1.1.12
lcsStatusCertsScepCaWebIfcProfilesEntryStateOrProvince OBJECT-TYPE
    SYNTAX     DisplayString (SIZE(0..32))
    MAX-ACCESS read-only
    STATUS     current
    DESCRIPTION
            "-- empty --"
    ::= { lcsStatusCertsScepCaWebIfcProfilesEntry 12 }

-- {COLUMN} 1.3.6.1.4.1.2356.11.1.61.2.4.1.1.13
lcsStatusCertsScepCaWebIfcProfilesEntryEMail OBJECT-TYPE
    SYNTAX     DisplayString (SIZE(0..64))
    MAX-ACCESS read-only
    STATUS     current
    DESCRIPTION
            "-- empty --"
    ::= { lcsStatusCertsScepCaWebIfcProfilesEntry 13 }

-- {COLUMN} 1.3.6.1.4.1.2356.11.1.61.2.4.1.1.14
lcsStatusCertsScepCaWebIfcProfilesEntrySurname OBJECT-TYPE
    SYNTAX     DisplayString (SIZE(0..32))
    MAX-ACCESS read-only
    STATUS     current
    DESCRIPTION
            "-- empty --"
    ::= { lcsStatusCertsScepCaWebIfcProfilesEntry 14 }

-- {COLUMN} 1.3.6.1.4.1.2356.11.1.61.2.4.1.1.15
lcsStatusCertsScepCaWebIfcProfilesEntrySerialNumber OBJECT-TYPE
    SYNTAX     DisplayString (SIZE(0..32))
    MAX-ACCESS read-only
    STATUS     current
    DESCRIPTION
            "-- empty --"
    ::= { lcsStatusCertsScepCaWebIfcProfilesEntry 15 }

-- {COLUMN} 1.3.6.1.4.1.2356.11.1.61.2.4.1.1.16
lcsStatusCertsScepCaWebIfcProfilesEntryPostalCode OBJECT-TYPE
    SYNTAX     DisplayString (SIZE(0..25))
    MAX-ACCESS read-only
    STATUS     current
    DESCRIPTION
            "-- empty --"
    ::= { lcsStatusCertsScepCaWebIfcProfilesEntry 16 }

-- {COLUMN} 1.3.6.1.4.1.2356.11.1.61.2.4.1.1.17
lcsStatusCertsScepCaWebIfcProfilesEntryTemplate OBJECT-TYPE
    SYNTAX     DisplayString (SIZE(0..31))
    MAX-ACCESS read-only
    STATUS     current
    DESCRIPTION
            "-- empty --"
    ::= { lcsStatusCertsScepCaWebIfcProfilesEntry 17 }

-- {COLUMN} 1.3.6.1.4.1.2356.11.1.61.2.4.1.1.18
lcsStatusCertsScepCaWebIfcProfilesEntrySubjectAlternativeName OBJECT-TYPE
    SYNTAX     DisplayString (SIZE(0..254))
    MAX-ACCESS read-only
    STATUS     current
    DESCRIPTION
            "-- empty --"
    ::= { lcsStatusCertsScepCaWebIfcProfilesEntry 18 }

-- {COLUMN} 1.3.6.1.4.1.2356.11.1.61.2.4.1.1.19
lcsStatusCertsScepCaWebIfcProfilesEntryOcspAia OBJECT-TYPE
    SYNTAX     DisplayString (SIZE(0..254))
    MAX-ACCESS read-only
    STATUS     current
    DESCRIPTION
            "-- empty --"
    ::= { lcsStatusCertsScepCaWebIfcProfilesEntry 19 }

-- {TABLE} 1.3.6.1.4.1.2356.11.1.61.2.4.2
lcsStatusCertsScepCaWebIfcTemplateTable OBJECT-TYPE
    SYNTAX     SEQUENCE OF LcsStatusCertsScepCaWebIfcTemplateEntry
    MAX-ACCESS not-accessible
    STATUS     current
    DESCRIPTION
            "-- empty --"
    ::= { lcsStatusCertsScepCaWebIfc 2 }

-- {ROW} 1.3.6.1.4.1.2356.11.1.61.2.4.2.1
lcsStatusCertsScepCaWebIfcTemplateEntry OBJECT-TYPE
    SYNTAX     LcsStatusCertsScepCaWebIfcTemplateEntry
    MAX-ACCESS not-accessible
    STATUS     current
    DESCRIPTION
            ""
    INDEX {
            lcsStatusCertsScepCaWebIfcTemplateEntryName
          }
    ::= { lcsStatusCertsScepCaWebIfcTemplateTable 1 }

LcsStatusCertsScepCaWebIfcTemplateEntry ::= SEQUENCE {
            lcsStatusCertsScepCaWebIfcTemplateEntryName DisplayString,
            lcsStatusCertsScepCaWebIfcTemplateEntryKeyUsage INTEGER,
            lcsStatusCertsScepCaWebIfcTemplateEntryExtendedKeyUsage INTEGER,
            lcsStatusCertsScepCaWebIfcTemplateEntryRsaKeyLength INTEGER,
            lcsStatusCertsScepCaWebIfcTemplateEntryValidityPeriod INTEGER,
            lcsStatusCertsScepCaWebIfcTemplateEntryCa INTEGER,
            lcsStatusCertsScepCaWebIfcTemplateEntryPassword Integer32,
            lcsStatusCertsScepCaWebIfcTemplateEntryCountryName INTEGER,
            lcsStatusCertsScepCaWebIfcTemplateEntryLocalityName INTEGER,
            lcsStatusCertsScepCaWebIfcTemplateEntryOrganizationName INTEGER,
            lcsStatusCertsScepCaWebIfcTemplateEntryOrganizationUnitName INTEGER,
            lcsStatusCertsScepCaWebIfcTemplateEntryStateOrProvince INTEGER,
            lcsStatusCertsScepCaWebIfcTemplateEntryEMail INTEGER,
            lcsStatusCertsScepCaWebIfcTemplateEntrySurname INTEGER,
            lcsStatusCertsScepCaWebIfcTemplateEntrySerialNumber INTEGER,
            lcsStatusCertsScepCaWebIfcTemplateEntryPostalCode INTEGER,
            lcsStatusCertsScepCaWebIfcTemplateEntrySubjectAlternativeName INTEGER,
            lcsStatusCertsScepCaWebIfcTemplateEntryOcspAia INTEGER
    }

-- {COLUMN} 1.3.6.1.4.1.2356.11.1.61.2.4.2.1.1
lcsStatusCertsScepCaWebIfcTemplateEntryName OBJECT-TYPE
    SYNTAX     DisplayString (SIZE(0..31))
    MAX-ACCESS read-only
    STATUS     current
    DESCRIPTION
            "-- empty --"
    ::= { lcsStatusCertsScepCaWebIfcTemplateEntry 1 }

-- {COLUMN} 1.3.6.1.4.1.2356.11.1.61.2.4.2.1.2
lcsStatusCertsScepCaWebIfcTemplateEntryKeyUsage OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 2 }

-- {COLUMN} 1.3.6.1.4.1.2356.11.1.61.2.4.2.1.3
lcsStatusCertsScepCaWebIfcTemplateEntryExtendedKeyUsage OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 3 }

-- {COLUMN} 1.3.6.1.4.1.2356.11.1.61.2.4.2.1.4
lcsStatusCertsScepCaWebIfcTemplateEntryRsaKeyLength OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 4 }

-- {COLUMN} 1.3.6.1.4.1.2356.11.1.61.2.4.2.1.5
lcsStatusCertsScepCaWebIfcTemplateEntryValidityPeriod OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 5 }

-- {COLUMN} 1.3.6.1.4.1.2356.11.1.61.2.4.2.1.6
lcsStatusCertsScepCaWebIfcTemplateEntryCa OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 6 }

-- {COLUMN} 1.3.6.1.4.1.2356.11.1.61.2.4.2.1.7
lcsStatusCertsScepCaWebIfcTemplateEntryPassword OBJECT-TYPE
    SYNTAX     Integer32 (0..255)
    MAX-ACCESS read-only
    STATUS     current
    DESCRIPTION
            "-- empty --"
    ::= { lcsStatusCertsScepCaWebIfcTemplateEntry 7 }

-- {COLUMN} 1.3.6.1.4.1.2356.11.1.61.2.4.2.1.8
lcsStatusCertsScepCaWebIfcTemplateEntryCountryName OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 8 }

-- {COLUMN} 1.3.6.1.4.1.2356.11.1.61.2.4.2.1.9
lcsStatusCertsScepCaWebIfcTemplateEntryLocalityName OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 9 }

-- {COLUMN} 1.3.6.1.4.1.2356.11.1.61.2.4.2.1.10
lcsStatusCertsScepCaWebIfcTemplateEntryOrganizationName OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 10 }

-- {COLUMN} 1.3.6.1.4.1.2356.11.1.61.2.4.2.1.11
lcsStatusCertsScepCaWebIfcTemplateEntryOrganizationUnitName OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 11 }

-- {COLUMN} 1.3.6.1.4.1.2356.11.1.61.2.4.2.1.12
lcsStatusCertsScepCaWebIfcTemplateEntryStateOrProvince OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 12 }

-- {COLUMN} 1.3.6.1.4.1.2356.11.1.61.2.4.2.1.13
lcsStatusCertsScepCaWebIfcTemplateEntryEMail OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 13 }

-- {COLUMN} 1.3.6.1.4.1.2356.11.1.61.2.4.2.1.14
lcsStatusCertsScepCaWebIfcTemplateEntrySurname OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 14 }

-- {COLUMN} 1.3.6.1.4.1.2356.11.1.61.2.4.2.1.15
lcsStatusCertsScepCaWebIfcTemplateEntrySerialNumber OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 15 }

-- {COLUMN} 1.3.6.1.4.1.2356.11.1.61.2.4.2.1.16
lcsStatusCertsScepCaWebIfcTemplateEntryPostalCode OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 16 }

-- {COLUMN} 1.3.6.1.4.1.2356.11.1.61.2.4.2.1.17
lcsStatusCertsScepCaWebIfcTemplateEntrySubjectAlternativeName OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 17 }

-- {COLUMN} 1.3.6.1.4.1.2356.11.1.61.2.4.2.1.18
lcsStatusCertsScepCaWebIfcTemplateEntryOcspAia OBJECT-TYPE
    SYNTAX     INTEGER {
                  eNo (0),
                  eYes (1),
                  eMandatory (2),
                  eFixed (3)
            }
    MAX-ACCESS read-only
    STATUS     current
    DESCRIPTION
            "-- empty --"
    ::= { lcsStatusCertsScepCaWebIfcTemplateEntry 18 }

-- {NODE} 1.3.6.1.4.1.2356.11.1.61.3
lcsStatusCertsCrls OBJECT IDENTIFIER ::= { lcsStatusCerts 3 }

-- {SCALAR} 1.3.6.1.4.1.2356.11.1.61.3.1
lcsStatusCertsCrlsNumcrls OBJECT-TYPE
    SYNTAX     Integer32 (0..2147483647)
    MAX-ACCESS read-only
    STATUS     current
    DESCRIPTION
            ""
    ::= { lcsStatusCertsCrls 1 }

-- {TABLE} 1.3.6.1.4.1.2356.11.1.61.3.2
lcsStatusCertsCrlsCrlsTable OBJECT-TYPE
    SYNTAX     SEQUENCE OF LcsStatusCertsCrlsCrlsEntry
    MAX-ACCESS not-accessible
    STATUS     current
    DESCRIPTION
            ""
    ::= { lcsStatusCertsCrls 2 }

-- {ROW} 1.3.6.1.4.1.2356.11.1.61.3.2.1
lcsStatusCertsCrlsCrlsEntry OBJECT-TYPE
    SYNTAX     LcsStatusCertsCrlsCrlsEntry
    MAX-ACCESS not-accessible
    STATUS     current
    DESCRIPTION
            ""
    INDEX {
            lcsStatusCertsCrlsCrlsEntryIdx
          }
    ::= { lcsStatusCertsCrlsCrlsTable 1 }

LcsStatusCertsCrlsCrlsEntry ::= SEQUENCE {
            lcsStatusCertsCrlsCrlsEntryIdx Integer32,
            lcsStatusCertsCrlsCrlsEntryExpires DisplayString,
            lcsStatusCertsCrlsCrlsEntryIssued DisplayString,
            lcsStatusCertsCrlsCrlsEntryIssuer DisplayString,
            lcsStatusCertsCrlsCrlsEntryDistributionPoint DisplayString,
            lcsStatusCertsCrlsCrlsEntryStatSnmp Integer32,
            lcsStatusCertsCrlsCrlsEntryExpSnmp Counter32,
            lcsStatusCertsCrlsCrlsEntryIssSnmp Counter32,
            lcsStatusCertsCrlsCrlsEntryStatus DisplayString
    }

-- {COLUMN} 1.3.6.1.4.1.2356.11.1.61.3.2.1.1
lcsStatusCertsCrlsCrlsEntryIdx OBJECT-TYPE
    SYNTAX     Integer32 (0..2147483647)
    MAX-ACCESS read-only
    STATUS     current
    DESCRIPTION
            ""
    ::= { lcsStatusCertsCrlsCrlsEntry 1 }

-- {COLUMN} 1.3.6.1.4.1.2356.11.1.61.3.2.1.2
lcsStatusCertsCrlsCrlsEntryExpires OBJECT-TYPE
    SYNTAX     DisplayString (SIZE(0..255))
    MAX-ACCESS read-only
    STATUS     current
    DESCRIPTION
            ""
    ::= { lcsStatusCertsCrlsCrlsEntry 2 }

-- {COLUMN} 1.3.6.1.4.1.2356.11.1.61.3.2.1.3
lcsStatusCertsCrlsCrlsEntryIssued OBJECT-TYPE
    SYNTAX     DisplayString (SIZE(0..255))
    MAX-ACCESS read-only
    STATUS     current
    DESCRIPTION
            ""
    ::= { lcsStatusCertsCrlsCrlsEntry 3 }

-- {COLUMN} 1.3.6.1.4.1.2356.11.1.61.3.2.1.4
lcsStatusCertsCrlsCrlsEntryIssuer OBJECT-TYPE
    SYNTAX     DisplayString (SIZE(0..255))
    MAX-ACCESS read-only
    STATUS     current
    DESCRIPTION
            ""
    ::= { lcsStatusCertsCrlsCrlsEntry 4 }

-- {COLUMN} 1.3.6.1.4.1.2356.11.1.61.3.2.1.5
lcsStatusCertsCrlsCrlsEntryDistributionPoint OBJECT-TYPE
    SYNTAX     DisplayString (SIZE(0..255))
    MAX-ACCESS read-only
    STATUS     current
    DESCRIPTION
            ""
    ::= { lcsStatusCertsCrlsCrlsEntry 5 }

-- {COLUMN} 1.3.6.1.4.1.2356.11.1.61.3.2.1.6
lcsStatusCertsCrlsCrlsEntryStatSnmp OBJECT-TYPE
    SYNTAX     Integer32 (0..2147483647)
    MAX-ACCESS read-only
    STATUS     current
    DESCRIPTION
            ""
    ::= { lcsStatusCertsCrlsCrlsEntry 6 }

-- {COLUMN} 1.3.6.1.4.1.2356.11.1.61.3.2.1.7
lcsStatusCertsCrlsCrlsEntryExpSnmp OBJECT-TYPE
    SYNTAX     Counter32
    MAX-ACCESS read-only
    STATUS     current
    DESCRIPTION
            ""
    ::= { lcsStatusCertsCrlsCrlsEntry 7 }

-- {COLUMN} 1.3.6.1.4.1.2356.11.1.61.3.2.1.8
lcsStatusCertsCrlsCrlsEntryIssSnmp OBJECT-TYPE
    SYNTAX     Counter32
    MAX-ACCESS read-only
    STATUS     current
    DESCRIPTION
            ""
    ::= { lcsStatusCertsCrlsCrlsEntry 8 }

-- {COLUMN} 1.3.6.1.4.1.2356.11.1.61.3.2.1.9
lcsStatusCertsCrlsCrlsEntryStatus OBJECT-TYPE
    SYNTAX     DisplayString (SIZE(0..255))
    MAX-ACCESS read-only
    STATUS     current
    DESCRIPTION
            ""
    ::= { lcsStatusCertsCrlsCrlsEntry 9 }

-- {SCALAR} 1.3.6.1.4.1.2356.11.1.61.3.3
lcsStatusCertsCrlsDeleteCrl OBJECT-TYPE
    SYNTAX     DisplayString
    MAX-ACCESS read-write
    STATUS     current
    DESCRIPTION
            "-- empty --"
    ::= { lcsStatusCertsCrls 3 }

-- {TABLE} 1.3.6.1.4.1.2356.11.1.61.4
lcsStatusCertsDeviceCertificatesTable OBJECT-TYPE
    SYNTAX     SEQUENCE OF LcsStatusCertsDeviceCertificatesEntry
    MAX-ACCESS not-accessible
    STATUS     current
    DESCRIPTION
            ""
    ::= { lcsStatusCerts 4 }

-- {ROW} 1.3.6.1.4.1.2356.11.1.61.4.1
lcsStatusCertsDeviceCertificatesEntry OBJECT-TYPE
    SYNTAX     LcsStatusCertsDeviceCertificatesEntry
    MAX-ACCESS not-accessible
    STATUS     current
    DESCRIPTION
            ""
    INDEX {
            lcsStatusCertsDeviceCertificatesEntryFilename
          }
    ::= { lcsStatusCertsDeviceCertificatesTable 1 }

LcsStatusCertsDeviceCertificatesEntry ::= SEQUENCE {
            lcsStatusCertsDeviceCertificatesEntryFilename DisplayString,
            lcsStatusCertsDeviceCertificatesEntryAvailable INTEGER,
            lcsStatusCertsDeviceCertificatesEntryExpires DisplayString,
            lcsStatusCertsDeviceCertificatesEntryIssued DisplayString,
            lcsStatusCertsDeviceCertificatesEntryKeyUsage DisplayString,
            lcsStatusCertsDeviceCertificatesEntrySubjectaltname DisplayString,
            lcsStatusCertsDeviceCertificatesEntryIssuer DisplayString,
            lcsStatusCertsDeviceCertificatesEntrySubject DisplayString,
            lcsStatusCertsDeviceCertificatesEntryApplication DisplayString,
            lcsStatusCertsDeviceCertificatesEntryExtendedKeyusage DisplayString
    }

-- {COLUMN} 1.3.6.1.4.1.2356.11.1.61.4.1.1
lcsStatusCertsDeviceCertificatesEntryFilename OBJECT-TYPE
    SYNTAX     DisplayString (SIZE(0..255))
    MAX-ACCESS read-only
    STATUS     current
    DESCRIPTION
            ""
    ::= { lcsStatusCertsDeviceCertificatesEntry 1 }

-- {COLUMN} 1.3.6.1.4.1.2356.11.1.61.4.1.2
lcsStatusCertsDeviceCertificatesEntryAvailable OBJECT-TYPE
    SYNTAX     INTEGER {
                  eNo (0),
                  eYes (1)
            }
    MAX-ACCESS read-only
    STATUS     current
    DESCRIPTION
            ""
    ::= { lcsStatusCertsDeviceCertificatesEntry 2 }

-- {COLUMN} 1.3.6.1.4.1.2356.11.1.61.4.1.3
lcsStatusCertsDeviceCertificatesEntryExpires OBJECT-TYPE
    SYNTAX     DisplayString (SIZE(0..20))
    MAX-ACCESS read-only
    STATUS     current
    DESCRIPTION
            ""
    ::= { lcsStatusCertsDeviceCertificatesEntry 3 }

-- {COLUMN} 1.3.6.1.4.1.2356.11.1.61.4.1.4
lcsStatusCertsDeviceCertificatesEntryIssued OBJECT-TYPE
    SYNTAX     DisplayString (SIZE(0..20))
    MAX-ACCESS read-only
    STATUS     current
    DESCRIPTION
            ""
    ::= { lcsStatusCertsDeviceCertificatesEntry 4 }

-- {COLUMN} 1.3.6.1.4.1.2356.11.1.61.4.1.5
lcsStatusCertsDeviceCertificatesEntryKeyUsage OBJECT-TYPE
    SYNTAX     DisplayString (SIZE(0..251))
    MAX-ACCESS read-only
    STATUS     current
    DESCRIPTION
            ""
    ::= { lcsStatusCertsDeviceCertificatesEntry 5 }

-- {COLUMN} 1.3.6.1.4.1.2356.11.1.61.4.1.6
lcsStatusCertsDeviceCertificatesEntrySubjectaltname OBJECT-TYPE
    SYNTAX     DisplayString (SIZE(0..251))
    MAX-ACCESS read-only
    STATUS     current
    DESCRIPTION
            ""
    ::= { lcsStatusCertsDeviceCertificatesEntry 6 }

-- {COLUMN} 1.3.6.1.4.1.2356.11.1.61.4.1.7
lcsStatusCertsDeviceCertificatesEntryIssuer OBJECT-TYPE
    SYNTAX     DisplayString (SIZE(0..251))
    MAX-ACCESS read-only
    STATUS     current
    DESCRIPTION
            ""
    ::= { lcsStatusCertsDeviceCertificatesEntry 7 }

-- {COLUMN} 1.3.6.1.4.1.2356.11.1.61.4.1.8
lcsStatusCertsDeviceCertificatesEntrySubject OBJECT-TYPE
    SYNTAX     DisplayString (SIZE(0..251))
    MAX-ACCESS read-only
    STATUS     current
    DESCRIPTION
            ""
    ::= { lcsStatusCertsDeviceCertificatesEntry 8 }

-- {COLUMN} 1.3.6.1.4.1.2356.11.1.61.4.1.9
lcsStatusCertsDeviceCertificatesEntryApplication OBJECT-TYPE
    SYNTAX     DisplayString (SIZE(0..15))
    MAX-ACCESS read-only
    STATUS     current
    DESCRIPTION
            ""
    ::= { lcsStatusCertsDeviceCertificatesEntry 9 }

-- {COLUMN} 1.3.6.1.4.1.2356.11.1.61.4.1.12
lcsStatusCertsDeviceCertificatesEntryExtendedKeyusage OBJECT-TYPE
    SYNTAX     DisplayString (SIZE(0..251))
    MAX-ACCESS read-only
    STATUS     current
    DESCRIPTION
            ""
    ::= { lcsStatusCertsDeviceCertificatesEntry 12 }

-- {NODE} 1.3.6.1.4.1.2356.11.1.61.6
lcsStatusCertsOcspClient OBJECT IDENTIFIER ::= { lcsStatusCerts 6 }

-- {TABLE} 1.3.6.1.4.1.2356.11.1.61.6.1
lcsStatusCertsOcspClientCaStatusTableTable OBJECT-TYPE
    SYNTAX     SEQUENCE OF LcsStatusCertsOcspClientCaStatusTableEntry
    MAX-ACCESS not-accessible
    STATUS     current
    DESCRIPTION
            ""
    ::= { lcsStatusCertsOcspClient 1 }

-- {ROW} 1.3.6.1.4.1.2356.11.1.61.6.1.1
lcsStatusCertsOcspClientCaStatusTableEntry OBJECT-TYPE
    SYNTAX     LcsStatusCertsOcspClientCaStatusTableEntry
    MAX-ACCESS not-accessible
    STATUS     current
    DESCRIPTION
            ""
    INDEX {
            lcsStatusCertsOcspClientCaStatusTableEntryProfileName
          }
    ::= { lcsStatusCertsOcspClientCaStatusTableTable 1 }

LcsStatusCertsOcspClientCaStatusTableEntry ::= SEQUENCE {
            lcsStatusCertsOcspClientCaStatusTableEntryProfileName DisplayString,
            lcsStatusCertsOcspClientCaStatusTableEntryRequests Integer32,
            lcsStatusCertsOcspClientCaStatusTableEntryResponses Integer32,
            lcsStatusCertsOcspClientCaStatusTableEntryGoodResponses Integer32,
            lcsStatusCertsOcspClientCaStatusTableEntryRevokeResponses Integer32,
            lcsStatusCertsOcspClientCaStatusTableEntryUnknownResponses Integer32,
            lcsStatusCertsOcspClientCaStatusTableEntrySuccessfulResponses Integer32,
            lcsStatusCertsOcspClientCaStatusTableEntryErrorResponses Integer32,
            lcsStatusCertsOcspClientCaStatusTableEntryMalformedRequests Integer32,
            lcsStatusCertsOcspClientCaStatusTableEntryIntErrorResponses Integer32,
            lcsStatusCertsOcspClientCaStatusTableEntryTryLaterResponses Integer32,
            lcsStatusCertsOcspClientCaStatusTableEntrySignRequiredResponses Integer32,
            lcsStatusCertsOcspClientCaStatusTableEntryUnauthorizedResponses Integer32,
            lcsStatusCertsOcspClientCaStatusTableEntrySignerVerifyFailures Integer32,
            lcsStatusCertsOcspClientCaStatusTableEntryCertTimedOuts Integer32,
            lcsStatusCertsOcspClientCaStatusTableEntryGenericErrors Integer32,
            lcsStatusCertsOcspClientCaStatusTableEntryTransportErrors Integer32
    }

-- {COLUMN} 1.3.6.1.4.1.2356.11.1.61.6.1.1.1
lcsStatusCertsOcspClientCaStatusTableEntryProfileName OBJECT-TYPE
    SYNTAX     DisplayString (SIZE(0..32))
    MAX-ACCESS read-only
    STATUS     current
    DESCRIPTION
            ""
    ::= { lcsStatusCertsOcspClientCaStatusTableEntry 1 }

-- {COLUMN} 1.3.6.1.4.1.2356.11.1.61.6.1.1.2
lcsStatusCertsOcspClientCaStatusTableEntryRequests OBJECT-TYPE
    SYNTAX     Integer32 (0..2147483647)
    MAX-ACCESS read-only
    STATUS     current
    DESCRIPTION
            ""
    ::= { lcsStatusCertsOcspClientCaStatusTableEntry 2 }

-- {COLUMN} 1.3.6.1.4.1.2356.11.1.61.6.1.1.3
lcsStatusCertsOcspClientCaStatusTableEntryResponses OBJECT-TYPE
    SYNTAX     Integer32 (0..2147483647)
    MAX-ACCESS read-only
    STATUS     current
    DESCRIPTION
            ""
    ::= { lcsStatusCertsOcspClientCaStatusTableEntry 3 }

-- {COLUMN} 1.3.6.1.4.1.2356.11.1.61.6.1.1.4
lcsStatusCertsOcspClientCaStatusTableEntryGoodResponses OBJECT-TYPE
    SYNTAX     Integer32 (0..2147483647)
    MAX-ACCESS read-only
    STATUS     current
    DESCRIPTION
            ""
    ::= { lcsStatusCertsOcspClientCaStatusTableEntry 4 }

-- {COLUMN} 1.3.6.1.4.1.2356.11.1.61.6.1.1.5
lcsStatusCertsOcspClientCaStatusTableEntryRevokeResponses OBJECT-TYPE
    SYNTAX     Integer32 (0..2147483647)
    MAX-ACCESS read-only
    STATUS     current
    DESCRIPTION
            ""
    ::= { lcsStatusCertsOcspClientCaStatusTableEntry 5 }

-- {COLUMN} 1.3.6.1.4.1.2356.11.1.61.6.1.1.6
lcsStatusCertsOcspClientCaStatusTableEntryUnknownResponses OBJECT-TYPE
    SYNTAX     Integer32 (0..2147483647)
    MAX-ACCESS read-only
    STATUS     current
    DESCRIPTION
            ""
    ::= { lcsStatusCertsOcspClientCaStatusTableEntry 6 }

-- {COLUMN} 1.3.6.1.4.1.2356.11.1.61.6.1.1.7
lcsStatusCertsOcspClientCaStatusTableEntrySuccessfulResponses OBJECT-TYPE
    SYNTAX     Integer32 (0..2147483647)
    MAX-ACCESS read-only
    STATUS     current
    DESCRIPTION
            ""
    ::= { lcsStatusCertsOcspClientCaStatusTableEntry 7 }

-- {COLUMN} 1.3.6.1.4.1.2356.11.1.61.6.1.1.8
lcsStatusCertsOcspClientCaStatusTableEntryErrorResponses OBJECT-TYPE
    SYNTAX     Integer32 (0..2147483647)
    MAX-ACCESS read-only
    STATUS     current
    DESCRIPTION
            ""
    ::= { lcsStatusCertsOcspClientCaStatusTableEntry 8 }

-- {COLUMN} 1.3.6.1.4.1.2356.11.1.61.6.1.1.9
lcsStatusCertsOcspClientCaStatusTableEntryMalformedRequests OBJECT-TYPE
    SYNTAX     Integer32 (0..2147483647)
    MAX-ACCESS read-only
    STATUS     current
    DESCRIPTION
            ""
    ::= { lcsStatusCertsOcspClientCaStatusTableEntry 9 }

-- {COLUMN} 1.3.6.1.4.1.2356.11.1.61.6.1.1.10
lcsStatusCertsOcspClientCaStatusTableEntryIntErrorResponses OBJECT-TYPE
    SYNTAX     Integer32 (0..2147483647)
    MAX-ACCESS read-only
    STATUS     current
    DESCRIPTION
            ""
    ::= { lcsStatusCertsOcspClientCaStatusTableEntry 10 }

-- {COLUMN} 1.3.6.1.4.1.2356.11.1.61.6.1.1.11
lcsStatusCertsOcspClientCaStatusTableEntryTryLaterResponses OBJECT-TYPE
    SYNTAX     Integer32 (0..2147483647)
    MAX-ACCESS read-only
    STATUS     current
    DESCRIPTION
            ""
    ::= { lcsStatusCertsOcspClientCaStatusTableEntry 11 }

-- {COLUMN} 1.3.6.1.4.1.2356.11.1.61.6.1.1.12
lcsStatusCertsOcspClientCaStatusTableEntrySignRequiredResponses OBJECT-TYPE
    SYNTAX     Integer32 (0..2147483647)
    MAX-ACCESS read-only
    STATUS     current
    DESCRIPTION
            ""
    ::= { lcsStatusCertsOcspClientCaStatusTableEntry 12 }

-- {COLUMN} 1.3.6.1.4.1.2356.11.1.61.6.1.1.13
lcsStatusCertsOcspClientCaStatusTableEntryUnauthorizedResponses OBJECT-TYPE
    SYNTAX     Integer32 (0..2147483647)
    MAX-ACCESS read-only
    STATUS     current
    DESCRIPTION
            ""
    ::= { lcsStatusCertsOcspClientCaStatusTableEntry 13 }

-- {COLUMN} 1.3.6.1.4.1.2356.11.1.61.6.1.1.14
lcsStatusCertsOcspClientCaStatusTableEntrySignerVerifyFailures OBJECT-TYPE
    SYNTAX     Integer32 (0..2147483647)
    MAX-ACCESS read-only
    STATUS     current
    DESCRIPTION
            ""
    ::= { lcsStatusCertsOcspClientCaStatusTableEntry 14 }

-- {COLUMN} 1.3.6.1.4.1.2356.11.1.61.6.1.1.15
lcsStatusCertsOcspClientCaStatusTableEntryCertTimedOuts OBJECT-TYPE
    SYNTAX     Integer32 (0..2147483647)
    MAX-ACCESS read-only
    STATUS     current
    DESCRIPTION
            ""
    ::= { lcsStatusCertsOcspClientCaStatusTableEntry 15 }

-- {COLUMN} 1.3.6.1.4.1.2356.11.1.61.6.1.1.16
lcsStatusCertsOcspClientCaStatusTableEntryGenericErrors OBJECT-TYPE
    SYNTAX     Integer32 (0..2147483647)
    MAX-ACCESS read-only
    STATUS     current
    DESCRIPTION
            ""
    ::= { lcsStatusCertsOcspClientCaStatusTableEntry 16 }

-- {COLUMN} 1.3.6.1.4.1.2356.11.1.61.6.1.1.17
lcsStatusCertsOcspClientCaStatusTableEntryTransportErrors OBJECT-TYPE
    SYNTAX     Integer32 (0..2147483647)
    MAX-ACCESS read-only
    STATUS     current
    DESCRIPTION
            ""
    ::= { lcsStatusCertsOcspClientCaStatusTableEntry 17 }

-- {NODE} 1.3.6.1.4.1.2356.11.1.61.7
lcsStatusCertsOcspServer OBJECT IDENTIFIER ::= { lcsStatusCerts 7 }

-- {SCALAR} 1.3.6.1.4.1.2356.11.1.61.7.1
lcsStatusCertsOcspServerOperating OBJECT-TYPE
    SYNTAX     INTEGER {
                  eNo (0),
                  eYes (1)
            }
    MAX-ACCESS read-only
    STATUS     current
    DESCRIPTION
            "-- empty --"
    ::= { lcsStatusCertsOcspServer 1 }

-- {SCALAR} 1.3.6.1.4.1.2356.11.1.61.7.2
lcsStatusCertsOcspServerPort OBJECT-TYPE
    SYNTAX     Integer32 (0..65535)
    MAX-ACCESS read-only
    STATUS     current
    DESCRIPTION
            "-- empty --"
    ::= { lcsStatusCertsOcspServer 2 }

-- {SCALAR} 1.3.6.1.4.1.2356.11.1.61.7.3
lcsStatusCertsOcspServerCertificateSubject OBJECT-TYPE
    SYNTAX     DisplayString (SIZE(0..251))
    MAX-ACCESS read-only
    STATUS     current
    DESCRIPTION
            "-- empty --"
    ::= { lcsStatusCertsOcspServer 3 }

-- {SCALAR} 1.3.6.1.4.1.2356.11.1.61.7.4
lcsStatusCertsOcspServerWanAccess OBJECT-TYPE
    SYNTAX     INTEGER {
                  eNo (0),
                  eYes (1),
                  eOverVpn (2)
            }
    MAX-ACCESS read-only
    STATUS     current
    DESCRIPTION
            "-- empty --"
    ::= { lcsStatusCertsOcspServer 4 }

-- {SCALAR} 1.3.6.1.4.1.2356.11.1.61.7.5
lcsStatusCertsOcspServerNbRequests OBJECT-TYPE
    SYNTAX     Integer32 (0..65535)
    MAX-ACCESS read-only
    STATUS     current
    DESCRIPTION
            "-- empty --"
    ::= { lcsStatusCertsOcspServer 5 }

-- {SCALAR} 1.3.6.1.4.1.2356.11.1.61.7.6
lcsStatusCertsOcspServerAnsweredWithRevoke OBJECT-TYPE
    SYNTAX     Integer32 (0..65535)
    MAX-ACCESS read-only
    STATUS     current
    DESCRIPTION
            "-- empty --"
    ::= { lcsStatusCertsOcspServer 6 }

-- {SCALAR} 1.3.6.1.4.1.2356.11.1.61.7.7
lcsStatusCertsOcspServerAnsweredWithValid OBJECT-TYPE
    SYNTAX     Integer32 (0..65535)
    MAX-ACCESS read-only
    STATUS     current
    DESCRIPTION
            "-- empty --"
    ::= { lcsStatusCertsOcspServer 7 }

-- {SCALAR} 1.3.6.1.4.1.2356.11.1.61.7.8
lcsStatusCertsOcspServerAnsweredWithUnknown OBJECT-TYPE
    SYNTAX     Integer32 (0..65535)
    MAX-ACCESS read-only
    STATUS     current
    DESCRIPTION
            "-- empty --"
    ::= { lcsStatusCertsOcspServer 8 }

-- {SCALAR} 1.3.6.1.4.1.2356.11.1.61.7.9
lcsStatusCertsOcspServerNotAnswered OBJECT-TYPE
    SYNTAX     Integer32 (0..65535)
    MAX-ACCESS read-only
    STATUS     current
    DESCRIPTION
            "-- empty --"
    ::= { lcsStatusCertsOcspServer 9 }

-- {SCALAR} 1.3.6.1.4.1.2356.11.1.61.7.10
lcsStatusCertsOcspServerMalformedRequests OBJECT-TYPE
    SYNTAX     Integer32 (0..65535)
    MAX-ACCESS read-only
    STATUS     current
    DESCRIPTION
            "-- empty --"
    ::= { lcsStatusCertsOcspServer 10 }

-- {SCALAR} 1.3.6.1.4.1.2356.11.1.61.7.11
lcsStatusCertsOcspServerInternalErrors OBJECT-TYPE
    SYNTAX     Integer32 (0..65535)
    MAX-ACCESS read-only
    STATUS     current
    DESCRIPTION
            "-- empty --"
    ::= { lcsStatusCertsOcspServer 11 }

-- {NODE} 1.3.6.1.4.1.2356.11.1.62
lcsStatusVlan OBJECT IDENTIFIER ::= { lcsStatus 62 }

-- {TABLE} 1.3.6.1.4.1.2356.11.1.62.1
lcsStatusVlanNetworksTable OBJECT-TYPE
    SYNTAX     SEQUENCE OF LcsStatusVlanNetworksEntry
    MAX-ACCESS not-accessible
    STATUS     current
    DESCRIPTION
            ""
    ::= { lcsStatusVlan 1 }

-- {ROW} 1.3.6.1.4.1.2356.11.1.62.1.1
lcsStatusVlanNetworksEntry OBJECT-TYPE
    SYNTAX     LcsStatusVlanNetworksEntry
    MAX-ACCESS not-accessible
    STATUS     current
    DESCRIPTION
            ""
    INDEX {
            lcsStatusVlanNetworksEntryVlanId
          }
    ::= { lcsStatusVlanNetworksTable 1 }

LcsStatusVlanNetworksEntry ::= SEQUENCE {
            lcsStatusVlanNetworksEntryVlanId Integer32,
            lcsStatusVlanNetworksEntryPorts DisplayString
    }

-- {COLUMN} 1.3.6.1.4.1.2356.11.1.62.1.1.1
lcsStatusVlanNetworksEntryVlanId OBJECT-TYPE
    SYNTAX     Integer32 (0..65535)
    MAX-ACCESS read-only
    STATUS     current
    DESCRIPTION
            ""
    ::= { lcsStatusVlanNetworksEntry 1 }

-- {COLUMN} 1.3.6.1.4.1.2356.11.1.62.1.1.4
lcsStatusVlanNetworksEntryPorts OBJECT-TYPE
    SYNTAX     DisplayString (SIZE(0..255))
    MAX-ACCESS read-only
    STATUS     current
    DESCRIPTION
            ""
    ::= { lcsStatusVlanNetworksEntry 4 }

-- {TABLE} 1.3.6.1.4.1.2356.11.1.62.2
lcsStatusVlanPortTableTable OBJECT-TYPE
    SYNTAX     SEQUENCE OF LcsStatusVlanPortTableEntry
    MAX-ACCESS not-accessible
    STATUS     current
    DESCRIPTION
            ""
    ::= { lcsStatusVlan 2 }

-- {ROW} 1.3.6.1.4.1.2356.11.1.62.2.1
lcsStatusVlanPortTableEntry OBJECT-TYPE
    SYNTAX     LcsStatusVlanPortTableEntry
    MAX-ACCESS not-accessible
    STATUS     current
    DESCRIPTION
            ""
    INDEX {
            lcsStatusVlanPortTableEntryPort
          }
    ::= { lcsStatusVlanPortTableTable 1 }

LcsStatusVlanPortTableEntry ::= SEQUENCE {
            lcsStatusVlanPortTableEntryPort DisplayString,
            lcsStatusVlanPortTableEntryAllowAllVlans INTEGER,
            lcsStatusVlanPortTableEntryPortVlanId Integer32,
            lcsStatusVlanPortTableEntryTaggingMode INTEGER
    }

-- {COLUMN} 1.3.6.1.4.1.2356.11.1.62.2.1.1
lcsStatusVlanPortTableEntryPort OBJECT-TYPE
    SYNTAX     DisplayString (SIZE(0..255))
    MAX-ACCESS read-only
    STATUS     current
    DESCRIPTION
            ""
    ::= { lcsStatusVlanPortTableEntry 1 }

-- {COLUMN} 1.3.6.1.4.1.2356.11.1.62.2.1.4
lcsStatusVlanPortTableEntryAllowAllVlans OBJECT-TYPE
    SYNTAX     INTEGER {
                  eNo (0),
                  eYes (1)
            }
    MAX-ACCESS read-only
    STATUS     current
    DESCRIPTION
            ""
    ::= { lcsStatusVlanPortTableEntry 4 }

-- {COLUMN} 1.3.6.1.4.1.2356.11.1.62.2.1.5
lcsStatusVlanPortTableEntryPortVlanId OBJECT-TYPE
    SYNTAX     Integer32 (0..65535)
    MAX-ACCESS read-only
    STATUS     current
    DESCRIPTION
            ""
    ::= { lcsStatusVlanPortTableEntry 5 }

-- {COLUMN} 1.3.6.1.4.1.2356.11.1.62.2.1.6
lcsStatusVlanPortTableEntryTaggingMode OBJECT-TYPE
    SYNTAX     INTEGER {
                  eIngressMixed (0),
                  eNever (1),
                  eMixed (2),
                  eAlways (3)
            }
    MAX-ACCESS read-only
    STATUS     current
    DESCRIPTION
            ""
    ::= { lcsStatusVlanPortTableEntry 6 }

-- {SCALAR} 1.3.6.1.4.1.2356.11.1.62.4
lcsStatusVlanOperating OBJECT-TYPE
    SYNTAX     INTEGER {
                  eNo (0),
                  eYes (1)
            }
    MAX-ACCESS read-only
    STATUS     current
    DESCRIPTION
            ""
    ::= { lcsStatusVlan 4 }

-- {NODE} 1.3.6.1.4.1.2356.11.1.63
lcsStatusGps OBJECT IDENTIFIER ::= { lcsStatus 63 }

-- {SCALAR} 1.3.6.1.4.1.2356.11.1.63.1
lcsStatusGpsOperating OBJECT-TYPE
    SYNTAX     INTEGER {
                  eNo (0),
                  eYes (1)
            }
    MAX-ACCESS read-only
    STATUS     current
    DESCRIPTION
            ""
    ::= { lcsStatusGps 1 }

-- {SCALAR} 1.3.6.1.4.1.2356.11.1.63.2
lcsStatusGpsFixType OBJECT-TYPE
    SYNTAX     INTEGER {
                  eNone (0),
                  e2d (2),
                  e3d (3)
            }
    MAX-ACCESS read-only
    STATUS     current
    DESCRIPTION
            ""
    ::= { lcsStatusGps 2 }

-- {SCALAR} 1.3.6.1.4.1.2356.11.1.63.3
lcsStatusGpsTimestampGps OBJECT-TYPE
    SYNTAX     Gauge32
    MAX-ACCESS read-only
    STATUS     current
    DESCRIPTION
            ""
    ::= { lcsStatusGps 3 }

-- {SCALAR} 1.3.6.1.4.1.2356.11.1.63.4
lcsStatusGpsLongitudeDeg OBJECT-TYPE
    SYNTAX     DisplayString (SIZE(0..11))
    MAX-ACCESS read-only
    STATUS     current
    DESCRIPTION
            ""
    ::= { lcsStatusGps 4 }

-- {SCALAR} 1.3.6.1.4.1.2356.11.1.63.5
lcsStatusGpsLatitudeDeg OBJECT-TYPE
    SYNTAX     DisplayString (SIZE(0..10))
    MAX-ACCESS read-only
    STATUS     current
    DESCRIPTION
            ""
    ::= { lcsStatusGps 5 }

-- {SCALAR} 1.3.6.1.4.1.2356.11.1.63.6
lcsStatusGpsAltitudeM OBJECT-TYPE
    SYNTAX     Integer32 (-2147483648..2147483647)
    MAX-ACCESS read-only
    STATUS     current
    DESCRIPTION
            ""
    ::= { lcsStatusGps 6 }

-- {SCALAR} 1.3.6.1.4.1.2356.11.1.63.7
lcsStatusGpsPositionValid OBJECT-TYPE
    SYNTAX     INTEGER {
                  eNo (0),
                  eYes (1)
            }
    MAX-ACCESS read-only
    STATUS     current
    DESCRIPTION
            ""
    ::= { lcsStatusGps 7 }

-- {NODE} 1.3.6.1.4.1.2356.11.1.64
lcsStatusUtm OBJECT IDENTIFIER ::= { lcsStatus 64 }

-- {NODE} 1.3.6.1.4.1.2356.11.1.64.3
lcsStatusUtmCf OBJECT IDENTIFIER ::= { lcsStatusUtm 3 }

-- {SCALAR} 1.3.6.1.4.1.2356.11.1.64.3.1
lcsStatusUtmCfAllowedUrls OBJECT-TYPE
    SYNTAX     Integer32 (0..2147483647)
    MAX-ACCESS read-only
    STATUS     current
    DESCRIPTION
            ""
    ::= { lcsStatusUtmCf 1 }

-- {SCALAR} 1.3.6.1.4.1.2356.11.1.64.3.2
lcsStatusUtmCfOverridddenUrls OBJECT-TYPE
    SYNTAX     Integer32 (0..2147483647)
    MAX-ACCESS read-only
    STATUS     current
    DESCRIPTION
            ""
    ::= { lcsStatusUtmCf 2 }

-- {SCALAR} 1.3.6.1.4.1.2356.11.1.64.3.3
lcsStatusUtmCfBlockedUrls OBJECT-TYPE
    SYNTAX     Integer32 (0..2147483647)
    MAX-ACCESS read-only
    STATUS     current
    DESCRIPTION
            ""
    ::= { lcsStatusUtmCf 3 }

-- {SCALAR} 1.3.6.1.4.1.2356.11.1.64.3.4
lcsStatusUtmCfWhitelistedUrls OBJECT-TYPE
    SYNTAX     Integer32 (0..2147483647)
    MAX-ACCESS read-only
    STATUS     current
    DESCRIPTION
            ""
    ::= { lcsStatusUtmCf 4 }

-- {SCALAR} 1.3.6.1.4.1.2356.11.1.64.3.5
lcsStatusUtmCfBlacklistedUrls OBJECT-TYPE
    SYNTAX     Integer32 (0..2147483647)
    MAX-ACCESS read-only
    STATUS     current
    DESCRIPTION
            ""
    ::= { lcsStatusUtmCf 5 }

-- {SCALAR} 1.3.6.1.4.1.2356.11.1.64.3.6
lcsStatusUtmCfErrorCount OBJECT-TYPE
    SYNTAX     Integer32 (0..2147483647)
    MAX-ACCESS read-only
    STATUS     current
    DESCRIPTION
            ""
    ::= { lcsStatusUtmCf 6 }

-- {SCALAR} 1.3.6.1.4.1.2356.11.1.64.3.7
lcsStatusUtmCfUncategorizedUrls OBJECT-TYPE
    SYNTAX     Integer32 (0..2147483647)
    MAX-ACCESS read-only
    STATUS     current
    DESCRIPTION
            ""
    ::= { lcsStatusUtmCf 7 }

-- {SCALAR} 1.3.6.1.4.1.2356.11.1.64.3.8
lcsStatusUtmCfStatisticsFlush OBJECT-TYPE
    SYNTAX     DisplayString
    MAX-ACCESS read-write
    STATUS     current
    DESCRIPTION
            ""
    ::= { lcsStatusUtmCf 8 }

-- {TABLE} 1.3.6.1.4.1.2356.11.1.64.3.17
lcsStatusUtmCfLogTable OBJECT-TYPE
    SYNTAX     SEQUENCE OF LcsStatusUtmCfLogEntry
    MAX-ACCESS not-accessible
    STATUS     current
    DESCRIPTION
            ""
    ::= { lcsStatusUtmCf 17 }

-- {ROW} 1.3.6.1.4.1.2356.11.1.64.3.17.1
lcsStatusUtmCfLogEntry OBJECT-TYPE
    SYNTAX     LcsStatusUtmCfLogEntry
    MAX-ACCESS not-accessible
    STATUS     current
    DESCRIPTION
            ""
    INDEX {
            lcsStatusUtmCfLogEntryIdx
          }
    ::= { lcsStatusUtmCfLogTable 1 }

LcsStatusUtmCfLogEntry ::= SEQUENCE {
            lcsStatusUtmCfLogEntryIdx Integer32,
            lcsStatusUtmCfLogEntrySystemTime Counter32,
            lcsStatusUtmCfLogEntryCause INTEGER,
            lcsStatusUtmCfLogEntryUserProfile DisplayString,
            lcsStatusUtmCfLogEntryCategoryError DisplayString,
            lcsStatusUtmCfLogEntryUrl DisplayString
    }

-- {COLUMN} 1.3.6.1.4.1.2356.11.1.64.3.17.1.1
lcsStatusUtmCfLogEntryIdx OBJECT-TYPE
    SYNTAX     Integer32 (0..2147483647)
    MAX-ACCESS read-only
    STATUS     current
    DESCRIPTION
            ""
    ::= { lcsStatusUtmCfLogEntry 1 }

-- {COLUMN} 1.3.6.1.4.1.2356.11.1.64.3.17.1.2
lcsStatusUtmCfLogEntrySystemTime OBJECT-TYPE
    SYNTAX     Counter32
    MAX-ACCESS read-only
    STATUS     current
    DESCRIPTION
            ""
    ::= { lcsStatusUtmCfLogEntry 2 }

-- {COLUMN} 1.3.6.1.4.1.2356.11.1.64.3.17.1.3
lcsStatusUtmCfLogEntryCause OBJECT-TYPE
    SYNTAX     INTEGER {
                  eSpamMail (1),
                  ePhishingMail (2),
                  eUpdate (3),
                  eInfected (4),
                  eBlockedUrl (5),
                  eError (6),
                  eLicenseExpired (7),
                  eLicenseExceeded (8),
                  eOverride (9),
                  eProxyLimit (10)
            }
    MAX-ACCESS read-only
    STATUS     current
    DESCRIPTION
            ""
    ::= { lcsStatusUtmCfLogEntry 3 }

-- {COLUMN} 1.3.6.1.4.1.2356.11.1.64.3.17.1.4
lcsStatusUtmCfLogEntryUserProfile OBJECT-TYPE
    SYNTAX     DisplayString (SIZE(0..32))
    MAX-ACCESS read-only
    STATUS     current
    DESCRIPTION
            ""
    ::= { lcsStatusUtmCfLogEntry 4 }

-- {COLUMN} 1.3.6.1.4.1.2356.11.1.64.3.17.1.5
lcsStatusUtmCfLogEntryCategoryError OBJECT-TYPE
    SYNTAX     DisplayString (SIZE(0..64))
    MAX-ACCESS read-only
    STATUS     current
    DESCRIPTION
            ""
    ::= { lcsStatusUtmCfLogEntry 5 }

-- {COLUMN} 1.3.6.1.4.1.2356.11.1.64.3.17.1.6
lcsStatusUtmCfLogEntryUrl OBJECT-TYPE
    SYNTAX     DisplayString (SIZE(0..64))
    MAX-ACCESS read-only
    STATUS     current
    DESCRIPTION
            ""
    ::= { lcsStatusUtmCfLogEntry 6 }

-- {SCALAR} 1.3.6.1.4.1.2356.11.1.64.3.18
lcsStatusUtmCfLicenseCount OBJECT-TYPE
    SYNTAX     Integer32 (0..2147483647)
    MAX-ACCESS read-only
    STATUS     current
    DESCRIPTION
            ""
    ::= { lcsStatusUtmCf 18 }

-- {TABLE} 1.3.6.1.4.1.2356.11.1.64.3.19
lcsStatusUtmCfUsersTable OBJECT-TYPE
    SYNTAX     SEQUENCE OF LcsStatusUtmCfUsersEntry
    MAX-ACCESS not-accessible
    STATUS     current
    DESCRIPTION
            ""
    ::= { lcsStatusUtmCf 19 }

-- {ROW} 1.3.6.1.4.1.2356.11.1.64.3.19.1
lcsStatusUtmCfUsersEntry OBJECT-TYPE
    SYNTAX     LcsStatusUtmCfUsersEntry
    MAX-ACCESS not-accessible
    STATUS     current
    DESCRIPTION
            ""
    INDEX {
            lcsStatusUtmCfUsersEntryIndex
          }
    ::= { lcsStatusUtmCfUsersTable 1 }

LcsStatusUtmCfUsersEntry ::= SEQUENCE {
            lcsStatusUtmCfUsersEntryIndex Integer32,
            lcsStatusUtmCfUsersEntryIpAddress IpAddress,
            lcsStatusUtmCfUsersEntryMacAddress DisplayString
    }

-- {COLUMN} 1.3.6.1.4.1.2356.11.1.64.3.19.1.1
lcsStatusUtmCfUsersEntryIndex OBJECT-TYPE
    SYNTAX     Integer32 (0..2147483647)
    MAX-ACCESS read-only
    STATUS     current
    DESCRIPTION
            ""
    ::= { lcsStatusUtmCfUsersEntry 1 }

-- {COLUMN} 1.3.6.1.4.1.2356.11.1.64.3.19.1.2
lcsStatusUtmCfUsersEntryIpAddress OBJECT-TYPE
    SYNTAX     IpAddress
    MAX-ACCESS read-only
    STATUS     current
    DESCRIPTION
            ""
    ::= { lcsStatusUtmCfUsersEntry 2 }

-- {COLUMN} 1.3.6.1.4.1.2356.11.1.64.3.19.1.3
lcsStatusUtmCfUsersEntryMacAddress OBJECT-TYPE
    SYNTAX     DisplayString (SIZE(0..255))
    MAX-ACCESS read-only
    STATUS     current
    DESCRIPTION
            ""
    ::= { lcsStatusUtmCfUsersEntry 3 }

-- {TABLE} 1.3.6.1.4.1.2356.11.1.64.3.20
lcsStatusUtmCfOverrideLogTable OBJECT-TYPE
    SYNTAX     SEQUENCE OF LcsStatusUtmCfOverrideLogEntry
    MAX-ACCESS not-accessible
    STATUS     current
    DESCRIPTION
            ""
    ::= { lcsStatusUtmCf 20 }

-- {ROW} 1.3.6.1.4.1.2356.11.1.64.3.20.1
lcsStatusUtmCfOverrideLogEntry OBJECT-TYPE
    SYNTAX     LcsStatusUtmCfOverrideLogEntry
    MAX-ACCESS not-accessible
    STATUS     current
    DESCRIPTION
            ""
    INDEX {
            lcsStatusUtmCfOverrideLogEntryIndex
          }
    ::= { lcsStatusUtmCfOverrideLogTable 1 }

LcsStatusUtmCfOverrideLogEntry ::= SEQUENCE {
            lcsStatusUtmCfOverrideLogEntryIndex Integer32,
            lcsStatusUtmCfOverrideLogEntryDateTime DisplayString,
            lcsStatusUtmCfOverrideLogEntryUserIp IpAddress,
            lcsStatusUtmCfOverrideLogEntryUserMac DisplayString,
            lcsStatusUtmCfOverrideLogEntryTargetUrl DisplayString
    }

-- {COLUMN} 1.3.6.1.4.1.2356.11.1.64.3.20.1.1
lcsStatusUtmCfOverrideLogEntryIndex OBJECT-TYPE
    SYNTAX     Integer32 (0..2147483647)
    MAX-ACCESS read-only
    STATUS     current
    DESCRIPTION
            ""
    ::= { lcsStatusUtmCfOverrideLogEntry 1 }

-- {COLUMN} 1.3.6.1.4.1.2356.11.1.64.3.20.1.2
lcsStatusUtmCfOverrideLogEntryDateTime OBJECT-TYPE
    SYNTAX     DisplayString (SIZE(0..255))
    MAX-ACCESS read-only
    STATUS     current
    DESCRIPTION
            ""
    ::= { lcsStatusUtmCfOverrideLogEntry 2 }

-- {COLUMN} 1.3.6.1.4.1.2356.11.1.64.3.20.1.3
lcsStatusUtmCfOverrideLogEntryUserIp OBJECT-TYPE
    SYNTAX     IpAddress
    MAX-ACCESS read-only
    STATUS     current
    DESCRIPTION
            ""
    ::= { lcsStatusUtmCfOverrideLogEntry 3 }

-- {COLUMN} 1.3.6.1.4.1.2356.11.1.64.3.20.1.4
lcsStatusUtmCfOverrideLogEntryUserMac OBJECT-TYPE
    SYNTAX     DisplayString (SIZE(0..255))
    MAX-ACCESS read-only
    STATUS     current
    DESCRIPTION
            ""
    ::= { lcsStatusUtmCfOverrideLogEntry 4 }

-- {COLUMN} 1.3.6.1.4.1.2356.11.1.64.3.20.1.5
lcsStatusUtmCfOverrideLogEntryTargetUrl OBJECT-TYPE
    SYNTAX     DisplayString (SIZE(0..255))
    MAX-ACCESS read-only
    STATUS     current
    DESCRIPTION
            ""
    ::= { lcsStatusUtmCfOverrideLogEntry 5 }

-- {SCALAR} 1.3.6.1.4.1.2356.11.1.64.3.21
lcsStatusUtmCfLogFlush OBJECT-TYPE
    SYNTAX     DisplayString
    MAX-ACCESS read-write
    STATUS     current
    DESCRIPTION
            ""
    ::= { lcsStatusUtmCf 21 }

-- {TABLE} 1.3.6.1.4.1.2356.11.1.64.3.22
lcsStatusUtmCfCategoryStatisticsTable OBJECT-TYPE
    SYNTAX     SEQUENCE OF LcsStatusUtmCfCategoryStatisticsEntry
    MAX-ACCESS not-accessible
    STATUS     current
    DESCRIPTION
            ""
    ::= { lcsStatusUtmCf 22 }

-- {ROW} 1.3.6.1.4.1.2356.11.1.64.3.22.1
lcsStatusUtmCfCategoryStatisticsEntry OBJECT-TYPE
    SYNTAX     LcsStatusUtmCfCategoryStatisticsEntry
    MAX-ACCESS not-accessible
    STATUS     current
    DESCRIPTION
            ""
    INDEX {
            lcsStatusUtmCfCategoryStatisticsEntryCat
          }
    ::= { lcsStatusUtmCfCategoryStatisticsTable 1 }

LcsStatusUtmCfCategoryStatisticsEntry ::= SEQUENCE {
            lcsStatusUtmCfCategoryStatisticsEntryCat INTEGER,
            lcsStatusUtmCfCategoryStatisticsEntryHit Integer32
    }

-- {COLUMN} 1.3.6.1.4.1.2356.11.1.64.3.22.1.1
lcsStatusUtmCfCategoryStatisticsEntryCat OBJECT-TYPE
    SYNTAX     INTEGER {
                  ePornographyEroticSex (1),
                  eEroticSex (2),
                  eSwimwearLingerie (3),
                  eShopping (4),
                  eAuctionsClassifiedAds (5),
                  eGovNonProv (6),
                  eNonGovernmentalOrganizations (7),
                  eCitiesRegionsCountries (8),
                  eEducation (9),
                  ePoliticalParties (10),
                  eReligionSpirituality (11),
                  eSects (12),
                  eIllegalActivities (13),
                  eComputerCrimeWarezHacking (14),
                  ePolHateDiscr (15),
                  eWarezSoftwarePrivacy (16),
                  eViolenceExtreme (17),
                  eGamblingLottery (18),
                  eComputerGames (19),
                  eToys (20),
                  eCinTvSocial (21),
                  eRecrFacThemPark (22),
                  eArtsMuseumsTheaters (23),
                  eMusicRadioBroadcast (24),
                  eLiteratureBooks (25),
                  eHumorCartoons (26),
                  eNewsMagazines (27),
                  eWebmailUnifiedMessaging (28),
                  eChat (29),
                  eBlogsBulletinBoards (30),
                  eMobileTelephony (31),
                  eDigitalPostcards (32),
                  eSearchWebPortal (33),
                  eSoftwareHardware (34),
                  eCommunicationServices (35),
                  eItSecurityItInformation (36),
                  eWebSiteTranslation (37),
                  eAnonymousProxies (38),
                  eIllegalDrugs (39),
                  eAlcoholTobacco (40),
                  eTobacco (41),
                  eSelfHelpAddiction (42),
                  eDatingNetworks (43),
                  eRestEnter (44),
                  eTravel (45),
                  eFashionCosmeticsJewelry (46),
                  eSports (47),
                  eArchConstFurn (48),
                  eEnvironmentClimatePets (49),
                  ePersonalWebSites (50),
                  eJobSearch (51),
                  eFinanceInvestment (52),
                  eFinServInsurance (53),
                  eBanking (54),
                  eVehicles (55),
                  eWeaponsMilitary (56),
                  eMedicineHealthSelfHelp (57),
                  eAbortion (58),
                  eSpamUrls (60),
                  eMalware (61),
                  ePhishingUrls (62),
                  eInstantMessaging (63),
                  eGeneralBusiness (67),
                  eBannerAdvertisements (74),
                  eSocialNetworking (77),
                  eBusinessNetworking (78),
                  eSocialMedia (79),
                  eWebStorage (80),
                  eCommandControlServer (81),
                  eBotnetCommandAndControlServer (82),
                  eCloud (83),
                  eInfrastructureAsAService (84),
                  ePlatformAsAService (85),
                  eSoftwareAsAService (86)
            }
    MAX-ACCESS read-only
    STATUS     current
    DESCRIPTION
            "Category"
    ::= { lcsStatusUtmCfCategoryStatisticsEntry 1 }

-- {COLUMN} 1.3.6.1.4.1.2356.11.1.64.3.22.1.2
lcsStatusUtmCfCategoryStatisticsEntryHit OBJECT-TYPE
    SYNTAX     Integer32 (0..2147483647)
    MAX-ACCESS read-only
    STATUS     current
    DESCRIPTION
            ""
    ::= { lcsStatusUtmCfCategoryStatisticsEntry 2 }

-- {TABLE} 1.3.6.1.4.1.2356.11.1.64.3.23
lcsStatusUtmCfLastSnapshotTable OBJECT-TYPE
    SYNTAX     SEQUENCE OF LcsStatusUtmCfLastSnapshotEntry
    MAX-ACCESS not-accessible
    STATUS     current
    DESCRIPTION
            ""
    ::= { lcsStatusUtmCf 23 }

-- {ROW} 1.3.6.1.4.1.2356.11.1.64.3.23.1
lcsStatusUtmCfLastSnapshotEntry OBJECT-TYPE
    SYNTAX     LcsStatusUtmCfLastSnapshotEntry
    MAX-ACCESS not-accessible
    STATUS     current
    DESCRIPTION
            ""
    INDEX {
            lcsStatusUtmCfLastSnapshotEntryCat
          }
    ::= { lcsStatusUtmCfLastSnapshotTable 1 }

LcsStatusUtmCfLastSnapshotEntry ::= SEQUENCE {
            lcsStatusUtmCfLastSnapshotEntryCat INTEGER,
            lcsStatusUtmCfLastSnapshotEntryHit Integer32
    }

-- {COLUMN} 1.3.6.1.4.1.2356.11.1.64.3.23.1.1
lcsStatusUtmCfLastSnapshotEntryCat OBJECT-TYPE
    SYNTAX     INTEGER {
                  ePornographyEroticSex (1),
                  eEroticSex (2),
                  eSwimwearLingerie (3),
                  eShopping (4),
                  eAuctionsClassifiedAds (5),
                  eGovNonProv (6),
                  eNonGovernmentalOrganizations (7),
                  eCitiesRegionsCountries (8),
                  eEducation (9),
                  ePoliticalParties (10),
                  eReligionSpirituality (11),
                  eSects (12),
                  eIllegalActivities (13),
                  eComputerCrimeWarezHacking (14),
                  ePolHateDiscr (15),
                  eWarezSoftwarePrivacy (16),
                  eViolenceExtreme (17),
                  eGamblingLottery (18),
                  eComputerGames (19),
                  eToys (20),
                  eCinTvSocial (21),
                  eRecrFacThemPark (22),
                  eArtsMuseumsTheaters (23),
                  eMusicRadioBroadcast (24),
                  eLiteratureBooks (25),
                  eHumorCartoons (26),
                  eNewsMagazines (27),
                  eWebmailUnifiedMessaging (28),
                  eChat (29),
                  eBlogsBulletinBoards (30),
                  eMobileTelephony (31),
                  eDigitalPostcards (32),
                  eSearchWebPortal (33),
                  eSoftwareHardware (34),
                  eCommunicationServices (35),
                  eItSecurityItInformation (36),
                  eWebSiteTranslation (37),
                  eAnonymousProxies (38),
                  eIllegalDrugs (39),
                  eAlcoholTobacco (40),
                  eTobacco (41),
                  eSelfHelpAddiction (42),
                  eDatingNetworks (43),
                  eRestEnter (44),
                  eTravel (45),
                  eFashionCosmeticsJewelry (46),
                  eSports (47),
                  eArchConstFurn (48),
                  eEnvironmentClimatePets (49),
                  ePersonalWebSites (50),
                  eJobSearch (51),
                  eFinanceInvestment (52),
                  eFinServInsurance (53),
                  eBanking (54),
                  eVehicles (55),
                  eWeaponsMilitary (56),
                  eMedicineHealthSelfHelp (57),
                  eAbortion (58),
                  eSpamUrls (60),
                  eMalware (61),
                  ePhishingUrls (62),
                  eInstantMessaging (63),
                  eGeneralBusiness (67),
                  eBannerAdvertisements (74),
                  eSocialNetworking (77),
                  eBusinessNetworking (78),
                  eSocialMedia (79),
                  eWebStorage (80),
                  eCommandControlServer (81),
                  eBotnetCommandAndControlServer (82),
                  eCloud (83),
                  eInfrastructureAsAService (84),
                  ePlatformAsAService (85),
                  eSoftwareAsAService (86)
            }
    MAX-ACCESS read-only
    STATUS     current
    DESCRIPTION
            "Category"
    ::= { lcsStatusUtmCfLastSnapshotEntry 1 }

-- {COLUMN} 1.3.6.1.4.1.2356.11.1.64.3.23.1.2
lcsStatusUtmCfLastSnapshotEntryHit OBJECT-TYPE
    SYNTAX     Integer32 (0..2147483647)
    MAX-ACCESS read-only
    STATUS     current
    DESCRIPTION
            ""
    ::= { lcsStatusUtmCfLastSnapshotEntry 2 }

-- {SCALAR} 1.3.6.1.4.1.2356.11.1.64.3.24
lcsStatusUtmCfSnapshotDate OBJECT-TYPE
    SYNTAX     Counter32
    MAX-ACCESS read-only
    STATUS     current
    DESCRIPTION
            ""
    ::= { lcsStatusUtmCf 24 }

-- {SCALAR} 1.3.6.1.4.1.2356.11.1.64.3.25
lcsStatusUtmCfCategoryStatisticsFlush OBJECT-TYPE
    SYNTAX     DisplayString
    MAX-ACCESS read-write
    STATUS     current
    DESCRIPTION
            ""
    ::= { lcsStatusUtmCf 25 }

-- {NODE} 1.3.6.1.4.1.2356.11.1.64.3.27
lcsStatusUtmCfPerf OBJECT IDENTIFIER ::= { lcsStatusUtmCf 27 }

-- {SCALAR} 1.3.6.1.4.1.2356.11.1.64.3.27.1
lcsStatusUtmCfPerfRatingServer OBJECT-TYPE
    SYNTAX     DisplayString (SIZE(0..31))
    MAX-ACCESS read-only
    STATUS     current
    DESCRIPTION
            ""
    ::= { lcsStatusUtmCfPerf 1 }

-- {SCALAR} 1.3.6.1.4.1.2356.11.1.64.3.27.2
lcsStatusUtmCfPerfUsedSince OBJECT-TYPE
    SYNTAX     Counter32
    MAX-ACCESS read-only
    STATUS     current
    DESCRIPTION
            ""
    ::= { lcsStatusUtmCfPerf 2 }

-- {SCALAR} 1.3.6.1.4.1.2356.11.1.64.3.27.3
lcsStatusUtmCfPerfIniServTime OBJECT-TYPE
    SYNTAX     Integer32 (-2147483648..2147483647)
    MAX-ACCESS read-only
    STATUS     current
    DESCRIPTION
            ""
    ::= { lcsStatusUtmCfPerf 3 }

-- {SCALAR} 1.3.6.1.4.1.2356.11.1.64.3.27.4
lcsStatusUtmCfPerfProcUrls OBJECT-TYPE
    SYNTAX     Integer32 (0..2147483647)
    MAX-ACCESS read-only
    STATUS     current
    DESCRIPTION
            ""
    ::= { lcsStatusUtmCfPerf 4 }

-- {SCALAR} 1.3.6.1.4.1.2356.11.1.64.3.27.5
lcsStatusUtmCfPerfProcTimeouts OBJECT-TYPE
    SYNTAX     Integer32 (0..2147483647)
    MAX-ACCESS read-only
    STATUS     current
    DESCRIPTION
            ""
    ::= { lcsStatusUtmCfPerf 5 }

-- {SCALAR} 1.3.6.1.4.1.2356.11.1.64.3.27.6
lcsStatusUtmCfPerfMinProcTime OBJECT-TYPE
    SYNTAX     DisplayString (SIZE(0..6))
    MAX-ACCESS read-only
    STATUS     current
    DESCRIPTION
            ""
    ::= { lcsStatusUtmCfPerf 6 }

-- {SCALAR} 1.3.6.1.4.1.2356.11.1.64.3.27.7
lcsStatusUtmCfPerfMaxProcTime OBJECT-TYPE
    SYNTAX     DisplayString (SIZE(0..6))
    MAX-ACCESS read-only
    STATUS     current
    DESCRIPTION
            ""
    ::= { lcsStatusUtmCfPerf 7 }

-- {SCALAR} 1.3.6.1.4.1.2356.11.1.64.3.27.8
lcsStatusUtmCfPerfAvgProcTime OBJECT-TYPE
    SYNTAX     DisplayString
    MAX-ACCESS read-only
    STATUS     current
    DESCRIPTION
            ""
    ::= { lcsStatusUtmCfPerf 8 }

-- {SCALAR} 1.3.6.1.4.1.2356.11.1.64.3.27.9
lcsStatusUtmCfPerf5minProcTime OBJECT-TYPE
    SYNTAX     DisplayString
    MAX-ACCESS read-only
    STATUS     current
    DESCRIPTION
            ""
    ::= { lcsStatusUtmCfPerf 9 }

-- {SCALAR} 1.3.6.1.4.1.2356.11.1.64.3.27.10
lcsStatusUtmCfPerfServRequests OBJECT-TYPE
    SYNTAX     Integer32 (0..2147483647)
    MAX-ACCESS read-only
    STATUS     current
    DESCRIPTION
            ""
    ::= { lcsStatusUtmCfPerf 10 }

-- {SCALAR} 1.3.6.1.4.1.2356.11.1.64.3.27.11
lcsStatusUtmCfPerfServTimeouts OBJECT-TYPE
    SYNTAX     Integer32 (0..2147483647)
    MAX-ACCESS read-only
    STATUS     current
    DESCRIPTION
            ""
    ::= { lcsStatusUtmCfPerf 11 }

-- {SCALAR} 1.3.6.1.4.1.2356.11.1.64.3.27.12
lcsStatusUtmCfPerfMinServTime OBJECT-TYPE
    SYNTAX     DisplayString (SIZE(0..6))
    MAX-ACCESS read-only
    STATUS     current
    DESCRIPTION
            ""
    ::= { lcsStatusUtmCfPerf 12 }

-- {SCALAR} 1.3.6.1.4.1.2356.11.1.64.3.27.13
lcsStatusUtmCfPerfMaxServTime OBJECT-TYPE
    SYNTAX     DisplayString (SIZE(0..6))
    MAX-ACCESS read-only
    STATUS     current
    DESCRIPTION
            ""
    ::= { lcsStatusUtmCfPerf 13 }

-- {SCALAR} 1.3.6.1.4.1.2356.11.1.64.3.27.14
lcsStatusUtmCfPerfAvgServTime OBJECT-TYPE
    SYNTAX     DisplayString
    MAX-ACCESS read-only
    STATUS     current
    DESCRIPTION
            ""
    ::= { lcsStatusUtmCfPerf 14 }

-- {SCALAR} 1.3.6.1.4.1.2356.11.1.64.3.27.15
lcsStatusUtmCfPerf5minServTime OBJECT-TYPE
    SYNTAX     DisplayString
    MAX-ACCESS read-only
    STATUS     current
    DESCRIPTION
            ""
    ::= { lcsStatusUtmCfPerf 15 }

-- {TABLE} 1.3.6.1.4.1.2356.11.1.64.3.27.16
lcsStatusUtmCfPerfPerfLogTable OBJECT-TYPE
    SYNTAX     SEQUENCE OF LcsStatusUtmCfPerfPerfLogEntry
    MAX-ACCESS not-accessible
    STATUS     current
    DESCRIPTION
            "Performance Log"
    ::= { lcsStatusUtmCfPerf 16 }

-- {ROW} 1.3.6.1.4.1.2356.11.1.64.3.27.16.1
lcsStatusUtmCfPerfPerfLogEntry OBJECT-TYPE
    SYNTAX     LcsStatusUtmCfPerfPerfLogEntry
    MAX-ACCESS not-accessible
    STATUS     current
    DESCRIPTION
            ""
    INDEX {
            lcsStatusUtmCfPerfPerfLogEntryIdx
          }
    ::= { lcsStatusUtmCfPerfPerfLogTable 1 }

LcsStatusUtmCfPerfPerfLogEntry ::= SEQUENCE {
            lcsStatusUtmCfPerfPerfLogEntryIdx Integer32,
            lcsStatusUtmCfPerfPerfLogEntryRatingServer DisplayString,
            lcsStatusUtmCfPerfPerfLogEntryUsedSince DisplayString,
            lcsStatusUtmCfPerfPerfLogEntryUsedSinceNumerical Counter32,
            lcsStatusUtmCfPerfPerfLogEntryIniServTime Integer32,
            lcsStatusUtmCfPerfPerfLogEntryProcUrls Integer32,
            lcsStatusUtmCfPerfPerfLogEntryProcTimeouts Integer32,
            lcsStatusUtmCfPerfPerfLogEntryMinProcTimeNumerical Integer32,
            lcsStatusUtmCfPerfPerfLogEntryMaxProcTimeNumerical Integer32,
            lcsStatusUtmCfPerfPerfLogEntryAvgProcTimeNumerical Integer32,
            lcsStatusUtmCfPerfPerfLogEntry5minProcTimeNumerical Integer32,
            lcsStatusUtmCfPerfPerfLogEntryServRequests Integer32,
            lcsStatusUtmCfPerfPerfLogEntryServTimeouts Integer32,
            lcsStatusUtmCfPerfPerfLogEntryMinServTimeNumerical Integer32,
            lcsStatusUtmCfPerfPerfLogEntryMaxServTimeNumerical Integer32,
            lcsStatusUtmCfPerfPerfLogEntryAvgServTimeNumerical Integer32,
            lcsStatusUtmCfPerfPerfLogEntry5minServTimeNumerical Integer32,
            lcsStatusUtmCfPerfPerfLogEntryMinProcTime DisplayString,
            lcsStatusUtmCfPerfPerfLogEntryMaxProcTime DisplayString,
            lcsStatusUtmCfPerfPerfLogEntryAvgProcTime DisplayString,
            lcsStatusUtmCfPerfPerfLogEntry5minProcTime DisplayString,
            lcsStatusUtmCfPerfPerfLogEntryMinServTime DisplayString,
            lcsStatusUtmCfPerfPerfLogEntryMaxServTime DisplayString,
            lcsStatusUtmCfPerfPerfLogEntryAvgServTime DisplayString,
            lcsStatusUtmCfPerfPerfLogEntry5minServTime DisplayString
    }

-- {COLUMN} 1.3.6.1.4.1.2356.11.1.64.3.27.16.1.1
lcsStatusUtmCfPerfPerfLogEntryIdx OBJECT-TYPE
    SYNTAX     Integer32 (0..2147483647)
    MAX-ACCESS read-only
    STATUS     current
    DESCRIPTION
            ""
    ::= { lcsStatusUtmCfPerfPerfLogEntry 1 }

-- {COLUMN} 1.3.6.1.4.1.2356.11.1.64.3.27.16.1.2
lcsStatusUtmCfPerfPerfLogEntryRatingServer OBJECT-TYPE
    SYNTAX     DisplayString (SIZE(0..255))
    MAX-ACCESS read-only
    STATUS     current
    DESCRIPTION
            ""
    ::= { lcsStatusUtmCfPerfPerfLogEntry 2 }

-- {COLUMN} 1.3.6.1.4.1.2356.11.1.64.3.27.16.1.3
lcsStatusUtmCfPerfPerfLogEntryUsedSince OBJECT-TYPE
    SYNTAX     DisplayString (SIZE(0..255))
    MAX-ACCESS read-only
    STATUS     current
    DESCRIPTION
            ""
    ::= { lcsStatusUtmCfPerfPerfLogEntry 3 }

-- {COLUMN} 1.3.6.1.4.1.2356.11.1.64.3.27.16.1.4
lcsStatusUtmCfPerfPerfLogEntryUsedSinceNumerical OBJECT-TYPE
    SYNTAX     Counter32
    MAX-ACCESS read-only
    STATUS     current
    DESCRIPTION
            ""
    ::= { lcsStatusUtmCfPerfPerfLogEntry 4 }

-- {COLUMN} 1.3.6.1.4.1.2356.11.1.64.3.27.16.1.5
lcsStatusUtmCfPerfPerfLogEntryIniServTime OBJECT-TYPE
    SYNTAX     Integer32 (-2147483648..2147483647)
    MAX-ACCESS read-only
    STATUS     current
    DESCRIPTION
            ""
    ::= { lcsStatusUtmCfPerfPerfLogEntry 5 }

-- {COLUMN} 1.3.6.1.4.1.2356.11.1.64.3.27.16.1.6
lcsStatusUtmCfPerfPerfLogEntryProcUrls OBJECT-TYPE
    SYNTAX     Integer32 (0..2147483647)
    MAX-ACCESS read-only
    STATUS     current
    DESCRIPTION
            ""
    ::= { lcsStatusUtmCfPerfPerfLogEntry 6 }

-- {COLUMN} 1.3.6.1.4.1.2356.11.1.64.3.27.16.1.7
lcsStatusUtmCfPerfPerfLogEntryProcTimeouts OBJECT-TYPE
    SYNTAX     Integer32 (0..2147483647)
    MAX-ACCESS read-only
    STATUS     current
    DESCRIPTION
            ""
    ::= { lcsStatusUtmCfPerfPerfLogEntry 7 }

-- {COLUMN} 1.3.6.1.4.1.2356.11.1.64.3.27.16.1.8
lcsStatusUtmCfPerfPerfLogEntryMinProcTimeNumerical OBJECT-TYPE
    SYNTAX     Integer32 (-2147483648..2147483647)
    MAX-ACCESS read-only
    STATUS     current
    DESCRIPTION
            ""
    ::= { lcsStatusUtmCfPerfPerfLogEntry 8 }

-- {COLUMN} 1.3.6.1.4.1.2356.11.1.64.3.27.16.1.9
lcsStatusUtmCfPerfPerfLogEntryMaxProcTimeNumerical OBJECT-TYPE
    SYNTAX     Integer32 (-2147483648..2147483647)
    MAX-ACCESS read-only
    STATUS     current
    DESCRIPTION
            ""
    ::= { lcsStatusUtmCfPerfPerfLogEntry 9 }

-- {COLUMN} 1.3.6.1.4.1.2356.11.1.64.3.27.16.1.10
lcsStatusUtmCfPerfPerfLogEntryAvgProcTimeNumerical OBJECT-TYPE
    SYNTAX     Integer32 (-2147483648..2147483647)
    MAX-ACCESS read-only
    STATUS     current
    DESCRIPTION
            ""
    ::= { lcsStatusUtmCfPerfPerfLogEntry 10 }

-- {COLUMN} 1.3.6.1.4.1.2356.11.1.64.3.27.16.1.11
lcsStatusUtmCfPerfPerfLogEntry5minProcTimeNumerical OBJECT-TYPE
    SYNTAX     Integer32 (-2147483648..2147483647)
    MAX-ACCESS read-only
    STATUS     current
    DESCRIPTION
            ""
    ::= { lcsStatusUtmCfPerfPerfLogEntry 11 }

-- {COLUMN} 1.3.6.1.4.1.2356.11.1.64.3.27.16.1.12
lcsStatusUtmCfPerfPerfLogEntryServRequests OBJECT-TYPE
    SYNTAX     Integer32 (0..2147483647)
    MAX-ACCESS read-only
    STATUS     current
    DESCRIPTION
            ""
    ::= { lcsStatusUtmCfPerfPerfLogEntry 12 }

-- {COLUMN} 1.3.6.1.4.1.2356.11.1.64.3.27.16.1.13
lcsStatusUtmCfPerfPerfLogEntryServTimeouts OBJECT-TYPE
    SYNTAX     Integer32 (0..2147483647)
    MAX-ACCESS read-only
    STATUS     current
    DESCRIPTION
            ""
    ::= { lcsStatusUtmCfPerfPerfLogEntry 13 }

-- {COLUMN} 1.3.6.1.4.1.2356.11.1.64.3.27.16.1.14
lcsStatusUtmCfPerfPerfLogEntryMinServTimeNumerical OBJECT-TYPE
    SYNTAX     Integer32 (-2147483648..2147483647)
    MAX-ACCESS read-only
    STATUS     current
    DESCRIPTION
            ""
    ::= { lcsStatusUtmCfPerfPerfLogEntry 14 }

-- {COLUMN} 1.3.6.1.4.1.2356.11.1.64.3.27.16.1.15
lcsStatusUtmCfPerfPerfLogEntryMaxServTimeNumerical OBJECT-TYPE
    SYNTAX     Integer32 (-2147483648..2147483647)
    MAX-ACCESS read-only
    STATUS     current
    DESCRIPTION
            ""
    ::= { lcsStatusUtmCfPerfPerfLogEntry 15 }

-- {COLUMN} 1.3.6.1.4.1.2356.11.1.64.3.27.16.1.16
lcsStatusUtmCfPerfPerfLogEntryAvgServTimeNumerical OBJECT-TYPE
    SYNTAX     Integer32 (-2147483648..2147483647)
    MAX-ACCESS read-only
    STATUS     current
    DESCRIPTION
            ""
    ::= { lcsStatusUtmCfPerfPerfLogEntry 16 }

-- {COLUMN} 1.3.6.1.4.1.2356.11.1.64.3.27.16.1.17
lcsStatusUtmCfPerfPerfLogEntry5minServTimeNumerical OBJECT-TYPE
    SYNTAX     Integer32 (-2147483648..2147483647)
    MAX-ACCESS read-only
    STATUS     current
    DESCRIPTION
            ""
    ::= { lcsStatusUtmCfPerfPerfLogEntry 17 }

-- {COLUMN} 1.3.6.1.4.1.2356.11.1.64.3.27.16.1.18
lcsStatusUtmCfPerfPerfLogEntryMinProcTime OBJECT-TYPE
    SYNTAX     DisplayString (SIZE(0..255))
    MAX-ACCESS read-only
    STATUS     current
    DESCRIPTION
            ""
    ::= { lcsStatusUtmCfPerfPerfLogEntry 18 }

-- {COLUMN} 1.3.6.1.4.1.2356.11.1.64.3.27.16.1.19
lcsStatusUtmCfPerfPerfLogEntryMaxProcTime OBJECT-TYPE
    SYNTAX     DisplayString (SIZE(0..255))
    MAX-ACCESS read-only
    STATUS     current
    DESCRIPTION
            ""
    ::= { lcsStatusUtmCfPerfPerfLogEntry 19 }

-- {COLUMN} 1.3.6.1.4.1.2356.11.1.64.3.27.16.1.20
lcsStatusUtmCfPerfPerfLogEntryAvgProcTime OBJECT-TYPE
    SYNTAX     DisplayString (SIZE(0..255))
    MAX-ACCESS read-only
    STATUS     current
    DESCRIPTION
            ""
    ::= { lcsStatusUtmCfPerfPerfLogEntry 20 }

-- {COLUMN} 1.3.6.1.4.1.2356.11.1.64.3.27.16.1.21
lcsStatusUtmCfPerfPerfLogEntry5minProcTime OBJECT-TYPE
    SYNTAX     DisplayString (SIZE(0..255))
    MAX-ACCESS read-only
    STATUS     current
    DESCRIPTION
            ""
    ::= { lcsStatusUtmCfPerfPerfLogEntry 21 }

-- {COLUMN} 1.3.6.1.4.1.2356.11.1.64.3.27.16.1.22
lcsStatusUtmCfPerfPerfLogEntryMinServTime OBJECT-TYPE
    SYNTAX     DisplayString (SIZE(0..255))
    MAX-ACCESS read-only
    STATUS     current
    DESCRIPTION
            ""
    ::= { lcsStatusUtmCfPerfPerfLogEntry 22 }

-- {COLUMN} 1.3.6.1.4.1.2356.11.1.64.3.27.16.1.23
lcsStatusUtmCfPerfPerfLogEntryMaxServTime OBJECT-TYPE
    SYNTAX     DisplayString (SIZE(0..255))
    MAX-ACCESS read-only
    STATUS     current
    DESCRIPTION
            ""
    ::= { lcsStatusUtmCfPerfPerfLogEntry 23 }

-- {COLUMN} 1.3.6.1.4.1.2356.11.1.64.3.27.16.1.24
lcsStatusUtmCfPerfPerfLogEntryAvgServTime OBJECT-TYPE
    SYNTAX     DisplayString (SIZE(0..255))
    MAX-ACCESS read-only
    STATUS     current
    DESCRIPTION
            ""
    ::= { lcsStatusUtmCfPerfPerfLogEntry 24 }

-- {COLUMN} 1.3.6.1.4.1.2356.11.1.64.3.27.16.1.25
lcsStatusUtmCfPerfPerfLogEntry5minServTime OBJECT-TYPE
    SYNTAX     DisplayString (SIZE(0..255))
    MAX-ACCESS read-only
    STATUS     current
    DESCRIPTION
            ""
    ::= { lcsStatusUtmCfPerfPerfLogEntry 25 }

-- {SCALAR} 1.3.6.1.4.1.2356.11.1.64.3.27.17
lcsStatusUtmCfPerfResetPerfStat OBJECT-TYPE
    SYNTAX     DisplayString
    MAX-ACCESS read-write
    STATUS     current
    DESCRIPTION
            "Reset Performance Statistics"
    ::= { lcsStatusUtmCfPerf 17 }

-- {NODE} 1.3.6.1.4.1.2356.11.1.64.3.28
lcsStatusUtmCfProxConn OBJECT IDENTIFIER ::= { lcsStatusUtmCf 28 }

-- {SCALAR} 1.3.6.1.4.1.2356.11.1.64.3.28.1
lcsStatusUtmCfProxConnCurrentConnections OBJECT-TYPE
    SYNTAX     Integer32 (0..2147483647)
    MAX-ACCESS read-only
    STATUS     current
    DESCRIPTION
            ""
    ::= { lcsStatusUtmCfProxConn 1 }

-- {SCALAR} 1.3.6.1.4.1.2356.11.1.64.3.28.2
lcsStatusUtmCfProxConnProxyConnectionsLimit OBJECT-TYPE
    SYNTAX     Integer32 (0..2147483647)
    MAX-ACCESS read-only
    STATUS     current
    DESCRIPTION
            ""
    ::= { lcsStatusUtmCfProxConn 2 }

-- {SCALAR} 1.3.6.1.4.1.2356.11.1.64.3.28.3
lcsStatusUtmCfProxConnMaxConnections OBJECT-TYPE
    SYNTAX     Integer32 (0..2147483647)
    MAX-ACCESS read-only
    STATUS     current
    DESCRIPTION
            ""
    ::= { lcsStatusUtmCfProxConn 3 }

-- {SCALAR} 1.3.6.1.4.1.2356.11.1.64.3.28.4
lcsStatusUtmCfProxConnAvgConnections OBJECT-TYPE
    SYNTAX     Integer32 (0..2147483647)
    MAX-ACCESS read-only
    STATUS     current
    DESCRIPTION
            ""
    ::= { lcsStatusUtmCfProxConn 4 }

-- {SCALAR} 1.3.6.1.4.1.2356.11.1.64.3.28.5
lcsStatusUtmCfProxConn5minAvgConnections OBJECT-TYPE
    SYNTAX     Integer32 (0..2147483647)
    MAX-ACCESS read-only
    STATUS     current
    DESCRIPTION
            ""
    ::= { lcsStatusUtmCfProxConn 5 }

-- {SCALAR} 1.3.6.1.4.1.2356.11.1.64.3.28.6
lcsStatusUtmCfProxConnTotalConnections OBJECT-TYPE
    SYNTAX     Integer32 (0..2147483647)
    MAX-ACCESS read-only
    STATUS     current
    DESCRIPTION
            ""
    ::= { lcsStatusUtmCfProxConn 6 }

-- {SCALAR} 1.3.6.1.4.1.2356.11.1.64.3.28.7
lcsStatusUtmCfProxConnDeniedConnectionAttempts OBJECT-TYPE
    SYNTAX     Integer32 (0..2147483647)
    MAX-ACCESS read-only
    STATUS     current
    DESCRIPTION
            ""
    ::= { lcsStatusUtmCfProxConn 7 }

-- {SCALAR} 1.3.6.1.4.1.2356.11.1.64.3.28.8
lcsStatusUtmCfProxConnConnectionStatisticsSince OBJECT-TYPE
    SYNTAX     Counter32
    MAX-ACCESS read-only
    STATUS     current
    DESCRIPTION
            ""
    ::= { lcsStatusUtmCfProxConn 8 }

-- {SCALAR} 1.3.6.1.4.1.2356.11.1.64.3.28.9
lcsStatusUtmCfProxConnResetConnectionStatistics OBJECT-TYPE
    SYNTAX     DisplayString
    MAX-ACCESS read-write
    STATUS     current
    DESCRIPTION
            ""
    ::= { lcsStatusUtmCfProxConn 9 }

-- {NODE} 1.3.6.1.4.1.2356.11.1.64.3.29
lcsStatusUtmCfCache OBJECT IDENTIFIER ::= { lcsStatusUtmCf 29 }

-- {SCALAR} 1.3.6.1.4.1.2356.11.1.64.3.29.1
lcsStatusUtmCfCacheMaximumSize OBJECT-TYPE
    SYNTAX     Integer32 (0..2147483647)
    MAX-ACCESS read-only
    STATUS     current
    DESCRIPTION
            ""
    ::= { lcsStatusUtmCfCache 1 }

-- {SCALAR} 1.3.6.1.4.1.2356.11.1.64.3.29.2
lcsStatusUtmCfCacheCurrentSize OBJECT-TYPE
    SYNTAX     Integer32 (0..2147483647)
    MAX-ACCESS read-only
    STATUS     current
    DESCRIPTION
            ""
    ::= { lcsStatusUtmCfCache 2 }

-- {SCALAR} 1.3.6.1.4.1.2356.11.1.64.3.29.3
lcsStatusUtmCfCacheHitRatInPerc OBJECT-TYPE
    SYNTAX     Integer32 (0..2147483647)
    MAX-ACCESS read-only
    STATUS     current
    DESCRIPTION
            "Hit ratio in percent"
    ::= { lcsStatusUtmCfCache 3 }

-- {TABLE} 1.3.6.1.4.1.2356.11.1.64.3.29.4
lcsStatusUtmCfCacheTop10AllowedHostsTable OBJECT-TYPE
    SYNTAX     SEQUENCE OF LcsStatusUtmCfCacheTop10AllowedHostsEntry
    MAX-ACCESS not-accessible
    STATUS     current
    DESCRIPTION
            ""
    ::= { lcsStatusUtmCfCache 4 }

-- {ROW} 1.3.6.1.4.1.2356.11.1.64.3.29.4.1
lcsStatusUtmCfCacheTop10AllowedHostsEntry OBJECT-TYPE
    SYNTAX     LcsStatusUtmCfCacheTop10AllowedHostsEntry
    MAX-ACCESS not-accessible
    STATUS     current
    DESCRIPTION
            ""
    INDEX {
            lcsStatusUtmCfCacheTop10AllowedHostsEntryHost
          }
    ::= { lcsStatusUtmCfCacheTop10AllowedHostsTable 1 }

LcsStatusUtmCfCacheTop10AllowedHostsEntry ::= SEQUENCE {
            lcsStatusUtmCfCacheTop10AllowedHostsEntryHost DisplayString,
            lcsStatusUtmCfCacheTop10AllowedHostsEntryCat DisplayString,
            lcsStatusUtmCfCacheTop10AllowedHostsEntryCount Integer32
    }

-- {COLUMN} 1.3.6.1.4.1.2356.11.1.64.3.29.4.1.1
lcsStatusUtmCfCacheTop10AllowedHostsEntryHost OBJECT-TYPE
    SYNTAX     DisplayString (SIZE(0..255))
    MAX-ACCESS read-only
    STATUS     current
    DESCRIPTION
            ""
    ::= { lcsStatusUtmCfCacheTop10AllowedHostsEntry 1 }

-- {COLUMN} 1.3.6.1.4.1.2356.11.1.64.3.29.4.1.2
lcsStatusUtmCfCacheTop10AllowedHostsEntryCat OBJECT-TYPE
    SYNTAX     DisplayString (SIZE(0..255))
    MAX-ACCESS read-only
    STATUS     current
    DESCRIPTION
            "Category"
    ::= { lcsStatusUtmCfCacheTop10AllowedHostsEntry 2 }

-- {COLUMN} 1.3.6.1.4.1.2356.11.1.64.3.29.4.1.3
lcsStatusUtmCfCacheTop10AllowedHostsEntryCount OBJECT-TYPE
    SYNTAX     Integer32 (0..2147483647)
    MAX-ACCESS read-only
    STATUS     current
    DESCRIPTION
            ""
    ::= { lcsStatusUtmCfCacheTop10AllowedHostsEntry 3 }

-- {TABLE} 1.3.6.1.4.1.2356.11.1.64.3.29.5
lcsStatusUtmCfCacheTop10OverriddenHostsTable OBJECT-TYPE
    SYNTAX     SEQUENCE OF LcsStatusUtmCfCacheTop10OverriddenHostsEntry
    MAX-ACCESS not-accessible
    STATUS     current
    DESCRIPTION
            ""
    ::= { lcsStatusUtmCfCache 5 }

-- {ROW} 1.3.6.1.4.1.2356.11.1.64.3.29.5.1
lcsStatusUtmCfCacheTop10OverriddenHostsEntry OBJECT-TYPE
    SYNTAX     LcsStatusUtmCfCacheTop10OverriddenHostsEntry
    MAX-ACCESS not-accessible
    STATUS     current
    DESCRIPTION
            ""
    INDEX {
            lcsStatusUtmCfCacheTop10OverriddenHostsEntryHost
          }
    ::= { lcsStatusUtmCfCacheTop10OverriddenHostsTable 1 }

LcsStatusUtmCfCacheTop10OverriddenHostsEntry ::= SEQUENCE {
            lcsStatusUtmCfCacheTop10OverriddenHostsEntryHost DisplayString,
            lcsStatusUtmCfCacheTop10OverriddenHostsEntryCat DisplayString,
            lcsStatusUtmCfCacheTop10OverriddenHostsEntryCount Integer32
    }

-- {COLUMN} 1.3.6.1.4.1.2356.11.1.64.3.29.5.1.1
lcsStatusUtmCfCacheTop10OverriddenHostsEntryHost OBJECT-TYPE
    SYNTAX     DisplayString (SIZE(0..255))
    MAX-ACCESS read-only
    STATUS     current
    DESCRIPTION
            ""
    ::= { lcsStatusUtmCfCacheTop10OverriddenHostsEntry 1 }

-- {COLUMN} 1.3.6.1.4.1.2356.11.1.64.3.29.5.1.2
lcsStatusUtmCfCacheTop10OverriddenHostsEntryCat OBJECT-TYPE
    SYNTAX     DisplayString (SIZE(0..255))
    MAX-ACCESS read-only
    STATUS     current
    DESCRIPTION
            "Category"
    ::= { lcsStatusUtmCfCacheTop10OverriddenHostsEntry 2 }

-- {COLUMN} 1.3.6.1.4.1.2356.11.1.64.3.29.5.1.3
lcsStatusUtmCfCacheTop10OverriddenHostsEntryCount OBJECT-TYPE
    SYNTAX     Integer32 (0..2147483647)
    MAX-ACCESS read-only
    STATUS     current
    DESCRIPTION
            ""
    ::= { lcsStatusUtmCfCacheTop10OverriddenHostsEntry 3 }

-- {TABLE} 1.3.6.1.4.1.2356.11.1.64.3.29.6
lcsStatusUtmCfCacheTop10BlockedHostsTable OBJECT-TYPE
    SYNTAX     SEQUENCE OF LcsStatusUtmCfCacheTop10BlockedHostsEntry
    MAX-ACCESS not-accessible
    STATUS     current
    DESCRIPTION
            ""
    ::= { lcsStatusUtmCfCache 6 }

-- {ROW} 1.3.6.1.4.1.2356.11.1.64.3.29.6.1
lcsStatusUtmCfCacheTop10BlockedHostsEntry OBJECT-TYPE
    SYNTAX     LcsStatusUtmCfCacheTop10BlockedHostsEntry
    MAX-ACCESS not-accessible
    STATUS     current
    DESCRIPTION
            ""
    INDEX {
            lcsStatusUtmCfCacheTop10BlockedHostsEntryHost
          }
    ::= { lcsStatusUtmCfCacheTop10BlockedHostsTable 1 }

LcsStatusUtmCfCacheTop10BlockedHostsEntry ::= SEQUENCE {
            lcsStatusUtmCfCacheTop10BlockedHostsEntryHost DisplayString,
            lcsStatusUtmCfCacheTop10BlockedHostsEntryCat DisplayString,
            lcsStatusUtmCfCacheTop10BlockedHostsEntryCount Integer32
    }

-- {COLUMN} 1.3.6.1.4.1.2356.11.1.64.3.29.6.1.1
lcsStatusUtmCfCacheTop10BlockedHostsEntryHost OBJECT-TYPE
    SYNTAX     DisplayString (SIZE(0..255))
    MAX-ACCESS read-only
    STATUS     current
    DESCRIPTION
            ""
    ::= { lcsStatusUtmCfCacheTop10BlockedHostsEntry 1 }

-- {COLUMN} 1.3.6.1.4.1.2356.11.1.64.3.29.6.1.2
lcsStatusUtmCfCacheTop10BlockedHostsEntryCat OBJECT-TYPE
    SYNTAX     DisplayString (SIZE(0..255))
    MAX-ACCESS read-only
    STATUS     current
    DESCRIPTION
            "Category"
    ::= { lcsStatusUtmCfCacheTop10BlockedHostsEntry 2 }

-- {COLUMN} 1.3.6.1.4.1.2356.11.1.64.3.29.6.1.3
lcsStatusUtmCfCacheTop10BlockedHostsEntryCount OBJECT-TYPE
    SYNTAX     Integer32 (0..2147483647)
    MAX-ACCESS read-only
    STATUS     current
    DESCRIPTION
            ""
    ::= { lcsStatusUtmCfCacheTop10BlockedHostsEntry 3 }

-- {SCALAR} 1.3.6.1.4.1.2356.11.1.64.3.29.7
lcsStatusUtmCfCacheCacheFlush OBJECT-TYPE
    SYNTAX     DisplayString
    MAX-ACCESS read-write
    STATUS     current
    DESCRIPTION
            ""
    ::= { lcsStatusUtmCfCache 7 }

-- {SCALAR} 1.3.6.1.4.1.2356.11.1.64.3.255
lcsStatusUtmCfOperating OBJECT-TYPE
    SYNTAX     INTEGER {
                  eNo (0),
                  eYes (1)
            }
    MAX-ACCESS read-only
    STATUS     current
    DESCRIPTION
            ""
    ::= { lcsStatusUtmCf 255 }

-- {NODE} 1.3.6.1.4.1.2356.11.1.67
lcsStatusComPorts OBJECT IDENTIFIER ::= { lcsStatus 67 }

-- {TABLE} 1.3.6.1.4.1.2356.11.1.67.1
lcsStatusComPortsDevTable OBJECT-TYPE
    SYNTAX     SEQUENCE OF LcsStatusComPortsDevEntry
    MAX-ACCESS not-accessible
    STATUS     current
    DESCRIPTION
            ""
    ::= { lcsStatusComPorts 1 }

-- {ROW} 1.3.6.1.4.1.2356.11.1.67.1.1
lcsStatusComPortsDevEntry OBJECT-TYPE
    SYNTAX     LcsStatusComPortsDevEntry
    MAX-ACCESS not-accessible
    STATUS     current
    DESCRIPTION
            ""
    INDEX {
            lcsStatusComPortsDevEntryIndex
          }
    ::= { lcsStatusComPortsDevTable 1 }

LcsStatusComPortsDevEntry ::= SEQUENCE {
            lcsStatusComPortsDevEntryIndex Integer32,
            lcsStatusComPortsDevEntryDeviceType INTEGER,
            lcsStatusComPortsDevEntryBus INTEGER,
            lcsStatusComPortsDevEntryDevice Integer32,
            lcsStatusComPortsDevEntryVendor Integer32,
            lcsStatusComPortsDevEntryUsbDriver INTEGER,
            lcsStatusComPortsDevEntryState INTEGER,
            lcsStatusComPortsDevEntryFirmwareVersion DisplayString,
            lcsStatusComPortsDevEntryServ INTEGER,
            lcsStatusComPortsDevEntryFullName DisplayString
    }

-- {COLUMN} 1.3.6.1.4.1.2356.11.1.67.1.1.1
lcsStatusComPortsDevEntryIndex OBJECT-TYPE
    SYNTAX     Integer32 (0..2147483647)
    MAX-ACCESS read-only
    STATUS     current
    DESCRIPTION
            ""
    ::= { lcsStatusComPortsDevEntry 1 }

-- {COLUMN} 1.3.6.1.4.1.2356.11.1.67.1.1.2
lcsStatusComPortsDevEntryDeviceType OBJECT-TYPE
    SYNTAX     INTEGER {
                  eOutband (1),
                  eOutbandModem (2),
                  eSierraMinicard8780 (11),
                  eSierraMinicard8781 (12),
                  eOptionIcon (17),
                  eOptionMinicard0201 (19),
                  eHuaweiE612E630E1750 (21),
                  e4gSystemsUxs1 (23),
                  eNovatelMerlinMc950d (26),
                  eSierraAircard875u (30),
                  eHuaweiE172E220E870 (31),
                  eBelkinF5u103 (33),
                  eProlific2303 (34),
                  eFtdi8u232am (35),
                  eGpsNmea (36),
                  eSierraMinicard8790 (38),
                  eSierraCompass885 (39),
                  eQualcomDm (45),
                  eSierraAircard501 (46),
                  eHuaweiK4505 (49),
                  eHuaweiK3765 (51),
                  eSierraDirectIp (53),
                  eHuaweiE182 (54),
                  eSierraMinicard8705 (55),
                  eSierraMinicard8801 (56),
                  eHuaweiE1750 (57),
                  eNokiaCs19 (59),
                  eHuaweiE398 (60),
                  eHuaweiE1550 (61),
                  eSierraMinicard7710 (62),
                  eHuaweiE352 (64),
                  eSierraQmi73xx (66),
                  eSierraQmi74xx (67),
                  eSierraQmi73xxBootloader (68),
                  eSierraQmi74xxBootloader (69),
                  eSierraDipBootloader (70),
                  eUsbSerialAdapter (72),
                  eSubghzModule (73),
                  eSierraQmi75xx (74),
                  eSierraQmi75xxBootloader (75),
                  eModuleConsole (76),
                  eFtdi232h (77)
            }
    MAX-ACCESS read-only
    STATUS     current
    DESCRIPTION
            ""
    ::= { lcsStatusComPortsDevEntry 2 }

-- {COLUMN} 1.3.6.1.4.1.2356.11.1.67.1.1.3
lcsStatusComPortsDevEntryBus OBJECT-TYPE
    SYNTAX     INTEGER {
                  eOutband (1),
                  eCardbus (2),
                  eUsb (3),
                  eVirtual (4)
            }
    MAX-ACCESS read-only
    STATUS     current
    DESCRIPTION
            ""
    ::= { lcsStatusComPortsDevEntry 3 }

-- {COLUMN} 1.3.6.1.4.1.2356.11.1.67.1.1.4
lcsStatusComPortsDevEntryDevice OBJECT-TYPE
    SYNTAX     Integer32 (0..65535)
    MAX-ACCESS read-only
    STATUS     current
    DESCRIPTION
            ""
    ::= { lcsStatusComPortsDevEntry 4 }

-- {COLUMN} 1.3.6.1.4.1.2356.11.1.67.1.1.5
lcsStatusComPortsDevEntryVendor OBJECT-TYPE
    SYNTAX     Integer32 (0..65535)
    MAX-ACCESS read-only
    STATUS     current
    DESCRIPTION
            ""
    ::= { lcsStatusComPortsDevEntry 5 }

-- {COLUMN} 1.3.6.1.4.1.2356.11.1.67.1.1.11
lcsStatusComPortsDevEntryUsbDriver OBJECT-TYPE
    SYNTAX     INTEGER {
                  eNone (0),
                  eUbsa (1),
                  eUchcom (2),
                  eUftdi (3),
                  eUgensa (4),
                  eUhmodem (5),
                  eUkyopon (6),
                  eUplcom (7),
                  eUslsa (8),
                  eUcdcacm (10),
                  eUcp210x (11),
                  eUch34x (12)
            }
    MAX-ACCESS read-only
    STATUS     current
    DESCRIPTION
            ""
    ::= { lcsStatusComPortsDevEntry 11 }

-- {COLUMN} 1.3.6.1.4.1.2356.11.1.67.1.1.13
lcsStatusComPortsDevEntryState OBJECT-TYPE
    SYNTAX     INTEGER {
                  eUnknown (0),
                  eInitialize (1),
                  eWaitForFirmware (2),
                  eReady (3),
                  eInUse (4),
                  eExclusive (5),
                  eInitialize2 (6),
                  eResetting (7)
            }
    MAX-ACCESS read-only
    STATUS     current
    DESCRIPTION
            ""
    ::= { lcsStatusComPortsDevEntry 13 }

-- {COLUMN} 1.3.6.1.4.1.2356.11.1.67.1.1.14
lcsStatusComPortsDevEntryFirmwareVersion OBJECT-TYPE
    SYNTAX     DisplayString (SIZE(0..63))
    MAX-ACCESS read-only
    STATUS     current
    DESCRIPTION
            ""
    ::= { lcsStatusComPortsDevEntry 14 }

-- {COLUMN} 1.3.6.1.4.1.2356.11.1.67.1.1.15
lcsStatusComPortsDevEntryServ OBJECT-TYPE
    SYNTAX     INTEGER {
                  eWan (1),
                  eCOMPortServ (2),
                  eBootloader (4),
                  eUps (8),
                  eEpaper (16)
            }
    MAX-ACCESS read-only
    STATUS     current
    DESCRIPTION
            ""
    ::= { lcsStatusComPortsDevEntry 15 }

-- {COLUMN} 1.3.6.1.4.1.2356.11.1.67.1.1.99
lcsStatusComPortsDevEntryFullName OBJECT-TYPE
    SYNTAX     DisplayString (SIZE(0..31))
    MAX-ACCESS read-only
    STATUS     current
    DESCRIPTION
            ""
    ::= { lcsStatusComPortsDevEntry 99 }

-- {NODE} 1.3.6.1.4.1.2356.11.1.67.2
lcsStatusComPortsComPortServer OBJECT IDENTIFIER ::= { lcsStatusComPorts 2 }

-- {TABLE} 1.3.6.1.4.1.2356.11.1.67.2.1
lcsStatusComPortsComPortServerNetworkStatusTable OBJECT-TYPE
    SYNTAX     SEQUENCE OF LcsStatusComPortsComPortServerNetworkStatusEntry
    MAX-ACCESS not-accessible
    STATUS     current
    DESCRIPTION
            ""
    ::= { lcsStatusComPortsComPortServer 1 }

-- {ROW} 1.3.6.1.4.1.2356.11.1.67.2.1.1
lcsStatusComPortsComPortServerNetworkStatusEntry OBJECT-TYPE
    SYNTAX     LcsStatusComPortsComPortServerNetworkStatusEntry
    MAX-ACCESS not-accessible
    STATUS     current
    DESCRIPTION
            ""
    INDEX {
            lcsStatusComPortsComPortServerNetworkStatusEntryDeviceType,
            lcsStatusComPortsComPortServerNetworkStatusEntryPortNumber
          }
    ::= { lcsStatusComPortsComPortServerNetworkStatusTable 1 }

LcsStatusComPortsComPortServerNetworkStatusEntry ::= SEQUENCE {
            lcsStatusComPortsComPortServerNetworkStatusEntryDeviceType INTEGER,
            lcsStatusComPortsComPortServerNetworkStatusEntryPortNumber Integer32,
            lcsStatusComPortsComPortServerNetworkStatusEntryConnectionStatus INTEGER,
            lcsStatusComPortsComPortServerNetworkStatusEntryLastError INTEGER,
            lcsStatusComPortsComPortServerNetworkStatusEntryRemoteAddress IpAddress,
            lcsStatusComPortsComPortServerNetworkStatusEntryLocalPort Integer32,
            lcsStatusComPortsComPortServerNetworkStatusEntryRemotePort Integer32,
            lcsStatusComPortsComPortServerNetworkStatusEntryRemoteIpv6Addr IpAddress,
            lcsStatusComPortsComPortServerNetworkStatusEntryFullName DisplayString
    }

-- {COLUMN} 1.3.6.1.4.1.2356.11.1.67.2.1.1.1
lcsStatusComPortsComPortServerNetworkStatusEntryDeviceType OBJECT-TYPE
    SYNTAX     INTEGER {
                  eOutband (1),
                  eBelkinF5u103 (33),
                  eProlific2303 (34),
                  eFtdi8u232am (35),
                  eGpsNmea (36),
                  eQualcomDm (45),
                  eUsbSerialAdapter (72),
                  eSubghzModule (73),
                  eModuleConsole (76),
                  eFtdi232h (77)
            }
    MAX-ACCESS read-only
    STATUS     current
    DESCRIPTION
            ""
    ::= { lcsStatusComPortsComPortServerNetworkStatusEntry 1 }

-- {COLUMN} 1.3.6.1.4.1.2356.11.1.67.2.1.1.2
lcsStatusComPortsComPortServerNetworkStatusEntryPortNumber OBJECT-TYPE
    SYNTAX     Integer32 (0..255)
    MAX-ACCESS read-only
    STATUS     current
    DESCRIPTION
            ""
    ::= { lcsStatusComPortsComPortServerNetworkStatusEntry 2 }

-- {COLUMN} 1.3.6.1.4.1.2356.11.1.67.2.1.1.4
lcsStatusComPortsComPortServerNetworkStatusEntryConnectionStatus OBJECT-TYPE
    SYNTAX     INTEGER {
                  eIdle (0),
                  eListening (1),
                  eConnecting (2),
                  eConnected (3),
                  eNotListening (4),
                  eConErrBackoff (5)
            }
    MAX-ACCESS read-only
    STATUS     current
    DESCRIPTION
            ""
    ::= { lcsStatusComPortsComPortServerNetworkStatusEntry 4 }

-- {COLUMN} 1.3.6.1.4.1.2356.11.1.67.2.1.1.5
lcsStatusComPortsComPortServerNetworkStatusEntryLastError OBJECT-TYPE
    SYNTAX     INTEGER {
                  eNone (0),
                  eDnsError (1),
                  eTCPConnErr (2),
                  eRemDisc (3)
            }
    MAX-ACCESS read-only
    STATUS     current
    DESCRIPTION
            ""
    ::= { lcsStatusComPortsComPortServerNetworkStatusEntry 5 }

-- {COLUMN} 1.3.6.1.4.1.2356.11.1.67.2.1.1.6
lcsStatusComPortsComPortServerNetworkStatusEntryRemoteAddress OBJECT-TYPE
    SYNTAX     IpAddress
    MAX-ACCESS read-only
    STATUS     current
    DESCRIPTION
            ""
    ::= { lcsStatusComPortsComPortServerNetworkStatusEntry 6 }

-- {COLUMN} 1.3.6.1.4.1.2356.11.1.67.2.1.1.7
lcsStatusComPortsComPortServerNetworkStatusEntryLocalPort OBJECT-TYPE
    SYNTAX     Integer32 (0..65535)
    MAX-ACCESS read-only
    STATUS     current
    DESCRIPTION
            ""
    ::= { lcsStatusComPortsComPortServerNetworkStatusEntry 7 }

-- {COLUMN} 1.3.6.1.4.1.2356.11.1.67.2.1.1.8
lcsStatusComPortsComPortServerNetworkStatusEntryRemotePort OBJECT-TYPE
    SYNTAX     Integer32 (0..65535)
    MAX-ACCESS read-only
    STATUS     current
    DESCRIPTION
            ""
    ::= { lcsStatusComPortsComPortServerNetworkStatusEntry 8 }

-- {COLUMN} 1.3.6.1.4.1.2356.11.1.67.2.1.1.10
lcsStatusComPortsComPortServerNetworkStatusEntryRemoteIpv6Addr OBJECT-TYPE
    SYNTAX     IpAddress
    MAX-ACCESS read-only
    STATUS     current
    DESCRIPTION
            ""
    ::= { lcsStatusComPortsComPortServerNetworkStatusEntry 10 }

-- {COLUMN} 1.3.6.1.4.1.2356.11.1.67.2.1.1.99
lcsStatusComPortsComPortServerNetworkStatusEntryFullName OBJECT-TYPE
    SYNTAX     DisplayString (SIZE(0..255))
    MAX-ACCESS read-only
    STATUS     current
    DESCRIPTION
            ""
    ::= { lcsStatusComPortsComPortServerNetworkStatusEntry 99 }

-- {TABLE} 1.3.6.1.4.1.2356.11.1.67.2.2
lcsStatusComPortsComPortServerComPortStatusTable OBJECT-TYPE
    SYNTAX     SEQUENCE OF LcsStatusComPortsComPortServerComPortStatusEntry
    MAX-ACCESS not-accessible
    STATUS     current
    DESCRIPTION
            ""
    ::= { lcsStatusComPortsComPortServer 2 }

-- {ROW} 1.3.6.1.4.1.2356.11.1.67.2.2.1
lcsStatusComPortsComPortServerComPortStatusEntry OBJECT-TYPE
    SYNTAX     LcsStatusComPortsComPortServerComPortStatusEntry
    MAX-ACCESS not-accessible
    STATUS     current
    DESCRIPTION
            ""
    INDEX {
            lcsStatusComPortsComPortServerComPortStatusEntryDeviceType,
            lcsStatusComPortsComPortServerComPortStatusEntryPortNumber
          }
    ::= { lcsStatusComPortsComPortServerComPortStatusTable 1 }

LcsStatusComPortsComPortServerComPortStatusEntry ::= SEQUENCE {
            lcsStatusComPortsComPortServerComPortStatusEntryDeviceType INTEGER,
            lcsStatusComPortsComPortServerComPortStatusEntryPortNumber Integer32,
            lcsStatusComPortsComPortServerComPortStatusEntryInterfaceStatus INTEGER,
            lcsStatusComPortsComPortServerComPortStatusEntryBitRate INTEGER,
            lcsStatusComPortsComPortServerComPortStatusEntryDataBits INTEGER,
            lcsStatusComPortsComPortServerComPortStatusEntryParity INTEGER,
            lcsStatusComPortsComPortServerComPortStatusEntryStopBits INTEGER,
            lcsStatusComPortsComPortServerComPortStatusEntryHandshake INTEGER,
            lcsStatusComPortsComPortServerComPortStatusEntryFullName DisplayString
    }

-- {COLUMN} 1.3.6.1.4.1.2356.11.1.67.2.2.1.1
lcsStatusComPortsComPortServerComPortStatusEntryDeviceType OBJECT-TYPE
    SYNTAX     INTEGER {
                  eOutband (1),
                  eBelkinF5u103 (33),
                  eProlific2303 (34),
                  eFtdi8u232am (35),
                  eGpsNmea (36),
                  eQualcomDm (45),
                  eUsbSerialAdapter (72),
                  eSubghzModule (73),
                  eModuleConsole (76),
                  eFtdi232h (77)
            }
    MAX-ACCESS read-only
    STATUS     current
    DESCRIPTION
            ""
    ::= { lcsStatusComPortsComPortServerComPortStatusEntry 1 }

-- {COLUMN} 1.3.6.1.4.1.2356.11.1.67.2.2.1.2
lcsStatusComPortsComPortServerComPortStatusEntryPortNumber OBJECT-TYPE
    SYNTAX     Integer32 (0..255)
    MAX-ACCESS read-only
    STATUS     current
    DESCRIPTION
            ""
    ::= { lcsStatusComPortsComPortServerComPortStatusEntry 2 }

-- {COLUMN} 1.3.6.1.4.1.2356.11.1.67.2.2.1.4
lcsStatusComPortsComPortServerComPortStatusEntryInterfaceStatus OBJECT-TYPE
    SYNTAX     INTEGER {
                  eNotPresent (0),
                  eNotReady (1),
                  eReady (2)
            }
    MAX-ACCESS read-only
    STATUS     current
    DESCRIPTION
            ""
    ::= { lcsStatusComPortsComPortServerComPortStatusEntry 4 }

-- {COLUMN} 1.3.6.1.4.1.2356.11.1.67.2.2.1.5
lcsStatusComPortsComPortServerComPortStatusEntryBitRate OBJECT-TYPE
    SYNTAX     INTEGER {
                  e110 (110),
                  e300 (300),
                  e600 (600),
                  e1200 (1200),
                  e2400 (2400),
                  e4800 (4800),
                  e9600 (9600),
                  e19200 (19200),
                  e38400 (38400),
                  e57600 (57600),
                  e74880 (74880),
                  e76800 (76800),
                  e115200 (115200),
                  e125000 (125000),
                  e230400 (230400),
                  e460800 (460800),
                  e921600 (921600),
                  e1000000 (1000000),
                  e1500000 (1500000),
                  e2000000 (2000000),
                  e3000000 (3000000)
            }
    MAX-ACCESS read-only
    STATUS     current
    DESCRIPTION
            ""
    ::= { lcsStatusComPortsComPortServerComPortStatusEntry 5 }

-- {COLUMN} 1.3.6.1.4.1.2356.11.1.67.2.2.1.6
lcsStatusComPortsComPortServerComPortStatusEntryDataBits OBJECT-TYPE
    SYNTAX     INTEGER {
                  e7 (7),
                  e8 (8)
            }
    MAX-ACCESS read-only
    STATUS     current
    DESCRIPTION
            ""
    ::= { lcsStatusComPortsComPortServerComPortStatusEntry 6 }

-- {COLUMN} 1.3.6.1.4.1.2356.11.1.67.2.2.1.7
lcsStatusComPortsComPortServerComPortStatusEntryParity OBJECT-TYPE
    SYNTAX     INTEGER {
                  eNone (1),
                  eOdd (2),
                  eEven (3)
            }
    MAX-ACCESS read-only
    STATUS     current
    DESCRIPTION
            ""
    ::= { lcsStatusComPortsComPortServerComPortStatusEntry 7 }

-- {COLUMN} 1.3.6.1.4.1.2356.11.1.67.2.2.1.8
lcsStatusComPortsComPortServerComPortStatusEntryStopBits OBJECT-TYPE
    SYNTAX     INTEGER {
                  e1 (1),
                  e2 (2)
            }
    MAX-ACCESS read-only
    STATUS     current
    DESCRIPTION
            ""
    ::= { lcsStatusComPortsComPortServerComPortStatusEntry 8 }

-- {COLUMN} 1.3.6.1.4.1.2356.11.1.67.2.2.1.9
lcsStatusComPortsComPortServerComPortStatusEntryHandshake OBJECT-TYPE
    SYNTAX     INTEGER {
                  eNone (0),
                  eRtsCts (1)
            }
    MAX-ACCESS read-only
    STATUS     current
    DESCRIPTION
            ""
    ::= { lcsStatusComPortsComPortServerComPortStatusEntry 9 }

-- {COLUMN} 1.3.6.1.4.1.2356.11.1.67.2.2.1.99
lcsStatusComPortsComPortServerComPortStatusEntryFullName OBJECT-TYPE
    SYNTAX     DisplayString (SIZE(0..255))
    MAX-ACCESS read-only
    STATUS     current
    DESCRIPTION
            ""
    ::= { lcsStatusComPortsComPortServerComPortStatusEntry 99 }

-- {TABLE} 1.3.6.1.4.1.2356.11.1.67.2.3
lcsStatusComPortsComPortServerByteCountersTable OBJECT-TYPE
    SYNTAX     SEQUENCE OF LcsStatusComPortsComPortServerByteCountersEntry
    MAX-ACCESS not-accessible
    STATUS     current
    DESCRIPTION
            ""
    ::= { lcsStatusComPortsComPortServer 3 }

-- {ROW} 1.3.6.1.4.1.2356.11.1.67.2.3.1
lcsStatusComPortsComPortServerByteCountersEntry OBJECT-TYPE
    SYNTAX     LcsStatusComPortsComPortServerByteCountersEntry
    MAX-ACCESS not-accessible
    STATUS     current
    DESCRIPTION
            ""
    INDEX {
            lcsStatusComPortsComPortServerByteCountersEntryDeviceType,
            lcsStatusComPortsComPortServerByteCountersEntryPortNumber
          }
    ::= { lcsStatusComPortsComPortServerByteCountersTable 1 }

LcsStatusComPortsComPortServerByteCountersEntry ::= SEQUENCE {
            lcsStatusComPortsComPortServerByteCountersEntryDeviceType INTEGER,
            lcsStatusComPortsComPortServerByteCountersEntryPortNumber Integer32,
            lcsStatusComPortsComPortServerByteCountersEntrySerialTx Integer32,
            lcsStatusComPortsComPortServerByteCountersEntrySerialRx Integer32,
            lcsStatusComPortsComPortServerByteCountersEntryNetworkTx Integer32,
            lcsStatusComPortsComPortServerByteCountersEntryNetworkRx Integer32,
            lcsStatusComPortsComPortServerByteCountersEntryFullName DisplayString
    }

-- {COLUMN} 1.3.6.1.4.1.2356.11.1.67.2.3.1.1
lcsStatusComPortsComPortServerByteCountersEntryDeviceType OBJECT-TYPE
    SYNTAX     INTEGER {
                  eOutband (1),
                  eBelkinF5u103 (33),
                  eProlific2303 (34),
                  eFtdi8u232am (35),
                  eGpsNmea (36),
                  eQualcomDm (45),
                  eUsbSerialAdapter (72),
                  eSubghzModule (73),
                  eModuleConsole (76),
                  eFtdi232h (77)
            }
    MAX-ACCESS read-only
    STATUS     current
    DESCRIPTION
            ""
    ::= { lcsStatusComPortsComPortServerByteCountersEntry 1 }

-- {COLUMN} 1.3.6.1.4.1.2356.11.1.67.2.3.1.2
lcsStatusComPortsComPortServerByteCountersEntryPortNumber OBJECT-TYPE
    SYNTAX     Integer32 (0..255)
    MAX-ACCESS read-only
    STATUS     current
    DESCRIPTION
            ""
    ::= { lcsStatusComPortsComPortServerByteCountersEntry 2 }

-- {COLUMN} 1.3.6.1.4.1.2356.11.1.67.2.3.1.4
lcsStatusComPortsComPortServerByteCountersEntrySerialTx OBJECT-TYPE
    SYNTAX     Integer32 (0..2147483647)
    MAX-ACCESS read-only
    STATUS     current
    DESCRIPTION
            ""
    ::= { lcsStatusComPortsComPortServerByteCountersEntry 4 }

-- {COLUMN} 1.3.6.1.4.1.2356.11.1.67.2.3.1.5
lcsStatusComPortsComPortServerByteCountersEntrySerialRx OBJECT-TYPE
    SYNTAX     Integer32 (0..2147483647)
    MAX-ACCESS read-only
    STATUS     current
    DESCRIPTION
            ""
    ::= { lcsStatusComPortsComPortServerByteCountersEntry 5 }

-- {COLUMN} 1.3.6.1.4.1.2356.11.1.67.2.3.1.6
lcsStatusComPortsComPortServerByteCountersEntryNetworkTx OBJECT-TYPE
    SYNTAX     Integer32 (0..2147483647)
    MAX-ACCESS read-only
    STATUS     current
    DESCRIPTION
            ""
    ::= { lcsStatusComPortsComPortServerByteCountersEntry 6 }

-- {COLUMN} 1.3.6.1.4.1.2356.11.1.67.2.3.1.7
lcsStatusComPortsComPortServerByteCountersEntryNetworkRx OBJECT-TYPE
    SYNTAX     Integer32 (0..2147483647)
    MAX-ACCESS read-only
    STATUS     current
    DESCRIPTION
            ""
    ::= { lcsStatusComPortsComPortServerByteCountersEntry 7 }

-- {COLUMN} 1.3.6.1.4.1.2356.11.1.67.2.3.1.99
lcsStatusComPortsComPortServerByteCountersEntryFullName OBJECT-TYPE
    SYNTAX     DisplayString (SIZE(0..255))
    MAX-ACCESS read-only
    STATUS     current
    DESCRIPTION
            ""
    ::= { lcsStatusComPortsComPortServerByteCountersEntry 99 }

-- {TABLE} 1.3.6.1.4.1.2356.11.1.67.2.4
lcsStatusComPortsComPortServerComPortErrorsTable OBJECT-TYPE
    SYNTAX     SEQUENCE OF LcsStatusComPortsComPortServerComPortErrorsEntry
    MAX-ACCESS not-accessible
    STATUS     current
    DESCRIPTION
            ""
    ::= { lcsStatusComPortsComPortServer 4 }

-- {ROW} 1.3.6.1.4.1.2356.11.1.67.2.4.1
lcsStatusComPortsComPortServerComPortErrorsEntry OBJECT-TYPE
    SYNTAX     LcsStatusComPortsComPortServerComPortErrorsEntry
    MAX-ACCESS not-accessible
    STATUS     current
    DESCRIPTION
            ""
    INDEX {
            lcsStatusComPortsComPortServerComPortErrorsEntryDeviceType,
            lcsStatusComPortsComPortServerComPortErrorsEntryPortNumber
          }
    ::= { lcsStatusComPortsComPortServerComPortErrorsTable 1 }

LcsStatusComPortsComPortServerComPortErrorsEntry ::= SEQUENCE {
            lcsStatusComPortsComPortServerComPortErrorsEntryDeviceType INTEGER,
            lcsStatusComPortsComPortServerComPortErrorsEntryPortNumber Integer32,
            lcsStatusComPortsComPortServerComPortErrorsEntryParityErrors Integer32,
            lcsStatusComPortsComPortServerComPortErrorsEntryFramingErrors Integer32,
            lcsStatusComPortsComPortServerComPortErrorsEntryRxLostErrors Integer32,
            lcsStatusComPortsComPortServerComPortErrorsEntryFullName DisplayString
    }

-- {COLUMN} 1.3.6.1.4.1.2356.11.1.67.2.4.1.1
lcsStatusComPortsComPortServerComPortErrorsEntryDeviceType OBJECT-TYPE
    SYNTAX     INTEGER {
                  eOutband (1),
                  eBelkinF5u103 (33),
                  eProlific2303 (34),
                  eFtdi8u232am (35),
                  eGpsNmea (36),
                  eQualcomDm (45),
                  eUsbSerialAdapter (72),
                  eSubghzModule (73),
                  eModuleConsole (76),
                  eFtdi232h (77)
            }
    MAX-ACCESS read-only
    STATUS     current
    DESCRIPTION
            ""
    ::= { lcsStatusComPortsComPortServerComPortErrorsEntry 1 }

-- {COLUMN} 1.3.6.1.4.1.2356.11.1.67.2.4.1.2
lcsStatusComPortsComPortServerComPortErrorsEntryPortNumber OBJECT-TYPE
    SYNTAX     Integer32 (0..255)
    MAX-ACCESS read-only
    STATUS     current
    DESCRIPTION
            ""
    ::= { lcsStatusComPortsComPortServerComPortErrorsEntry 2 }

-- {COLUMN} 1.3.6.1.4.1.2356.11.1.67.2.4.1.4
lcsStatusComPortsComPortServerComPortErrorsEntryParityErrors OBJECT-TYPE
    SYNTAX     Integer32 (0..2147483647)
    MAX-ACCESS read-only
    STATUS     current
    DESCRIPTION
            ""
    ::= { lcsStatusComPortsComPortServerComPortErrorsEntry 4 }

-- {COLUMN} 1.3.6.1.4.1.2356.11.1.67.2.4.1.5
lcsStatusComPortsComPortServerComPortErrorsEntryFramingErrors OBJECT-TYPE
    SYNTAX     Integer32 (0..2147483647)
    MAX-ACCESS read-only
    STATUS     current
    DESCRIPTION
            ""
    ::= { lcsStatusComPortsComPortServerComPortErrorsEntry 5 }

-- {COLUMN} 1.3.6.1.4.1.2356.11.1.67.2.4.1.6
lcsStatusComPortsComPortServerComPortErrorsEntryRxLostErrors OBJECT-TYPE
    SYNTAX     Integer32 (0..2147483647)
    MAX-ACCESS read-only
    STATUS     current
    DESCRIPTION
            ""
    ::= { lcsStatusComPortsComPortServerComPortErrorsEntry 6 }

-- {COLUMN} 1.3.6.1.4.1.2356.11.1.67.2.4.1.99
lcsStatusComPortsComPortServerComPortErrorsEntryFullName OBJECT-TYPE
    SYNTAX     DisplayString (SIZE(0..255))
    MAX-ACCESS read-only
    STATUS     current
    DESCRIPTION
            ""
    ::= { lcsStatusComPortsComPortServerComPortErrorsEntry 99 }

-- {TABLE} 1.3.6.1.4.1.2356.11.1.67.2.5
lcsStatusComPortsComPortServerConnTable OBJECT-TYPE
    SYNTAX     SEQUENCE OF LcsStatusComPortsComPortServerConnEntry
    MAX-ACCESS not-accessible
    STATUS     current
    DESCRIPTION
            ""
    ::= { lcsStatusComPortsComPortServer 5 }

-- {ROW} 1.3.6.1.4.1.2356.11.1.67.2.5.1
lcsStatusComPortsComPortServerConnEntry OBJECT-TYPE
    SYNTAX     LcsStatusComPortsComPortServerConnEntry
    MAX-ACCESS not-accessible
    STATUS     current
    DESCRIPTION
            ""
    INDEX {
            lcsStatusComPortsComPortServerConnEntryDeviceType,
            lcsStatusComPortsComPortServerConnEntryPortNumber
          }
    ::= { lcsStatusComPortsComPortServerConnTable 1 }

LcsStatusComPortsComPortServerConnEntry ::= SEQUENCE {
            lcsStatusComPortsComPortServerConnEntryDeviceType INTEGER,
            lcsStatusComPortsComPortServerConnEntryPortNumber Integer32,
            lcsStatusComPortsComPortServerConnEntryServGrant Integer32,
            lcsStatusComPortsComPortServerConnEntryServRej Integer32,
            lcsStatusComPortsComPortServerConnEntryClntSucc Integer32,
            lcsStatusComPortsComPortServerConnEntryClntDnsErr Integer32,
            lcsStatusComPortsComPortServerConnEntryClntTcpErr Integer32,
            lcsStatusComPortsComPortServerConnEntryClntRemDisc Integer32,
            lcsStatusComPortsComPortServerConnEntryFullName DisplayString
    }

-- {COLUMN} 1.3.6.1.4.1.2356.11.1.67.2.5.1.1
lcsStatusComPortsComPortServerConnEntryDeviceType OBJECT-TYPE
    SYNTAX     INTEGER {
                  eOutband (1),
                  eBelkinF5u103 (33),
                  eProlific2303 (34),
                  eFtdi8u232am (35),
                  eGpsNmea (36),
                  eQualcomDm (45),
                  eUsbSerialAdapter (72),
                  eSubghzModule (73),
                  eModuleConsole (76),
                  eFtdi232h (77)
            }
    MAX-ACCESS read-only
    STATUS     current
    DESCRIPTION
            ""
    ::= { lcsStatusComPortsComPortServerConnEntry 1 }

-- {COLUMN} 1.3.6.1.4.1.2356.11.1.67.2.5.1.2
lcsStatusComPortsComPortServerConnEntryPortNumber OBJECT-TYPE
    SYNTAX     Integer32 (0..255)
    MAX-ACCESS read-only
    STATUS     current
    DESCRIPTION
            ""
    ::= { lcsStatusComPortsComPortServerConnEntry 2 }

-- {COLUMN} 1.3.6.1.4.1.2356.11.1.67.2.5.1.4
lcsStatusComPortsComPortServerConnEntryServGrant OBJECT-TYPE
    SYNTAX     Integer32 (0..2147483647)
    MAX-ACCESS read-only
    STATUS     current
    DESCRIPTION
            ""
    ::= { lcsStatusComPortsComPortServerConnEntry 4 }

-- {COLUMN} 1.3.6.1.4.1.2356.11.1.67.2.5.1.5
lcsStatusComPortsComPortServerConnEntryServRej OBJECT-TYPE
    SYNTAX     Integer32 (0..2147483647)
    MAX-ACCESS read-only
    STATUS     current
    DESCRIPTION
            ""
    ::= { lcsStatusComPortsComPortServerConnEntry 5 }

-- {COLUMN} 1.3.6.1.4.1.2356.11.1.67.2.5.1.6
lcsStatusComPortsComPortServerConnEntryClntSucc OBJECT-TYPE
    SYNTAX     Integer32 (0..2147483647)
    MAX-ACCESS read-only
    STATUS     current
    DESCRIPTION
            ""
    ::= { lcsStatusComPortsComPortServerConnEntry 6 }

-- {COLUMN} 1.3.6.1.4.1.2356.11.1.67.2.5.1.7
lcsStatusComPortsComPortServerConnEntryClntDnsErr OBJECT-TYPE
    SYNTAX     Integer32 (0..2147483647)
    MAX-ACCESS read-only
    STATUS     current
    DESCRIPTION
            ""
    ::= { lcsStatusComPortsComPortServerConnEntry 7 }

-- {COLUMN} 1.3.6.1.4.1.2356.11.1.67.2.5.1.8
lcsStatusComPortsComPortServerConnEntryClntTcpErr OBJECT-TYPE
    SYNTAX     Integer32 (0..2147483647)
    MAX-ACCESS read-only
    STATUS     current
    DESCRIPTION
            ""
    ::= { lcsStatusComPortsComPortServerConnEntry 8 }

-- {COLUMN} 1.3.6.1.4.1.2356.11.1.67.2.5.1.9
lcsStatusComPortsComPortServerConnEntryClntRemDisc OBJECT-TYPE
    SYNTAX     Integer32 (0..2147483647)
    MAX-ACCESS read-only
    STATUS     current
    DESCRIPTION
            ""
    ::= { lcsStatusComPortsComPortServerConnEntry 9 }

-- {COLUMN} 1.3.6.1.4.1.2356.11.1.67.2.5.1.99
lcsStatusComPortsComPortServerConnEntryFullName OBJECT-TYPE
    SYNTAX     DisplayString (SIZE(0..255))
    MAX-ACCESS read-only
    STATUS     current
    DESCRIPTION
            ""
    ::= { lcsStatusComPortsComPortServerConnEntry 99 }

-- {SCALAR} 1.3.6.1.4.1.2356.11.1.67.2.99
lcsStatusComPortsComPortServerDeleteValues OBJECT-TYPE
    SYNTAX     DisplayString
    MAX-ACCESS read-write
    STATUS     current
    DESCRIPTION
            ""
    ::= { lcsStatusComPortsComPortServer 99 }

-- {NODE} 1.3.6.1.4.1.2356.11.1.68
lcsStatusBlockDevices OBJECT IDENTIFIER ::= { lcsStatus 68 }

-- {TABLE} 1.3.6.1.4.1.2356.11.1.68.1
lcsStatusBlockDevicesDeviceListTable OBJECT-TYPE
    SYNTAX     SEQUENCE OF LcsStatusBlockDevicesDeviceListEntry
    MAX-ACCESS not-accessible
    STATUS     current
    DESCRIPTION
            ""
    ::= { lcsStatusBlockDevices 1 }

-- {ROW} 1.3.6.1.4.1.2356.11.1.68.1.1
lcsStatusBlockDevicesDeviceListEntry OBJECT-TYPE
    SYNTAX     LcsStatusBlockDevicesDeviceListEntry
    MAX-ACCESS not-accessible
    STATUS     current
    DESCRIPTION
            ""
    INDEX {
            lcsStatusBlockDevicesDeviceListEntryId,
            lcsStatusBlockDevicesDeviceListEntryPartition
          }
    ::= { lcsStatusBlockDevicesDeviceListTable 1 }

LcsStatusBlockDevicesDeviceListEntry ::= SEQUENCE {
            lcsStatusBlockDevicesDeviceListEntryId Integer32,
            lcsStatusBlockDevicesDeviceListEntryType DisplayString,
            lcsStatusBlockDevicesDeviceListEntryBlocksize Integer32,
            lcsStatusBlockDevicesDeviceListEntryBlockcount Integer32,
            lcsStatusBlockDevicesDeviceListEntryPartition Integer32,
            lcsStatusBlockDevicesDeviceListEntryFirstBlock Integer32
    }

-- {COLUMN} 1.3.6.1.4.1.2356.11.1.68.1.1.1
lcsStatusBlockDevicesDeviceListEntryId OBJECT-TYPE
    SYNTAX     Integer32 (0..2147483647)
    MAX-ACCESS read-only
    STATUS     current
    DESCRIPTION
            ""
    ::= { lcsStatusBlockDevicesDeviceListEntry 1 }

-- {COLUMN} 1.3.6.1.4.1.2356.11.1.68.1.1.2
lcsStatusBlockDevicesDeviceListEntryType OBJECT-TYPE
    SYNTAX     DisplayString (SIZE(0..255))
    MAX-ACCESS read-only
    STATUS     current
    DESCRIPTION
            ""
    ::= { lcsStatusBlockDevicesDeviceListEntry 2 }

-- {COLUMN} 1.3.6.1.4.1.2356.11.1.68.1.1.3
lcsStatusBlockDevicesDeviceListEntryBlocksize OBJECT-TYPE
    SYNTAX     Integer32 (0..2147483647)
    MAX-ACCESS read-only
    STATUS     current
    DESCRIPTION
            ""
    ::= { lcsStatusBlockDevicesDeviceListEntry 3 }

-- {COLUMN} 1.3.6.1.4.1.2356.11.1.68.1.1.4
lcsStatusBlockDevicesDeviceListEntryBlockcount OBJECT-TYPE
    SYNTAX     Integer32 (0..2147483647)
    MAX-ACCESS read-only
    STATUS     current
    DESCRIPTION
            ""
    ::= { lcsStatusBlockDevicesDeviceListEntry 4 }

-- {COLUMN} 1.3.6.1.4.1.2356.11.1.68.1.1.5
lcsStatusBlockDevicesDeviceListEntryPartition OBJECT-TYPE
    SYNTAX     Integer32 (0..2147483647)
    MAX-ACCESS read-only
    STATUS     current
    DESCRIPTION
            ""
    ::= { lcsStatusBlockDevicesDeviceListEntry 5 }

-- {COLUMN} 1.3.6.1.4.1.2356.11.1.68.1.1.6
lcsStatusBlockDevicesDeviceListEntryFirstBlock OBJECT-TYPE
    SYNTAX     Integer32 (0..2147483647)
    MAX-ACCESS read-only
    STATUS     current
    DESCRIPTION
            ""
    ::= { lcsStatusBlockDevicesDeviceListEntry 6 }

-- {NODE} 1.3.6.1.4.1.2356.11.1.69
lcsStatusTacacsPlus OBJECT IDENTIFIER ::= { lcsStatus 69 }

-- {SCALAR} 1.3.6.1.4.1.2356.11.1.69.1
lcsStatusTacacsPlusAuthenticationErrors OBJECT-TYPE
    SYNTAX     Counter32
    MAX-ACCESS read-only
    STATUS     current
    DESCRIPTION
            ""
    ::= { lcsStatusTacacsPlus 1 }

-- {SCALAR} 1.3.6.1.4.1.2356.11.1.69.2
lcsStatusTacacsPlusAuthorisationErrors OBJECT-TYPE
    SYNTAX     Counter32
    MAX-ACCESS read-only
    STATUS     current
    DESCRIPTION
            ""
    ::= { lcsStatusTacacsPlus 2 }

-- {SCALAR} 1.3.6.1.4.1.2356.11.1.69.3
lcsStatusTacacsPlusDeleteValues OBJECT-TYPE
    SYNTAX     DisplayString
    MAX-ACCESS read-write
    STATUS     current
    DESCRIPTION
            ""
    ::= { lcsStatusTacacsPlus 3 }

-- {NODE} 1.3.6.1.4.1.2356.11.1.70
lcsStatusTemperatureMonitor OBJECT IDENTIFIER ::= { lcsStatus 70 }

-- {TABLE} 1.3.6.1.4.1.2356.11.1.70.1
lcsStatusTemperatureMonitorExtremesTable OBJECT-TYPE
    SYNTAX     SEQUENCE OF LcsStatusTemperatureMonitorExtremesEntry
    MAX-ACCESS not-accessible
    STATUS     current
    DESCRIPTION
            ""
    ::= { lcsStatusTemperatureMonitor 1 }

-- {ROW} 1.3.6.1.4.1.2356.11.1.70.1.1
lcsStatusTemperatureMonitorExtremesEntry OBJECT-TYPE
    SYNTAX     LcsStatusTemperatureMonitorExtremesEntry
    MAX-ACCESS not-accessible
    STATUS     current
    DESCRIPTION
            ""
    INDEX {
            lcsStatusTemperatureMonitorExtremesEntryType
          }
    ::= { lcsStatusTemperatureMonitorExtremesTable 1 }

LcsStatusTemperatureMonitorExtremesEntry ::= SEQUENCE {
            lcsStatusTemperatureMonitorExtremesEntryType INTEGER,
            lcsStatusTemperatureMonitorExtremesEntryValue Integer32,
            lcsStatusTemperatureMonitorExtremesEntryTime DisplayString
    }

-- {COLUMN} 1.3.6.1.4.1.2356.11.1.70.1.1.1
lcsStatusTemperatureMonitorExtremesEntryType OBJECT-TYPE
    SYNTAX     INTEGER {
                  eMinimum1 (1),
                  eMaximum1 (2),
                  eMinimum2 (257),
                  eMaximum2 (258),
                  eMinimum3 (513),
                  eMaximum3 (514),
                  eMinimum4 (769),
                  eMaximum4 (770),
                  eMinimum5 (1025),
                  eMaximum5 (1026),
                  eMinimum6 (1281),
                  eMaximum6 (1282),
                  eMinimum7 (1537),
                  eMaximum7 (1538),
                  eMinimum8 (1793),
                  eMaximum8 (1794)
            }
    MAX-ACCESS read-only
    STATUS     current
    DESCRIPTION
            ""
    ::= { lcsStatusTemperatureMonitorExtremesEntry 1 }

-- {COLUMN} 1.3.6.1.4.1.2356.11.1.70.1.1.2
lcsStatusTemperatureMonitorExtremesEntryValue OBJECT-TYPE
    SYNTAX     Integer32 (-32768..32767)
    MAX-ACCESS read-only
    STATUS     current
    DESCRIPTION
            ""
    ::= { lcsStatusTemperatureMonitorExtremesEntry 2 }

-- {COLUMN} 1.3.6.1.4.1.2356.11.1.70.1.1.3
lcsStatusTemperatureMonitorExtremesEntryTime OBJECT-TYPE
    SYNTAX     DisplayString (SIZE(0..255))
    MAX-ACCESS read-only
    STATUS     current
    DESCRIPTION
            ""
    ::= { lcsStatusTemperatureMonitorExtremesEntry 3 }

-- {NODE} 1.3.6.1.4.1.2356.11.1.72
lcsStatusDsl OBJECT IDENTIFIER ::= { lcsStatus 72 }

-- {TABLE} 1.3.6.1.4.1.2356.11.1.72.1
lcsStatusDslInterfacesTable OBJECT-TYPE
    SYNTAX     SEQUENCE OF LcsStatusDslInterfacesEntry
    MAX-ACCESS not-accessible
    STATUS     current
    DESCRIPTION
            ""
    ::= { lcsStatusDsl 1 }

-- {ROW} 1.3.6.1.4.1.2356.11.1.72.1.1
lcsStatusDslInterfacesEntry OBJECT-TYPE
    SYNTAX     LcsStatusDslInterfacesEntry
    MAX-ACCESS not-accessible
    STATUS     current
    DESCRIPTION
            ""
    INDEX {
            lcsStatusDslInterfacesEntryIfc
          }
    ::= { lcsStatusDslInterfacesTable 1 }

LcsStatusDslInterfacesEntry ::= SEQUENCE {
            lcsStatusDslInterfacesEntryIfc DisplayString,
            lcsStatusDslInterfacesEntryLinkActive INTEGER,
            lcsStatusDslInterfacesEntryMacAddress MacAddress
    }

-- {COLUMN} 1.3.6.1.4.1.2356.11.1.72.1.1.1
lcsStatusDslInterfacesEntryIfc OBJECT-TYPE
    SYNTAX     DisplayString (SIZE(0..255))
    MAX-ACCESS read-only
    STATUS     current
    DESCRIPTION
            ""
    ::= { lcsStatusDslInterfacesEntry 1 }

-- {COLUMN} 1.3.6.1.4.1.2356.11.1.72.1.1.3
lcsStatusDslInterfacesEntryLinkActive OBJECT-TYPE
    SYNTAX     INTEGER {
                  eNo (0),
                  eYes (1)
            }
    MAX-ACCESS read-only
    STATUS     current
    DESCRIPTION
            ""
    ::= { lcsStatusDslInterfacesEntry 3 }

-- {COLUMN} 1.3.6.1.4.1.2356.11.1.72.1.1.13
lcsStatusDslInterfacesEntryMacAddress OBJECT-TYPE
    SYNTAX     MacAddress
    MAX-ACCESS read-only
    STATUS     current
    DESCRIPTION
            "-- empty --"
    ::= { lcsStatusDslInterfacesEntry 13 }

-- {TABLE} 1.3.6.1.4.1.2356.11.1.72.2
lcsStatusDslByteTransportTable OBJECT-TYPE
    SYNTAX     SEQUENCE OF LcsStatusDslByteTransportEntry
    MAX-ACCESS not-accessible
    STATUS     current
    DESCRIPTION
            ""
    ::= { lcsStatusDsl 2 }

-- {ROW} 1.3.6.1.4.1.2356.11.1.72.2.1
lcsStatusDslByteTransportEntry OBJECT-TYPE
    SYNTAX     LcsStatusDslByteTransportEntry
    MAX-ACCESS not-accessible
    STATUS     current
    DESCRIPTION
            ""
    INDEX {
            lcsStatusDslByteTransportEntryIfc
          }
    ::= { lcsStatusDslByteTransportTable 1 }

LcsStatusDslByteTransportEntry ::= SEQUENCE {
            lcsStatusDslByteTransportEntryIfc DisplayString,
            lcsStatusDslByteTransportEntryTxBytes Counter64,
            lcsStatusDslByteTransportEntryRxBytes Counter64
    }

-- {COLUMN} 1.3.6.1.4.1.2356.11.1.72.2.1.1
lcsStatusDslByteTransportEntryIfc OBJECT-TYPE
    SYNTAX     DisplayString (SIZE(0..255))
    MAX-ACCESS read-only
    STATUS     current
    DESCRIPTION
            ""
    ::= { lcsStatusDslByteTransportEntry 1 }

-- {COLUMN} 1.3.6.1.4.1.2356.11.1.72.2.1.2
lcsStatusDslByteTransportEntryTxBytes OBJECT-TYPE
    SYNTAX     Counter64
    MAX-ACCESS read-only
    STATUS     current
    DESCRIPTION
            ""
    ::= { lcsStatusDslByteTransportEntry 2 }

-- {COLUMN} 1.3.6.1.4.1.2356.11.1.72.2.1.3
lcsStatusDslByteTransportEntryRxBytes OBJECT-TYPE
    SYNTAX     Counter64
    MAX-ACCESS read-only
    STATUS     current
    DESCRIPTION
            ""
    ::= { lcsStatusDslByteTransportEntry 3 }

-- {TABLE} 1.3.6.1.4.1.2356.11.1.72.3
lcsStatusDslPacketTransportTable OBJECT-TYPE
    SYNTAX     SEQUENCE OF LcsStatusDslPacketTransportEntry
    MAX-ACCESS not-accessible
    STATUS     current
    DESCRIPTION
            ""
    ::= { lcsStatusDsl 3 }

-- {ROW} 1.3.6.1.4.1.2356.11.1.72.3.1
lcsStatusDslPacketTransportEntry OBJECT-TYPE
    SYNTAX     LcsStatusDslPacketTransportEntry
    MAX-ACCESS not-accessible
    STATUS     current
    DESCRIPTION
            ""
    INDEX {
            lcsStatusDslPacketTransportEntryIfc
          }
    ::= { lcsStatusDslPacketTransportTable 1 }

LcsStatusDslPacketTransportEntry ::= SEQUENCE {
            lcsStatusDslPacketTransportEntryIfc DisplayString,
            lcsStatusDslPacketTransportEntryRxPackets Counter32,
            lcsStatusDslPacketTransportEntryTxPackets Counter32,
            lcsStatusDslPacketTransportEntryRxBroadcasts Counter32,
            lcsStatusDslPacketTransportEntryRxMulticasts Counter32,
            lcsStatusDslPacketTransportEntryRxUnicasts Counter32,
            lcsStatusDslPacketTransportEntryTxBroadcasts Counter32,
            lcsStatusDslPacketTransportEntryTxMulticasts Counter32,
            lcsStatusDslPacketTransportEntryTxUnicasts Counter32
    }

-- {COLUMN} 1.3.6.1.4.1.2356.11.1.72.3.1.1
lcsStatusDslPacketTransportEntryIfc OBJECT-TYPE
    SYNTAX     DisplayString (SIZE(0..255))
    MAX-ACCESS read-only
    STATUS     current
    DESCRIPTION
            ""
    ::= { lcsStatusDslPacketTransportEntry 1 }

-- {COLUMN} 1.3.6.1.4.1.2356.11.1.72.3.1.2
lcsStatusDslPacketTransportEntryRxPackets OBJECT-TYPE
    SYNTAX     Counter32
    MAX-ACCESS read-only
    STATUS     current
    DESCRIPTION
            ""
    ::= { lcsStatusDslPacketTransportEntry 2 }

-- {COLUMN} 1.3.6.1.4.1.2356.11.1.72.3.1.3
lcsStatusDslPacketTransportEntryTxPackets OBJECT-TYPE
    SYNTAX     Counter32
    MAX-ACCESS read-only
    STATUS     current
    DESCRIPTION
            ""
    ::= { lcsStatusDslPacketTransportEntry 3 }

-- {COLUMN} 1.3.6.1.4.1.2356.11.1.72.3.1.4
lcsStatusDslPacketTransportEntryRxBroadcasts OBJECT-TYPE
    SYNTAX     Counter32
    MAX-ACCESS read-only
    STATUS     current
    DESCRIPTION
            ""
    ::= { lcsStatusDslPacketTransportEntry 4 }

-- {COLUMN} 1.3.6.1.4.1.2356.11.1.72.3.1.5
lcsStatusDslPacketTransportEntryRxMulticasts OBJECT-TYPE
    SYNTAX     Counter32
    MAX-ACCESS read-only
    STATUS     current
    DESCRIPTION
            ""
    ::= { lcsStatusDslPacketTransportEntry 5 }

-- {COLUMN} 1.3.6.1.4.1.2356.11.1.72.3.1.6
lcsStatusDslPacketTransportEntryRxUnicasts OBJECT-TYPE
    SYNTAX     Counter32
    MAX-ACCESS read-only
    STATUS     current
    DESCRIPTION
            ""
    ::= { lcsStatusDslPacketTransportEntry 6 }

-- {COLUMN} 1.3.6.1.4.1.2356.11.1.72.3.1.7
lcsStatusDslPacketTransportEntryTxBroadcasts OBJECT-TYPE
    SYNTAX     Counter32
    MAX-ACCESS read-only
    STATUS     current
    DESCRIPTION
            ""
    ::= { lcsStatusDslPacketTransportEntry 7 }

-- {COLUMN} 1.3.6.1.4.1.2356.11.1.72.3.1.8
lcsStatusDslPacketTransportEntryTxMulticasts OBJECT-TYPE
    SYNTAX     Counter32
    MAX-ACCESS read-only
    STATUS     current
    DESCRIPTION
            ""
    ::= { lcsStatusDslPacketTransportEntry 8 }

-- {COLUMN} 1.3.6.1.4.1.2356.11.1.72.3.1.9
lcsStatusDslPacketTransportEntryTxUnicasts OBJECT-TYPE
    SYNTAX     Counter32
    MAX-ACCESS read-only
    STATUS     current
    DESCRIPTION
            ""
    ::= { lcsStatusDslPacketTransportEntry 9 }

-- {TABLE} 1.3.6.1.4.1.2356.11.1.72.4
lcsStatusDslErrorsTable OBJECT-TYPE
    SYNTAX     SEQUENCE OF LcsStatusDslErrorsEntry
    MAX-ACCESS not-accessible
    STATUS     current
    DESCRIPTION
            ""
    ::= { lcsStatusDsl 4 }

-- {ROW} 1.3.6.1.4.1.2356.11.1.72.4.1
lcsStatusDslErrorsEntry OBJECT-TYPE
    SYNTAX     LcsStatusDslErrorsEntry
    MAX-ACCESS not-accessible
    STATUS     current
    DESCRIPTION
            ""
    INDEX {
            lcsStatusDslErrorsEntryIfc
          }
    ::= { lcsStatusDslErrorsTable 1 }

LcsStatusDslErrorsEntry ::= SEQUENCE {
            lcsStatusDslErrorsEntryIfc DisplayString,
            lcsStatusDslErrorsEntryRxErrors Counter32,
            lcsStatusDslErrorsEntryTxErrors Counter32,
            lcsStatusDslErrorsEntryStackErrors Counter32,
            lcsStatusDslErrorsEntryNicErrors Counter32,
            lcsStatusDslErrorsEntryQueueErrors Counter32,
            lcsStatusDslErrorsEntryRxCrcErrors Counter32,
            lcsStatusDslErrorsEntryCollisions Counter32,
            lcsStatusDslErrorsEntrySingleCollisions Counter32,
            lcsStatusDslErrorsEntryMultipleCollisions Counter32,
            lcsStatusDslErrorsEntryLateCollisions Counter32,
            lcsStatusDslErrorsEntryExcessiveCollisions Counter32,
            lcsStatusDslErrorsEntryRxAlignErrors Counter32,
            lcsStatusDslErrorsEntryRxTooShort Counter32,
            lcsStatusDslErrorsEntryRxTooLong Counter32,
            lcsStatusDslErrorsEntryTxCarrier Counter32,
            lcsStatusDslErrorsEntryTxDeferred Counter32
    }

-- {COLUMN} 1.3.6.1.4.1.2356.11.1.72.4.1.1
lcsStatusDslErrorsEntryIfc OBJECT-TYPE
    SYNTAX     DisplayString (SIZE(0..255))
    MAX-ACCESS read-only
    STATUS     current
    DESCRIPTION
            ""
    ::= { lcsStatusDslErrorsEntry 1 }

-- {COLUMN} 1.3.6.1.4.1.2356.11.1.72.4.1.2
lcsStatusDslErrorsEntryRxErrors OBJECT-TYPE
    SYNTAX     Counter32
    MAX-ACCESS read-only
    STATUS     current
    DESCRIPTION
            ""
    ::= { lcsStatusDslErrorsEntry 2 }

-- {COLUMN} 1.3.6.1.4.1.2356.11.1.72.4.1.3
lcsStatusDslErrorsEntryTxErrors OBJECT-TYPE
    SYNTAX     Counter32
    MAX-ACCESS read-only
    STATUS     current
    DESCRIPTION
            ""
    ::= { lcsStatusDslErrorsEntry 3 }

-- {COLUMN} 1.3.6.1.4.1.2356.11.1.72.4.1.4
lcsStatusDslErrorsEntryStackErrors OBJECT-TYPE
    SYNTAX     Counter32
    MAX-ACCESS read-only
    STATUS     current
    DESCRIPTION
            ""
    ::= { lcsStatusDslErrorsEntry 4 }

-- {COLUMN} 1.3.6.1.4.1.2356.11.1.72.4.1.5
lcsStatusDslErrorsEntryNicErrors OBJECT-TYPE
    SYNTAX     Counter32
    MAX-ACCESS read-only
    STATUS     current
    DESCRIPTION
            ""
    ::= { lcsStatusDslErrorsEntry 5 }

-- {COLUMN} 1.3.6.1.4.1.2356.11.1.72.4.1.6
lcsStatusDslErrorsEntryQueueErrors OBJECT-TYPE
    SYNTAX     Counter32
    MAX-ACCESS read-only
    STATUS     current
    DESCRIPTION
            ""
    ::= { lcsStatusDslErrorsEntry 6 }

-- {COLUMN} 1.3.6.1.4.1.2356.11.1.72.4.1.7
lcsStatusDslErrorsEntryRxCrcErrors OBJECT-TYPE
    SYNTAX     Counter32
    MAX-ACCESS read-only
    STATUS     current
    DESCRIPTION
            ""
    ::= { lcsStatusDslErrorsEntry 7 }

-- {COLUMN} 1.3.6.1.4.1.2356.11.1.72.4.1.8
lcsStatusDslErrorsEntryCollisions OBJECT-TYPE
    SYNTAX     Counter32
    MAX-ACCESS read-only
    STATUS     current
    DESCRIPTION
            ""
    ::= { lcsStatusDslErrorsEntry 8 }

-- {COLUMN} 1.3.6.1.4.1.2356.11.1.72.4.1.9
lcsStatusDslErrorsEntrySingleCollisions OBJECT-TYPE
    SYNTAX     Counter32
    MAX-ACCESS read-only
    STATUS     current
    DESCRIPTION
            ""
    ::= { lcsStatusDslErrorsEntry 9 }

-- {COLUMN} 1.3.6.1.4.1.2356.11.1.72.4.1.10
lcsStatusDslErrorsEntryMultipleCollisions OBJECT-TYPE
    SYNTAX     Counter32
    MAX-ACCESS read-only
    STATUS     current
    DESCRIPTION
            ""
    ::= { lcsStatusDslErrorsEntry 10 }

-- {COLUMN} 1.3.6.1.4.1.2356.11.1.72.4.1.11
lcsStatusDslErrorsEntryLateCollisions OBJECT-TYPE
    SYNTAX     Counter32
    MAX-ACCESS read-only
    STATUS     current
    DESCRIPTION
            ""
    ::= { lcsStatusDslErrorsEntry 11 }

-- {COLUMN} 1.3.6.1.4.1.2356.11.1.72.4.1.12
lcsStatusDslErrorsEntryExcessiveCollisions OBJECT-TYPE
    SYNTAX     Counter32
    MAX-ACCESS read-only
    STATUS     current
    DESCRIPTION
            ""
    ::= { lcsStatusDslErrorsEntry 12 }

-- {COLUMN} 1.3.6.1.4.1.2356.11.1.72.4.1.13
lcsStatusDslErrorsEntryRxAlignErrors OBJECT-TYPE
    SYNTAX     Counter32
    MAX-ACCESS read-only
    STATUS     current
    DESCRIPTION
            ""
    ::= { lcsStatusDslErrorsEntry 13 }

-- {COLUMN} 1.3.6.1.4.1.2356.11.1.72.4.1.14
lcsStatusDslErrorsEntryRxTooShort OBJECT-TYPE
    SYNTAX     Counter32
    MAX-ACCESS read-only
    STATUS     current
    DESCRIPTION
            ""
    ::= { lcsStatusDslErrorsEntry 14 }

-- {COLUMN} 1.3.6.1.4.1.2356.11.1.72.4.1.15
lcsStatusDslErrorsEntryRxTooLong OBJECT-TYPE
    SYNTAX     Counter32
    MAX-ACCESS read-only
    STATUS     current
    DESCRIPTION
            ""
    ::= { lcsStatusDslErrorsEntry 15 }

-- {COLUMN} 1.3.6.1.4.1.2356.11.1.72.4.1.16
lcsStatusDslErrorsEntryTxCarrier OBJECT-TYPE
    SYNTAX     Counter32
    MAX-ACCESS read-only
    STATUS     current
    DESCRIPTION
            ""
    ::= { lcsStatusDslErrorsEntry 16 }

-- {COLUMN} 1.3.6.1.4.1.2356.11.1.72.4.1.17
lcsStatusDslErrorsEntryTxDeferred OBJECT-TYPE
    SYNTAX     Counter32
    MAX-ACCESS read-only
    STATUS     current
    DESCRIPTION
            ""
    ::= { lcsStatusDslErrorsEntry 17 }

-- {NODE} 1.3.6.1.4.1.2356.11.1.72.24
lcsStatusDslDslol OBJECT IDENTIFIER ::= { lcsStatusDsl 24 }

-- {SCALAR} 1.3.6.1.4.1.2356.11.1.72.24.1
lcsStatusDslDslolIpConfiguration OBJECT-TYPE
    SYNTAX     INTEGER {
                  eInvalid (0),
                  eValid (1)
            }
    MAX-ACCESS read-only
    STATUS     current
    DESCRIPTION
            "-- empty --"
    ::= { lcsStatusDslDslol 1 }

-- {SCALAR} 1.3.6.1.4.1.2356.11.1.72.24.2
lcsStatusDslDslolIpNetwork OBJECT-TYPE
    SYNTAX     IpAddress
    MAX-ACCESS read-only
    STATUS     current
    DESCRIPTION
            "-- empty --"
    ::= { lcsStatusDslDslol 2 }

-- {SCALAR} 1.3.6.1.4.1.2356.11.1.72.24.3
lcsStatusDslDslolIpNetmask OBJECT-TYPE
    SYNTAX     IpAddress
    MAX-ACCESS read-only
    STATUS     current
    DESCRIPTION
            "-- empty --"
    ::= { lcsStatusDslDslol 3 }

-- {SCALAR} 1.3.6.1.4.1.2356.11.1.72.24.4
lcsStatusDslDslolGatewayIp OBJECT-TYPE
    SYNTAX     IpAddress
    MAX-ACCESS read-only
    STATUS     current
    DESCRIPTION
            "-- empty --"
    ::= { lcsStatusDslDslol 4 }

-- {SCALAR} 1.3.6.1.4.1.2356.11.1.72.24.5
lcsStatusDslDslolGatewayMac OBJECT-TYPE
    SYNTAX     DisplayString (SIZE(0..12))
    MAX-ACCESS read-only
    STATUS     current
    DESCRIPTION
            "-- empty --"
    ::= { lcsStatusDslDslol 5 }

-- {SCALAR} 1.3.6.1.4.1.2356.11.1.72.24.6
lcsStatusDslDslolCatchDhcp OBJECT-TYPE
    SYNTAX     INTEGER {
                  eNo (0),
                  eYes (1)
            }
    MAX-ACCESS read-only
    STATUS     current
    DESCRIPTION
            "-- empty --"
    ::= { lcsStatusDslDslol 6 }

-- {SCALAR} 1.3.6.1.4.1.2356.11.1.72.24.7
lcsStatusDslDslolExclusiveMode OBJECT-TYPE
    SYNTAX     INTEGER {
                  eNo (0),
                  eYes (1)
            }
    MAX-ACCESS read-only
    STATUS     current
    DESCRIPTION
            "-- empty --"
    ::= { lcsStatusDslDslol 7 }

-- {SCALAR} 1.3.6.1.4.1.2356.11.1.72.30
lcsStatusDslDeleteValues OBJECT-TYPE
    SYNTAX     DisplayString
    MAX-ACCESS read-write
    STATUS     current
    DESCRIPTION
            ""
    ::= { lcsStatusDsl 30 }

-- {NODE} 1.3.6.1.4.1.2356.11.1.73
lcsStatusWlanMngmt OBJECT IDENTIFIER ::= { lcsStatus 73 }

-- {SCALAR} 1.3.6.1.4.1.2356.11.1.73.1
lcsStatusWlanMngmtControllerState OBJECT-TYPE
    SYNTAX     INTEGER {
                  eUnknown (0),
                  eInitScepClient (1),
                  eCertReqSent (2),
                  eReady (3),
                  eTimeNotSet (4),
                  eNoRandom (5),
                  eSubcaInitScep (6),
                  eDisabled (7)
            }
    MAX-ACCESS read-only
    STATUS     current
    DESCRIPTION
            ""
    ::= { lcsStatusWlanMngmt 1 }

-- {NODE} 1.3.6.1.4.1.2356.11.1.73.2
lcsStatusWlanMngmtApConf OBJECT IDENTIFIER ::= { lcsStatusWlanMngmt 2 }

-- {TABLE} 1.3.6.1.4.1.2356.11.1.73.2.1
lcsStatusWlanMngmtApConfNetwprofilsTable OBJECT-TYPE
    SYNTAX     SEQUENCE OF LcsStatusWlanMngmtApConfNetwprofilsEntry
    MAX-ACCESS not-accessible
    STATUS     current
    DESCRIPTION
            "network profiles"
    ::= { lcsStatusWlanMngmtApConf 1 }

-- {ROW} 1.3.6.1.4.1.2356.11.1.73.2.1.1
lcsStatusWlanMngmtApConfNetwprofilsEntry OBJECT-TYPE
    SYNTAX     LcsStatusWlanMngmtApConfNetwprofilsEntry
    MAX-ACCESS not-accessible
    STATUS     current
    DESCRIPTION
            ""
    INDEX {
            lcsStatusWlanMngmtApConfNetwprofilsEntryName
          }
    ::= { lcsStatusWlanMngmtApConfNetwprofilsTable 1 }

LcsStatusWlanMngmtApConfNetwprofilsEntry ::= SEQUENCE {
            lcsStatusWlanMngmtApConfNetwprofilsEntryName DisplayString,
            lcsStatusWlanMngmtApConfNetwprofilsEntryOperating INTEGER,
            lcsStatusWlanMngmtApConfNetwprofilsEntryVlanId Integer32,
            lcsStatusWlanMngmtApConfNetwprofilsEntryEncryption INTEGER,
            lcsStatusWlanMngmtApConfNetwprofilsEntryWpa1SessionKeytypes INTEGER,
            lcsStatusWlanMngmtApConfNetwprofilsEntryWpaVersion INTEGER,
            lcsStatusWlanMngmtApConfNetwprofilsEntryKey DisplayString,
            lcsStatusWlanMngmtApConfNetwprofilsEntryRadioBand INTEGER,
            lcsStatusWlanMngmtApConfNetwprofilsEntryContinuation Integer32,
            lcsStatusWlanMngmtApConfNetwprofilsEntryMinTxRate INTEGER,
            lcsStatusWlanMngmtApConfNetwprofilsEntryMaxTxRate INTEGER,
            lcsStatusWlanMngmtApConfNetwprofilsEntryBasicRate INTEGER,
            lcsStatusWlanMngmtApConfNetwprofilsEntry11bPreamble INTEGER,
            lcsStatusWlanMngmtApConfNetwprofilsEntryMacFilter INTEGER,
            lcsStatusWlanMngmtApConfNetwprofilsEntryClBrgSupport INTEGER,
            lcsStatusWlanMngmtApConfNetwprofilsEntryMaxStations Integer32,
            lcsStatusWlanMngmtApConfNetwprofilsEntrySsidBroadcast INTEGER,
            lcsStatusWlanMngmtApConfNetwprofilsEntrySsid DisplayString,
            lcsStatusWlanMngmtApConfNetwprofilsEntryMinHtMcs INTEGER,
            lcsStatusWlanMngmtApConfNetwprofilsEntryMaxHtMcs INTEGER,
            lcsStatusWlanMngmtApConfNetwprofilsEntryShortGuardInterval INTEGER,
            lcsStatusWlanMngmtApConfNetwprofilsEntryMaxSpatialStreams INTEGER,
            lcsStatusWlanMngmtApConfNetwprofilsEntrySendAggregates INTEGER,
            lcsStatusWlanMngmtApConfNetwprofilsEntryWpa2SessionKeytypes INTEGER,
            lcsStatusWlanMngmtApConfNetwprofilsEntryRadiusAccounting INTEGER,
            lcsStatusWlanMngmtApConfNetwprofilsEntryVlanMode INTEGER,
            lcsStatusWlanMngmtApConfNetwprofilsEntryConnectSsidTo INTEGER,
            lcsStatusWlanMngmtApConfNetwprofilsEntryInterStationTraffic INTEGER,
            lcsStatusWlanMngmtApConfNetwprofilsEntryVlanIdnew Integer32,
            lcsStatusWlanMngmtApConfNetwprofilsEntryRadiusProfile DisplayString,
            lcsStatusWlanMngmtApConfNetwprofilsEntryStbcActivated INTEGER,
            lcsStatusWlanMngmtApConfNetwprofilsEntryLdpcActivated INTEGER,
            lcsStatusWlanMngmtApConfNetwprofilsEntryMinClientStrength Integer32,
            lcsStatusWlanMngmtApConfNetwprofilsEntryIeee80211uNetworkProfile DisplayString,
            lcsStatusWlanMngmtApConfNetwprofilsEntryOkc INTEGER,
            lcsStatusWlanMngmtApConfNetwprofilsEntryWpa2KeyManagement BITS,
            lcsStatusWlanMngmtApConfNetwprofilsEntryApsd INTEGER,
            lcsStatusWlanMngmtApConfNetwprofilsEntryProtMgmtFrames INTEGER,
            lcsStatusWlanMngmtApConfNetwprofilsEntryTxLimit Integer32,
            lcsStatusWlanMngmtApConfNetwprofilsEntryRxLimit Integer32,
            lcsStatusWlanMngmtApConfNetwprofilsEntryLbsTracking INTEGER,
            lcsStatusWlanMngmtApConfNetwprofilsEntryLbsTrackingList DisplayString,
            lcsStatusWlanMngmtApConfNetwprofilsEntry11acBeamforming INTEGER,
            lcsStatusWlanMngmtApConfNetwprofilsEntryConvertToUnicast BITS,
            lcsStatusWlanMngmtApConfNetwprofilsEntryTransmitOnlyUnicasts INTEGER,
            lcsStatusWlanMngmtApConfNetwprofilsEntryContinuationUseDef INTEGER,
            lcsStatusWlanMngmtApConfNetwprofilsEntryWpa23SessionKeytypes BITS,
            lcsStatusWlanMngmtApConfNetwprofilsEntryWpa8021xSecurityLevel INTEGER,
            lcsStatusWlanMngmtApConfNetwprofilsEntryPerClientTxLimit Integer32,
            lcsStatusWlanMngmtApConfNetwprofilsEntryPerClientRxLimit Integer32,
            lcsStatusWlanMngmtApConfNetwprofilsEntryTimeframe DisplayString,
            lcsStatusWlanMngmtApConfNetwprofilsEntryMinClDisStr Integer32
    }

-- {COLUMN} 1.3.6.1.4.1.2356.11.1.73.2.1.1.1
lcsStatusWlanMngmtApConfNetwprofilsEntryName OBJECT-TYPE
    SYNTAX     DisplayString (SIZE(0..31))
    MAX-ACCESS read-only
    STATUS     current
    DESCRIPTION
            ""
    ::= { lcsStatusWlanMngmtApConfNetwprofilsEntry 1 }

-- {COLUMN} 1.3.6.1.4.1.2356.11.1.73.2.1.1.4
lcsStatusWlanMngmtApConfNetwprofilsEntryOperating OBJECT-TYPE
    SYNTAX     INTEGER {
                  eYes (0),
                  eNo (1)
            }
    MAX-ACCESS read-only
    STATUS     current
    DESCRIPTION
            ""
    ::= { lcsStatusWlanMngmtApConfNetwprofilsEntry 4 }

-- {COLUMN} 1.3.6.1.4.1.2356.11.1.73.2.1.1.5
lcsStatusWlanMngmtApConfNetwprofilsEntryVlanId OBJECT-TYPE
    SYNTAX     Integer32 (0..65535)
    MAX-ACCESS read-only
    STATUS     obsolete
    DESCRIPTION
            ""
    ::= { lcsStatusWlanMngmtApConfNetwprofilsEntry 5 }

-- {COLUMN} 1.3.6.1.4.1.2356.11.1.73.2.1.1.6
lcsStatusWlanMngmtApConfNetwprofilsEntryEncryption OBJECT-TYPE
    SYNTAX     INTEGER {
                  e80211iWpaPsk (0),
                  e80211iWpa8021x (1),
                  eWep104Bits (2),
                  eWep40Bits (3),
                  eWep104Bits8021x (4),
                  eWep40Bits8021x (5),
                  eNone (6),
                  eWPA-OWE (7),
                  eEnhancedOpenTransitional (8)
            }
    MAX-ACCESS read-only
    STATUS     current
    DESCRIPTION
            ""
    ::= { lcsStatusWlanMngmtApConfNetwprofilsEntry 6 }

-- {COLUMN} 1.3.6.1.4.1.2356.11.1.73.2.1.1.7
lcsStatusWlanMngmtApConfNetwprofilsEntryWpa1SessionKeytypes OBJECT-TYPE
    SYNTAX     INTEGER {
                  eTkipAes (0),
                  eAes (1),
                  eTkip (2)
            }
    MAX-ACCESS read-only
    STATUS     current
    DESCRIPTION
            ""
    ::= { lcsStatusWlanMngmtApConfNetwprofilsEntry 7 }

-- {COLUMN} 1.3.6.1.4.1.2356.11.1.73.2.1.1.8
lcsStatusWlanMngmtApConfNetwprofilsEntryWpaVersion OBJECT-TYPE
    SYNTAX     INTEGER {
                  eWpa12 (0),
                  eWpa1 (1),
                  eWpa2 (2),
                  eWpa3 (3),
                  eWpa23 (4),
                  eWpa123 (5)
            }
    MAX-ACCESS read-only
    STATUS     current
    DESCRIPTION
            ""
    ::= { lcsStatusWlanMngmtApConfNetwprofilsEntry 8 }

-- {COLUMN} 1.3.6.1.4.1.2356.11.1.73.2.1.1.9
lcsStatusWlanMngmtApConfNetwprofilsEntryKey OBJECT-TYPE
    SYNTAX     DisplayString (SIZE(0..63))
    MAX-ACCESS read-only
    STATUS     current
    DESCRIPTION
            ""
    ::= { lcsStatusWlanMngmtApConfNetwprofilsEntry 9 }

-- {COLUMN} 1.3.6.1.4.1.2356.11.1.73.2.1.1.10
lcsStatusWlanMngmtApConfNetwprofilsEntryRadioBand OBJECT-TYPE
    SYNTAX     INTEGER {
                  e24ghz5ghz (0),
                  e24ghz (1),
                  e5ghz (2)
            }
    MAX-ACCESS read-only
    STATUS     current
    DESCRIPTION
            ""
    ::= { lcsStatusWlanMngmtApConfNetwprofilsEntry 10 }

-- {COLUMN} 1.3.6.1.4.1.2356.11.1.73.2.1.1.11
lcsStatusWlanMngmtApConfNetwprofilsEntryContinuation OBJECT-TYPE
    SYNTAX     Integer32 (0..65535)
    MAX-ACCESS read-only
    STATUS     current
    DESCRIPTION
            ""
    ::= { lcsStatusWlanMngmtApConfNetwprofilsEntry 11 }

-- {COLUMN} 1.3.6.1.4.1.2356.11.1.73.2.1.1.12
lcsStatusWlanMngmtApConfNetwprofilsEntryMinTxRate OBJECT-TYPE
    SYNTAX     INTEGER {
                  eAuto (0),
                  e1M (1),
                  e2M (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-only
    STATUS     current
    DESCRIPTION
            ""
    ::= { lcsStatusWlanMngmtApConfNetwprofilsEntry 12 }

-- {COLUMN} 1.3.6.1.4.1.2356.11.1.73.2.1.1.13
lcsStatusWlanMngmtApConfNetwprofilsEntryMaxTxRate OBJECT-TYPE
    SYNTAX     INTEGER {
                  eAuto (0),
                  e1M (1),
                  e2M (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-only
    STATUS     current
    DESCRIPTION
            ""
    ::= { lcsStatusWlanMngmtApConfNetwprofilsEntry 13 }

-- {COLUMN} 1.3.6.1.4.1.2356.11.1.73.2.1.1.14
lcsStatusWlanMngmtApConfNetwprofilsEntryBasicRate OBJECT-TYPE
    SYNTAX     INTEGER {
                  e2M (0),
                  e1M (1),
                  eAuto (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-only
    STATUS     current
    DESCRIPTION
            ""
    ::= { lcsStatusWlanMngmtApConfNetwprofilsEntry 14 }

-- {COLUMN} 1.3.6.1.4.1.2356.11.1.73.2.1.1.15
lcsStatusWlanMngmtApConfNetwprofilsEntry11bPreamble OBJECT-TYPE
    SYNTAX     INTEGER {
                  eAuto (0),
                  eLong (1)
            }
    MAX-ACCESS read-only
    STATUS     current
    DESCRIPTION
            ""
    ::= { lcsStatusWlanMngmtApConfNetwprofilsEntry 15 }

-- {COLUMN} 1.3.6.1.4.1.2356.11.1.73.2.1.1.16
lcsStatusWlanMngmtApConfNetwprofilsEntryMacFilter OBJECT-TYPE
    SYNTAX     INTEGER {
                  eNo (0),
                  eYes (1)
            }
    MAX-ACCESS read-only
    STATUS     current
    DESCRIPTION
            ""
    ::= { lcsStatusWlanMngmtApConfNetwprofilsEntry 16 }

-- {COLUMN} 1.3.6.1.4.1.2356.11.1.73.2.1.1.17
lcsStatusWlanMngmtApConfNetwprofilsEntryClBrgSupport OBJECT-TYPE
    SYNTAX     INTEGER {
                  eNo (0),
                  eYes (1),
                  eExclusive (2)
            }
    MAX-ACCESS read-only
    STATUS     current
    DESCRIPTION
            ""
    ::= { lcsStatusWlanMngmtApConfNetwprofilsEntry 17 }

-- {COLUMN} 1.3.6.1.4.1.2356.11.1.73.2.1.1.18
lcsStatusWlanMngmtApConfNetwprofilsEntryMaxStations OBJECT-TYPE
    SYNTAX     Integer32 (0..65535)
    MAX-ACCESS read-only
    STATUS     current
    DESCRIPTION
            ""
    ::= { lcsStatusWlanMngmtApConfNetwprofilsEntry 18 }

-- {COLUMN} 1.3.6.1.4.1.2356.11.1.73.2.1.1.19
lcsStatusWlanMngmtApConfNetwprofilsEntrySsidBroadcast OBJECT-TYPE
    SYNTAX     INTEGER {
                  eYes (0),
                  eNo (1),
                  eTightened (2)
            }
    MAX-ACCESS read-only
    STATUS     current
    DESCRIPTION
            ""
    ::= { lcsStatusWlanMngmtApConfNetwprofilsEntry 19 }

-- {COLUMN} 1.3.6.1.4.1.2356.11.1.73.2.1.1.21
lcsStatusWlanMngmtApConfNetwprofilsEntrySsid OBJECT-TYPE
    SYNTAX     DisplayString (SIZE(0..32))
    MAX-ACCESS read-only
    STATUS     current
    DESCRIPTION
            ""
    ::= { lcsStatusWlanMngmtApConfNetwprofilsEntry 21 }

-- {COLUMN} 1.3.6.1.4.1.2356.11.1.73.2.1.1.22
lcsStatusWlanMngmtApConfNetwprofilsEntryMinHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-only
    STATUS     current
    DESCRIPTION
            ""
    ::= { lcsStatusWlanMngmtApConfNetwprofilsEntry 22 }

-- {COLUMN} 1.3.6.1.4.1.2356.11.1.73.2.1.1.23
lcsStatusWlanMngmtApConfNetwprofilsEntryMaxHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-only
    STATUS     current
    DESCRIPTION
            ""
    ::= { lcsStatusWlanMngmtApConfNetwprofilsEntry 23 }

-- {COLUMN} 1.3.6.1.4.1.2356.11.1.73.2.1.1.24
lcsStatusWlanMngmtApConfNetwprofilsEntryShortGuardInterval OBJECT-TYPE
    SYNTAX     INTEGER {
                  eAuto (0),
                  eNo (1)
            }
    MAX-ACCESS read-only
    STATUS     current
    DESCRIPTION
            ""
    ::= { lcsStatusWlanMngmtApConfNetwprofilsEntry 24 }

-- {COLUMN} 1.3.6.1.4.1.2356.11.1.73.2.1.1.25
lcsStatusWlanMngmtApConfNetwprofilsEntryMaxSpatialStreams OBJECT-TYPE
    SYNTAX     INTEGER {
                  eAuto (0),
                  eOne (1),
                  eTwo (2),
                  eThree (3),
                  eFour (4)
            }
    MAX-ACCESS read-only
    STATUS     current
    DESCRIPTION
            ""
    ::= { lcsStatusWlanMngmtApConfNetwprofilsEntry 25 }

-- {COLUMN} 1.3.6.1.4.1.2356.11.1.73.2.1.1.26
lcsStatusWlanMngmtApConfNetwprofilsEntrySendAggregates OBJECT-TYPE
    SYNTAX     INTEGER {
                  eNo (0),
                  eYes (1)
            }
    MAX-ACCESS read-only
    STATUS     current
    DESCRIPTION
            ""
    ::= { lcsStatusWlanMngmtApConfNetwprofilsEntry 26 }

-- {COLUMN} 1.3.6.1.4.1.2356.11.1.73.2.1.1.27
lcsStatusWlanMngmtApConfNetwprofilsEntryWpa2SessionKeytypes OBJECT-TYPE
    SYNTAX     INTEGER {
                  eTkipAes (0),
                  eAes (1),
                  eTkip (2)
            }
    MAX-ACCESS read-only
    STATUS     current
    DESCRIPTION
            ""
    ::= { lcsStatusWlanMngmtApConfNetwprofilsEntry 27 }

-- {COLUMN} 1.3.6.1.4.1.2356.11.1.73.2.1.1.28
lcsStatusWlanMngmtApConfNetwprofilsEntryRadiusAccounting OBJECT-TYPE
    SYNTAX     INTEGER {
                  eNo (0),
                  eYes (1)
            }
    MAX-ACCESS read-only
    STATUS     current
    DESCRIPTION
            ""
    ::= { lcsStatusWlanMngmtApConfNetwprofilsEntry 28 }

-- {COLUMN} 1.3.6.1.4.1.2356.11.1.73.2.1.1.30
lcsStatusWlanMngmtApConfNetwprofilsEntryVlanMode OBJECT-TYPE
    SYNTAX     INTEGER {
                  eUntagged (0),
                  eTagged (1)
            }
    MAX-ACCESS read-only
    STATUS     current
    DESCRIPTION
            ""
    ::= { lcsStatusWlanMngmtApConfNetwprofilsEntry 30 }

-- {COLUMN} 1.3.6.1.4.1.2356.11.1.73.2.1.1.32
lcsStatusWlanMngmtApConfNetwprofilsEntryConnectSsidTo OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-only
    STATUS     current
    DESCRIPTION
            ""
    ::= { lcsStatusWlanMngmtApConfNetwprofilsEntry 32 }

-- {COLUMN} 1.3.6.1.4.1.2356.11.1.73.2.1.1.33
lcsStatusWlanMngmtApConfNetwprofilsEntryInterStationTraffic OBJECT-TYPE
    SYNTAX     INTEGER {
                  eNo (0),
                  eYes (1)
            }
    MAX-ACCESS read-only
    STATUS     current
    DESCRIPTION
            ""
    ::= { lcsStatusWlanMngmtApConfNetwprofilsEntry 33 }

-- {COLUMN} 1.3.6.1.4.1.2356.11.1.73.2.1.1.34
lcsStatusWlanMngmtApConfNetwprofilsEntryVlanIdnew OBJECT-TYPE
    SYNTAX     Integer32 (0..65535)
    MAX-ACCESS read-only
    STATUS     current
    DESCRIPTION
            ""
    ::= { lcsStatusWlanMngmtApConfNetwprofilsEntry 34 }

-- {COLUMN} 1.3.6.1.4.1.2356.11.1.73.2.1.1.35
lcsStatusWlanMngmtApConfNetwprofilsEntryRadiusProfile OBJECT-TYPE
    SYNTAX     DisplayString (SIZE(0..16))
    MAX-ACCESS read-only
    STATUS     current
    DESCRIPTION
            "-- empty --"
    ::= { lcsStatusWlanMngmtApConfNetwprofilsEntry 35 }

-- {COLUMN} 1.3.6.1.4.1.2356.11.1.73.2.1.1.36
lcsStatusWlanMngmtApConfNetwprofilsEntryStbcActivated OBJECT-TYPE
    SYNTAX     INTEGER {
                  eNo (0),
                  eYes (1)
            }
    MAX-ACCESS read-only
    STATUS     current
    DESCRIPTION
            "-- empty --"
    ::= { lcsStatusWlanMngmtApConfNetwprofilsEntry 36 }

-- {COLUMN} 1.3.6.1.4.1.2356.11.1.73.2.1.1.37
lcsStatusWlanMngmtApConfNetwprofilsEntryLdpcActivated OBJECT-TYPE
    SYNTAX     INTEGER {
                  eNo (0),
                  eYes (1)
            }
    MAX-ACCESS read-only
    STATUS     current
    DESCRIPTION
            "-- empty --"
    ::= { lcsStatusWlanMngmtApConfNetwprofilsEntry 37 }

-- {COLUMN} 1.3.6.1.4.1.2356.11.1.73.2.1.1.38
lcsStatusWlanMngmtApConfNetwprofilsEntryMinClientStrength OBJECT-TYPE
    SYNTAX     Integer32 (0..255)
    MAX-ACCESS read-only
    STATUS     current
    DESCRIPTION
            "-- empty --"
    ::= { lcsStatusWlanMngmtApConfNetwprofilsEntry 38 }

-- {COLUMN} 1.3.6.1.4.1.2356.11.1.73.2.1.1.39
lcsStatusWlanMngmtApConfNetwprofilsEntryIeee80211uNetworkProfile OBJECT-TYPE
    SYNTAX     DisplayString (SIZE(0..32))
    MAX-ACCESS read-only
    STATUS     current
    DESCRIPTION
            "-- empty --"
    ::= { lcsStatusWlanMngmtApConfNetwprofilsEntry 39 }

-- {COLUMN} 1.3.6.1.4.1.2356.11.1.73.2.1.1.40
lcsStatusWlanMngmtApConfNetwprofilsEntryOkc OBJECT-TYPE
    SYNTAX     INTEGER {
                  eNo (0),
                  eYes (1)
            }
    MAX-ACCESS read-only
    STATUS     current
    DESCRIPTION
            "-- empty --"
    ::= { lcsStatusWlanMngmtApConfNetwprofilsEntry 40 }

-- {COLUMN} 1.3.6.1.4.1.2356.11.1.73.2.1.1.41
lcsStatusWlanMngmtApConfNetwprofilsEntryWpa2KeyManagement OBJECT-TYPE
    SYNTAX     BITS {
                  eSha256 (5),
                  eFastRoaming (6),
                  eStandard (7)
            }
    MAX-ACCESS read-only
    STATUS     current
    DESCRIPTION
            "-- empty --"
    ::= { lcsStatusWlanMngmtApConfNetwprofilsEntry 41 }

-- {COLUMN} 1.3.6.1.4.1.2356.11.1.73.2.1.1.42
lcsStatusWlanMngmtApConfNetwprofilsEntryApsd OBJECT-TYPE
    SYNTAX     INTEGER {
                  eNo (0),
                  eYes (1)
            }
    MAX-ACCESS read-only
    STATUS     current
    DESCRIPTION
            "-- empty --"
    ::= { lcsStatusWlanMngmtApConfNetwprofilsEntry 42 }

-- {COLUMN} 1.3.6.1.4.1.2356.11.1.73.2.1.1.43
lcsStatusWlanMngmtApConfNetwprofilsEntryProtMgmtFrames OBJECT-TYPE
    SYNTAX     INTEGER {
                  eNo (0),
                  eOptional (1),
                  eMandatory (2)
            }
    MAX-ACCESS read-only
    STATUS     current
    DESCRIPTION
            "-- empty --"
    ::= { lcsStatusWlanMngmtApConfNetwprofilsEntry 43 }

-- {COLUMN} 1.3.6.1.4.1.2356.11.1.73.2.1.1.44
lcsStatusWlanMngmtApConfNetwprofilsEntryTxLimit OBJECT-TYPE
    SYNTAX     Integer32 (0..2147483647)
    MAX-ACCESS read-only
    STATUS     current
    DESCRIPTION
            "-- empty --"
    ::= { lcsStatusWlanMngmtApConfNetwprofilsEntry 44 }

-- {COLUMN} 1.3.6.1.4.1.2356.11.1.73.2.1.1.45
lcsStatusWlanMngmtApConfNetwprofilsEntryRxLimit OBJECT-TYPE
    SYNTAX     Integer32 (0..2147483647)
    MAX-ACCESS read-only
    STATUS     current
    DESCRIPTION
            "-- empty --"
    ::= { lcsStatusWlanMngmtApConfNetwprofilsEntry 45 }

-- {COLUMN} 1.3.6.1.4.1.2356.11.1.73.2.1.1.46
lcsStatusWlanMngmtApConfNetwprofilsEntryLbsTracking OBJECT-TYPE
    SYNTAX     INTEGER {
                  eNo (0),
                  eYes (1)
            }
    MAX-ACCESS read-only
    STATUS     current
    DESCRIPTION
            "-- empty --"
    ::= { lcsStatusWlanMngmtApConfNetwprofilsEntry 46 }

-- {COLUMN} 1.3.6.1.4.1.2356.11.1.73.2.1.1.47
lcsStatusWlanMngmtApConfNetwprofilsEntryLbsTrackingList OBJECT-TYPE
    SYNTAX     DisplayString (SIZE(0..32))
    MAX-ACCESS read-only
    STATUS     current
    DESCRIPTION
            "-- empty --"
    ::= { lcsStatusWlanMngmtApConfNetwprofilsEntry 47 }

-- {COLUMN} 1.3.6.1.4.1.2356.11.1.73.2.1.1.49
lcsStatusWlanMngmtApConfNetwprofilsEntry11acBeamforming OBJECT-TYPE
    SYNTAX     INTEGER {
                  eAuto (0),
                  eNo (1),
                  eSuMimo (2),
                  eMuMimo (3)
            }
    MAX-ACCESS read-only
    STATUS     current
    DESCRIPTION
            "-- empty --"
    ::= { lcsStatusWlanMngmtApConfNetwprofilsEntry 49 }

-- {COLUMN} 1.3.6.1.4.1.2356.11.1.73.2.1.1.50
lcsStatusWlanMngmtApConfNetwprofilsEntryConvertToUnicast OBJECT-TYPE
    SYNTAX     BITS {
                  eMulticast (14),
                  eDhcp (15)
            }
    MAX-ACCESS read-only
    STATUS     current
    DESCRIPTION
            "-- empty --"
    ::= { lcsStatusWlanMngmtApConfNetwprofilsEntry 50 }

-- {COLUMN} 1.3.6.1.4.1.2356.11.1.73.2.1.1.51
lcsStatusWlanMngmtApConfNetwprofilsEntryTransmitOnlyUnicasts OBJECT-TYPE
    SYNTAX     INTEGER {
                  eNo (0),
                  eYes (1)
            }
    MAX-ACCESS read-only
    STATUS     current
    DESCRIPTION
            "-- empty --"
    ::= { lcsStatusWlanMngmtApConfNetwprofilsEntry 51 }

-- {COLUMN} 1.3.6.1.4.1.2356.11.1.73.2.1.1.52
lcsStatusWlanMngmtApConfNetwprofilsEntryContinuationUseDef OBJECT-TYPE
    SYNTAX     INTEGER {
                  eNo (0),
                  eYes (1)
            }
    MAX-ACCESS read-only
    STATUS     current
    DESCRIPTION
            ""
    ::= { lcsStatusWlanMngmtApConfNetwprofilsEntry 52 }

-- {COLUMN} 1.3.6.1.4.1.2356.11.1.73.2.1.1.53
lcsStatusWlanMngmtApConfNetwprofilsEntryWpa23SessionKeytypes OBJECT-TYPE
    SYNTAX     BITS {
                  eAesGcmp256 (2),
                  eAesGcmp128 (3),
                  eAesCcmp256 (4),
                  eAesCcm (5),
                  eTkip (6)
            }
    MAX-ACCESS read-only
    STATUS     current
    DESCRIPTION
            "-- empty --"
    ::= { lcsStatusWlanMngmtApConfNetwprofilsEntry 53 }

-- {COLUMN} 1.3.6.1.4.1.2356.11.1.73.2.1.1.54
lcsStatusWlanMngmtApConfNetwprofilsEntryWpa8021xSecurityLevel OBJECT-TYPE
    SYNTAX     INTEGER {
                  eStandard (0),
                  eSuiteB128Bits (1),
                  eSuiteB192Bits (2)
            }
    MAX-ACCESS read-only
    STATUS     current
    DESCRIPTION
            "-- empty --"
    ::= { lcsStatusWlanMngmtApConfNetwprofilsEntry 54 }

-- {COLUMN} 1.3.6.1.4.1.2356.11.1.73.2.1.1.55
lcsStatusWlanMngmtApConfNetwprofilsEntryPerClientTxLimit OBJECT-TYPE
    SYNTAX     Integer32 (0..2147483647)
    MAX-ACCESS read-only
    STATUS     current
    DESCRIPTION
            "-- empty --"
    ::= { lcsStatusWlanMngmtApConfNetwprofilsEntry 55 }

-- {COLUMN} 1.3.6.1.4.1.2356.11.1.73.2.1.1.56
lcsStatusWlanMngmtApConfNetwprofilsEntryPerClientRxLimit OBJECT-TYPE
    SYNTAX     Integer32 (0..2147483647)
    MAX-ACCESS read-only
    STATUS     current
    DESCRIPTION
            "-- empty --"
    ::= { lcsStatusWlanMngmtApConfNetwprofilsEntry 56 }

-- {COLUMN} 1.3.6.1.4.1.2356.11.1.73.2.1.1.57
lcsStatusWlanMngmtApConfNetwprofilsEntryTimeframe OBJECT-TYPE
    SYNTAX     DisplayString (SIZE(0..31))
    MAX-ACCESS read-only
    STATUS     current
    DESCRIPTION
            "-- empty --"
    ::= { lcsStatusWlanMngmtApConfNetwprofilsEntry 57 }

-- {COLUMN} 1.3.6.1.4.1.2356.11.1.73.2.1.1.58
lcsStatusWlanMngmtApConfNetwprofilsEntryMinClDisStr OBJECT-TYPE
    SYNTAX     Integer32 (0..255)
    MAX-ACCESS read-only
    STATUS     current
    DESCRIPTION
            ""
    ::= { lcsStatusWlanMngmtApConfNetwprofilsEntry 58 }

-- {TABLE} 1.3.6.1.4.1.2356.11.1.73.2.2
lcsStatusWlanMngmtApConfRadioprofilsTable OBJECT-TYPE
    SYNTAX     SEQUENCE OF LcsStatusWlanMngmtApConfRadioprofilsEntry
    MAX-ACCESS not-accessible
    STATUS     current
    DESCRIPTION
            ""
    ::= { lcsStatusWlanMngmtApConf 2 }

-- {ROW} 1.3.6.1.4.1.2356.11.1.73.2.2.1
lcsStatusWlanMngmtApConfRadioprofilsEntry OBJECT-TYPE
    SYNTAX     LcsStatusWlanMngmtApConfRadioprofilsEntry
    MAX-ACCESS not-accessible
    STATUS     current
    DESCRIPTION
            ""
    INDEX {
            lcsStatusWlanMngmtApConfRadioprofilsEntryName
          }
    ::= { lcsStatusWlanMngmtApConfRadioprofilsTable 1 }

LcsStatusWlanMngmtApConfRadioprofilsEntry ::= SEQUENCE {
            lcsStatusWlanMngmtApConfRadioprofilsEntryName DisplayString,
            lcsStatusWlanMngmtApConfRadioprofilsEntryCountry INTEGER,
            lcsStatusWlanMngmtApConfRadioprofilsEntryChannelList DisplayString,
            lcsStatusWlanMngmtApConfRadioprofilsEntry24ghzMode INTEGER,
            lcsStatusWlanMngmtApConfRadioprofilsEntry5ghzMode INTEGER,
            lcsStatusWlanMngmtApConfRadioprofilsEntrySubbands INTEGER,
            lcsStatusWlanMngmtApConfRadioprofilsEntryQos INTEGER,
            lcsStatusWlanMngmtApConfRadioprofilsEntryDtimPeriod Integer32,
            lcsStatusWlanMngmtApConfRadioprofilsEntryBackgroundScan Integer32,
            lcsStatusWlanMngmtApConfRadioprofilsEntryAntennaGain Integer32,
            lcsStatusWlanMngmtApConfRadioprofilsEntryTxPowerReduction Integer32,
            lcsStatusWlanMngmtApConfRadioprofilsEntryMgmtVLANId Integer32,
            lcsStatusWlanMngmtApConfRadioprofilsEntryIndoorOnlyOperation INTEGER,
            lcsStatusWlanMngmtApConfRadioprofilsEntryActVlanModOfMngdAps INTEGER,
            lcsStatusWlanMngmtApConfRadioprofilsEntryMgmtVlanMode INTEGER,
            lcsStatusWlanMngmtApConfRadioprofilsEntryMgmtVLANIdnew Integer32,
            lcsStatusWlanMngmtApConfRadioprofilsEntryReportSeenClients INTEGER,
            lcsStatusWlanMngmtApConfRadioprofilsEntryClientSteering INTEGER,
            lcsStatusWlanMngmtApConfRadioprofilsEntryPreferredBand INTEGER,
            lcsStatusWlanMngmtApConfRadioprofilsEntryPrReqAgeO Integer32,
            lcsStatusWlanMngmtApConfRadioprofilsEntryAdaptiveRfOptimization INTEGER,
            lcsStatusWlanMngmtApConfRadioprofilsEntryRxPacketSensReduction Integer32
    }

-- {COLUMN} 1.3.6.1.4.1.2356.11.1.73.2.2.1.1
lcsStatusWlanMngmtApConfRadioprofilsEntryName OBJECT-TYPE
    SYNTAX     DisplayString (SIZE(0..31))
    MAX-ACCESS read-only
    STATUS     current
    DESCRIPTION
            ""
    ::= { lcsStatusWlanMngmtApConfRadioprofilsEntry 1 }

-- {COLUMN} 1.3.6.1.4.1.2356.11.1.73.2.2.1.4
lcsStatusWlanMngmtApConfRadioprofilsEntryCountry OBJECT-TYPE
    SYNTAX     INTEGER {
                  eDefault (0),
                  eAlbania (8),
                  eAlgeria (12),
                  eArgentina (32),
                  eAustralia (36),
                  eAustria (40),
                  eBahrain (48),
                  eBangladesh (50),
                  eBelgium (56),
                  eBosniaHerzegovina (70),
                  eBrazil (76),
                  eBruneiDarussalam (96),
                  eBulgaria (100),
                  eBelarus (112),
                  eCanada (124),
                  eChile (152),
                  eChina (156),
                  eTaiwan (158),
                  eColombia (170),
                  eCostaRica (188),
                  eCroatia (191),
                  eCyprus (196),
                  eCzech (203),
                  eDenmark (208),
                  eEcuador (218),
                  eEstonia (233),
                  eFinland (246),
                  eFrance (250),
                  eGermany (276),
                  eGhana (288),
                  eGreece (300),
                  eGuatemala (320),
                  eHonduras (340),
                  eHongKong (344),
                  eHungary (348),
                  eIceland (352),
                  eIndia (356),
                  eIndonesia (360),
                  eIreland (372),
                  eIsrael (376),
                  eItaly (380),
                  eJapan (392),
                  eJordan (400),
                  eSouthKorea (410),
                  eKuwait (414),
                  eLebanon (422),
                  eLatvia (428),
                  eLiechtenstein (438),
                  eLithuania (440),
                  eLuxembourg (442),
                  eMacau (446),
                  eMalaysia (458),
                  eMalta (470),
                  eMexico (484),
                  eMoldavia (498),
                  eMorocco (504),
                  eOman (512),
                  eNetherlands (528),
                  eNewZealand (554),
                  eNicaragua (558),
                  eNorway (578),
                  ePakistan (586),
                  ePanama (591),
                  eParaguay (600),
                  ePeru (604),
                  ePhilippines (608),
                  ePoland (616),
                  ePortugal (620),
                  ePuertoRico (630),
                  eQatar (634),
                  eRomania (642),
                  eRussia (643),
                  eSaudiArabia (682),
                  eSingapore (702),
                  eSlovak (703),
                  eSlovenia (705),
                  eSouthAfrica (710),
                  eSpain (724),
                  eSweden (752),
                  eSwitzerland (756),
                  eThailand (764),
                  eUnitedArabEmirates (784),
                  eTunisia (788),
                  eTurkey (792),
                  eUganda (800),
                  eUkraine (804),
                  eMacedonia (807),
                  eEgypt (818),
                  eUnitedKingdom (826),
                  eTanzania (834),
                  eUnitedStatesFcc (840),
                  eUruguay (858),
                  eVenezuela (862),
                  eEurope (998),
                  eEgalistan (999)
            }
    MAX-ACCESS read-only
    STATUS     current
    DESCRIPTION
            ""
    ::= { lcsStatusWlanMngmtApConfRadioprofilsEntry 4 }

-- {COLUMN} 1.3.6.1.4.1.2356.11.1.73.2.2.1.5
lcsStatusWlanMngmtApConfRadioprofilsEntryChannelList OBJECT-TYPE
    SYNTAX     DisplayString (SIZE(0..48))
    MAX-ACCESS read-only
    STATUS     current
    DESCRIPTION
            ""
    ::= { lcsStatusWlanMngmtApConfRadioprofilsEntry 5 }

-- {COLUMN} 1.3.6.1.4.1.2356.11.1.73.2.2.1.6
lcsStatusWlanMngmtApConfRadioprofilsEntry24ghzMode OBJECT-TYPE
    SYNTAX     INTEGER {
                  e11bgMixed (0),
                  e11gOnly (1),
                  e11bOnly (2),
                  e108mbps (3),
                  e11bgnMixed (4),
                  e11gnMixed (5),
                  eGreenfield (6),
                  eAuto (255)
            }
    MAX-ACCESS read-only
    STATUS     current
    DESCRIPTION
            ""
    ::= { lcsStatusWlanMngmtApConfRadioprofilsEntry 6 }

-- {COLUMN} 1.3.6.1.4.1.2356.11.1.73.2.2.1.7
lcsStatusWlanMngmtApConfRadioprofilsEntry5ghzMode OBJECT-TYPE
    SYNTAX     INTEGER {
                  eNormal (0),
                  e108mbps (3),
                  e11anMixed (4),
                  eGreenfield (5),
                  e11anacMixed (6),
                  e11nacMixed (7),
                  e11acOnly (8),
                  eAuto (255)
            }
    MAX-ACCESS read-only
    STATUS     current
    DESCRIPTION
            ""
    ::= { lcsStatusWlanMngmtApConfRadioprofilsEntry 7 }

-- {COLUMN} 1.3.6.1.4.1.2356.11.1.73.2.2.1.8
lcsStatusWlanMngmtApConfRadioprofilsEntrySubbands OBJECT-TYPE
    SYNTAX     INTEGER {
                  eBand1Plus2Plus3 (0),
                  eBand1 (1),
                  eBand2 (2),
                  eBand3 (3),
                  eBand1Plus2 (4),
                  eBand1Plus3 (5),
                  eBand2Plus3 (6)
            }
    MAX-ACCESS read-only
    STATUS     current
    DESCRIPTION
            ""
    ::= { lcsStatusWlanMngmtApConfRadioprofilsEntry 8 }

-- {COLUMN} 1.3.6.1.4.1.2356.11.1.73.2.2.1.9
lcsStatusWlanMngmtApConfRadioprofilsEntryQos OBJECT-TYPE
    SYNTAX     INTEGER {
                  eNo (0),
                  eYes (1)
            }
    MAX-ACCESS read-only
    STATUS     current
    DESCRIPTION
            ""
    ::= { lcsStatusWlanMngmtApConfRadioprofilsEntry 9 }

-- {COLUMN} 1.3.6.1.4.1.2356.11.1.73.2.2.1.10
lcsStatusWlanMngmtApConfRadioprofilsEntryDtimPeriod OBJECT-TYPE
    SYNTAX     Integer32 (0..255)
    MAX-ACCESS read-only
    STATUS     current
    DESCRIPTION
            ""
    ::= { lcsStatusWlanMngmtApConfRadioprofilsEntry 10 }

-- {COLUMN} 1.3.6.1.4.1.2356.11.1.73.2.2.1.11
lcsStatusWlanMngmtApConfRadioprofilsEntryBackgroundScan OBJECT-TYPE
    SYNTAX     Integer32 (0..2147483647)
    MAX-ACCESS read-only
    STATUS     current
    DESCRIPTION
            ""
    ::= { lcsStatusWlanMngmtApConfRadioprofilsEntry 11 }

-- {COLUMN} 1.3.6.1.4.1.2356.11.1.73.2.2.1.12
lcsStatusWlanMngmtApConfRadioprofilsEntryAntennaGain OBJECT-TYPE
    SYNTAX     Integer32 (-128..127)
    MAX-ACCESS read-only
    STATUS     current
    DESCRIPTION
            ""
    ::= { lcsStatusWlanMngmtApConfRadioprofilsEntry 12 }

-- {COLUMN} 1.3.6.1.4.1.2356.11.1.73.2.2.1.13
lcsStatusWlanMngmtApConfRadioprofilsEntryTxPowerReduction OBJECT-TYPE
    SYNTAX     Integer32 (0..255)
    MAX-ACCESS read-only
    STATUS     current
    DESCRIPTION
            ""
    ::= { lcsStatusWlanMngmtApConfRadioprofilsEntry 13 }

-- {COLUMN} 1.3.6.1.4.1.2356.11.1.73.2.2.1.14
lcsStatusWlanMngmtApConfRadioprofilsEntryMgmtVLANId OBJECT-TYPE
    SYNTAX     Integer32 (0..65535)
    MAX-ACCESS read-only
    STATUS     obsolete
    DESCRIPTION
            ""
    ::= { lcsStatusWlanMngmtApConfRadioprofilsEntry 14 }

-- {COLUMN} 1.3.6.1.4.1.2356.11.1.73.2.2.1.16
lcsStatusWlanMngmtApConfRadioprofilsEntryIndoorOnlyOperation OBJECT-TYPE
    SYNTAX     INTEGER {
                  eNo (0),
                  eYes (1)
            }
    MAX-ACCESS read-only
    STATUS     current
    DESCRIPTION
            ""
    ::= { lcsStatusWlanMngmtApConfRadioprofilsEntry 16 }

-- {COLUMN} 1.3.6.1.4.1.2356.11.1.73.2.2.1.17
lcsStatusWlanMngmtApConfRadioprofilsEntryActVlanModOfMngdAps OBJECT-TYPE
    SYNTAX     INTEGER {
                  eNo (0),
                  eYes (1)
            }
    MAX-ACCESS read-only
    STATUS     current
    DESCRIPTION
            ""
    ::= { lcsStatusWlanMngmtApConfRadioprofilsEntry 17 }

-- {COLUMN} 1.3.6.1.4.1.2356.11.1.73.2.2.1.18
lcsStatusWlanMngmtApConfRadioprofilsEntryMgmtVlanMode OBJECT-TYPE
    SYNTAX     INTEGER {
                  eUntagged (0),
                  eTagged (1)
            }
    MAX-ACCESS read-only
    STATUS     current
    DESCRIPTION
            ""
    ::= { lcsStatusWlanMngmtApConfRadioprofilsEntry 18 }

-- {COLUMN} 1.3.6.1.4.1.2356.11.1.73.2.2.1.19
lcsStatusWlanMngmtApConfRadioprofilsEntryMgmtVLANIdnew OBJECT-TYPE
    SYNTAX     Integer32 (0..65535)
    MAX-ACCESS read-only
    STATUS     current
    DESCRIPTION
            ""
    ::= { lcsStatusWlanMngmtApConfRadioprofilsEntry 19 }

-- {COLUMN} 1.3.6.1.4.1.2356.11.1.73.2.2.1.20
lcsStatusWlanMngmtApConfRadioprofilsEntryReportSeenClients OBJECT-TYPE
    SYNTAX     INTEGER {
                  eNo (0),
                  eYes (1)
            }
    MAX-ACCESS read-only
    STATUS     current
    DESCRIPTION
            ""
    ::= { lcsStatusWlanMngmtApConfRadioprofilsEntry 20 }

-- {COLUMN} 1.3.6.1.4.1.2356.11.1.73.2.2.1.21
lcsStatusWlanMngmtApConfRadioprofilsEntryClientSteering OBJECT-TYPE
    SYNTAX     INTEGER {
                  eOff (0),
                  eYes (1),
                  eOn (2),
                  eClientManagement (3)
            }
    MAX-ACCESS read-only
    STATUS     current
    DESCRIPTION
            "-- empty --"
    ::= { lcsStatusWlanMngmtApConfRadioprofilsEntry 21 }

-- {COLUMN} 1.3.6.1.4.1.2356.11.1.73.2.2.1.22
lcsStatusWlanMngmtApConfRadioprofilsEntryPreferredBand OBJECT-TYPE
    SYNTAX     INTEGER {
                  e24ghz (1),
                  e5ghz (2)
            }
    MAX-ACCESS read-only
    STATUS     current
    DESCRIPTION
            "-- empty --"
    ::= { lcsStatusWlanMngmtApConfRadioprofilsEntry 22 }

-- {COLUMN} 1.3.6.1.4.1.2356.11.1.73.2.2.1.23
lcsStatusWlanMngmtApConfRadioprofilsEntryPrReqAgeO OBJECT-TYPE
    SYNTAX     Integer32 (0..2147483647)
    MAX-ACCESS read-only
    STATUS     current
    DESCRIPTION
            ""
    ::= { lcsStatusWlanMngmtApConfRadioprofilsEntry 23 }

-- {COLUMN} 1.3.6.1.4.1.2356.11.1.73.2.2.1.24
lcsStatusWlanMngmtApConfRadioprofilsEntryAdaptiveRfOptimization OBJECT-TYPE
    SYNTAX     INTEGER {
                  eNo (0),
                  eYes (1)
            }
    MAX-ACCESS read-only
    STATUS     current
    DESCRIPTION
            "-- empty --"
    ::= { lcsStatusWlanMngmtApConfRadioprofilsEntry 24 }

-- {COLUMN} 1.3.6.1.4.1.2356.11.1.73.2.2.1.25
lcsStatusWlanMngmtApConfRadioprofilsEntryRxPacketSensReduction OBJECT-TYPE
    SYNTAX     Integer32 (0..255)
    MAX-ACCESS read-only
    STATUS     current
    DESCRIPTION
            "-- empty --"
    ::= { lcsStatusWlanMngmtApConfRadioprofilsEntry 25 }

-- {TABLE} 1.3.6.1.4.1.2356.11.1.73.2.3
lcsStatusWlanMngmtApConfCommonprofilsTable OBJECT-TYPE
    SYNTAX     SEQUENCE OF LcsStatusWlanMngmtApConfCommonprofilsEntry
    MAX-ACCESS not-accessible
    STATUS     current
    DESCRIPTION
            ""
    ::= { lcsStatusWlanMngmtApConf 3 }

-- {ROW} 1.3.6.1.4.1.2356.11.1.73.2.3.1
lcsStatusWlanMngmtApConfCommonprofilsEntry OBJECT-TYPE
    SYNTAX     LcsStatusWlanMngmtApConfCommonprofilsEntry
    MAX-ACCESS not-accessible
    STATUS     current
    DESCRIPTION
            ""
    INDEX {
            lcsStatusWlanMngmtApConfCommonprofilsEntryName
          }
    ::= { lcsStatusWlanMngmtApConfCommonprofilsTable 1 }

LcsStatusWlanMngmtApConfCommonprofilsEntry ::= SEQUENCE {
            lcsStatusWlanMngmtApConfCommonprofilsEntryName DisplayString,
            lcsStatusWlanMngmtApConfCommonprofilsEntryNetw DisplayString,
            lcsStatusWlanMngmtApConfCommonprofilsEntryApParams DisplayString,
            lcsStatusWlanMngmtApConfCommonprofilsEntryContr DisplayString,
            lcsStatusWlanMngmtApConfCommonprofilsEntryIeee80211uGeneral DisplayString,
            lcsStatusWlanMngmtApConfCommonprofilsEntryConfigurationDelay Integer32,
            lcsStatusWlanMngmtApConfCommonprofilsEntryLedProfile DisplayString,
            lcsStatusWlanMngmtApConfCommonprofilsEntryLbsGeneralProfile DisplayString,
            lcsStatusWlanMngmtApConfCommonprofilsEntryWirelessEpaperProfile DisplayString,
            lcsStatusWlanMngmtApConfCommonprofilsEntryEventTimeout Integer32,
            lcsStatusWlanMngmtApConfCommonprofilsEntryWirelessIdsProfile DisplayString
    }

-- {COLUMN} 1.3.6.1.4.1.2356.11.1.73.2.3.1.1
lcsStatusWlanMngmtApConfCommonprofilsEntryName OBJECT-TYPE
    SYNTAX     DisplayString (SIZE(0..31))
    MAX-ACCESS read-only
    STATUS     current
    DESCRIPTION
            ""
    ::= { lcsStatusWlanMngmtApConfCommonprofilsEntry 1 }

-- {COLUMN} 1.3.6.1.4.1.2356.11.1.73.2.3.1.2
lcsStatusWlanMngmtApConfCommonprofilsEntryNetw OBJECT-TYPE
    SYNTAX     DisplayString (SIZE(0..251))
    MAX-ACCESS read-only
    STATUS     current
    DESCRIPTION
            ""
    ::= { lcsStatusWlanMngmtApConfCommonprofilsEntry 2 }

-- {COLUMN} 1.3.6.1.4.1.2356.11.1.73.2.3.1.3
lcsStatusWlanMngmtApConfCommonprofilsEntryApParams OBJECT-TYPE
    SYNTAX     DisplayString (SIZE(0..31))
    MAX-ACCESS read-only
    STATUS     current
    DESCRIPTION
            ""
    ::= { lcsStatusWlanMngmtApConfCommonprofilsEntry 3 }

-- {COLUMN} 1.3.6.1.4.1.2356.11.1.73.2.3.1.4
lcsStatusWlanMngmtApConfCommonprofilsEntryContr OBJECT-TYPE
    SYNTAX     DisplayString (SIZE(0..159))
    MAX-ACCESS read-only
    STATUS     current
    DESCRIPTION
            ""
    ::= { lcsStatusWlanMngmtApConfCommonprofilsEntry 4 }

-- {COLUMN} 1.3.6.1.4.1.2356.11.1.73.2.3.1.6
lcsStatusWlanMngmtApConfCommonprofilsEntryIeee80211uGeneral OBJECT-TYPE
    SYNTAX     DisplayString (SIZE(0..31))
    MAX-ACCESS read-only
    STATUS     current
    DESCRIPTION
            "-- empty --"
    ::= { lcsStatusWlanMngmtApConfCommonprofilsEntry 6 }

-- {COLUMN} 1.3.6.1.4.1.2356.11.1.73.2.3.1.7
lcsStatusWlanMngmtApConfCommonprofilsEntryConfigurationDelay OBJECT-TYPE
    SYNTAX     Integer32 (0..2147483647)
    MAX-ACCESS read-only
    STATUS     current
    DESCRIPTION
            "-- empty --"
    ::= { lcsStatusWlanMngmtApConfCommonprofilsEntry 7 }

-- {COLUMN} 1.3.6.1.4.1.2356.11.1.73.2.3.1.8
lcsStatusWlanMngmtApConfCommonprofilsEntryLedProfile OBJECT-TYPE
    SYNTAX     DisplayString (SIZE(0..31))
    MAX-ACCESS read-only
    STATUS     current
    DESCRIPTION
            "-- empty --"
    ::= { lcsStatusWlanMngmtApConfCommonprofilsEntry 8 }

-- {COLUMN} 1.3.6.1.4.1.2356.11.1.73.2.3.1.9
lcsStatusWlanMngmtApConfCommonprofilsEntryLbsGeneralProfile OBJECT-TYPE
    SYNTAX     DisplayString (SIZE(0..31))
    MAX-ACCESS read-only
    STATUS     current
    DESCRIPTION
            "-- empty --"
    ::= { lcsStatusWlanMngmtApConfCommonprofilsEntry 9 }

-- {COLUMN} 1.3.6.1.4.1.2356.11.1.73.2.3.1.10
lcsStatusWlanMngmtApConfCommonprofilsEntryWirelessEpaperProfile OBJECT-TYPE
    SYNTAX     DisplayString (SIZE(0..31))
    MAX-ACCESS read-only
    STATUS     current
    DESCRIPTION
            "-- empty --"
    ::= { lcsStatusWlanMngmtApConfCommonprofilsEntry 10 }

-- {COLUMN} 1.3.6.1.4.1.2356.11.1.73.2.3.1.11
lcsStatusWlanMngmtApConfCommonprofilsEntryEventTimeout OBJECT-TYPE
    SYNTAX     Integer32 (0..2147483647)
    MAX-ACCESS read-only
    STATUS     current
    DESCRIPTION
            "-- empty --"
    ::= { lcsStatusWlanMngmtApConfCommonprofilsEntry 11 }

-- {COLUMN} 1.3.6.1.4.1.2356.11.1.73.2.3.1.248
lcsStatusWlanMngmtApConfCommonprofilsEntryWirelessIdsProfile OBJECT-TYPE
    SYNTAX     DisplayString (SIZE(0..31))
    MAX-ACCESS read-only
    STATUS     current
    DESCRIPTION
            "-- empty --"
    ::= { lcsStatusWlanMngmtApConfCommonprofilsEntry 248 }

-- {TABLE} 1.3.6.1.4.1.2356.11.1.73.2.4
lcsStatusWlanMngmtApConfApsTable OBJECT-TYPE
    SYNTAX     SEQUENCE OF LcsStatusWlanMngmtApConfApsEntry
    MAX-ACCESS not-accessible
    STATUS     current
    DESCRIPTION
            "accesspoints"
    ::= { lcsStatusWlanMngmtApConf 4 }

-- {ROW} 1.3.6.1.4.1.2356.11.1.73.2.4.1
lcsStatusWlanMngmtApConfApsEntry OBJECT-TYPE
    SYNTAX     LcsStatusWlanMngmtApConfApsEntry
    MAX-ACCESS not-accessible
    STATUS     current
    DESCRIPTION
            ""
    INDEX {
            lcsStatusWlanMngmtApConfApsEntryMacAddress
          }
    ::= { lcsStatusWlanMngmtApConfApsTable 1 }

LcsStatusWlanMngmtApConfApsEntry ::= SEQUENCE {
            lcsStatusWlanMngmtApConfApsEntryMacAddress DisplayString,
            lcsStatusWlanMngmtApConfApsEntryName DisplayString,
            lcsStatusWlanMngmtApConfApsEntryLocation DisplayString,
            lcsStatusWlanMngmtApConfApsEntryProfile DisplayString,
            lcsStatusWlanMngmtApConfApsEntryDeviceParameters DisplayString,
            lcsStatusWlanMngmtApConfApsEntryEncryption INTEGER,
            lcsStatusWlanMngmtApConfApsEntryWlanModule1 INTEGER,
            lcsStatusWlanMngmtApConfApsEntryWlanModule2 INTEGER,
            lcsStatusWlanMngmtApConfApsEntryModule1ChannelList DisplayString,
            lcsStatusWlanMngmtApConfApsEntryModule2ChannelList DisplayString,
            lcsStatusWlanMngmtApConfApsEntryOperating INTEGER,
            lcsStatusWlanMngmtApConfApsEntryIpAddress IpAddress,
            lcsStatusWlanMngmtApConfApsEntryNetmask IpAddress,
            lcsStatusWlanMngmtApConfApsEntryGateway IpAddress,
            lcsStatusWlanMngmtApConfApsEntryAllow40mhz INTEGER,
            lcsStatusWlanMngmtApConfApsEntryAntennaMask INTEGER,
            lcsStatusWlanMngmtApConfApsEntryApIntranet DisplayString,
            lcsStatusWlanMngmtApConfApsEntryManageFirmware INTEGER,
            lcsStatusWlanMngmtApConfApsEntryMngmtFwAddInfo INTEGER,
            lcsStatusWlanMngmtApConfApsEntryModule1AntGain DisplayString,
            lcsStatusWlanMngmtApConfApsEntryModule2AntGain DisplayString,
            lcsStatusWlanMngmtApConfApsEntryModule1TxReduct DisplayString,
            lcsStatusWlanMngmtApConfApsEntryModule2TxReduct DisplayString,
            lcsStatusWlanMngmtApConfApsEntryGroups DisplayString,
            lcsStatusWlanMngmtApConfApsEntryModule2MaxChannelBandwidth INTEGER,
            lcsStatusWlanMngmtApConfApsEntryModule1MaxChannelBandwidth INTEGER,
            lcsStatusWlanMngmtApConfApsEntryClientSteeringProfile DisplayString,
            lcsStatusWlanMngmtApConfApsEntryLbsDeviceLocationProfile DisplayString,
            lcsStatusWlanMngmtApConfApsEntryWirelessEpaperChannel INTEGER,
            lcsStatusWlanMngmtApConfApsEntryIbeaconProfile DisplayString,
            lcsStatusWlanMngmtApConfApsEntryIbeaconChannel BITS,
            lcsStatusWlanMngmtApConfApsEntryMinor Integer32,
            lcsStatusWlanMngmtApConfApsEntryIbeaconTransmitPower INTEGER,
            lcsStatusWlanMngmtApConfApsEntrySnmpComment DisplayString,
            lcsStatusWlanMngmtApConfApsEntryModule1AntGainMode INTEGER,
            lcsStatusWlanMngmtApConfApsEntryModule2AntGainMode INTEGER,
            lcsStatusWlanMngmtApConfApsEntryModule1RxPacketSensReduction DisplayString,
            lcsStatusWlanMngmtApConfApsEntryModule2RxPacketSensReduction DisplayString
    }

-- {COLUMN} 1.3.6.1.4.1.2356.11.1.73.2.4.1.1
lcsStatusWlanMngmtApConfApsEntryMacAddress OBJECT-TYPE
    SYNTAX     DisplayString (SIZE(0..12))
    MAX-ACCESS read-only
    STATUS     current
    DESCRIPTION
            ""
    ::= { lcsStatusWlanMngmtApConfApsEntry 1 }

-- {COLUMN} 1.3.6.1.4.1.2356.11.1.73.2.4.1.2
lcsStatusWlanMngmtApConfApsEntryName OBJECT-TYPE
    SYNTAX     DisplayString (SIZE(0..64))
    MAX-ACCESS read-only
    STATUS     current
    DESCRIPTION
            ""
    ::= { lcsStatusWlanMngmtApConfApsEntry 2 }

-- {COLUMN} 1.3.6.1.4.1.2356.11.1.73.2.4.1.3
lcsStatusWlanMngmtApConfApsEntryLocation OBJECT-TYPE
    SYNTAX     DisplayString (SIZE(0..251))
    MAX-ACCESS read-only
    STATUS     current
    DESCRIPTION
            ""
    ::= { lcsStatusWlanMngmtApConfApsEntry 3 }

-- {COLUMN} 1.3.6.1.4.1.2356.11.1.73.2.4.1.4
lcsStatusWlanMngmtApConfApsEntryProfile OBJECT-TYPE
    SYNTAX     DisplayString (SIZE(0..31))
    MAX-ACCESS read-only
    STATUS     current
    DESCRIPTION
            ""
    ::= { lcsStatusWlanMngmtApConfApsEntry 4 }

-- {COLUMN} 1.3.6.1.4.1.2356.11.1.73.2.4.1.5
lcsStatusWlanMngmtApConfApsEntryDeviceParameters OBJECT-TYPE
    SYNTAX     DisplayString (SIZE(0..31))
    MAX-ACCESS read-only
    STATUS     current
    DESCRIPTION
            ""
    ::= { lcsStatusWlanMngmtApConfApsEntry 5 }

-- {COLUMN} 1.3.6.1.4.1.2356.11.1.73.2.4.1.6
lcsStatusWlanMngmtApConfApsEntryEncryption OBJECT-TYPE
    SYNTAX     INTEGER {
                  eDefault (0),
                  eDtls (1),
                  eNo (2)
            }
    MAX-ACCESS read-only
    STATUS     current
    DESCRIPTION
            ""
    ::= { lcsStatusWlanMngmtApConfApsEntry 6 }

-- {COLUMN} 1.3.6.1.4.1.2356.11.1.73.2.4.1.7
lcsStatusWlanMngmtApConfApsEntryWlanModule1 OBJECT-TYPE
    SYNTAX     INTEGER {
                  eDefault (0),
                  e24ghz (1),
                  e5ghz (2),
                  eOff (3),
                  eAuto (255)
            }
    MAX-ACCESS read-only
    STATUS     current
    DESCRIPTION
            ""
    ::= { lcsStatusWlanMngmtApConfApsEntry 7 }

-- {COLUMN} 1.3.6.1.4.1.2356.11.1.73.2.4.1.8
lcsStatusWlanMngmtApConfApsEntryWlanModule2 OBJECT-TYPE
    SYNTAX     INTEGER {
                  eDefault (0),
                  e24ghz (1),
                  e5ghz (2),
                  eOff (3),
                  eAuto (255)
            }
    MAX-ACCESS read-only
    STATUS     current
    DESCRIPTION
            ""
    ::= { lcsStatusWlanMngmtApConfApsEntry 8 }

-- {COLUMN} 1.3.6.1.4.1.2356.11.1.73.2.4.1.9
lcsStatusWlanMngmtApConfApsEntryModule1ChannelList OBJECT-TYPE
    SYNTAX     DisplayString (SIZE(0..48))
    MAX-ACCESS read-only
    STATUS     current
    DESCRIPTION
            ""
    ::= { lcsStatusWlanMngmtApConfApsEntry 9 }

-- {COLUMN} 1.3.6.1.4.1.2356.11.1.73.2.4.1.10
lcsStatusWlanMngmtApConfApsEntryModule2ChannelList OBJECT-TYPE
    SYNTAX     DisplayString (SIZE(0..48))
    MAX-ACCESS read-only
    STATUS     current
    DESCRIPTION
            ""
    ::= { lcsStatusWlanMngmtApConfApsEntry 10 }

-- {COLUMN} 1.3.6.1.4.1.2356.11.1.73.2.4.1.11
lcsStatusWlanMngmtApConfApsEntryOperating OBJECT-TYPE
    SYNTAX     INTEGER {
                  eYes (0),
                  eNo (1)
            }
    MAX-ACCESS read-only
    STATUS     current
    DESCRIPTION
            ""
    ::= { lcsStatusWlanMngmtApConfApsEntry 11 }

-- {COLUMN} 1.3.6.1.4.1.2356.11.1.73.2.4.1.12
lcsStatusWlanMngmtApConfApsEntryIpAddress OBJECT-TYPE
    SYNTAX     IpAddress
    MAX-ACCESS read-only
    STATUS     current
    DESCRIPTION
            ""
    ::= { lcsStatusWlanMngmtApConfApsEntry 12 }

-- {COLUMN} 1.3.6.1.4.1.2356.11.1.73.2.4.1.13
lcsStatusWlanMngmtApConfApsEntryNetmask OBJECT-TYPE
    SYNTAX     IpAddress
    MAX-ACCESS read-only
    STATUS     current
    DESCRIPTION
            ""
    ::= { lcsStatusWlanMngmtApConfApsEntry 13 }

-- {COLUMN} 1.3.6.1.4.1.2356.11.1.73.2.4.1.14
lcsStatusWlanMngmtApConfApsEntryGateway OBJECT-TYPE
    SYNTAX     IpAddress
    MAX-ACCESS read-only
    STATUS     current
    DESCRIPTION
            ""
    ::= { lcsStatusWlanMngmtApConfApsEntry 14 }

-- {COLUMN} 1.3.6.1.4.1.2356.11.1.73.2.4.1.15
lcsStatusWlanMngmtApConfApsEntryAllow40mhz OBJECT-TYPE
    SYNTAX     INTEGER {
                  eAuto (0),
                  eNo (1)
            }
    MAX-ACCESS read-only
    STATUS     current
    DESCRIPTION
            ""
    ::= { lcsStatusWlanMngmtApConfApsEntry 15 }

-- {COLUMN} 1.3.6.1.4.1.2356.11.1.73.2.4.1.16
lcsStatusWlanMngmtApConfApsEntryAntennaMask OBJECT-TYPE
    SYNTAX     INTEGER {
                  eAuto (0),
                  eAntenna1 (1),
                  eAntenna1Plus2 (3),
                  eAntenna1Plus3 (5),
                  eAntenna1Plus2Plus3 (7),
                  eAntenna1Plus2Plus3Plus4 (15)
            }
    MAX-ACCESS read-only
    STATUS     current
    DESCRIPTION
            ""
    ::= { lcsStatusWlanMngmtApConfApsEntry 16 }

-- {COLUMN} 1.3.6.1.4.1.2356.11.1.73.2.4.1.17
lcsStatusWlanMngmtApConfApsEntryApIntranet OBJECT-TYPE
    SYNTAX     DisplayString (SIZE(0..31))
    MAX-ACCESS read-only
    STATUS     current
    DESCRIPTION
            ""
    ::= { lcsStatusWlanMngmtApConfApsEntry 17 }

-- {COLUMN} 1.3.6.1.4.1.2356.11.1.73.2.4.1.18
lcsStatusWlanMngmtApConfApsEntryManageFirmware OBJECT-TYPE
    SYNTAX     INTEGER {
                  eYes (0),
                  eNo (1)
            }
    MAX-ACCESS read-only
    STATUS     current
    DESCRIPTION
            ""
    ::= { lcsStatusWlanMngmtApConfApsEntry 18 }

-- {COLUMN} 1.3.6.1.4.1.2356.11.1.73.2.4.1.19
lcsStatusWlanMngmtApConfApsEntryMngmtFwAddInfo OBJECT-TYPE
    SYNTAX     INTEGER {
                  eDisabledDueToErrorDuringUpdate (1),
                  eDisabledByManualUpload (2)
            }
    MAX-ACCESS read-only
    STATUS     current
    DESCRIPTION
            ""
    ::= { lcsStatusWlanMngmtApConfApsEntry 19 }

-- {COLUMN} 1.3.6.1.4.1.2356.11.1.73.2.4.1.20
lcsStatusWlanMngmtApConfApsEntryModule1AntGain OBJECT-TYPE
    SYNTAX     DisplayString (SIZE(0..4))
    MAX-ACCESS read-only
    STATUS     current
    DESCRIPTION
            ""
    ::= { lcsStatusWlanMngmtApConfApsEntry 20 }

-- {COLUMN} 1.3.6.1.4.1.2356.11.1.73.2.4.1.21
lcsStatusWlanMngmtApConfApsEntryModule2AntGain OBJECT-TYPE
    SYNTAX     DisplayString (SIZE(0..4))
    MAX-ACCESS read-only
    STATUS     current
    DESCRIPTION
            ""
    ::= { lcsStatusWlanMngmtApConfApsEntry 21 }

-- {COLUMN} 1.3.6.1.4.1.2356.11.1.73.2.4.1.22
lcsStatusWlanMngmtApConfApsEntryModule1TxReduct OBJECT-TYPE
    SYNTAX     DisplayString (SIZE(0..3))
    MAX-ACCESS read-only
    STATUS     current
    DESCRIPTION
            ""
    ::= { lcsStatusWlanMngmtApConfApsEntry 22 }

-- {COLUMN} 1.3.6.1.4.1.2356.11.1.73.2.4.1.23
lcsStatusWlanMngmtApConfApsEntryModule2TxReduct OBJECT-TYPE
    SYNTAX     DisplayString (SIZE(0..3))
    MAX-ACCESS read-only
    STATUS     current
    DESCRIPTION
            ""
    ::= { lcsStatusWlanMngmtApConfApsEntry 23 }

-- {COLUMN} 1.3.6.1.4.1.2356.11.1.73.2.4.1.24
lcsStatusWlanMngmtApConfApsEntryGroups OBJECT-TYPE
    SYNTAX     DisplayString (SIZE(0..251))
    MAX-ACCESS read-only
    STATUS     current
    DESCRIPTION
            "-- empty --"
    ::= { lcsStatusWlanMngmtApConfApsEntry 24 }

-- {COLUMN} 1.3.6.1.4.1.2356.11.1.73.2.4.1.25
lcsStatusWlanMngmtApConfApsEntryModule2MaxChannelBandwidth OBJECT-TYPE
    SYNTAX     INTEGER {
                  e20mhz (0),
                  e40mhz (1),
                  e80mhz (2),
                  e160mhz (3),
                  e80Plus80mhz (4),
                  eAuto (255)
            }
    MAX-ACCESS read-only
    STATUS     current
    DESCRIPTION
            "-- empty --"
    ::= { lcsStatusWlanMngmtApConfApsEntry 25 }

-- {COLUMN} 1.3.6.1.4.1.2356.11.1.73.2.4.1.26
lcsStatusWlanMngmtApConfApsEntryModule1MaxChannelBandwidth OBJECT-TYPE
    SYNTAX     INTEGER {
                  e20mhz (0),
                  e40mhz (1),
                  e80mhz (2),
                  e160mhz (3),
                  e80Plus80mhz (4),
                  eAuto (255)
            }
    MAX-ACCESS read-only
    STATUS     current
    DESCRIPTION
            "-- empty --"
    ::= { lcsStatusWlanMngmtApConfApsEntry 26 }

-- {COLUMN} 1.3.6.1.4.1.2356.11.1.73.2.4.1.27
lcsStatusWlanMngmtApConfApsEntryClientSteeringProfile OBJECT-TYPE
    SYNTAX     DisplayString (SIZE(0..31))
    MAX-ACCESS read-only
    STATUS     current
    DESCRIPTION
            "-- empty --"
    ::= { lcsStatusWlanMngmtApConfApsEntry 27 }

-- {COLUMN} 1.3.6.1.4.1.2356.11.1.73.2.4.1.28
lcsStatusWlanMngmtApConfApsEntryLbsDeviceLocationProfile OBJECT-TYPE
    SYNTAX     DisplayString (SIZE(0..32))
    MAX-ACCESS read-only
    STATUS     current
    DESCRIPTION
            "-- empty --"
    ::= { lcsStatusWlanMngmtApConfApsEntry 28 }

-- {COLUMN} 1.3.6.1.4.1.2356.11.1.73.2.4.1.29
lcsStatusWlanMngmtApConfApsEntryWirelessEpaperChannel OBJECT-TYPE
    SYNTAX     INTEGER {
                  e2404mhz (0),
                  e2410mhz (1),
                  e2422mhz (2),
                  e2425mhz (3),
                  e2442mhz (4),
                  e2450mhz (5),
                  e2462mhz (6),
                  e2470mhz (7),
                  e2474mhz (8),
                  e2477mhz (9),
                  e2480mhz (10),
                  eAuto (255)
            }
    MAX-ACCESS read-only
    STATUS     current
    DESCRIPTION
            "-- empty --"
    ::= { lcsStatusWlanMngmtApConfApsEntry 29 }

-- {COLUMN} 1.3.6.1.4.1.2356.11.1.73.2.4.1.30
lcsStatusWlanMngmtApConfApsEntryIbeaconProfile OBJECT-TYPE
    SYNTAX     DisplayString (SIZE(0..31))
    MAX-ACCESS read-only
    STATUS     current
    DESCRIPTION
            "-- empty --"
    ::= { lcsStatusWlanMngmtApConfApsEntry 30 }

-- {COLUMN} 1.3.6.1.4.1.2356.11.1.73.2.4.1.31
lcsStatusWlanMngmtApConfApsEntryIbeaconChannel OBJECT-TYPE
    SYNTAX     BITS {
                  e2480mhz (5),
                  e2426mhz (6),
                  e2402mhz (7)
            }
    MAX-ACCESS read-only
    STATUS     current
    DESCRIPTION
            "-- empty --"
    ::= { lcsStatusWlanMngmtApConfApsEntry 31 }

-- {COLUMN} 1.3.6.1.4.1.2356.11.1.73.2.4.1.32
lcsStatusWlanMngmtApConfApsEntryMinor OBJECT-TYPE
    SYNTAX     Integer32 (0..65535)
    MAX-ACCESS read-only
    STATUS     current
    DESCRIPTION
            "-- empty --"
    ::= { lcsStatusWlanMngmtApConfApsEntry 32 }

-- {COLUMN} 1.3.6.1.4.1.2356.11.1.73.2.4.1.33
lcsStatusWlanMngmtApConfApsEntryIbeaconTransmitPower OBJECT-TYPE
    SYNTAX     INTEGER {
                  eLow (0),
                  eMedium (1),
                  eHigh (2)
            }
    MAX-ACCESS read-only
    STATUS     current
    DESCRIPTION
            "-- empty --"
    ::= { lcsStatusWlanMngmtApConfApsEntry 33 }

-- {COLUMN} 1.3.6.1.4.1.2356.11.1.73.2.4.1.34
lcsStatusWlanMngmtApConfApsEntrySnmpComment OBJECT-TYPE
    SYNTAX     DisplayString (SIZE(0..251))
    MAX-ACCESS read-only
    STATUS     current
    DESCRIPTION
            "-- empty --"
    ::= { lcsStatusWlanMngmtApConfApsEntry 34 }

-- {COLUMN} 1.3.6.1.4.1.2356.11.1.73.2.4.1.35
lcsStatusWlanMngmtApConfApsEntryModule1AntGainMode OBJECT-TYPE
    SYNTAX     INTEGER {
                  eStandard (0),
                  eUserDefined (1)
            }
    MAX-ACCESS read-only
    STATUS     current
    DESCRIPTION
            "-- empty --"
    ::= { lcsStatusWlanMngmtApConfApsEntry 35 }

-- {COLUMN} 1.3.6.1.4.1.2356.11.1.73.2.4.1.36
lcsStatusWlanMngmtApConfApsEntryModule2AntGainMode OBJECT-TYPE
    SYNTAX     INTEGER {
                  eStandard (0),
                  eUserDefined (1)
            }
    MAX-ACCESS read-only
    STATUS     current
    DESCRIPTION
            "-- empty --"
    ::= { lcsStatusWlanMngmtApConfApsEntry 36 }

-- {COLUMN} 1.3.6.1.4.1.2356.11.1.73.2.4.1.37
lcsStatusWlanMngmtApConfApsEntryModule1RxPacketSensReduction OBJECT-TYPE
    SYNTAX     DisplayString (SIZE(0..3))
    MAX-ACCESS read-only
    STATUS     current
    DESCRIPTION
            "-- empty --"
    ::= { lcsStatusWlanMngmtApConfApsEntry 37 }

-- {COLUMN} 1.3.6.1.4.1.2356.11.1.73.2.4.1.38
lcsStatusWlanMngmtApConfApsEntryModule2RxPacketSensReduction OBJECT-TYPE
    SYNTAX     DisplayString (SIZE(0..3))
    MAX-ACCESS read-only
    STATUS     current
    DESCRIPTION
            "-- empty --"
    ::= { lcsStatusWlanMngmtApConfApsEntry 38 }

-- {TABLE} 1.3.6.1.4.1.2356.11.1.73.2.5
lcsStatusWlanMngmtApConfNetwProfErrorsTable OBJECT-TYPE
    SYNTAX     SEQUENCE OF LcsStatusWlanMngmtApConfNetwProfErrorsEntry
    MAX-ACCESS not-accessible
    STATUS     current
    DESCRIPTION
            ""
    ::= { lcsStatusWlanMngmtApConf 5 }

-- {ROW} 1.3.6.1.4.1.2356.11.1.73.2.5.1
lcsStatusWlanMngmtApConfNetwProfErrorsEntry OBJECT-TYPE
    SYNTAX     LcsStatusWlanMngmtApConfNetwProfErrorsEntry
    MAX-ACCESS not-accessible
    STATUS     current
    DESCRIPTION
            ""
    INDEX {
            lcsStatusWlanMngmtApConfNetwProfErrorsEntryIndex
          }
    ::= { lcsStatusWlanMngmtApConfNetwProfErrorsTable 1 }

LcsStatusWlanMngmtApConfNetwProfErrorsEntry ::= SEQUENCE {
            lcsStatusWlanMngmtApConfNetwProfErrorsEntryIndex Integer32,
            lcsStatusWlanMngmtApConfNetwProfErrorsEntryName DisplayString,
            lcsStatusWlanMngmtApConfNetwProfErrorsEntryError INTEGER
    }

-- {COLUMN} 1.3.6.1.4.1.2356.11.1.73.2.5.1.1
lcsStatusWlanMngmtApConfNetwProfErrorsEntryIndex OBJECT-TYPE
    SYNTAX     Integer32 (0..2147483647)
    MAX-ACCESS read-only
    STATUS     current
    DESCRIPTION
            ""
    ::= { lcsStatusWlanMngmtApConfNetwProfErrorsEntry 1 }

-- {COLUMN} 1.3.6.1.4.1.2356.11.1.73.2.5.1.2
lcsStatusWlanMngmtApConfNetwProfErrorsEntryName OBJECT-TYPE
    SYNTAX     DisplayString (SIZE(0..31))
    MAX-ACCESS read-only
    STATUS     current
    DESCRIPTION
            ""
    ::= { lcsStatusWlanMngmtApConfNetwProfErrorsEntry 2 }

-- {COLUMN} 1.3.6.1.4.1.2356.11.1.73.2.5.1.3
lcsStatusWlanMngmtApConfNetwProfErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eWlanProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20),
                  eAutowdsSsidNotUnique (21),
                  eAutowdsProfileNotUnique (22),
                  eAutowdsSsidNotDefined (23),
                  eLepsUProfileIsMissing (24)
            }
    MAX-ACCESS read-only
    STATUS     current
    DESCRIPTION
            ""
    ::= { lcsStatusWlanMngmtApConfNetwProfErrorsEntry 3 }

-- {TABLE} 1.3.6.1.4.1.2356.11.1.73.2.6
lcsStatusWlanMngmtApConfRadioProfErrorsTable OBJECT-TYPE
    SYNTAX     SEQUENCE OF LcsStatusWlanMngmtApConfRadioProfErrorsEntry
    MAX-ACCESS not-accessible
    STATUS     current
    DESCRIPTION
            ""
    ::= { lcsStatusWlanMngmtApConf 6 }

-- {ROW} 1.3.6.1.4.1.2356.11.1.73.2.6.1
lcsStatusWlanMngmtApConfRadioProfErrorsEntry OBJECT-TYPE
    SYNTAX     LcsStatusWlanMngmtApConfRadioProfErrorsEntry
    MAX-ACCESS not-accessible
    STATUS     current
    DESCRIPTION
            ""
    INDEX {
            lcsStatusWlanMngmtApConfRadioProfErrorsEntryIndex
          }
    ::= { lcsStatusWlanMngmtApConfRadioProfErrorsTable 1 }

LcsStatusWlanMngmtApConfRadioProfErrorsEntry ::= SEQUENCE {
            lcsStatusWlanMngmtApConfRadioProfErrorsEntryIndex Integer32,
            lcsStatusWlanMngmtApConfRadioProfErrorsEntryName DisplayString,
            lcsStatusWlanMngmtApConfRadioProfErrorsEntryError INTEGER
    }

-- {COLUMN} 1.3.6.1.4.1.2356.11.1.73.2.6.1.1
lcsStatusWlanMngmtApConfRadioProfErrorsEntryIndex OBJECT-TYPE
    SYNTAX     Integer32 (0..2147483647)
    MAX-ACCESS read-only
    STATUS     current
    DESCRIPTION
            ""
    ::= { lcsStatusWlanMngmtApConfRadioProfErrorsEntry 1 }

-- {COLUMN} 1.3.6.1.4.1.2356.11.1.73.2.6.1.2
lcsStatusWlanMngmtApConfRadioProfErrorsEntryName OBJECT-TYPE
    SYNTAX     DisplayString (SIZE(0..31))
    MAX-ACCESS read-only
    STATUS     current
    DESCRIPTION
            ""
    ::= { lcsStatusWlanMngmtApConfRadioProfErrorsEntry 2 }

-- {COLUMN} 1.3.6.1.4.1.2356.11.1.73.2.6.1.3
lcsStatusWlanMngmtApConfRadioProfErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eWlanProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20),
                  eAutowdsSsidNotUnique (21),
                  eAutowdsProfileNotUnique (22),
                  eAutowdsSsidNotDefined (23),
                  eLepsUProfileIsMissing (24)
            }
    MAX-ACCESS read-only
    STATUS     current
    DESCRIPTION
            ""
    ::= { lcsStatusWlanMngmtApConfRadioProfErrorsEntry 3 }

-- {TABLE} 1.3.6.1.4.1.2356.11.1.73.2.7
lcsStatusWlanMngmtApConfCommProfErrorsTable OBJECT-TYPE
    SYNTAX     SEQUENCE OF LcsStatusWlanMngmtApConfCommProfErrorsEntry
    MAX-ACCESS not-accessible
    STATUS     current
    DESCRIPTION
            ""
    ::= { lcsStatusWlanMngmtApConf 7 }

-- {ROW} 1.3.6.1.4.1.2356.11.1.73.2.7.1
lcsStatusWlanMngmtApConfCommProfErrorsEntry OBJECT-TYPE
    SYNTAX     LcsStatusWlanMngmtApConfCommProfErrorsEntry
    MAX-ACCESS not-accessible
    STATUS     current
    DESCRIPTION
            ""
    INDEX {
            lcsStatusWlanMngmtApConfCommProfErrorsEntryIndex
          }
    ::= { lcsStatusWlanMngmtApConfCommProfErrorsTable 1 }

LcsStatusWlanMngmtApConfCommProfErrorsEntry ::= SEQUENCE {
            lcsStatusWlanMngmtApConfCommProfErrorsEntryIndex Integer32,
            lcsStatusWlanMngmtApConfCommProfErrorsEntryName DisplayString,
            lcsStatusWlanMngmtApConfCommProfErrorsEntryError INTEGER,
            lcsStatusWlanMngmtApConfCommProfErrorsEntryNetworkApParameters DisplayString
    }

-- {COLUMN} 1.3.6.1.4.1.2356.11.1.73.2.7.1.1
lcsStatusWlanMngmtApConfCommProfErrorsEntryIndex OBJECT-TYPE
    SYNTAX     Integer32 (0..2147483647)
    MAX-ACCESS read-only
    STATUS     current
    DESCRIPTION
            ""
    ::= { lcsStatusWlanMngmtApConfCommProfErrorsEntry 1 }

-- {COLUMN} 1.3.6.1.4.1.2356.11.1.73.2.7.1.2
lcsStatusWlanMngmtApConfCommProfErrorsEntryName OBJECT-TYPE
    SYNTAX     DisplayString (SIZE(0..31))
    MAX-ACCESS read-only
    STATUS     current
    DESCRIPTION
            ""
    ::= { lcsStatusWlanMngmtApConfCommProfErrorsEntry 2 }

-- {COLUMN} 1.3.6.1.4.1.2356.11.1.73.2.7.1.3
lcsStatusWlanMngmtApConfCommProfErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eWlanProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20),
                  eAutowdsSsidNotUnique (21),
                  eAutowdsProfileNotUnique (22),
                  eAutowdsSsidNotDefined (23),
                  eLepsUProfileIsMissing (24)
            }
    MAX-ACCESS read-only
    STATUS     current
    DESCRIPTION
            ""
    ::= { lcsStatusWlanMngmtApConfCommProfErrorsEntry 3 }

-- {COLUMN} 1.3.6.1.4.1.2356.11.1.73.2.7.1.4
lcsStatusWlanMngmtApConfCommProfErrorsEntryNetworkApParameters OBJECT-TYPE
    SYNTAX     DisplayString (SIZE(0..31))
    MAX-ACCESS read-only
    STATUS     current
    DESCRIPTION
            ""
    ::= { lcsStatusWlanMngmtApConfCommProfErrorsEntry 4 }

-- {TABLE} 1.3.6.1.4.1.2356.11.1.73.2.8
lcsStatusWlanMngmtApConfApConfErrorsTable OBJECT-TYPE
    SYNTAX     SEQUENCE OF LcsStatusWlanMngmtApConfApConfErrorsEntry
    MAX-ACCESS not-accessible
    STATUS     current
    DESCRIPTION
            ""
    ::= { lcsStatusWlanMngmtApConf 8 }

-- {ROW} 1.3.6.1.4.1.2356.11.1.73.2.8.1
lcsStatusWlanMngmtApConfApConfErrorsEntry OBJECT-TYPE
    SYNTAX     LcsStatusWlanMngmtApConfApConfErrorsEntry
    MAX-ACCESS not-accessible
    STATUS     current
    DESCRIPTION
            ""
    INDEX {
            lcsStatusWlanMngmtApConfApConfErrorsEntryIndex
          }
    ::= { lcsStatusWlanMngmtApConfApConfErrorsTable 1 }

LcsStatusWlanMngmtApConfApConfErrorsEntry ::= SEQUENCE {
            lcsStatusWlanMngmtApConfApConfErrorsEntryIndex Integer32,
            lcsStatusWlanMngmtApConfApConfErrorsEntryName DisplayString,
            lcsStatusWlanMngmtApConfApConfErrorsEntryError INTEGER,
            lcsStatusWlanMngmtApConfApConfErrorsEntryProfile DisplayString,
            lcsStatusWlanMngmtApConfApConfErrorsEntryMacAddress DisplayString,
            lcsStatusWlanMngmtApConfApConfErrorsEntryGroup DisplayString,
            lcsStatusWlanMngmtApConfApConfErrorsEntryErrorMessage DisplayString
    }

-- {COLUMN} 1.3.6.1.4.1.2356.11.1.73.2.8.1.1
lcsStatusWlanMngmtApConfApConfErrorsEntryIndex OBJECT-TYPE
    SYNTAX     Integer32 (0..2147483647)
    MAX-ACCESS read-only
    STATUS     current
    DESCRIPTION
            ""
    ::= { lcsStatusWlanMngmtApConfApConfErrorsEntry 1 }

-- {COLUMN} 1.3.6.1.4.1.2356.11.1.73.2.8.1.2
lcsStatusWlanMngmtApConfApConfErrorsEntryName OBJECT-TYPE
    SYNTAX     DisplayString (SIZE(0..31))
    MAX-ACCESS read-only
    STATUS     current
    DESCRIPTION
            ""
    ::= { lcsStatusWlanMngmtApConfApConfErrorsEntry 2 }

-- {COLUMN} 1.3.6.1.4.1.2356.11.1.73.2.8.1.3
lcsStatusWlanMngmtApConfApConfErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eWlanProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20),
                  eAutowdsSsidNotUnique (21),
                  eAutowdsProfileNotUnique (22),
                  eAutowdsSsidNotDefined (23),
                  eLepsUProfileIsMissing (24)
            }
    MAX-ACCESS read-only
    STATUS     current
    DESCRIPTION
            ""
    ::= { lcsStatusWlanMngmtApConfApConfErrorsEntry 3 }

-- {COLUMN} 1.3.6.1.4.1.2356.11.1.73.2.8.1.4
lcsStatusWlanMngmtApConfApConfErrorsEntryProfile OBJECT-TYPE
    SYNTAX     DisplayString (SIZE(0..31))
    MAX-ACCESS read-only
    STATUS     current
    DESCRIPTION
            ""
    ::= { lcsStatusWlanMngmtApConfApConfErrorsEntry 4 }

-- {COLUMN} 1.3.6.1.4.1.2356.11.1.73.2.8.1.5
lcsStatusWlanMngmtApConfApConfErrorsEntryMacAddress OBJECT-TYPE
    SYNTAX     DisplayString (SIZE(0..12))
    MAX-ACCESS read-only
    STATUS     current
    DESCRIPTION
            "-- empty --"
    ::= { lcsStatusWlanMngmtApConfApConfErrorsEntry 5 }

-- {COLUMN} 1.3.6.1.4.1.2356.11.1.73.2.8.1.6
lcsStatusWlanMngmtApConfApConfErrorsEntryGroup OBJECT-TYPE
    SYNTAX     DisplayString (SIZE(0..31))
    MAX-ACCESS read-only
    STATUS     current
    DESCRIPTION
            "-- empty --"
    ::= { lcsStatusWlanMngmtApConfApConfErrorsEntry 6 }

-- {COLUMN} 1.3.6.1.4.1.2356.11.1.73.2.8.1.7
lcsStatusWlanMngmtApConfApConfErrorsEntryErrorMessage OBJECT-TYPE
    SYNTAX     DisplayString (SIZE(0..127))
    MAX-ACCESS read-only
    STATUS     current
    DESCRIPTION
            "-- empty --"
    ::= { lcsStatusWlanMngmtApConfApConfErrorsEntry 7 }

-- {TABLE} 1.3.6.1.4.1.2356.11.1.73.2.9
lcsStatusWlanMngmtApConfApIntranetsTable OBJECT-TYPE
    SYNTAX     SEQUENCE OF LcsStatusWlanMngmtApConfApIntranetsEntry
    MAX-ACCESS not-accessible
    STATUS     current
    DESCRIPTION
            ""
    ::= { lcsStatusWlanMngmtApConf 9 }

-- {ROW} 1.3.6.1.4.1.2356.11.1.73.2.9.1
lcsStatusWlanMngmtApConfApIntranetsEntry OBJECT-TYPE
    SYNTAX     LcsStatusWlanMngmtApConfApIntranetsEntry
    MAX-ACCESS not-accessible
    STATUS     current
    DESCRIPTION
            ""
    INDEX {
            lcsStatusWlanMngmtApConfApIntranetsEntryName
          }
    ::= { lcsStatusWlanMngmtApConfApIntranetsTable 1 }

LcsStatusWlanMngmtApConfApIntranetsEntry ::= SEQUENCE {
            lcsStatusWlanMngmtApConfApIntranetsEntryName DisplayString,
            lcsStatusWlanMngmtApConfApIntranetsEntryParentName DisplayString,
            lcsStatusWlanMngmtApConfApIntranetsEntryLocVal DisplayString,
            lcsStatusWlanMngmtApConfApIntranetsEntryDomainName DisplayString,
            lcsStatusWlanMngmtApConfApIntranetsEntryNetmask IpAddress,
            lcsStatusWlanMngmtApConfApIntranetsEntryGateway IpAddress,
            lcsStatusWlanMngmtApConfApIntranetsEntryPrimaryDnsSrv IpAddress,
            lcsStatusWlanMngmtApConfApIntranetsEntrySecondaryDnsSrv IpAddress,
            lcsStatusWlanMngmtApConfApIntranetsEntryIpv4ConfigPoolStart DisplayString,
            lcsStatusWlanMngmtApConfApIntranetsEntryIpv4ConfigPoolEnd DisplayString
    }

-- {COLUMN} 1.3.6.1.4.1.2356.11.1.73.2.9.1.1
lcsStatusWlanMngmtApConfApIntranetsEntryName OBJECT-TYPE
    SYNTAX     DisplayString (SIZE(0..31))
    MAX-ACCESS read-only
    STATUS     current
    DESCRIPTION
            ""
    ::= { lcsStatusWlanMngmtApConfApIntranetsEntry 1 }

-- {COLUMN} 1.3.6.1.4.1.2356.11.1.73.2.9.1.2
lcsStatusWlanMngmtApConfApIntranetsEntryParentName OBJECT-TYPE
    SYNTAX     DisplayString (SIZE(0..31))
    MAX-ACCESS read-only
    STATUS     current
    DESCRIPTION
            ""
    ::= { lcsStatusWlanMngmtApConfApIntranetsEntry 2 }

-- {COLUMN} 1.3.6.1.4.1.2356.11.1.73.2.9.1.3
lcsStatusWlanMngmtApConfApIntranetsEntryLocVal OBJECT-TYPE
    SYNTAX     DisplayString (SIZE(0..2))
    MAX-ACCESS read-only
    STATUS     current
    DESCRIPTION
            "local values"
    ::= { lcsStatusWlanMngmtApConfApIntranetsEntry 3 }

-- {COLUMN} 1.3.6.1.4.1.2356.11.1.73.2.9.1.4
lcsStatusWlanMngmtApConfApIntranetsEntryDomainName OBJECT-TYPE
    SYNTAX     DisplayString (SIZE(0..63))
    MAX-ACCESS read-only
    STATUS     current
    DESCRIPTION
            ""
    ::= { lcsStatusWlanMngmtApConfApIntranetsEntry 4 }

-- {COLUMN} 1.3.6.1.4.1.2356.11.1.73.2.9.1.5
lcsStatusWlanMngmtApConfApIntranetsEntryNetmask OBJECT-TYPE
    SYNTAX     IpAddress
    MAX-ACCESS read-only
    STATUS     current
    DESCRIPTION
            ""
    ::= { lcsStatusWlanMngmtApConfApIntranetsEntry 5 }

-- {COLUMN} 1.3.6.1.4.1.2356.11.1.73.2.9.1.6
lcsStatusWlanMngmtApConfApIntranetsEntryGateway OBJECT-TYPE
    SYNTAX     IpAddress
    MAX-ACCESS read-only
    STATUS     current
    DESCRIPTION
            ""
    ::= { lcsStatusWlanMngmtApConfApIntranetsEntry 6 }

-- {COLUMN} 1.3.6.1.4.1.2356.11.1.73.2.9.1.7
lcsStatusWlanMngmtApConfApIntranetsEntryPrimaryDnsSrv OBJECT-TYPE
    SYNTAX     IpAddress
    MAX-ACCESS read-only
    STATUS     current
    DESCRIPTION
            ""
    ::= { lcsStatusWlanMngmtApConfApIntranetsEntry 7 }

-- {COLUMN} 1.3.6.1.4.1.2356.11.1.73.2.9.1.8
lcsStatusWlanMngmtApConfApIntranetsEntrySecondaryDnsSrv OBJECT-TYPE
    SYNTAX     IpAddress
    MAX-ACCESS read-only
    STATUS     current
    DESCRIPTION
            ""
    ::= { lcsStatusWlanMngmtApConfApIntranetsEntry 8 }

-- {COLUMN} 1.3.6.1.4.1.2356.11.1.73.2.9.1.9
lcsStatusWlanMngmtApConfApIntranetsEntryIpv4ConfigPoolStart OBJECT-TYPE
    SYNTAX     DisplayString (SIZE(0..15))
    MAX-ACCESS read-only
    STATUS     current
    DESCRIPTION
            "-- empty --"
    ::= { lcsStatusWlanMngmtApConfApIntranetsEntry 9 }

-- {COLUMN} 1.3.6.1.4.1.2356.11.1.73.2.9.1.10
lcsStatusWlanMngmtApConfApIntranetsEntryIpv4ConfigPoolEnd OBJECT-TYPE
    SYNTAX     DisplayString (SIZE(0..15))
    MAX-ACCESS read-only
    STATUS     current
    DESCRIPTION
            "-- empty --"
    ::= { lcsStatusWlanMngmtApConfApIntranetsEntry 10 }

-- {TABLE} 1.3.6.1.4.1.2356.11.1.73.2.10
lcsStatusWlanMngmtApConfApIntranetErrorsTable OBJECT-TYPE
    SYNTAX     SEQUENCE OF LcsStatusWlanMngmtApConfApIntranetErrorsEntry
    MAX-ACCESS not-accessible
    STATUS     current
    DESCRIPTION
            ""
    ::= { lcsStatusWlanMngmtApConf 10 }

-- {ROW} 1.3.6.1.4.1.2356.11.1.73.2.10.1
lcsStatusWlanMngmtApConfApIntranetErrorsEntry OBJECT-TYPE
    SYNTAX     LcsStatusWlanMngmtApConfApIntranetErrorsEntry
    MAX-ACCESS not-accessible
    STATUS     current
    DESCRIPTION
            ""
    INDEX {
            lcsStatusWlanMngmtApConfApIntranetErrorsEntryIndex
          }
    ::= { lcsStatusWlanMngmtApConfApIntranetErrorsTable 1 }

LcsStatusWlanMngmtApConfApIntranetErrorsEntry ::= SEQUENCE {
            lcsStatusWlanMngmtApConfApIntranetErrorsEntryIndex Integer32,
            lcsStatusWlanMngmtApConfApIntranetErrorsEntryName DisplayString,
            lcsStatusWlanMngmtApConfApIntranetErrorsEntryError INTEGER
    }

-- {COLUMN} 1.3.6.1.4.1.2356.11.1.73.2.10.1.1
lcsStatusWlanMngmtApConfApIntranetErrorsEntryIndex OBJECT-TYPE
    SYNTAX     Integer32 (0..2147483647)
    MAX-ACCESS read-only
    STATUS     current
    DESCRIPTION
            ""
    ::= { lcsStatusWlanMngmtApConfApIntranetErrorsEntry 1 }

-- {COLUMN} 1.3.6.1.4.1.2356.11.1.73.2.10.1.2
lcsStatusWlanMngmtApConfApIntranetErrorsEntryName OBJECT-TYPE
    SYNTAX     DisplayString (SIZE(0..31))
    MAX-ACCESS read-only
    STATUS     current
    DESCRIPTION
            ""
    ::= { lcsStatusWlanMngmtApConfApIntranetErrorsEntry 2 }

-- {COLUMN} 1.3.6.1.4.1.2356.11.1.73.2.10.1.3
lcsStatusWlanMngmtApConfApIntranetErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eWlanProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20),
                  eAutowdsSsidNotUnique (21),
                  eAutowdsProfileNotUnique (22),
                  eAutowdsSsidNotDefined (23),
                  eLepsUProfileIsMissing (24)
            }
    MAX-ACCESS read-only
    STATUS     current
    DESCRIPTION
            ""
    ::= { lcsStatusWlanMngmtApConfApIntranetErrorsEntry 3 }

-- {TABLE} 1.3.6.1.4.1.2356.11.1.73.2.11
lcsStatusWlanMngmtApConfAutowdsProfilesTable OBJECT-TYPE
    SYNTAX     SEQUENCE OF LcsStatusWlanMngmtApConfAutowdsProfilesEntry
    MAX-ACCESS not-accessible
    STATUS     current
    DESCRIPTION
            "-- empty --"
    ::= { lcsStatusWlanMngmtApConf 11 }

-- {ROW} 1.3.6.1.4.1.2356.11.1.73.2.11.1
lcsStatusWlanMngmtApConfAutowdsProfilesEntry OBJECT-TYPE
    SYNTAX     LcsStatusWlanMngmtApConfAutowdsProfilesEntry
    MAX-ACCESS not-accessible
    STATUS     current
    DESCRIPTION
            ""
    INDEX {
            lcsStatusWlanMngmtApConfAutowdsProfilesEntryName
          }
    ::= { lcsStatusWlanMngmtApConfAutowdsProfilesTable 1 }

LcsStatusWlanMngmtApConfAutowdsProfilesEntry ::= SEQUENCE {
            lcsStatusWlanMngmtApConfAutowdsProfilesEntryName DisplayString,
            lcsStatusWlanMngmtApConfAutowdsProfilesEntryCommonprofile DisplayString,
            lcsStatusWlanMngmtApConfAutowdsProfilesEntrySsid DisplayString,
            lcsStatusWlanMngmtApConfAutowdsProfilesEntryKey DisplayString,
            lcsStatusWlanMngmtApConfAutowdsProfilesEntryEnabled INTEGER,
            lcsStatusWlanMngmtApConfAutowdsProfilesEntryAllowExprInt INTEGER,
            lcsStatusWlanMngmtApConfAutowdsProfilesEntryTopologyManagement INTEGER,
            lcsStatusWlanMngmtApConfAutowdsProfilesEntrySlaveTxLimit Integer32,
            lcsStatusWlanMngmtApConfAutowdsProfilesEntryMasterTxLimit Integer32,
            lcsStatusWlanMngmtApConfAutowdsProfilesEntryLinkLossTimeout Integer32,
            lcsStatusWlanMngmtApConfAutowdsProfilesEntryContinuation Integer32,
            lcsStatusWlanMngmtApConfAutowdsProfilesEntryTimeTillPreconfScan Integer32,
            lcsStatusWlanMngmtApConfAutowdsProfilesEntryTimeTillExpressScan Integer32,
            lcsStatusWlanMngmtApConfAutowdsProfilesEntryInterfacePairing INTEGER,
            lcsStatusWlanMngmtApConfAutowdsProfilesEntrySlaveRadioMultiHop INTEGER,
            lcsStatusWlanMngmtApConfAutowdsProfilesEntryRadioBand INTEGER,
            lcsStatusWlanMngmtApConfAutowdsProfilesEntrySsidBroadcast INTEGER
    }

-- {COLUMN} 1.3.6.1.4.1.2356.11.1.73.2.11.1.1
lcsStatusWlanMngmtApConfAutowdsProfilesEntryName OBJECT-TYPE
    SYNTAX     DisplayString (SIZE(0..15))
    MAX-ACCESS read-only
    STATUS     current
    DESCRIPTION
            "-- empty --"
    ::= { lcsStatusWlanMngmtApConfAutowdsProfilesEntry 1 }

-- {COLUMN} 1.3.6.1.4.1.2356.11.1.73.2.11.1.2
lcsStatusWlanMngmtApConfAutowdsProfilesEntryCommonprofile OBJECT-TYPE
    SYNTAX     DisplayString (SIZE(0..31))
    MAX-ACCESS read-only
    STATUS     current
    DESCRIPTION
            "-- empty --"
    ::= { lcsStatusWlanMngmtApConfAutowdsProfilesEntry 2 }

-- {COLUMN} 1.3.6.1.4.1.2356.11.1.73.2.11.1.3
lcsStatusWlanMngmtApConfAutowdsProfilesEntrySsid OBJECT-TYPE
    SYNTAX     DisplayString (SIZE(0..32))
    MAX-ACCESS read-only
    STATUS     current
    DESCRIPTION
            "-- empty --"
    ::= { lcsStatusWlanMngmtApConfAutowdsProfilesEntry 3 }

-- {COLUMN} 1.3.6.1.4.1.2356.11.1.73.2.11.1.4
lcsStatusWlanMngmtApConfAutowdsProfilesEntryKey OBJECT-TYPE
    SYNTAX     DisplayString (SIZE(0..63))
    MAX-ACCESS read-only
    STATUS     current
    DESCRIPTION
            "-- empty --"
    ::= { lcsStatusWlanMngmtApConfAutowdsProfilesEntry 4 }

-- {COLUMN} 1.3.6.1.4.1.2356.11.1.73.2.11.1.6
lcsStatusWlanMngmtApConfAutowdsProfilesEntryEnabled OBJECT-TYPE
    SYNTAX     INTEGER {
                  eNo (0),
                  eYes (1)
            }
    MAX-ACCESS read-only
    STATUS     current
    DESCRIPTION
            "-- empty --"
    ::= { lcsStatusWlanMngmtApConfAutowdsProfilesEntry 6 }

-- {COLUMN} 1.3.6.1.4.1.2356.11.1.73.2.11.1.7
lcsStatusWlanMngmtApConfAutowdsProfilesEntryAllowExprInt OBJECT-TYPE
    SYNTAX     INTEGER {
                  eNo (0),
                  eYes (1)
            }
    MAX-ACCESS read-only
    STATUS     current
    DESCRIPTION
            "Allow-Express-Integration"
    ::= { lcsStatusWlanMngmtApConfAutowdsProfilesEntry 7 }

-- {COLUMN} 1.3.6.1.4.1.2356.11.1.73.2.11.1.8
lcsStatusWlanMngmtApConfAutowdsProfilesEntryTopologyManagement OBJECT-TYPE
    SYNTAX     INTEGER {
                  eAutomatic (0),
                  eSemiAutomatic (1),
                  eManual (2)
            }
    MAX-ACCESS read-only
    STATUS     current
    DESCRIPTION
            "-- empty --"
    ::= { lcsStatusWlanMngmtApConfAutowdsProfilesEntry 8 }

-- {COLUMN} 1.3.6.1.4.1.2356.11.1.73.2.11.1.10
lcsStatusWlanMngmtApConfAutowdsProfilesEntrySlaveTxLimit OBJECT-TYPE
    SYNTAX     Integer32 (0..2147483647)
    MAX-ACCESS read-only
    STATUS     current
    DESCRIPTION
            "-- empty --"
    ::= { lcsStatusWlanMngmtApConfAutowdsProfilesEntry 10 }

-- {COLUMN} 1.3.6.1.4.1.2356.11.1.73.2.11.1.11
lcsStatusWlanMngmtApConfAutowdsProfilesEntryMasterTxLimit OBJECT-TYPE
    SYNTAX     Integer32 (0..2147483647)
    MAX-ACCESS read-only
    STATUS     current
    DESCRIPTION
            "-- empty --"
    ::= { lcsStatusWlanMngmtApConfAutowdsProfilesEntry 11 }

-- {COLUMN} 1.3.6.1.4.1.2356.11.1.73.2.11.1.12
lcsStatusWlanMngmtApConfAutowdsProfilesEntryLinkLossTimeout OBJECT-TYPE
    SYNTAX     Integer32 (0..2147483647)
    MAX-ACCESS read-only
    STATUS     current
    DESCRIPTION
            "-- empty --"
    ::= { lcsStatusWlanMngmtApConfAutowdsProfilesEntry 12 }

-- {COLUMN} 1.3.6.1.4.1.2356.11.1.73.2.11.1.14
lcsStatusWlanMngmtApConfAutowdsProfilesEntryContinuation OBJECT-TYPE
    SYNTAX     Integer32 (0..65535)
    MAX-ACCESS read-only
    STATUS     current
    DESCRIPTION
            ""
    ::= { lcsStatusWlanMngmtApConfAutowdsProfilesEntry 14 }

-- {COLUMN} 1.3.6.1.4.1.2356.11.1.73.2.11.1.15
lcsStatusWlanMngmtApConfAutowdsProfilesEntryTimeTillPreconfScan OBJECT-TYPE
    SYNTAX     Integer32 (0..2147483647)
    MAX-ACCESS read-only
    STATUS     current
    DESCRIPTION
            "-- empty --"
    ::= { lcsStatusWlanMngmtApConfAutowdsProfilesEntry 15 }

-- {COLUMN} 1.3.6.1.4.1.2356.11.1.73.2.11.1.16
lcsStatusWlanMngmtApConfAutowdsProfilesEntryTimeTillExpressScan OBJECT-TYPE
    SYNTAX     Integer32 (0..2147483647)
    MAX-ACCESS read-only
    STATUS     current
    DESCRIPTION
            "-- empty --"
    ::= { lcsStatusWlanMngmtApConfAutowdsProfilesEntry 16 }

-- {COLUMN} 1.3.6.1.4.1.2356.11.1.73.2.11.1.17
lcsStatusWlanMngmtApConfAutowdsProfilesEntryInterfacePairing OBJECT-TYPE
    SYNTAX     INTEGER {
                  eAutomatic (0),
                  eStrict (1),
                  eMixed (2)
            }
    MAX-ACCESS read-only
    STATUS     current
    DESCRIPTION
            "-- empty --"
    ::= { lcsStatusWlanMngmtApConfAutowdsProfilesEntry 17 }

-- {COLUMN} 1.3.6.1.4.1.2356.11.1.73.2.11.1.18
lcsStatusWlanMngmtApConfAutowdsProfilesEntrySlaveRadioMultiHop OBJECT-TYPE
    SYNTAX     INTEGER {
                  eNo (0),
                  eYes (1),
                  eSingleRadioApOnly (2)
            }
    MAX-ACCESS read-only
    STATUS     current
    DESCRIPTION
            "-- empty --"
    ::= { lcsStatusWlanMngmtApConfAutowdsProfilesEntry 18 }

-- {COLUMN} 1.3.6.1.4.1.2356.11.1.73.2.11.1.19
lcsStatusWlanMngmtApConfAutowdsProfilesEntryRadioBand OBJECT-TYPE
    SYNTAX     INTEGER {
                  e24ghz5ghz (0),
                  e24ghz (1),
                  e5ghz (2)
            }
    MAX-ACCESS read-only
    STATUS     current
    DESCRIPTION
            "-- empty --"
    ::= { lcsStatusWlanMngmtApConfAutowdsProfilesEntry 19 }

-- {COLUMN} 1.3.6.1.4.1.2356.11.1.73.2.11.1.20
lcsStatusWlanMngmtApConfAutowdsProfilesEntrySsidBroadcast OBJECT-TYPE
    SYNTAX     INTEGER {
                  eNo (0),
                  eYes (1)
            }
    MAX-ACCESS read-only
    STATUS     current
    DESCRIPTION
            "-- empty --"
    ::= { lcsStatusWlanMngmtApConfAutowdsProfilesEntry 20 }

-- {TABLE} 1.3.6.1.4.1.2356.11.1.73.2.12
lcsStatusWlanMngmtApConfAutowdsTopologyTable OBJECT-TYPE
    SYNTAX     SEQUENCE OF LcsStatusWlanMngmtApConfAutowdsTopologyEntry
    MAX-ACCESS not-accessible
    STATUS     current
    DESCRIPTION
            "-- empty --"
    ::= { lcsStatusWlanMngmtApConf 12 }

-- {ROW} 1.3.6.1.4.1.2356.11.1.73.2.12.1
lcsStatusWlanMngmtApConfAutowdsTopologyEntry OBJECT-TYPE
    SYNTAX     LcsStatusWlanMngmtApConfAutowdsTopologyEntry
    MAX-ACCESS not-accessible
    STATUS     current
    DESCRIPTION
            ""
    INDEX {
            lcsStatusWlanMngmtApConfAutowdsTopologyEntryAutowdsProfile,
            lcsStatusWlanMngmtApConfAutowdsTopologyEntryPriority,
            lcsStatusWlanMngmtApConfAutowdsTopologyEntrySlaveApName,
            lcsStatusWlanMngmtApConfAutowdsTopologyEntrySlaveApWlanIfc,
            lcsStatusWlanMngmtApConfAutowdsTopologyEntrySlaveApWlanMac
          }
    ::= { lcsStatusWlanMngmtApConfAutowdsTopologyTable 1 }

LcsStatusWlanMngmtApConfAutowdsTopologyEntry ::= SEQUENCE {
            lcsStatusWlanMngmtApConfAutowdsTopologyEntryAutowdsProfile DisplayString,
            lcsStatusWlanMngmtApConfAutowdsTopologyEntryPriority Integer32,
            lcsStatusWlanMngmtApConfAutowdsTopologyEntrySlaveApName DisplayString,
            lcsStatusWlanMngmtApConfAutowdsTopologyEntrySlaveApWlanIfc INTEGER,
            lcsStatusWlanMngmtApConfAutowdsTopologyEntrySlaveApWlanMac DisplayString,
            lcsStatusWlanMngmtApConfAutowdsTopologyEntryMasterApName DisplayString,
            lcsStatusWlanMngmtApConfAutowdsTopologyEntryMasterApWlanIfc INTEGER,
            lcsStatusWlanMngmtApConfAutowdsTopologyEntryMasterApWlanMac DisplayString,
            lcsStatusWlanMngmtApConfAutowdsTopologyEntryKey DisplayString,
            lcsStatusWlanMngmtApConfAutowdsTopologyEntryEnabled INTEGER,
            lcsStatusWlanMngmtApConfAutowdsTopologyEntrySlaveTxLimit Integer32,
            lcsStatusWlanMngmtApConfAutowdsTopologyEntryMasterTxLimit Integer32,
            lcsStatusWlanMngmtApConfAutowdsTopologyEntryLinkLossTimeout Integer32,
            lcsStatusWlanMngmtApConfAutowdsTopologyEntryContinuation Integer32,
            lcsStatusWlanMngmtApConfAutowdsTopologyEntryGenerated INTEGER,
            lcsStatusWlanMngmtApConfAutowdsTopologyEntryState INTEGER
    }

-- {COLUMN} 1.3.6.1.4.1.2356.11.1.73.2.12.1.1
lcsStatusWlanMngmtApConfAutowdsTopologyEntryAutowdsProfile OBJECT-TYPE
    SYNTAX     DisplayString (SIZE(0..15))
    MAX-ACCESS read-only
    STATUS     current
    DESCRIPTION
            "-- empty --"
    ::= { lcsStatusWlanMngmtApConfAutowdsTopologyEntry 1 }

-- {COLUMN} 1.3.6.1.4.1.2356.11.1.73.2.12.1.2
lcsStatusWlanMngmtApConfAutowdsTopologyEntryPriority OBJECT-TYPE
    SYNTAX     Integer32 (0..65535)
    MAX-ACCESS read-only
    STATUS     current
    DESCRIPTION
            "-- empty --"
    ::= { lcsStatusWlanMngmtApConfAutowdsTopologyEntry 2 }

-- {COLUMN} 1.3.6.1.4.1.2356.11.1.73.2.12.1.3
lcsStatusWlanMngmtApConfAutowdsTopologyEntrySlaveApName OBJECT-TYPE
    SYNTAX     DisplayString (SIZE(0..64))
    MAX-ACCESS read-only
    STATUS     current
    DESCRIPTION
            "-- empty --"
    ::= { lcsStatusWlanMngmtApConfAutowdsTopologyEntry 3 }

-- {COLUMN} 1.3.6.1.4.1.2356.11.1.73.2.12.1.4
lcsStatusWlanMngmtApConfAutowdsTopologyEntrySlaveApWlanIfc OBJECT-TYPE
    SYNTAX     INTEGER {
                  eWlan1 (1),
                  eWlan2 (2)
            }
    MAX-ACCESS read-only
    STATUS     current
    DESCRIPTION
            "-- empty --"
    ::= { lcsStatusWlanMngmtApConfAutowdsTopologyEntry 4 }

-- {COLUMN} 1.3.6.1.4.1.2356.11.1.73.2.12.1.5
lcsStatusWlanMngmtApConfAutowdsTopologyEntrySlaveApWlanMac OBJECT-TYPE
    SYNTAX     DisplayString (SIZE(0..12))
    MAX-ACCESS read-only
    STATUS     current
    DESCRIPTION
            "-- empty --"
    ::= { lcsStatusWlanMngmtApConfAutowdsTopologyEntry 5 }

-- {COLUMN} 1.3.6.1.4.1.2356.11.1.73.2.12.1.6
lcsStatusWlanMngmtApConfAutowdsTopologyEntryMasterApName OBJECT-TYPE
    SYNTAX     DisplayString (SIZE(0..64))
    MAX-ACCESS read-only
    STATUS     current
    DESCRIPTION
            "-- empty --"
    ::= { lcsStatusWlanMngmtApConfAutowdsTopologyEntry 6 }

-- {COLUMN} 1.3.6.1.4.1.2356.11.1.73.2.12.1.7
lcsStatusWlanMngmtApConfAutowdsTopologyEntryMasterApWlanIfc OBJECT-TYPE
    SYNTAX     INTEGER {
                  eWlan1 (1),
                  eWlan2 (2)
            }
    MAX-ACCESS read-only
    STATUS     current
    DESCRIPTION
            "-- empty --"
    ::= { lcsStatusWlanMngmtApConfAutowdsTopologyEntry 7 }

-- {COLUMN} 1.3.6.1.4.1.2356.11.1.73.2.12.1.8
lcsStatusWlanMngmtApConfAutowdsTopologyEntryMasterApWlanMac OBJECT-TYPE
    SYNTAX     DisplayString (SIZE(0..12))
    MAX-ACCESS read-only
    STATUS     current
    DESCRIPTION
            "-- empty --"
    ::= { lcsStatusWlanMngmtApConfAutowdsTopologyEntry 8 }

-- {COLUMN} 1.3.6.1.4.1.2356.11.1.73.2.12.1.9
lcsStatusWlanMngmtApConfAutowdsTopologyEntryKey OBJECT-TYPE
    SYNTAX     DisplayString (SIZE(0..63))
    MAX-ACCESS read-only
    STATUS     current
    DESCRIPTION
            "-- empty --"
    ::= { lcsStatusWlanMngmtApConfAutowdsTopologyEntry 9 }

-- {COLUMN} 1.3.6.1.4.1.2356.11.1.73.2.12.1.10
lcsStatusWlanMngmtApConfAutowdsTopologyEntryEnabled OBJECT-TYPE
    SYNTAX     INTEGER {
                  eNo (0),
                  eYes (1)
            }
    MAX-ACCESS read-only
    STATUS     current
    DESCRIPTION
            "-- empty --"
    ::= { lcsStatusWlanMngmtApConfAutowdsTopologyEntry 10 }

-- {COLUMN} 1.3.6.1.4.1.2356.11.1.73.2.12.1.12
lcsStatusWlanMngmtApConfAutowdsTopologyEntrySlaveTxLimit OBJECT-TYPE
    SYNTAX     Integer32 (0..2147483647)
    MAX-ACCESS read-only
    STATUS     current
    DESCRIPTION
            "-- empty --"
    ::= { lcsStatusWlanMngmtApConfAutowdsTopologyEntry 12 }

-- {COLUMN} 1.3.6.1.4.1.2356.11.1.73.2.12.1.13
lcsStatusWlanMngmtApConfAutowdsTopologyEntryMasterTxLimit OBJECT-TYPE
    SYNTAX     Integer32 (0..2147483647)
    MAX-ACCESS read-only
    STATUS     current
    DESCRIPTION
            "-- empty --"
    ::= { lcsStatusWlanMngmtApConfAutowdsTopologyEntry 13 }

-- {COLUMN} 1.3.6.1.4.1.2356.11.1.73.2.12.1.14
lcsStatusWlanMngmtApConfAutowdsTopologyEntryLinkLossTimeout OBJECT-TYPE
    SYNTAX     Integer32 (0..2147483647)
    MAX-ACCESS read-only
    STATUS     current
    DESCRIPTION
            "-- empty --"
    ::= { lcsStatusWlanMngmtApConfAutowdsTopologyEntry 14 }

-- {COLUMN} 1.3.6.1.4.1.2356.11.1.73.2.12.1.16
lcsStatusWlanMngmtApConfAutowdsTopologyEntryContinuation OBJECT-TYPE
    SYNTAX     Integer32 (0..65535)
    MAX-ACCESS read-only
    STATUS     current
    DESCRIPTION
            ""
    ::= { lcsStatusWlanMngmtApConfAutowdsTopologyEntry 16 }

-- {COLUMN} 1.3.6.1.4.1.2356.11.1.73.2.12.1.17
lcsStatusWlanMngmtApConfAutowdsTopologyEntryGenerated OBJECT-TYPE
    SYNTAX     INTEGER {
                  eNo (0),
                  eYes (1)
            }
    MAX-ACCESS read-only
    STATUS     current
    DESCRIPTION
            "-- empty --"
    ::= { lcsStatusWlanMngmtApConfAutowdsTopologyEntry 17 }

-- {COLUMN} 1.3.6.1.4.1.2356.11.1.73.2.12.1.18
lcsStatusWlanMngmtApConfAutowdsTopologyEntryState OBJECT-TYPE
    SYNTAX     INTEGER {
                  eNone (0),
                  eActive (1),
                  eInactive (2)
            }
    MAX-ACCESS read-only
    STATUS     current
    DESCRIPTION
            "-- empty --"
    ::= { lcsStatusWlanMngmtApConfAutowdsTopologyEntry 18 }

-- {TABLE} 1.3.6.1.4.1.2356.11.1.73.2.13
lcsStatusWlanMngmtApConfAutowdsAutoTopologyTable OBJECT-TYPE
    SYNTAX     SEQUENCE OF LcsStatusWlanMngmtApConfAutowdsAutoTopologyEntry
    MAX-ACCESS not-accessible
    STATUS     current
    DESCRIPTION
            "-- empty --"
    ::= { lcsStatusWlanMngmtApConf 13 }

-- {ROW} 1.3.6.1.4.1.2356.11.1.73.2.13.1
lcsStatusWlanMngmtApConfAutowdsAutoTopologyEntry OBJECT-TYPE
    SYNTAX     LcsStatusWlanMngmtApConfAutowdsAutoTopologyEntry
    MAX-ACCESS not-accessible
    STATUS     current
    DESCRIPTION
            ""
    INDEX {
            lcsStatusWlanMngmtApConfAutowdsAutoTopologyEntryAutowdsProfile,
            lcsStatusWlanMngmtApConfAutowdsAutoTopologyEntryPriority,
            lcsStatusWlanMngmtApConfAutowdsAutoTopologyEntrySlaveApName,
            lcsStatusWlanMngmtApConfAutowdsAutoTopologyEntrySlaveApWlanIfc,
            lcsStatusWlanMngmtApConfAutowdsAutoTopologyEntrySlaveApWlanMac
          }
    ::= { lcsStatusWlanMngmtApConfAutowdsAutoTopologyTable 1 }

LcsStatusWlanMngmtApConfAutowdsAutoTopologyEntry ::= SEQUENCE {
            lcsStatusWlanMngmtApConfAutowdsAutoTopologyEntryAutowdsProfile DisplayString,
            lcsStatusWlanMngmtApConfAutowdsAutoTopologyEntryPriority Integer32,
            lcsStatusWlanMngmtApConfAutowdsAutoTopologyEntrySlaveApName DisplayString,
            lcsStatusWlanMngmtApConfAutowdsAutoTopologyEntrySlaveApWlanIfc INTEGER,
            lcsStatusWlanMngmtApConfAutowdsAutoTopologyEntrySlaveApWlanMac DisplayString,
            lcsStatusWlanMngmtApConfAutowdsAutoTopologyEntryMasterApName DisplayString,
            lcsStatusWlanMngmtApConfAutowdsAutoTopologyEntryMasterApWlanIfc INTEGER,
            lcsStatusWlanMngmtApConfAutowdsAutoTopologyEntryMasterApWlanMac DisplayString,
            lcsStatusWlanMngmtApConfAutowdsAutoTopologyEntryKey DisplayString,
            lcsStatusWlanMngmtApConfAutowdsAutoTopologyEntryEnabled INTEGER,
            lcsStatusWlanMngmtApConfAutowdsAutoTopologyEntrySlaveTxLimit Integer32,
            lcsStatusWlanMngmtApConfAutowdsAutoTopologyEntryMasterTxLimit Integer32,
            lcsStatusWlanMngmtApConfAutowdsAutoTopologyEntryLinkLossTimeout Integer32,
            lcsStatusWlanMngmtApConfAutowdsAutoTopologyEntryContinuation Integer32,
            lcsStatusWlanMngmtApConfAutowdsAutoTopologyEntryGenerated INTEGER,
            lcsStatusWlanMngmtApConfAutowdsAutoTopologyEntryState INTEGER
    }

-- {COLUMN} 1.3.6.1.4.1.2356.11.1.73.2.13.1.1
lcsStatusWlanMngmtApConfAutowdsAutoTopologyEntryAutowdsProfile OBJECT-TYPE
    SYNTAX     DisplayString (SIZE(0..15))
    MAX-ACCESS read-only
    STATUS     current
    DESCRIPTION
            "-- empty --"
    ::= { lcsStatusWlanMngmtApConfAutowdsAutoTopologyEntry 1 }

-- {COLUMN} 1.3.6.1.4.1.2356.11.1.73.2.13.1.2
lcsStatusWlanMngmtApConfAutowdsAutoTopologyEntryPriority OBJECT-TYPE
    SYNTAX     Integer32 (0..65535)
    MAX-ACCESS read-only
    STATUS     current
    DESCRIPTION
            "-- empty --"
    ::= { lcsStatusWlanMngmtApConfAutowdsAutoTopologyEntry 2 }

-- {COLUMN} 1.3.6.1.4.1.2356.11.1.73.2.13.1.3
lcsStatusWlanMngmtApConfAutowdsAutoTopologyEntrySlaveApName OBJECT-TYPE
    SYNTAX     DisplayString (SIZE(0..64))
    MAX-ACCESS read-only
    STATUS     current
    DESCRIPTION
            "-- empty --"
    ::= { lcsStatusWlanMngmtApConfAutowdsAutoTopologyEntry 3 }

-- {COLUMN} 1.3.6.1.4.1.2356.11.1.73.2.13.1.4
lcsStatusWlanMngmtApConfAutowdsAutoTopologyEntrySlaveApWlanIfc OBJECT-TYPE
    SYNTAX     INTEGER {
                  eWlan1 (1),
                  eWlan2 (2)
            }
    MAX-ACCESS read-only
    STATUS     current
    DESCRIPTION
            "-- empty --"
    ::= { lcsStatusWlanMngmtApConfAutowdsAutoTopologyEntry 4 }

-- {COLUMN} 1.3.6.1.4.1.2356.11.1.73.2.13.1.5
lcsStatusWlanMngmtApConfAutowdsAutoTopologyEntrySlaveApWlanMac OBJECT-TYPE
    SYNTAX     DisplayString (SIZE(0..12))
    MAX-ACCESS read-only
    STATUS     current
    DESCRIPTION
            "-- empty --"
    ::= { lcsStatusWlanMngmtApConfAutowdsAutoTopologyEntry 5 }

-- {COLUMN} 1.3.6.1.4.1.2356.11.1.73.2.13.1.6
lcsStatusWlanMngmtApConfAutowdsAutoTopologyEntryMasterApName OBJECT-TYPE
    SYNTAX     DisplayString (SIZE(0..64))
    MAX-ACCESS read-only
    STATUS     current
    DESCRIPTION
            "-- empty --"
    ::= { lcsStatusWlanMngmtApConfAutowdsAutoTopologyEntry 6 }

-- {COLUMN} 1.3.6.1.4.1.2356.11.1.73.2.13.1.7
lcsStatusWlanMngmtApConfAutowdsAutoTopologyEntryMasterApWlanIfc OBJECT-TYPE
    SYNTAX     INTEGER {
                  eWlan1 (1),
                  eWlan2 (2)
            }
    MAX-ACCESS read-only
    STATUS     current
    DESCRIPTION
            "-- empty --"
    ::= { lcsStatusWlanMngmtApConfAutowdsAutoTopologyEntry 7 }

-- {COLUMN} 1.3.6.1.4.1.2356.11.1.73.2.13.1.8
lcsStatusWlanMngmtApConfAutowdsAutoTopologyEntryMasterApWlanMac OBJECT-TYPE
    SYNTAX     DisplayString (SIZE(0..12))
    MAX-ACCESS read-only
    STATUS     current
    DESCRIPTION
            "-- empty --"
    ::= { lcsStatusWlanMngmtApConfAutowdsAutoTopologyEntry 8 }

-- {COLUMN} 1.3.6.1.4.1.2356.11.1.73.2.13.1.9
lcsStatusWlanMngmtApConfAutowdsAutoTopologyEntryKey OBJECT-TYPE
    SYNTAX     DisplayString (SIZE(0..63))
    MAX-ACCESS read-only
    STATUS     current
    DESCRIPTION
            "-- empty --"
    ::= { lcsStatusWlanMngmtApConfAutowdsAutoTopologyEntry 9 }

-- {COLUMN} 1.3.6.1.4.1.2356.11.1.73.2.13.1.10
lcsStatusWlanMngmtApConfAutowdsAutoTopologyEntryEnabled OBJECT-TYPE
    SYNTAX     INTEGER {
                  eNo (0),
                  eYes (1)
            }
    MAX-ACCESS read-only
    STATUS     current
    DESCRIPTION
            "-- empty --"
    ::= { lcsStatusWlanMngmtApConfAutowdsAutoTopologyEntry 10 }

-- {COLUMN} 1.3.6.1.4.1.2356.11.1.73.2.13.1.12
lcsStatusWlanMngmtApConfAutowdsAutoTopologyEntrySlaveTxLimit OBJECT-TYPE
    SYNTAX     Integer32 (0..2147483647)
    MAX-ACCESS read-only
    STATUS     current
    DESCRIPTION
            "-- empty --"
    ::= { lcsStatusWlanMngmtApConfAutowdsAutoTopologyEntry 12 }

-- {COLUMN} 1.3.6.1.4.1.2356.11.1.73.2.13.1.13
lcsStatusWlanMngmtApConfAutowdsAutoTopologyEntryMasterTxLimit OBJECT-TYPE
    SYNTAX     Integer32 (0..2147483647)
    MAX-ACCESS read-only
    STATUS     current
    DESCRIPTION
            "-- empty --"
    ::= { lcsStatusWlanMngmtApConfAutowdsAutoTopologyEntry 13 }

-- {COLUMN} 1.3.6.1.4.1.2356.11.1.73.2.13.1.14
lcsStatusWlanMngmtApConfAutowdsAutoTopologyEntryLinkLossTimeout OBJECT-TYPE
    SYNTAX     Integer32 (0..2147483647)
    MAX-ACCESS read-only
    STATUS     current
    DESCRIPTION
            "-- empty --"
    ::= { lcsStatusWlanMngmtApConfAutowdsAutoTopologyEntry 14 }

-- {COLUMN} 1.3.6.1.4.1.2356.11.1.73.2.13.1.16
lcsStatusWlanMngmtApConfAutowdsAutoTopologyEntryContinuation OBJECT-TYPE
    SYNTAX     Integer32 (0..65535)
    MAX-ACCESS read-only
    STATUS     current
    DESCRIPTION
            ""
    ::= { lcsStatusWlanMngmtApConfAutowdsAutoTopologyEntry 16 }

-- {COLUMN} 1.3.6.1.4.1.2356.11.1.73.2.13.1.17
lcsStatusWlanMngmtApConfAutowdsAutoTopologyEntryGenerated OBJECT-TYPE
    SYNTAX     INTEGER {
                  eNo (0),
                  eYes (1)
            }
    MAX-ACCESS read-only
    STATUS     current
    DESCRIPTION
            "-- empty --"
    ::= { lcsStatusWlanMngmtApConfAutowdsAutoTopologyEntry 17 }

-- {COLUMN} 1.3.6.1.4.1.2356.11.1.73.2.13.1.18
lcsStatusWlanMngmtApConfAutowdsAutoTopologyEntryState OBJECT-TYPE
    SYNTAX     INTEGER {
                  eNone (0),
                  eActive (1),
                  eInactive (2)
            }
    MAX-ACCESS read-only
    STATUS     current
    DESCRIPTION
            "-- empty --"
    ::= { lcsStatusWlanMngmtApConfAutowdsAutoTopologyEntry 18 }

-- {TABLE} 1.3.6.1.4.1.2356.11.1.73.2.14
lcsStatusWlanMngmtApConfAutowdsProfErrTable OBJECT-TYPE
    SYNTAX     SEQUENCE OF LcsStatusWlanMngmtApConfAutowdsProfErrEntry
    MAX-ACCESS not-accessible
    STATUS     current
    DESCRIPTION
            ""
    ::= { lcsStatusWlanMngmtApConf 14 }

-- {ROW} 1.3.6.1.4.1.2356.11.1.73.2.14.1
lcsStatusWlanMngmtApConfAutowdsProfErrEntry OBJECT-TYPE
    SYNTAX     LcsStatusWlanMngmtApConfAutowdsProfErrEntry
    MAX-ACCESS not-accessible
    STATUS     current
    DESCRIPTION
            ""
    INDEX {
            lcsStatusWlanMngmtApConfAutowdsProfErrEntryIndex
          }
    ::= { lcsStatusWlanMngmtApConfAutowdsProfErrTable 1 }

LcsStatusWlanMngmtApConfAutowdsProfErrEntry ::= SEQUENCE {
            lcsStatusWlanMngmtApConfAutowdsProfErrEntryIndex Integer32,
            lcsStatusWlanMngmtApConfAutowdsProfErrEntryName DisplayString,
            lcsStatusWlanMngmtApConfAutowdsProfErrEntryError INTEGER,
            lcsStatusWlanMngmtApConfAutowdsProfErrEntryNetworkApParameters DisplayString
    }

-- {COLUMN} 1.3.6.1.4.1.2356.11.1.73.2.14.1.1
lcsStatusWlanMngmtApConfAutowdsProfErrEntryIndex OBJECT-TYPE
    SYNTAX     Integer32 (0..2147483647)
    MAX-ACCESS read-only
    STATUS     current
    DESCRIPTION
            "-- empty --"
    ::= { lcsStatusWlanMngmtApConfAutowdsProfErrEntry 1 }

-- {COLUMN} 1.3.6.1.4.1.2356.11.1.73.2.14.1.2
lcsStatusWlanMngmtApConfAutowdsProfErrEntryName OBJECT-TYPE
    SYNTAX     DisplayString (SIZE(0..31))
    MAX-ACCESS read-only
    STATUS     current
    DESCRIPTION
            "-- empty --"
    ::= { lcsStatusWlanMngmtApConfAutowdsProfErrEntry 2 }

-- {COLUMN} 1.3.6.1.4.1.2356.11.1.73.2.14.1.3
lcsStatusWlanMngmtApConfAutowdsProfErrEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eWlanProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20),
                  eAutowdsSsidNotUnique (21),
                  eAutowdsProfileNotUnique (22),
                  eAutowdsSsidNotDefined (23),
                  eLepsUProfileIsMissing (24)
            }
    MAX-ACCESS read-only
    STATUS     current
    DESCRIPTION
            "-- empty --"
    ::= { lcsStatusWlanMngmtApConfAutowdsProfErrEntry 3 }

-- {COLUMN} 1.3.6.1.4.1.2356.11.1.73.2.14.1.4
lcsStatusWlanMngmtApConfAutowdsProfErrEntryNetworkApParameters OBJECT-TYPE
    SYNTAX     DisplayString (SIZE(0..31))
    MAX-ACCESS read-only
    STATUS     current
    DESCRIPTION
            "-- empty --"
    ::= { lcsStatusWlanMngmtApConfAutowdsProfErrEntry 4 }

-- {TABLE} 1.3.6.1.4.1.2356.11.1.73.2.15
lcsStatusWlanMngmtApConfAutowdsTopoErrorsTable OBJECT-TYPE
    SYNTAX     SEQUENCE OF LcsStatusWlanMngmtApConfAutowdsTopoErrorsEntry
    MAX-ACCESS not-accessible
    STATUS     current
    DESCRIPTION
            "-- empty --"
    ::= { lcsStatusWlanMngmtApConf 15 }

-- {ROW} 1.3.6.1.4.1.2356.11.1.73.2.15.1
lcsStatusWlanMngmtApConfAutowdsTopoErrorsEntry OBJECT-TYPE
    SYNTAX     LcsStatusWlanMngmtApConfAutowdsTopoErrorsEntry
    MAX-ACCESS not-accessible
    STATUS     current
    DESCRIPTION
            ""
    INDEX {
            lcsStatusWlanMngmtApConfAutowdsTopoErrorsEntryIndex,
            lcsStatusWlanMngmtApConfAutowdsTopoErrorsEntryPriority,
            lcsStatusWlanMngmtApConfAutowdsTopoErrorsEntrySlaveApName,
            lcsStatusWlanMngmtApConfAutowdsTopoErrorsEntrySlaveApWlanIfc
          }
    ::= { lcsStatusWlanMngmtApConfAutowdsTopoErrorsTable 1 }

LcsStatusWlanMngmtApConfAutowdsTopoErrorsEntry ::= SEQUENCE {
            lcsStatusWlanMngmtApConfAutowdsTopoErrorsEntryIndex Integer32,
            lcsStatusWlanMngmtApConfAutowdsTopoErrorsEntryAutowdsProfile DisplayString,
            lcsStatusWlanMngmtApConfAutowdsTopoErrorsEntryPriority Integer32,
            lcsStatusWlanMngmtApConfAutowdsTopoErrorsEntrySlaveApName DisplayString,
            lcsStatusWlanMngmtApConfAutowdsTopoErrorsEntrySlaveApWlanIfc INTEGER,
            lcsStatusWlanMngmtApConfAutowdsTopoErrorsEntrySlaveApWlanMac DisplayString,
            lcsStatusWlanMngmtApConfAutowdsTopoErrorsEntryMasterApName DisplayString,
            lcsStatusWlanMngmtApConfAutowdsTopoErrorsEntryMasterApWlanIfc INTEGER,
            lcsStatusWlanMngmtApConfAutowdsTopoErrorsEntryMasterApWlanMac DisplayString,
            lcsStatusWlanMngmtApConfAutowdsTopoErrorsEntryError INTEGER
    }

-- {COLUMN} 1.3.6.1.4.1.2356.11.1.73.2.15.1.1
lcsStatusWlanMngmtApConfAutowdsTopoErrorsEntryIndex OBJECT-TYPE
    SYNTAX     Integer32 (0..2147483647)
    MAX-ACCESS read-only
    STATUS     current
    DESCRIPTION
            "-- empty --"
    ::= { lcsStatusWlanMngmtApConfAutowdsTopoErrorsEntry 1 }

-- {COLUMN} 1.3.6.1.4.1.2356.11.1.73.2.15.1.2
lcsStatusWlanMngmtApConfAutowdsTopoErrorsEntryAutowdsProfile OBJECT-TYPE
    SYNTAX     DisplayString (SIZE(0..31))
    MAX-ACCESS read-only
    STATUS     current
    DESCRIPTION
            "-- empty --"
    ::= { lcsStatusWlanMngmtApConfAutowdsTopoErrorsEntry 2 }

-- {COLUMN} 1.3.6.1.4.1.2356.11.1.73.2.15.1.3
lcsStatusWlanMngmtApConfAutowdsTopoErrorsEntryPriority OBJECT-TYPE
    SYNTAX     Integer32 (0..65535)
    MAX-ACCESS read-only
    STATUS     current
    DESCRIPTION
            "-- empty --"
    ::= { lcsStatusWlanMngmtApConfAutowdsTopoErrorsEntry 3 }

-- {COLUMN} 1.3.6.1.4.1.2356.11.1.73.2.15.1.4
lcsStatusWlanMngmtApConfAutowdsTopoErrorsEntrySlaveApName OBJECT-TYPE
    SYNTAX     DisplayString (SIZE(0..64))
    MAX-ACCESS read-only
    STATUS     current
    DESCRIPTION
            "-- empty --"
    ::= { lcsStatusWlanMngmtApConfAutowdsTopoErrorsEntry 4 }

-- {COLUMN} 1.3.6.1.4.1.2356.11.1.73.2.15.1.5
lcsStatusWlanMngmtApConfAutowdsTopoErrorsEntrySlaveApWlanIfc OBJECT-TYPE
    SYNTAX     INTEGER {
                  eWlan1 (1),
                  eWlan2 (2)
            }
    MAX-ACCESS read-only
    STATUS     current
    DESCRIPTION
            "-- empty --"
    ::= { lcsStatusWlanMngmtApConfAutowdsTopoErrorsEntry 5 }

-- {COLUMN} 1.3.6.1.4.1.2356.11.1.73.2.15.1.6
lcsStatusWlanMngmtApConfAutowdsTopoErrorsEntrySlaveApWlanMac OBJECT-TYPE
    SYNTAX     DisplayString (SIZE(0..12))
    MAX-ACCESS read-only
    STATUS     current
    DESCRIPTION
            "-- empty --"
    ::= { lcsStatusWlanMngmtApConfAutowdsTopoErrorsEntry 6 }

-- {COLUMN} 1.3.6.1.4.1.2356.11.1.73.2.15.1.7
lcsStatusWlanMngmtApConfAutowdsTopoErrorsEntryMasterApName OBJECT-TYPE
    SYNTAX     DisplayString (SIZE(0..64))
    MAX-ACCESS read-only
    STATUS     current
    DESCRIPTION
            "-- empty --"
    ::= { lcsStatusWlanMngmtApConfAutowdsTopoErrorsEntry 7 }

-- {COLUMN} 1.3.6.1.4.1.2356.11.1.73.2.15.1.8
lcsStatusWlanMngmtApConfAutowdsTopoErrorsEntryMasterApWlanIfc OBJECT-TYPE
    SYNTAX     INTEGER {
                  eWlan1 (1),
                  eWlan2 (2)
            }
    MAX-ACCESS read-only
    STATUS     current
    DESCRIPTION
            "-- empty --"
    ::= { lcsStatusWlanMngmtApConfAutowdsTopoErrorsEntry 8 }

-- {COLUMN} 1.3.6.1.4.1.2356.11.1.73.2.15.1.9
lcsStatusWlanMngmtApConfAutowdsTopoErrorsEntryMasterApWlanMac OBJECT-TYPE
    SYNTAX     DisplayString (SIZE(0..12))
    MAX-ACCESS read-only
    STATUS     current
    DESCRIPTION
            "-- empty --"
    ::= { lcsStatusWlanMngmtApConfAutowdsTopoErrorsEntry 9 }

-- {COLUMN} 1.3.6.1.4.1.2356.11.1.73.2.15.1.10
lcsStatusWlanMngmtApConfAutowdsTopoErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eWlanProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20),
                  eAutowdsSsidNotUnique (21),
                  eAutowdsProfileNotUnique (22),
                  eAutowdsSsidNotDefined (23),
                  eLepsUProfileIsMissing (24)
            }
    MAX-ACCESS read-only
    STATUS     current
    DESCRIPTION
            "-- empty --"
    ::= { lcsStatusWlanMngmtApConfAutowdsTopoErrorsEntry 10 }

-- {NODE} 1.3.6.1.4.1.2356.11.1.73.2.17
lcsStatusWlanMngmtApConf11u OBJECT IDENTIFIER ::= { lcsStatusWlanMngmtApConf 17 }

-- {TABLE} 1.3.6.1.4.1.2356.11.1.73.2.17.1
lcsStatusWlanMngmtApConf11u11u-NwTable OBJECT-TYPE
    SYNTAX     SEQUENCE OF LcsStatusWlanMngmtApConf11u11u-NwEntry
    MAX-ACCESS not-accessible
    STATUS     current
    DESCRIPTION
            "IEEE802.11u-Networks"
    ::= { lcsStatusWlanMngmtApConf11u 1 }

-- {ROW} 1.3.6.1.4.1.2356.11.1.73.2.17.1.1
lcsStatusWlanMngmtApConf11u11u-NwEntry OBJECT-TYPE
    SYNTAX     LcsStatusWlanMngmtApConf11u11u-NwEntry
    MAX-ACCESS not-accessible
    STATUS     current
    DESCRIPTION
            ""
    INDEX {
            lcsStatusWlanMngmtApConf11u11u-NwEntryName
          }
    ::= { lcsStatusWlanMngmtApConf11u11u-NwTable 1 }

LcsStatusWlanMngmtApConf11u11u-NwEntry ::= SEQUENCE {
            lcsStatusWlanMngmtApConf11u11u-NwEntryName DisplayString,
            lcsStatusWlanMngmtApConf11u11u-NwEntryOper INTEGER,
            lcsStatusWlanMngmtApConf11u11u-NwEntryHs20 INTEGER,
            lcsStatusWlanMngmtApConf11u11u-NwEntryInet INTEGER,
            lcsStatusWlanMngmtApConf11u11u-NwEntryNwType INTEGER,
            lcsStatusWlanMngmtApConf11u11u-NwEntryAsra INTEGER,
            lcsStatusWlanMngmtApConf11u11u-NwEntryHESSIDT INTEGER,
            lcsStatusWlanMngmtApConf11u11u-NwEntryHESSIDM MacAddress,
            lcsStatusWlanMngmtApConf11u11u-NwEntryANQP-Prof DisplayString,
            lcsStatusWlanMngmtApConf11u11u-NwEntryHs20-Prof DisplayString
    }

-- {COLUMN} 1.3.6.1.4.1.2356.11.1.73.2.17.1.1.1
lcsStatusWlanMngmtApConf11u11u-NwEntryName OBJECT-TYPE
    SYNTAX     DisplayString (SIZE(0..32))
    MAX-ACCESS read-only
    STATUS     current
    DESCRIPTION
            "-- empty --"
    ::= { lcsStatusWlanMngmtApConf11u11u-NwEntry 1 }

-- {COLUMN} 1.3.6.1.4.1.2356.11.1.73.2.17.1.1.2
lcsStatusWlanMngmtApConf11u11u-NwEntryOper OBJECT-TYPE
    SYNTAX     INTEGER {
                  eNo (0),
                  eYes (1)
            }
    MAX-ACCESS read-only
    STATUS     current
    DESCRIPTION
            "Operating"
    ::= { lcsStatusWlanMngmtApConf11u11u-NwEntry 2 }

-- {COLUMN} 1.3.6.1.4.1.2356.11.1.73.2.17.1.1.3
lcsStatusWlanMngmtApConf11u11u-NwEntryHs20 OBJECT-TYPE
    SYNTAX     INTEGER {
                  eNo (0),
                  eYes (1)
            }
    MAX-ACCESS read-only
    STATUS     current
    DESCRIPTION
            "Hotspot2.0"
    ::= { lcsStatusWlanMngmtApConf11u11u-NwEntry 3 }

-- {COLUMN} 1.3.6.1.4.1.2356.11.1.73.2.17.1.1.4
lcsStatusWlanMngmtApConf11u11u-NwEntryInet OBJECT-TYPE
    SYNTAX     INTEGER {
                  eNo (0),
                  eYes (1)
            }
    MAX-ACCESS read-only
    STATUS     current
    DESCRIPTION
            "Internet"
    ::= { lcsStatusWlanMngmtApConf11u11u-NwEntry 4 }

-- {COLUMN} 1.3.6.1.4.1.2356.11.1.73.2.17.1.1.5
lcsStatusWlanMngmtApConf11u11u-NwEntryNwType OBJECT-TYPE
    SYNTAX     INTEGER {
                  ePrivate (0),
                  ePrivateGuestacc (1),
                  ePublicCharge (2),
                  ePublicFree (3),
                  ePersonalDev (4),
                  eEmergency (5),
                  eExperimental (14),
                  eWildcard (15)
            }
    MAX-ACCESS read-only
    STATUS     current
    DESCRIPTION
            "Network-Type"
    ::= { lcsStatusWlanMngmtApConf11u11u-NwEntry 5 }

-- {COLUMN} 1.3.6.1.4.1.2356.11.1.73.2.17.1.1.6
lcsStatusWlanMngmtApConf11u11u-NwEntryAsra OBJECT-TYPE
    SYNTAX     INTEGER {
                  eNo (0),
                  eYes (1)
            }
    MAX-ACCESS read-only
    STATUS     current
    DESCRIPTION
            "Asra"
    ::= { lcsStatusWlanMngmtApConf11u11u-NwEntry 6 }

-- {COLUMN} 1.3.6.1.4.1.2356.11.1.73.2.17.1.1.7
lcsStatusWlanMngmtApConf11u11u-NwEntryHESSIDT OBJECT-TYPE
    SYNTAX     INTEGER {
                  eAuto (0),
                  eUser (1),
                  eNone (2)
            }
    MAX-ACCESS read-only
    STATUS     current
    DESCRIPTION
            "HESSID-Type"
    ::= { lcsStatusWlanMngmtApConf11u11u-NwEntry 7 }

-- {COLUMN} 1.3.6.1.4.1.2356.11.1.73.2.17.1.1.8
lcsStatusWlanMngmtApConf11u11u-NwEntryHESSIDM OBJECT-TYPE
    SYNTAX     MacAddress
    MAX-ACCESS read-only
    STATUS     current
    DESCRIPTION
            "HESSID-MAC"
    ::= { lcsStatusWlanMngmtApConf11u11u-NwEntry 8 }

-- {COLUMN} 1.3.6.1.4.1.2356.11.1.73.2.17.1.1.10
lcsStatusWlanMngmtApConf11u11u-NwEntryANQP-Prof OBJECT-TYPE
    SYNTAX     DisplayString (SIZE(0..32))
    MAX-ACCESS read-only
    STATUS     current
    DESCRIPTION
            "ANQP-Profile"
    ::= { lcsStatusWlanMngmtApConf11u11u-NwEntry 10 }

-- {COLUMN} 1.3.6.1.4.1.2356.11.1.73.2.17.1.1.12
lcsStatusWlanMngmtApConf11u11u-NwEntryHs20-Prof OBJECT-TYPE
    SYNTAX     DisplayString (SIZE(0..32))
    MAX-ACCESS read-only
    STATUS     current
    DESCRIPTION
            "HS20-Profile"
    ::= { lcsStatusWlanMngmtApConf11u11u-NwEntry 12 }

-- {TABLE} 1.3.6.1.4.1.2356.11.1.73.2.17.2
lcsStatusWlanMngmtApConf11uANQP-ProfsTable OBJECT-TYPE
    SYNTAX     SEQUENCE OF LcsStatusWlanMngmtApConf11uANQP-ProfsEntry
    MAX-ACCESS not-accessible
    STATUS     current
    DESCRIPTION
            "ANQP-Profiles"
    ::= { lcsStatusWlanMngmtApConf11u 2 }

-- {ROW} 1.3.6.1.4.1.2356.11.1.73.2.17.2.1
lcsStatusWlanMngmtApConf11uANQP-ProfsEntry OBJECT-TYPE
    SYNTAX     LcsStatusWlanMngmtApConf11uANQP-ProfsEntry
    MAX-ACCESS not-accessible
    STATUS     current
    DESCRIPTION
            ""
    INDEX {
            lcsStatusWlanMngmtApConf11uANQP-ProfsEntryName
          }
    ::= { lcsStatusWlanMngmtApConf11uANQP-ProfsTable 1 }

LcsStatusWlanMngmtApConf11uANQP-ProfsEntry ::= SEQUENCE {
            lcsStatusWlanMngmtApConf11uANQP-ProfsEntryName DisplayString,
            lcsStatusWlanMngmtApConf11uANQP-ProfsEntryIncOUI DisplayString,
            lcsStatusWlanMngmtApConf11uANQP-ProfsEntryAddOUI DisplayString,
            lcsStatusWlanMngmtApConf11uANQP-ProfsEntryDomainList DisplayString,
            lcsStatusWlanMngmtApConf11uANQP-ProfsEntryNaiRealmList DisplayString,
            lcsStatusWlanMngmtApConf11uANQP-ProfsEntryCellularList DisplayString,
            lcsStatusWlanMngmtApConf11uANQP-ProfsEntryNetList DisplayString
    }

-- {COLUMN} 1.3.6.1.4.1.2356.11.1.73.2.17.2.1.1
lcsStatusWlanMngmtApConf11uANQP-ProfsEntryName OBJECT-TYPE
    SYNTAX     DisplayString (SIZE(0..32))
    MAX-ACCESS read-only
    STATUS     current
    DESCRIPTION
            "-- empty --"
    ::= { lcsStatusWlanMngmtApConf11uANQP-ProfsEntry 1 }

-- {COLUMN} 1.3.6.1.4.1.2356.11.1.73.2.17.2.1.2
lcsStatusWlanMngmtApConf11uANQP-ProfsEntryIncOUI OBJECT-TYPE
    SYNTAX     DisplayString (SIZE(0..65))
    MAX-ACCESS read-only
    STATUS     current
    DESCRIPTION
            "Include-in-Beacon-OUI"
    ::= { lcsStatusWlanMngmtApConf11uANQP-ProfsEntry 2 }

-- {COLUMN} 1.3.6.1.4.1.2356.11.1.73.2.17.2.1.3
lcsStatusWlanMngmtApConf11uANQP-ProfsEntryAddOUI OBJECT-TYPE
    SYNTAX     DisplayString (SIZE(0..65))
    MAX-ACCESS read-only
    STATUS     current
    DESCRIPTION
            "Additional-OUI"
    ::= { lcsStatusWlanMngmtApConf11uANQP-ProfsEntry 3 }

-- {COLUMN} 1.3.6.1.4.1.2356.11.1.73.2.17.2.1.4
lcsStatusWlanMngmtApConf11uANQP-ProfsEntryDomainList OBJECT-TYPE
    SYNTAX     DisplayString (SIZE(0..65))
    MAX-ACCESS read-only
    STATUS     current
    DESCRIPTION
            "-- empty --"
    ::= { lcsStatusWlanMngmtApConf11uANQP-ProfsEntry 4 }

-- {COLUMN} 1.3.6.1.4.1.2356.11.1.73.2.17.2.1.5
lcsStatusWlanMngmtApConf11uANQP-ProfsEntryNaiRealmList OBJECT-TYPE
    SYNTAX     DisplayString (SIZE(0..65))
    MAX-ACCESS read-only
    STATUS     current
    DESCRIPTION
            "-- empty --"
    ::= { lcsStatusWlanMngmtApConf11uANQP-ProfsEntry 5 }

-- {COLUMN} 1.3.6.1.4.1.2356.11.1.73.2.17.2.1.6
lcsStatusWlanMngmtApConf11uANQP-ProfsEntryCellularList OBJECT-TYPE
    SYNTAX     DisplayString (SIZE(0..65))
    MAX-ACCESS read-only
    STATUS     current
    DESCRIPTION
            "-- empty --"
    ::= { lcsStatusWlanMngmtApConf11uANQP-ProfsEntry 6 }

-- {COLUMN} 1.3.6.1.4.1.2356.11.1.73.2.17.2.1.7
lcsStatusWlanMngmtApConf11uANQP-ProfsEntryNetList OBJECT-TYPE
    SYNTAX     DisplayString (SIZE(0..65))
    MAX-ACCESS read-only
    STATUS     current
    DESCRIPTION
            "Network-Auth-Type-List"
    ::= { lcsStatusWlanMngmtApConf11uANQP-ProfsEntry 7 }

-- {TABLE} 1.3.6.1.4.1.2356.11.1.73.2.17.3
lcsStatusWlanMngmtApConf11uHs20-ProfsTable OBJECT-TYPE
    SYNTAX     SEQUENCE OF LcsStatusWlanMngmtApConf11uHs20-ProfsEntry
    MAX-ACCESS not-accessible
    STATUS     current
    DESCRIPTION
            "Hotspot2.0-Profiles"
    ::= { lcsStatusWlanMngmtApConf11u 3 }

-- {ROW} 1.3.6.1.4.1.2356.11.1.73.2.17.3.1
lcsStatusWlanMngmtApConf11uHs20-ProfsEntry OBJECT-TYPE
    SYNTAX     LcsStatusWlanMngmtApConf11uHs20-ProfsEntry
    MAX-ACCESS not-accessible
    STATUS     current
    DESCRIPTION
            ""
    INDEX {
            lcsStatusWlanMngmtApConf11uHs20-ProfsEntryName
          }
    ::= { lcsStatusWlanMngmtApConf11uHs20-ProfsTable 1 }

LcsStatusWlanMngmtApConf11uHs20-ProfsEntry ::= SEQUENCE {
            lcsStatusWlanMngmtApConf11uHs20-ProfsEntryName DisplayString,
            lcsStatusWlanMngmtApConf11uHs20-ProfsEntryOperatorName DisplayString,
            lcsStatusWlanMngmtApConf11uHs20-ProfsEntryConnCaps DisplayString,
            lcsStatusWlanMngmtApConf11uHs20-ProfsEntryOpClass DisplayString
    }

-- {COLUMN} 1.3.6.1.4.1.2356.11.1.73.2.17.3.1.1
lcsStatusWlanMngmtApConf11uHs20-ProfsEntryName OBJECT-TYPE
    SYNTAX     DisplayString (SIZE(0..32))
    MAX-ACCESS read-only
    STATUS     current
    DESCRIPTION
            "-- empty --"
    ::= { lcsStatusWlanMngmtApConf11uHs20-ProfsEntry 1 }

-- {COLUMN} 1.3.6.1.4.1.2356.11.1.73.2.17.3.1.2
lcsStatusWlanMngmtApConf11uHs20-ProfsEntryOperatorName OBJECT-TYPE
    SYNTAX     DisplayString (SIZE(0..65))
    MAX-ACCESS read-only
    STATUS     current
    DESCRIPTION
            "-- empty --"
    ::= { lcsStatusWlanMngmtApConf11uHs20-ProfsEntry 2 }

-- {COLUMN} 1.3.6.1.4.1.2356.11.1.73.2.17.3.1.3
lcsStatusWlanMngmtApConf11uHs20-ProfsEntryConnCaps OBJECT-TYPE
    SYNTAX     DisplayString (SIZE(0..250))
    MAX-ACCESS read-only
    STATUS     current
    DESCRIPTION
            "Connection-Capabilities"
    ::= { lcsStatusWlanMngmtApConf11uHs20-ProfsEntry 3 }

-- {COLUMN} 1.3.6.1.4.1.2356.11.1.73.2.17.3.1.4
lcsStatusWlanMngmtApConf11uHs20-ProfsEntryOpClass OBJECT-TYPE
    SYNTAX     DisplayString (SIZE(0..32))
    MAX-ACCESS read-only
    STATUS     current
    DESCRIPTION
            "Operating-Class"
    ::= { lcsStatusWlanMngmtApConf11uHs20-ProfsEntry 4 }

-- {TABLE} 1.3.6.1.4.1.2356.11.1.73.2.17.4
lcsStatusWlanMngmtApConf11uNetAuthTable OBJECT-TYPE
    SYNTAX     SEQUENCE OF LcsStatusWlanMngmtApConf11uNetAuthEntry
    MAX-ACCESS not-accessible
    STATUS     current
    DESCRIPTION
            "Network-Authentication-Type"
    ::= { lcsStatusWlanMngmtApConf11u 4 }

-- {ROW} 1.3.6.1.4.1.2356.11.1.73.2.17.4.1
lcsStatusWlanMngmtApConf11uNetAuthEntry OBJECT-TYPE
    SYNTAX     LcsStatusWlanMngmtApConf11uNetAuthEntry
    MAX-ACCESS not-accessible
    STATUS     current
    DESCRIPTION
            ""
    INDEX {
            lcsStatusWlanMngmtApConf11uNetAuthEntryName
          }
    ::= { lcsStatusWlanMngmtApConf11uNetAuthTable 1 }

LcsStatusWlanMngmtApConf11uNetAuthEntry ::= SEQUENCE {
            lcsStatusWlanMngmtApConf11uNetAuthEntryName DisplayString,
            lcsStatusWlanMngmtApConf11uNetAuthEntryNetType INTEGER,
            lcsStatusWlanMngmtApConf11uNetAuthEntryReUrl DisplayString
    }

-- {COLUMN} 1.3.6.1.4.1.2356.11.1.73.2.17.4.1.1
lcsStatusWlanMngmtApConf11uNetAuthEntryName OBJECT-TYPE
    SYNTAX     DisplayString (SIZE(0..32))
    MAX-ACCESS read-only
    STATUS     current
    DESCRIPTION
            "-- empty --"
    ::= { lcsStatusWlanMngmtApConf11uNetAuthEntry 1 }

-- {COLUMN} 1.3.6.1.4.1.2356.11.1.73.2.17.4.1.2
lcsStatusWlanMngmtApConf11uNetAuthEntryNetType OBJECT-TYPE
    SYNTAX     INTEGER {
                  eAcceptTermsCond (0),
                  eOnlineEnrollment (1),
                  eHttpRedirection (2),
                  eDnsRedirection (3)
            }
    MAX-ACCESS read-only
    STATUS     current
    DESCRIPTION
            "Network-Auth-Type"
    ::= { lcsStatusWlanMngmtApConf11uNetAuthEntry 2 }

-- {COLUMN} 1.3.6.1.4.1.2356.11.1.73.2.17.4.1.3
lcsStatusWlanMngmtApConf11uNetAuthEntryReUrl OBJECT-TYPE
    SYNTAX     DisplayString (SIZE(0..65))
    MAX-ACCESS read-only
    STATUS     current
    DESCRIPTION
            "Redirect-URL"
    ::= { lcsStatusWlanMngmtApConf11uNetAuthEntry 3 }

-- {TABLE} 1.3.6.1.4.1.2356.11.1.73.2.17.5
lcsStatusWlanMngmtApConf11uCellListTable OBJECT-TYPE
    SYNTAX     SEQUENCE OF LcsStatusWlanMngmtApConf11uCellListEntry
    MAX-ACCESS not-accessible
    STATUS     current
    DESCRIPTION
            "Cellular-Network-Information-List"
    ::= { lcsStatusWlanMngmtApConf11u 5 }

-- {ROW} 1.3.6.1.4.1.2356.11.1.73.2.17.5.1
lcsStatusWlanMngmtApConf11uCellListEntry OBJECT-TYPE
    SYNTAX     LcsStatusWlanMngmtApConf11uCellListEntry
    MAX-ACCESS not-accessible
    STATUS     current
    DESCRIPTION
            ""
    INDEX {
            lcsStatusWlanMngmtApConf11uCellListEntryName
          }
    ::= { lcsStatusWlanMngmtApConf11uCellListTable 1 }

LcsStatusWlanMngmtApConf11uCellListEntry ::= SEQUENCE {
            lcsStatusWlanMngmtApConf11uCellListEntryName DisplayString,
            lcsStatusWlanMngmtApConf11uCellListEntryCountry DisplayString,
            lcsStatusWlanMngmtApConf11uCellListEntryNetwork DisplayString
    }

-- {COLUMN} 1.3.6.1.4.1.2356.11.1.73.2.17.5.1.1
lcsStatusWlanMngmtApConf11uCellListEntryName OBJECT-TYPE
    SYNTAX     DisplayString (SIZE(0..32))
    MAX-ACCESS read-only
    STATUS     current
    DESCRIPTION
            "-- empty --"
    ::= { lcsStatusWlanMngmtApConf11uCellListEntry 1 }

-- {COLUMN} 1.3.6.1.4.1.2356.11.1.73.2.17.5.1.2
lcsStatusWlanMngmtApConf11uCellListEntryCountry OBJECT-TYPE
    SYNTAX     DisplayString (SIZE(0..3))
    MAX-ACCESS read-only
    STATUS     current
    DESCRIPTION
            "Country-Code"
    ::= { lcsStatusWlanMngmtApConf11uCellListEntry 2 }

-- {COLUMN} 1.3.6.1.4.1.2356.11.1.73.2.17.5.1.3
lcsStatusWlanMngmtApConf11uCellListEntryNetwork OBJECT-TYPE
    SYNTAX     DisplayString (SIZE(0..3))
    MAX-ACCESS read-only
    STATUS     current
    DESCRIPTION
            "Network-Code"
    ::= { lcsStatusWlanMngmtApConf11uCellListEntry 3 }

-- {TABLE} 1.3.6.1.4.1.2356.11.1.73.2.17.6
lcsStatusWlanMngmtApConf11uVenueNameTable OBJECT-TYPE
    SYNTAX     SEQUENCE OF LcsStatusWlanMngmtApConf11uVenueNameEntry
    MAX-ACCESS not-accessible
    STATUS     current
    DESCRIPTION
            "-- empty --"
    ::= { lcsStatusWlanMngmtApConf11u 6 }

-- {ROW} 1.3.6.1.4.1.2356.11.1.73.2.17.6.1
lcsStatusWlanMngmtApConf11uVenueNameEntry OBJECT-TYPE
    SYNTAX     LcsStatusWlanMngmtApConf11uVenueNameEntry
    MAX-ACCESS not-accessible
    STATUS     current
    DESCRIPTION
            ""
    INDEX {
            lcsStatusWlanMngmtApConf11uVenueNameEntryName,
            lcsStatusWlanMngmtApConf11uVenueNameEntryLanguage
          }
    ::= { lcsStatusWlanMngmtApConf11uVenueNameTable 1 }

LcsStatusWlanMngmtApConf11uVenueNameEntry ::= SEQUENCE {
            lcsStatusWlanMngmtApConf11uVenueNameEntryName DisplayString,
            lcsStatusWlanMngmtApConf11uVenueNameEntryLanguage INTEGER,
            lcsStatusWlanMngmtApConf11uVenueNameEntryVenueName DisplayString
    }

-- {COLUMN} 1.3.6.1.4.1.2356.11.1.73.2.17.6.1.1
lcsStatusWlanMngmtApConf11uVenueNameEntryName OBJECT-TYPE
    SYNTAX     DisplayString (SIZE(0..32))
    MAX-ACCESS read-only
    STATUS     current
    DESCRIPTION
            "-- empty --"
    ::= { lcsStatusWlanMngmtApConf11uVenueNameEntry 1 }

-- {COLUMN} 1.3.6.1.4.1.2356.11.1.73.2.17.6.1.2
lcsStatusWlanMngmtApConf11uVenueNameEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13)
            }
    MAX-ACCESS read-only
    STATUS     current
    DESCRIPTION
            "-- empty --"
    ::= { lcsStatusWlanMngmtApConf11uVenueNameEntry 2 }

-- {COLUMN} 1.3.6.1.4.1.2356.11.1.73.2.17.6.1.3
lcsStatusWlanMngmtApConf11uVenueNameEntryVenueName OBJECT-TYPE
    SYNTAX     DisplayString (SIZE(0..65))
    MAX-ACCESS read-only
    STATUS     current
    DESCRIPTION
            "-- empty --"
    ::= { lcsStatusWlanMngmtApConf11uVenueNameEntry 3 }

-- {TABLE} 1.3.6.1.4.1.2356.11.1.73.2.17.7
lcsStatusWlanMngmtApConf11uNAIsTable OBJECT-TYPE
    SYNTAX     SEQUENCE OF LcsStatusWlanMngmtApConf11uNAIsEntry
    MAX-ACCESS not-accessible
    STATUS     current
    DESCRIPTION
            "NAI-Realms"
    ::= { lcsStatusWlanMngmtApConf11u 7 }

-- {ROW} 1.3.6.1.4.1.2356.11.1.73.2.17.7.1
lcsStatusWlanMngmtApConf11uNAIsEntry OBJECT-TYPE
    SYNTAX     LcsStatusWlanMngmtApConf11uNAIsEntry
    MAX-ACCESS not-accessible
    STATUS     current
    DESCRIPTION
            ""
    INDEX {
            lcsStatusWlanMngmtApConf11uNAIsEntryName
          }
    ::= { lcsStatusWlanMngmtApConf11uNAIsTable 1 }

LcsStatusWlanMngmtApConf11uNAIsEntry ::= SEQUENCE {
            lcsStatusWlanMngmtApConf11uNAIsEntryName DisplayString,
            lcsStatusWlanMngmtApConf11uNAIsEntryNaiRealm DisplayString,
            lcsStatusWlanMngmtApConf11uNAIsEntryEapMethod INTEGER,
            lcsStatusWlanMngmtApConf11uNAIsEntryAuthPar DisplayString
    }

-- {COLUMN} 1.3.6.1.4.1.2356.11.1.73.2.17.7.1.1
lcsStatusWlanMngmtApConf11uNAIsEntryName OBJECT-TYPE
    SYNTAX     DisplayString (SIZE(0..32))
    MAX-ACCESS read-only
    STATUS     current
    DESCRIPTION
            "-- empty --"
    ::= { lcsStatusWlanMngmtApConf11uNAIsEntry 1 }

-- {COLUMN} 1.3.6.1.4.1.2356.11.1.73.2.17.7.1.2
lcsStatusWlanMngmtApConf11uNAIsEntryNaiRealm OBJECT-TYPE
    SYNTAX     DisplayString (SIZE(0..32))
    MAX-ACCESS read-only
    STATUS     current
    DESCRIPTION
            "-- empty --"
    ::= { lcsStatusWlanMngmtApConf11uNAIsEntry 2 }

-- {COLUMN} 1.3.6.1.4.1.2356.11.1.73.2.17.7.1.3
lcsStatusWlanMngmtApConf11uNAIsEntryEapMethod OBJECT-TYPE
    SYNTAX     INTEGER {
                  eNone (0),
                  eEapTls (13),
                  eEapSim (18),
                  eEapTtls (21),
                  eEapAka (23)
            }
    MAX-ACCESS read-only
    STATUS     current
    DESCRIPTION
            "-- empty --"
    ::= { lcsStatusWlanMngmtApConf11uNAIsEntry 3 }

-- {COLUMN} 1.3.6.1.4.1.2356.11.1.73.2.17.7.1.4
lcsStatusWlanMngmtApConf11uNAIsEntryAuthPar OBJECT-TYPE
    SYNTAX     DisplayString (SIZE(0..65))
    MAX-ACCESS read-only
    STATUS     current
    DESCRIPTION
            "Auth-Parameter-List"
    ::= { lcsStatusWlanMngmtApConf11uNAIsEntry 4 }

-- {TABLE} 1.3.6.1.4.1.2356.11.1.73.2.17.8
lcsStatusWlanMngmtApConf11uOperatorListTable OBJECT-TYPE
    SYNTAX     SEQUENCE OF LcsStatusWlanMngmtApConf11uOperatorListEntry
    MAX-ACCESS not-accessible
    STATUS     current
    DESCRIPTION
            "-- empty --"
    ::= { lcsStatusWlanMngmtApConf11u 8 }

-- {ROW} 1.3.6.1.4.1.2356.11.1.73.2.17.8.1
lcsStatusWlanMngmtApConf11uOperatorListEntry OBJECT-TYPE
    SYNTAX     LcsStatusWlanMngmtApConf11uOperatorListEntry
    MAX-ACCESS not-accessible
    STATUS     current
    DESCRIPTION
            ""
    INDEX {
            lcsStatusWlanMngmtApConf11uOperatorListEntryName,
            lcsStatusWlanMngmtApConf11uOperatorListEntryLanguage
          }
    ::= { lcsStatusWlanMngmtApConf11uOperatorListTable 1 }

LcsStatusWlanMngmtApConf11uOperatorListEntry ::= SEQUENCE {
            lcsStatusWlanMngmtApConf11uOperatorListEntryName DisplayString,
            lcsStatusWlanMngmtApConf11uOperatorListEntryLanguage INTEGER,
            lcsStatusWlanMngmtApConf11uOperatorListEntryOperatorName DisplayString
    }

-- {COLUMN} 1.3.6.1.4.1.2356.11.1.73.2.17.8.1.1
lcsStatusWlanMngmtApConf11uOperatorListEntryName OBJECT-TYPE
    SYNTAX     DisplayString (SIZE(0..32))
    MAX-ACCESS read-only
    STATUS     current
    DESCRIPTION
            "-- empty --"
    ::= { lcsStatusWlanMngmtApConf11uOperatorListEntry 1 }

-- {COLUMN} 1.3.6.1.4.1.2356.11.1.73.2.17.8.1.2
lcsStatusWlanMngmtApConf11uOperatorListEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13)
            }
    MAX-ACCESS read-only
    STATUS     current
    DESCRIPTION
            "-- empty --"
    ::= { lcsStatusWlanMngmtApConf11uOperatorListEntry 2 }

-- {COLUMN} 1.3.6.1.4.1.2356.11.1.73.2.17.8.1.3
lcsStatusWlanMngmtApConf11uOperatorListEntryOperatorName OBJECT-TYPE
    SYNTAX     DisplayString (SIZE(0..65))
    MAX-ACCESS read-only
    STATUS     current
    DESCRIPTION
            "-- empty --"
    ::= { lcsStatusWlanMngmtApConf11uOperatorListEntry 3 }

-- {TABLE} 1.3.6.1.4.1.2356.11.1.73.2.17.9
lcsStatusWlanMngmtApConf11uGeneralTable OBJECT-TYPE
    SYNTAX     SEQUENCE OF LcsStatusWlanMngmtApConf11uGeneralEntry
    MAX-ACCESS not-accessible
    STATUS     current
    DESCRIPTION
            "-- empty --"
    ::= { lcsStatusWlanMngmtApConf11u 9 }

-- {ROW} 1.3.6.1.4.1.2356.11.1.73.2.17.9.1
lcsStatusWlanMngmtApConf11uGeneralEntry OBJECT-TYPE
    SYNTAX     LcsStatusWlanMngmtApConf11uGeneralEntry
    MAX-ACCESS not-accessible
    STATUS     current
    DESCRIPTION
            ""
    INDEX {
            lcsStatusWlanMngmtApConf11uGeneralEntryName
          }
    ::= { lcsStatusWlanMngmtApConf11uGeneralTable 1 }

LcsStatusWlanMngmtApConf11uGeneralEntry ::= SEQUENCE {
            lcsStatusWlanMngmtApConf11uGeneralEntryName DisplayString,
            lcsStatusWlanMngmtApConf11uGeneralEntryLinkStatus INTEGER,
            lcsStatusWlanMngmtApConf11uGeneralEntryDownlinkSpeed Integer32,
            lcsStatusWlanMngmtApConf11uGeneralEntryUplinkSpeed Integer32,
            lcsStatusWlanMngmtApConf11uGeneralEntryIpv4AddrType INTEGER,
            lcsStatusWlanMngmtApConf11uGeneralEntryIpv6AddrType INTEGER,
            lcsStatusWlanMngmtApConf11uGeneralEntryVenueGroup INTEGER,
            lcsStatusWlanMngmtApConf11uGeneralEntryVenueType Integer32,
            lcsStatusWlanMngmtApConf11uGeneralEntryVenueName DisplayString
    }

-- {COLUMN} 1.3.6.1.4.1.2356.11.1.73.2.17.9.1.1
lcsStatusWlanMngmtApConf11uGeneralEntryName OBJECT-TYPE
    SYNTAX     DisplayString (SIZE(0..32))
    MAX-ACCESS read-only
    STATUS     current
    DESCRIPTION
            "-- empty --"
    ::= { lcsStatusWlanMngmtApConf11uGeneralEntry 1 }

-- {COLUMN} 1.3.6.1.4.1.2356.11.1.73.2.17.9.1.2
lcsStatusWlanMngmtApConf11uGeneralEntryLinkStatus OBJECT-TYPE
    SYNTAX     INTEGER {
                  eAuto (0),
                  eLinkUp (1),
                  eLinkDown (2),
                  eLinkTest (3)
            }
    MAX-ACCESS read-only
    STATUS     current
    DESCRIPTION
            "-- empty --"
    ::= { lcsStatusWlanMngmtApConf11uGeneralEntry 2 }

-- {COLUMN} 1.3.6.1.4.1.2356.11.1.73.2.17.9.1.3
lcsStatusWlanMngmtApConf11uGeneralEntryDownlinkSpeed OBJECT-TYPE
    SYNTAX     Integer32 (0..2147483647)
    MAX-ACCESS read-only
    STATUS     current
    DESCRIPTION
            "-- empty --"
    ::= { lcsStatusWlanMngmtApConf11uGeneralEntry 3 }

-- {COLUMN} 1.3.6.1.4.1.2356.11.1.73.2.17.9.1.4
lcsStatusWlanMngmtApConf11uGeneralEntryUplinkSpeed OBJECT-TYPE
    SYNTAX     Integer32 (0..2147483647)
    MAX-ACCESS read-only
    STATUS     current
    DESCRIPTION
            "-- empty --"
    ::= { lcsStatusWlanMngmtApConf11uGeneralEntry 4 }

-- {COLUMN} 1.3.6.1.4.1.2356.11.1.73.2.17.9.1.5
lcsStatusWlanMngmtApConf11uGeneralEntryIpv4AddrType OBJECT-TYPE
    SYNTAX     INTEGER {
                  eNotAvailable (0),
                  ePublicAddrAvailable (1),
                  ePortRestrAddrAvail (2),
                  eSingleNatPrivAddrAvail (3),
                  eDoubleNatPrivAddrAvail (4),
                  ePortRestrSingleNatAddrAvail (5),
                  ePortRestrDoubleNatAddrAvail (6),
                  eAvailabilityNotKnown (7)
            }
    MAX-ACCESS read-only
    STATUS     current
    DESCRIPTION
            "-- empty --"
    ::= { lcsStatusWlanMngmtApConf11uGeneralEntry 5 }

-- {COLUMN} 1.3.6.1.4.1.2356.11.1.73.2.17.9.1.6
lcsStatusWlanMngmtApConf11uGeneralEntryIpv6AddrType OBJECT-TYPE
    SYNTAX     INTEGER {
                  eNotAvailable (0),
                  eAvailable (1),
                  eAvailabilityNotKnown (2)
            }
    MAX-ACCESS read-only
    STATUS     current
    DESCRIPTION
            "-- empty --"
    ::= { lcsStatusWlanMngmtApConf11uGeneralEntry 6 }

-- {COLUMN} 1.3.6.1.4.1.2356.11.1.73.2.17.9.1.7
lcsStatusWlanMngmtApConf11uGeneralEntryVenueGroup OBJECT-TYPE
    SYNTAX     INTEGER {
                  eUnspecified (0),
                  eAssembly (1),
                  eBusiness (2),
                  eEducational (3),
                  eFactoryAndIndustrial (4),
                  eInstitutional (5),
                  eMercantile (6),
                  eResindential (7),
                  eStorage (8),
                  eUtilityAndMiscellaneous (9),
                  eVehicular (10),
                  eOutdoor (11)
            }
    MAX-ACCESS read-only
    STATUS     current
    DESCRIPTION
            "-- empty --"
    ::= { lcsStatusWlanMngmtApConf11uGeneralEntry 7 }

-- {COLUMN} 1.3.6.1.4.1.2356.11.1.73.2.17.9.1.8
lcsStatusWlanMngmtApConf11uGeneralEntryVenueType OBJECT-TYPE
    SYNTAX     Integer32 (0..255)
    MAX-ACCESS read-only
    STATUS     current
    DESCRIPTION
            "-- empty --"
    ::= { lcsStatusWlanMngmtApConf11uGeneralEntry 8 }

-- {COLUMN} 1.3.6.1.4.1.2356.11.1.73.2.17.9.1.9
lcsStatusWlanMngmtApConf11uGeneralEntryVenueName OBJECT-TYPE
    SYNTAX     DisplayString (SIZE(0..32))
    MAX-ACCESS read-only
    STATUS     current
    DESCRIPTION
            "-- empty --"
    ::= { lcsStatusWlanMngmtApConf11uGeneralEntry 9 }

-- {TABLE} 1.3.6.1.4.1.2356.11.1.73.2.19
lcsStatusWlanMngmtApConfCfgAsgGrpTable OBJECT-TYPE
    SYNTAX     SEQUENCE OF LcsStatusWlanMngmtApConfCfgAsgGrpEntry
    MAX-ACCESS not-accessible
    STATUS     current
    DESCRIPTION
            ""
    ::= { lcsStatusWlanMngmtApConf 19 }

-- {ROW} 1.3.6.1.4.1.2356.11.1.73.2.19.1
lcsStatusWlanMngmtApConfCfgAsgGrpEntry OBJECT-TYPE
    SYNTAX     LcsStatusWlanMngmtApConfCfgAsgGrpEntry
    MAX-ACCESS not-accessible
    STATUS     current
    DESCRIPTION
            ""
    INDEX {
            lcsStatusWlanMngmtApConfCfgAsgGrpEntryName
          }
    ::= { lcsStatusWlanMngmtApConfCfgAsgGrpTable 1 }

LcsStatusWlanMngmtApConfCfgAsgGrpEntry ::= SEQUENCE {
            lcsStatusWlanMngmtApConfCfgAsgGrpEntryName DisplayString,
            lcsStatusWlanMngmtApConfCfgAsgGrpEntryProfile DisplayString,
            lcsStatusWlanMngmtApConfCfgAsgGrpEntryApIntranet DisplayString,
            lcsStatusWlanMngmtApConfCfgAsgGrpEntryIpv4ReferencePoolStart DisplayString,
            lcsStatusWlanMngmtApConfCfgAsgGrpEntryIpv4ReferencePoolEnd DisplayString,
            lcsStatusWlanMngmtApConfCfgAsgGrpEntryClientSteeringProfile DisplayString,
            lcsStatusWlanMngmtApConfCfgAsgGrpEntryIbeaconProfile DisplayString
    }

-- {COLUMN} 1.3.6.1.4.1.2356.11.1.73.2.19.1.1
lcsStatusWlanMngmtApConfCfgAsgGrpEntryName OBJECT-TYPE
    SYNTAX     DisplayString (SIZE(0..31))
    MAX-ACCESS read-only
    STATUS     current
    DESCRIPTION
            "-- empty --"
    ::= { lcsStatusWlanMngmtApConfCfgAsgGrpEntry 1 }

-- {COLUMN} 1.3.6.1.4.1.2356.11.1.73.2.19.1.2
lcsStatusWlanMngmtApConfCfgAsgGrpEntryProfile OBJECT-TYPE
    SYNTAX     DisplayString (SIZE(0..31))
    MAX-ACCESS read-only
    STATUS     current
    DESCRIPTION
            "-- empty --"
    ::= { lcsStatusWlanMngmtApConfCfgAsgGrpEntry 2 }

-- {COLUMN} 1.3.6.1.4.1.2356.11.1.73.2.19.1.3
lcsStatusWlanMngmtApConfCfgAsgGrpEntryApIntranet OBJECT-TYPE
    SYNTAX     DisplayString (SIZE(0..31))
    MAX-ACCESS read-only
    STATUS     current
    DESCRIPTION
            "-- empty --"
    ::= { lcsStatusWlanMngmtApConfCfgAsgGrpEntry 3 }

-- {COLUMN} 1.3.6.1.4.1.2356.11.1.73.2.19.1.4
lcsStatusWlanMngmtApConfCfgAsgGrpEntryIpv4ReferencePoolStart OBJECT-TYPE
    SYNTAX     DisplayString (SIZE(0..15))
    MAX-ACCESS read-only
    STATUS     current
    DESCRIPTION
            "-- empty --"
    ::= { lcsStatusWlanMngmtApConfCfgAsgGrpEntry 4 }

-- {COLUMN} 1.3.6.1.4.1.2356.11.1.73.2.19.1.5
lcsStatusWlanMngmtApConfCfgAsgGrpEntryIpv4ReferencePoolEnd OBJECT-TYPE
    SYNTAX     DisplayString (SIZE(0..15))
    MAX-ACCESS read-only
    STATUS     current
    DESCRIPTION
            "-- empty --"
    ::= { lcsStatusWlanMngmtApConfCfgAsgGrpEntry 5 }

-- {COLUMN} 1.3.6.1.4.1.2356.11.1.73.2.19.1.6
lcsStatusWlanMngmtApConfCfgAsgGrpEntryClientSteeringProfile OBJECT-TYPE
    SYNTAX     DisplayString (SIZE(0..31))
    MAX-ACCESS read-only
    STATUS     current
    DESCRIPTION
            "-- empty --"
    ::= { lcsStatusWlanMngmtApConfCfgAsgGrpEntry 6 }

-- {COLUMN} 1.3.6.1.4.1.2356.11.1.73.2.19.1.7
lcsStatusWlanMngmtApConfCfgAsgGrpEntryIbeaconProfile OBJECT-TYPE
    SYNTAX     DisplayString (SIZE(0..31))
    MAX-ACCESS read-only
    STATUS     current
    DESCRIPTION
            "-- empty --"
    ::= { lcsStatusWlanMngmtApConfCfgAsgGrpEntry 7 }

-- {TABLE} 1.3.6.1.4.1.2356.11.1.73.2.20
lcsStatusWlanMngmtApConfGroupsConfigErrorsTable OBJECT-TYPE
    SYNTAX     SEQUENCE OF LcsStatusWlanMngmtApConfGroupsConfigErrorsEntry
    MAX-ACCESS not-accessible
    STATUS     current
    DESCRIPTION
            "-- empty --"
    ::= { lcsStatusWlanMngmtApConf 20 }

-- {ROW} 1.3.6.1.4.1.2356.11.1.73.2.20.1
lcsStatusWlanMngmtApConfGroupsConfigErrorsEntry OBJECT-TYPE
    SYNTAX     LcsStatusWlanMngmtApConfGroupsConfigErrorsEntry
    MAX-ACCESS not-accessible
    STATUS     current
    DESCRIPTION
            ""
    INDEX {
            lcsStatusWlanMngmtApConfGroupsConfigErrorsEntryIndex
          }
    ::= { lcsStatusWlanMngmtApConfGroupsConfigErrorsTable 1 }

LcsStatusWlanMngmtApConfGroupsConfigErrorsEntry ::= SEQUENCE {
            lcsStatusWlanMngmtApConfGroupsConfigErrorsEntryIndex Integer32,
            lcsStatusWlanMngmtApConfGroupsConfigErrorsEntryGroup DisplayString,
            lcsStatusWlanMngmtApConfGroupsConfigErrorsEntryError INTEGER
    }

-- {COLUMN} 1.3.6.1.4.1.2356.11.1.73.2.20.1.1
lcsStatusWlanMngmtApConfGroupsConfigErrorsEntryIndex OBJECT-TYPE
    SYNTAX     Integer32 (0..2147483647)
    MAX-ACCESS read-only
    STATUS     current
    DESCRIPTION
            "-- empty --"
    ::= { lcsStatusWlanMngmtApConfGroupsConfigErrorsEntry 1 }

-- {COLUMN} 1.3.6.1.4.1.2356.11.1.73.2.20.1.2
lcsStatusWlanMngmtApConfGroupsConfigErrorsEntryGroup OBJECT-TYPE
    SYNTAX     DisplayString (SIZE(0..31))
    MAX-ACCESS read-only
    STATUS     current
    DESCRIPTION
            "-- empty --"
    ::= { lcsStatusWlanMngmtApConfGroupsConfigErrorsEntry 2 }

-- {COLUMN} 1.3.6.1.4.1.2356.11.1.73.2.20.1.3
lcsStatusWlanMngmtApConfGroupsConfigErrorsEntryError OBJECT-TYPE
    SYNTAX     INTEGER {
                  eIntranetNotFound (1),
                  eProfileNotFound (2),
                  eGroupNotFound (3)
            }
    MAX-ACCESS read-only
    STATUS     current
    DESCRIPTION
            "-- empty --"
    ::= { lcsStatusWlanMngmtApConfGroupsConfigErrorsEntry 3 }

-- {TABLE} 1.3.6.1.4.1.2356.11.1.73.2.21
lcsStatusWlanMngmtApConfTagGroupsTable OBJECT-TYPE
    SYNTAX     SEQUENCE OF LcsStatusWlanMngmtApConfTagGroupsEntry
    MAX-ACCESS not-accessible
    STATUS     current
    DESCRIPTION
            "-- empty --"
    ::= { lcsStatusWlanMngmtApConf 21 }

-- {ROW} 1.3.6.1.4.1.2356.11.1.73.2.21.1
lcsStatusWlanMngmtApConfTagGroupsEntry OBJECT-TYPE
    SYNTAX     LcsStatusWlanMngmtApConfTagGroupsEntry
    MAX-ACCESS not-accessible
    STATUS     current
    DESCRIPTION
            ""
    INDEX {
            lcsStatusWlanMngmtApConfTagGroupsEntryName
          }
    ::= { lcsStatusWlanMngmtApConfTagGroupsTable 1 }

LcsStatusWlanMngmtApConfTagGroupsEntry ::= SEQUENCE {
            lcsStatusWlanMngmtApConfTagGroupsEntryName DisplayString
    }

-- {COLUMN} 1.3.6.1.4.1.2356.11.1.73.2.21.1.1
lcsStatusWlanMngmtApConfTagGroupsEntryName OBJECT-TYPE
    SYNTAX     DisplayString (SIZE(0..31))
    MAX-ACCESS read-only
    STATUS     current
    DESCRIPTION
            "-- empty --"
    ::= { lcsStatusWlanMngmtApConfTagGroupsEntry 1 }

-- {TABLE} 1.3.6.1.4.1.2356.11.1.73.2.22
lcsStatusWlanMngmtApConfLedProfErrorsTable OBJECT-TYPE
    SYNTAX     SEQUENCE OF LcsStatusWlanMngmtApConfLedProfErrorsEntry
    MAX-ACCESS not-accessible
    STATUS     current
    DESCRIPTION
            "-- empty --"
    ::= { lcsStatusWlanMngmtApConf 22 }

-- {ROW} 1.3.6.1.4.1.2356.11.1.73.2.22.1
lcsStatusWlanMngmtApConfLedProfErrorsEntry OBJECT-TYPE
    SYNTAX     LcsStatusWlanMngmtApConfLedProfErrorsEntry
    MAX-ACCESS not-accessible
    STATUS     current
    DESCRIPTION
            ""
    INDEX {
            lcsStatusWlanMngmtApConfLedProfErrorsEntryIndex
          }
    ::= { lcsStatusWlanMngmtApConfLedProfErrorsTable 1 }

LcsStatusWlanMngmtApConfLedProfErrorsEntry ::= SEQUENCE {
            lcsStatusWlanMngmtApConfLedProfErrorsEntryIndex Integer32,
            lcsStatusWlanMngmtApConfLedProfErrorsEntryName DisplayString,
            lcsStatusWlanMngmtApConfLedProfErrorsEntryError INTEGER
    }

-- {COLUMN} 1.3.6.1.4.1.2356.11.1.73.2.22.1.1
lcsStatusWlanMngmtApConfLedProfErrorsEntryIndex OBJECT-TYPE
    SYNTAX     Integer32 (0..2147483647)
    MAX-ACCESS read-only
    STATUS     current
    DESCRIPTION
            "-- empty --"
    ::= { lcsStatusWlanMngmtApConfLedProfErrorsEntry 1 }

-- {COLUMN} 1.3.6.1.4.1.2356.11.1.73.2.22.1.2
lcsStatusWlanMngmtApConfLedProfErrorsEntryName OBJECT-TYPE
    SYNTAX     DisplayString (SIZE(0..31))
    MAX-ACCESS read-only
    STATUS     current
    DESCRIPTION
            "-- empty --"
    ::= { lcsStatusWlanMngmtApConfLedProfErrorsEntry 2 }

-- {COLUMN} 1.3.6.1.4.1.2356.11.1.73.2.22.1.3
lcsStatusWlanMngmtApConfLedProfErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eWlanProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20),
                  eAutowdsSsidNotUnique (21),
                  eAutowdsProfileNotUnique (22),
                  eAutowdsSsidNotDefined (23),
                  eLepsUProfileIsMissing (24)
            }
    MAX-ACCESS read-only
    STATUS     current
    DESCRIPTION
            "-- empty --"
    ::= { lcsStatusWlanMngmtApConfLedProfErrorsEntry 3 }

-- {TABLE} 1.3.6.1.4.1.2356.11.1.73.2.23
lcsStatusWlanMngmtApConfLedProfilesTable OBJECT-TYPE
    SYNTAX     SEQUENCE OF LcsStatusWlanMngmtApConfLedProfilesEntry
    MAX-ACCESS not-accessible
    STATUS     current
    DESCRIPTION
            "-- empty --"
    ::= { lcsStatusWlanMngmtApConf 23 }

-- {ROW} 1.3.6.1.4.1.2356.11.1.73.2.23.1
lcsStatusWlanMngmtApConfLedProfilesEntry OBJECT-TYPE
    SYNTAX     LcsStatusWlanMngmtApConfLedProfilesEntry
    MAX-ACCESS not-accessible
    STATUS     current
    DESCRIPTION
            ""
    INDEX {
            lcsStatusWlanMngmtApConfLedProfilesEntryName
          }
    ::= { lcsStatusWlanMngmtApConfLedProfilesTable 1 }

LcsStatusWlanMngmtApConfLedProfilesEntry ::= SEQUENCE {
            lcsStatusWlanMngmtApConfLedProfilesEntryName DisplayString,
            lcsStatusWlanMngmtApConfLedProfilesEntryLedMode INTEGER,
            lcsStatusWlanMngmtApConfLedProfilesEntryLedOffSeconds Integer32
    }

-- {COLUMN} 1.3.6.1.4.1.2356.11.1.73.2.23.1.1
lcsStatusWlanMngmtApConfLedProfilesEntryName OBJECT-TYPE
    SYNTAX     DisplayString (SIZE(0..31))
    MAX-ACCESS read-only
    STATUS     current
    DESCRIPTION
            "-- empty --"
    ::= { lcsStatusWlanMngmtApConfLedProfilesEntry 1 }

-- {COLUMN} 1.3.6.1.4.1.2356.11.1.73.2.23.1.4
lcsStatusWlanMngmtApConfLedProfilesEntryLedMode OBJECT-TYPE
    SYNTAX     INTEGER {
                  eOn (0),
                  eOff (1),
                  eTimedOff (2)
            }
    MAX-ACCESS read-only
    STATUS     current
    DESCRIPTION
            "-- empty --"
    ::= { lcsStatusWlanMngmtApConfLedProfilesEntry 4 }

-- {COLUMN} 1.3.6.1.4.1.2356.11.1.73.2.23.1.5
lcsStatusWlanMngmtApConfLedProfilesEntryLedOffSeconds OBJECT-TYPE
    SYNTAX     Integer32 (0..2147483647)
    MAX-ACCESS read-only
    STATUS     current
    DESCRIPTION
            "-- empty --"
    ::= { lcsStatusWlanMngmtApConfLedProfilesEntry 5 }

-- {NODE} 1.3.6.1.4.1.2356.11.1.73.2.24
lcsStatusWlanMngmtApConfLbs OBJECT IDENTIFIER ::= { lcsStatusWlanMngmtApConf 24 }

-- {TABLE} 1.3.6.1.4.1.2356.11.1.73.2.24.1
lcsStatusWlanMngmtApConfLbsGeneralTable OBJECT-TYPE
    SYNTAX     SEQUENCE OF LcsStatusWlanMngmtApConfLbsGeneralEntry
    MAX-ACCESS not-accessible
    STATUS     current
    DESCRIPTION
            "-- empty --"
    ::= { lcsStatusWlanMngmtApConfLbs 1 }

-- {ROW} 1.3.6.1.4.1.2356.11.1.73.2.24.1.1
lcsStatusWlanMngmtApConfLbsGeneralEntry OBJECT-TYPE
    SYNTAX     LcsStatusWlanMngmtApConfLbsGeneralEntry
    MAX-ACCESS not-accessible
    STATUS     current
    DESCRIPTION
            ""
    INDEX {
            lcsStatusWlanMngmtApConfLbsGeneralEntryName
          }
    ::= { lcsStatusWlanMngmtApConfLbsGeneralTable 1 }

LcsStatusWlanMngmtApConfLbsGeneralEntry ::= SEQUENCE {
            lcsStatusWlanMngmtApConfLbsGeneralEntryName DisplayString,
            lcsStatusWlanMngmtApConfLbsGeneralEntryOperating INTEGER,
            lcsStatusWlanMngmtApConfLbsGeneralEntryUseTlsConnection INTEGER,
            lcsStatusWlanMngmtApConfLbsGeneralEntryLbsServerAddress DisplayString,
            lcsStatusWlanMngmtApConfLbsGeneralEntryLbsServerPort Integer32,
            lcsStatusWlanMngmtApConfLbsGeneralEntryUserName DisplayString,
            lcsStatusWlanMngmtApConfLbsGeneralEntryPassword DisplayString,
            lcsStatusWlanMngmtApConfLbsGeneralEntryAggregation INTEGER,
            lcsStatusWlanMngmtApConfLbsGeneralEntrySequenceNumberTransmit INTEGER,
            lcsStatusWlanMngmtApConfLbsGeneralEntrySsidTransmit INTEGER,
            lcsStatusWlanMngmtApConfLbsGeneralEntryIfcTrans INTEGER,
            lcsStatusWlanMngmtApConfLbsGeneralEntryBssidTransmit INTEGER,
            lcsStatusWlanMngmtApConfLbsGeneralEntrySignalLevelTransmit INTEGER,
            lcsStatusWlanMngmtApConfLbsGeneralEntryFrequencyTransmit INTEGER,
            lcsStatusWlanMngmtApConfLbsGeneralEntryNoiseTransmit INTEGER,
            lcsStatusWlanMngmtApConfLbsGeneralEntryWlanFrameTypeTransmit INTEGER
    }

-- {COLUMN} 1.3.6.1.4.1.2356.11.1.73.2.24.1.1.1
lcsStatusWlanMngmtApConfLbsGeneralEntryName OBJECT-TYPE
    SYNTAX     DisplayString (SIZE(0..31))
    MAX-ACCESS read-only
    STATUS     current
    DESCRIPTION
            "-- empty --"
    ::= { lcsStatusWlanMngmtApConfLbsGeneralEntry 1 }

-- {COLUMN} 1.3.6.1.4.1.2356.11.1.73.2.24.1.1.2
lcsStatusWlanMngmtApConfLbsGeneralEntryOperating OBJECT-TYPE
    SYNTAX     INTEGER {
                  eNo (0),
                  eYes (1)
            }
    MAX-ACCESS read-only
    STATUS     current
    DESCRIPTION
            "-- empty --"
    ::= { lcsStatusWlanMngmtApConfLbsGeneralEntry 2 }

-- {COLUMN} 1.3.6.1.4.1.2356.11.1.73.2.24.1.1.3
lcsStatusWlanMngmtApConfLbsGeneralEntryUseTlsConnection OBJECT-TYPE
    SYNTAX     INTEGER {
                  eNo (0),
                  eYes (1)
            }
    MAX-ACCESS read-only
    STATUS     current
    DESCRIPTION
            "-- empty --"
    ::= { lcsStatusWlanMngmtApConfLbsGeneralEntry 3 }

-- {COLUMN} 1.3.6.1.4.1.2356.11.1.73.2.24.1.1.4
lcsStatusWlanMngmtApConfLbsGeneralEntryLbsServerAddress OBJECT-TYPE
    SYNTAX     DisplayString (SIZE(0..64))
    MAX-ACCESS read-only
    STATUS     current
    DESCRIPTION
            "-- empty --"
    ::= { lcsStatusWlanMngmtApConfLbsGeneralEntry 4 }

-- {COLUMN} 1.3.6.1.4.1.2356.11.1.73.2.24.1.1.5
lcsStatusWlanMngmtApConfLbsGeneralEntryLbsServerPort OBJECT-TYPE
    SYNTAX     Integer32 (0..65535)
    MAX-ACCESS read-only
    STATUS     current
    DESCRIPTION
            "-- empty --"
    ::= { lcsStatusWlanMngmtApConfLbsGeneralEntry 5 }

-- {COLUMN} 1.3.6.1.4.1.2356.11.1.73.2.24.1.1.6
lcsStatusWlanMngmtApConfLbsGeneralEntryUserName OBJECT-TYPE
    SYNTAX     DisplayString (SIZE(0..64))
    MAX-ACCESS read-only
    STATUS     current
    DESCRIPTION
            "-- empty --"
    ::= { lcsStatusWlanMngmtApConfLbsGeneralEntry 6 }

-- {COLUMN} 1.3.6.1.4.1.2356.11.1.73.2.24.1.1.7
lcsStatusWlanMngmtApConfLbsGeneralEntryPassword OBJECT-TYPE
    SYNTAX     DisplayString (SIZE(0..32))
    MAX-ACCESS read-only
    STATUS     current
    DESCRIPTION
            "-- empty --"
    ::= { lcsStatusWlanMngmtApConfLbsGeneralEntry 7 }

-- {COLUMN} 1.3.6.1.4.1.2356.11.1.73.2.24.1.1.8
lcsStatusWlanMngmtApConfLbsGeneralEntryAggregation OBJECT-TYPE
    SYNTAX     INTEGER {
                  eNo (0),
                  eYes (1)
            }
    MAX-ACCESS read-only
    STATUS     current
    DESCRIPTION
            "-- empty --"
    ::= { lcsStatusWlanMngmtApConfLbsGeneralEntry 8 }

-- {COLUMN} 1.3.6.1.4.1.2356.11.1.73.2.24.1.1.9
lcsStatusWlanMngmtApConfLbsGeneralEntrySequenceNumberTransmit OBJECT-TYPE
    SYNTAX     INTEGER {
                  eNo (0),
                  eYes (1)
            }
    MAX-ACCESS read-only
    STATUS     current
    DESCRIPTION
            "-- empty --"
    ::= { lcsStatusWlanMngmtApConfLbsGeneralEntry 9 }

-- {COLUMN} 1.3.6.1.4.1.2356.11.1.73.2.24.1.1.10
lcsStatusWlanMngmtApConfLbsGeneralEntrySsidTransmit OBJECT-TYPE
    SYNTAX     INTEGER {
                  eNo (0),
                  eYes (1)
            }
    MAX-ACCESS read-only
    STATUS     current
    DESCRIPTION
            "-- empty --"
    ::= { lcsStatusWlanMngmtApConfLbsGeneralEntry 10 }

-- {COLUMN} 1.3.6.1.4.1.2356.11.1.73.2.24.1.1.11
lcsStatusWlanMngmtApConfLbsGeneralEntryIfcTrans OBJECT-TYPE
    SYNTAX     INTEGER {
                  eNo (0),
                  eYes (1)
            }
    MAX-ACCESS read-only
    STATUS     current
    DESCRIPTION
            ""
    ::= { lcsStatusWlanMngmtApConfLbsGeneralEntry 11 }

-- {COLUMN} 1.3.6.1.4.1.2356.11.1.73.2.24.1.1.12
lcsStatusWlanMngmtApConfLbsGeneralEntryBssidTransmit OBJECT-TYPE
    SYNTAX     INTEGER {
                  eNo (0),
                  eYes (1)
            }
    MAX-ACCESS read-only
    STATUS     current
    DESCRIPTION
            "-- empty --"
    ::= { lcsStatusWlanMngmtApConfLbsGeneralEntry 12 }

-- {COLUMN} 1.3.6.1.4.1.2356.11.1.73.2.24.1.1.13
lcsStatusWlanMngmtApConfLbsGeneralEntrySignalLevelTransmit OBJECT-TYPE
    SYNTAX     INTEGER {
                  eNo (0),
                  eYes (1)
            }
    MAX-ACCESS read-only
    STATUS     current
    DESCRIPTION
            "-- empty --"
    ::= { lcsStatusWlanMngmtApConfLbsGeneralEntry 13 }

-- {COLUMN} 1.3.6.1.4.1.2356.11.1.73.2.24.1.1.14
lcsStatusWlanMngmtApConfLbsGeneralEntryFrequencyTransmit OBJECT-TYPE
    SYNTAX     INTEGER {
                  eNo (0),
                  eYes (1)
            }
    MAX-ACCESS read-only
    STATUS     current
    DESCRIPTION
            "-- empty --"
    ::= { lcsStatusWlanMngmtApConfLbsGeneralEntry 14 }

-- {COLUMN} 1.3.6.1.4.1.2356.11.1.73.2.24.1.1.15
lcsStatusWlanMngmtApConfLbsGeneralEntryNoiseTransmit OBJECT-TYPE
    SYNTAX     INTEGER {
                  eNo (0),
                  eYes (1)
            }
    MAX-ACCESS read-only
    STATUS     current
    DESCRIPTION
            "-- empty --"
    ::= { lcsStatusWlanMngmtApConfLbsGeneralEntry 15 }

-- {COLUMN} 1.3.6.1.4.1.2356.11.1.73.2.24.1.1.16
lcsStatusWlanMngmtApConfLbsGeneralEntryWlanFrameTypeTransmit OBJECT-TYPE
    SYNTAX     INTEGER {
                  eNo (0),
                  eYes (1)
            }
    MAX-ACCESS read-only
    STATUS     current
    DESCRIPTION
            "-- empty --"
    ::= { lcsStatusWlanMngmtApConfLbsGeneralEntry 16 }

-- {TABLE} 1.3.6.1.4.1.2356.11.1.73.2.24.2
lcsStatusWlanMngmtApConfLbsDevLocTable OBJECT-TYPE
    SYNTAX     SEQUENCE OF LcsStatusWlanMngmtApConfLbsDevLocEntry
    MAX-ACCESS not-accessible
    STATUS     current
    DESCRIPTION
            ""
    ::= { lcsStatusWlanMngmtApConfLbs 2 }

-- {ROW} 1.3.6.1.4.1.2356.11.1.73.2.24.2.1
lcsStatusWlanMngmtApConfLbsDevLocEntry OBJECT-TYPE
    SYNTAX     LcsStatusWlanMngmtApConfLbsDevLocEntry
    MAX-ACCESS not-accessible
    STATUS     current
    DESCRIPTION
            ""
    INDEX {
            lcsStatusWlanMngmtApConfLbsDevLocEntryName
          }
    ::= { lcsStatusWlanMngmtApConfLbsDevLocTable 1 }

LcsStatusWlanMngmtApConfLbsDevLocEntry ::= SEQUENCE {
            lcsStatusWlanMngmtApConfLbsDevLocEntryName DisplayString,
            lcsStatusWlanMngmtApConfLbsDevLocEntryFloor Integer32,
            lcsStatusWlanMngmtApConfLbsDevLocEntryHeight Integer32,
            lcsStatusWlanMngmtApConfLbsDevLocEntryLatDeg Integer32,
            lcsStatusWlanMngmtApConfLbsDevLocEntryLatMin Integer32,
            lcsStatusWlanMngmtApConfLbsDevLocEntryLatSec Integer32,
            lcsStatusWlanMngmtApConfLbsDevLocEntryLatHemi INTEGER,
            lcsStatusWlanMngmtApConfLbsDevLocEntryLongDeg Integer32,
            lcsStatusWlanMngmtApConfLbsDevLocEntryLongMin Integer32,
            lcsStatusWlanMngmtApConfLbsDevLocEntryLongSec Integer32,
            lcsStatusWlanMngmtApConfLbsDevLocEntryLongHemi INTEGER,
            lcsStatusWlanMngmtApConfLbsDevLocEntryDescription DisplayString,
            lcsStatusWlanMngmtApConfLbsDevLocEntryLatDecDeg DisplayString,
            lcsStatusWlanMngmtApConfLbsDevLocEntryLongDecDeg DisplayString
    }

-- {COLUMN} 1.3.6.1.4.1.2356.11.1.73.2.24.2.1.1
lcsStatusWlanMngmtApConfLbsDevLocEntryName OBJECT-TYPE
    SYNTAX     DisplayString (SIZE(0..31))
    MAX-ACCESS read-only
    STATUS     current
    DESCRIPTION
            "-- empty --"
    ::= { lcsStatusWlanMngmtApConfLbsDevLocEntry 1 }

-- {COLUMN} 1.3.6.1.4.1.2356.11.1.73.2.24.2.1.2
lcsStatusWlanMngmtApConfLbsDevLocEntryFloor OBJECT-TYPE
    SYNTAX     Integer32 (-32768..32767)
    MAX-ACCESS read-only
    STATUS     current
    DESCRIPTION
            "-- empty --"
    ::= { lcsStatusWlanMngmtApConfLbsDevLocEntry 2 }

-- {COLUMN} 1.3.6.1.4.1.2356.11.1.73.2.24.2.1.3
lcsStatusWlanMngmtApConfLbsDevLocEntryHeight OBJECT-TYPE
    SYNTAX     Integer32 (-32768..32767)
    MAX-ACCESS read-only
    STATUS     current
    DESCRIPTION
            "-- empty --"
    ::= { lcsStatusWlanMngmtApConfLbsDevLocEntry 3 }

-- {COLUMN} 1.3.6.1.4.1.2356.11.1.73.2.24.2.1.4
lcsStatusWlanMngmtApConfLbsDevLocEntryLatDeg OBJECT-TYPE
    SYNTAX     Integer32 (0..255)
    MAX-ACCESS read-only
    STATUS     current
    DESCRIPTION
            ""
    ::= { lcsStatusWlanMngmtApConfLbsDevLocEntry 4 }

-- {COLUMN} 1.3.6.1.4.1.2356.11.1.73.2.24.2.1.5
lcsStatusWlanMngmtApConfLbsDevLocEntryLatMin OBJECT-TYPE
    SYNTAX     Integer32 (0..255)
    MAX-ACCESS read-only
    STATUS     current
    DESCRIPTION
            ""
    ::= { lcsStatusWlanMngmtApConfLbsDevLocEntry 5 }

-- {COLUMN} 1.3.6.1.4.1.2356.11.1.73.2.24.2.1.6
lcsStatusWlanMngmtApConfLbsDevLocEntryLatSec OBJECT-TYPE
    SYNTAX     Integer32 (0..2147483647)
    MAX-ACCESS read-only
    STATUS     current
    DESCRIPTION
            ""
    ::= { lcsStatusWlanMngmtApConfLbsDevLocEntry 6 }

-- {COLUMN} 1.3.6.1.4.1.2356.11.1.73.2.24.2.1.7
lcsStatusWlanMngmtApConfLbsDevLocEntryLatHemi OBJECT-TYPE
    SYNTAX     INTEGER {
                  eN (0),
                  eS (1)
            }
    MAX-ACCESS read-only
    STATUS     current
    DESCRIPTION
            ""
    ::= { lcsStatusWlanMngmtApConfLbsDevLocEntry 7 }

-- {COLUMN} 1.3.6.1.4.1.2356.11.1.73.2.24.2.1.8
lcsStatusWlanMngmtApConfLbsDevLocEntryLongDeg OBJECT-TYPE
    SYNTAX     Integer32 (0..255)
    MAX-ACCESS read-only
    STATUS     current
    DESCRIPTION
            ""
    ::= { lcsStatusWlanMngmtApConfLbsDevLocEntry 8 }

-- {COLUMN} 1.3.6.1.4.1.2356.11.1.73.2.24.2.1.9
lcsStatusWlanMngmtApConfLbsDevLocEntryLongMin OBJECT-TYPE
    SYNTAX     Integer32 (0..255)
    MAX-ACCESS read-only
    STATUS     current
    DESCRIPTION
            ""
    ::= { lcsStatusWlanMngmtApConfLbsDevLocEntry 9 }

-- {COLUMN} 1.3.6.1.4.1.2356.11.1.73.2.24.2.1.10
lcsStatusWlanMngmtApConfLbsDevLocEntryLongSec OBJECT-TYPE
    SYNTAX     Integer32 (0..2147483647)
    MAX-ACCESS read-only
    STATUS     current
    DESCRIPTION
            ""
    ::= { lcsStatusWlanMngmtApConfLbsDevLocEntry 10 }

-- {COLUMN} 1.3.6.1.4.1.2356.11.1.73.2.24.2.1.11
lcsStatusWlanMngmtApConfLbsDevLocEntryLongHemi OBJECT-TYPE
    SYNTAX     INTEGER {
                  eE (0),
                  eW (1)
            }
    MAX-ACCESS read-only
    STATUS     current
    DESCRIPTION
            ""
    ::= { lcsStatusWlanMngmtApConfLbsDevLocEntry 11 }

-- {COLUMN} 1.3.6.1.4.1.2356.11.1.73.2.24.2.1.12
lcsStatusWlanMngmtApConfLbsDevLocEntryDescription OBJECT-TYPE
    SYNTAX     DisplayString (SIZE(0..31))
    MAX-ACCESS read-only
    STATUS     current
    DESCRIPTION
            "-- empty --"
    ::= { lcsStatusWlanMngmtApConfLbsDevLocEntry 12 }

-- {COLUMN} 1.3.6.1.4.1.2356.11.1.73.2.24.2.1.13
lcsStatusWlanMngmtApConfLbsDevLocEntryLatDecDeg OBJECT-TYPE
    SYNTAX     DisplayString (SIZE(0..12))
    MAX-ACCESS read-only
    STATUS     current
    DESCRIPTION
            ""
    ::= { lcsStatusWlanMngmtApConfLbsDevLocEntry 13 }

-- {COLUMN} 1.3.6.1.4.1.2356.11.1.73.2.24.2.1.14
lcsStatusWlanMngmtApConfLbsDevLocEntryLongDecDeg OBJECT-TYPE
    SYNTAX     DisplayString (SIZE(0..12))
    MAX-ACCESS read-only
    STATUS     current
    DESCRIPTION
            ""
    ::= { lcsStatusWlanMngmtApConfLbsDevLocEntry 14 }

-- {TABLE} 1.3.6.1.4.1.2356.11.1.73.2.25
lcsStatusWlanMngmtApConfWirelessEpaperProfileTable OBJECT-TYPE
    SYNTAX     SEQUENCE OF LcsStatusWlanMngmtApConfWirelessEpaperProfileEntry
    MAX-ACCESS not-accessible
    STATUS     current
    DESCRIPTION
            "-- empty --"
    ::= { lcsStatusWlanMngmtApConf 25 }

-- {ROW} 1.3.6.1.4.1.2356.11.1.73.2.25.1
lcsStatusWlanMngmtApConfWirelessEpaperProfileEntry OBJECT-TYPE
    SYNTAX     LcsStatusWlanMngmtApConfWirelessEpaperProfileEntry
    MAX-ACCESS not-accessible
    STATUS     current
    DESCRIPTION
            ""
    INDEX {
            lcsStatusWlanMngmtApConfWirelessEpaperProfileEntryName
          }
    ::= { lcsStatusWlanMngmtApConfWirelessEpaperProfileTable 1 }

LcsStatusWlanMngmtApConfWirelessEpaperProfileEntry ::= SEQUENCE {
            lcsStatusWlanMngmtApConfWirelessEpaperProfileEntryName DisplayString,
            lcsStatusWlanMngmtApConfWirelessEpaperProfileEntryOperating INTEGER,
            lcsStatusWlanMngmtApConfWirelessEpaperProfileEntryPort Integer32
    }

-- {COLUMN} 1.3.6.1.4.1.2356.11.1.73.2.25.1.1
lcsStatusWlanMngmtApConfWirelessEpaperProfileEntryName OBJECT-TYPE
    SYNTAX     DisplayString (SIZE(0..31))
    MAX-ACCESS read-only
    STATUS     current
    DESCRIPTION
            "-- empty --"
    ::= { lcsStatusWlanMngmtApConfWirelessEpaperProfileEntry 1 }

-- {COLUMN} 1.3.6.1.4.1.2356.11.1.73.2.25.1.2
lcsStatusWlanMngmtApConfWirelessEpaperProfileEntryOperating OBJECT-TYPE
    SYNTAX     INTEGER {
                  eNo (0),
                  eYes (1)
            }
    MAX-ACCESS read-only
    STATUS     current
    DESCRIPTION
            "-- empty --"
    ::= { lcsStatusWlanMngmtApConfWirelessEpaperProfileEntry 2 }

-- {COLUMN} 1.3.6.1.4.1.2356.11.1.73.2.25.1.3
lcsStatusWlanMngmtApConfWirelessEpaperProfileEntryPort OBJECT-TYPE
    SYNTAX     Integer32 (0..65535)
    MAX-ACCESS read-only
    STATUS     current
    DESCRIPTION
            "-- empty --"
    ::= { lcsStatusWlanMngmtApConfWirelessEpaperProfileEntry 3 }

-- {TABLE} 1.3.6.1.4.1.2356.11.1.73.2.26
lcsStatusWlanMngmtApConfIbeaconProfileTable OBJECT-TYPE
    SYNTAX     SEQUENCE OF LcsStatusWlanMngmtApConfIbeaconProfileEntry
    MAX-ACCESS not-accessible
    STATUS     current
    DESCRIPTION
            "-- empty --"
    ::= { lcsStatusWlanMngmtApConf 26 }

-- {ROW} 1.3.6.1.4.1.2356.11.1.73.2.26.1
lcsStatusWlanMngmtApConfIbeaconProfileEntry OBJECT-TYPE
    SYNTAX     LcsStatusWlanMngmtApConfIbeaconProfileEntry
    MAX-ACCESS not-accessible
    STATUS     current
    DESCRIPTION
            ""
    INDEX {
            lcsStatusWlanMngmtApConfIbeaconProfileEntryName
          }
    ::= { lcsStatusWlanMngmtApConfIbeaconProfileTable 1 }

LcsStatusWlanMngmtApConfIbeaconProfileEntry ::= SEQUENCE {
            lcsStatusWlanMngmtApConfIbeaconProfileEntryName DisplayString,
            lcsStatusWlanMngmtApConfIbeaconProfileEntryOperating INTEGER,
            lcsStatusWlanMngmtApConfIbeaconProfileEntryMajor Integer32,
            lcsStatusWlanMngmtApConfIbeaconProfileEntryUuid DisplayString
    }

-- {COLUMN} 1.3.6.1.4.1.2356.11.1.73.2.26.1.1
lcsStatusWlanMngmtApConfIbeaconProfileEntryName OBJECT-TYPE
    SYNTAX     DisplayString (SIZE(0..31))
    MAX-ACCESS read-only
    STATUS     current
    DESCRIPTION
            "-- empty --"
    ::= { lcsStatusWlanMngmtApConfIbeaconProfileEntry 1 }

-- {COLUMN} 1.3.6.1.4.1.2356.11.1.73.2.26.1.2
lcsStatusWlanMngmtApConfIbeaconProfileEntryOperating OBJECT-TYPE
    SYNTAX     INTEGER {
                  eNo (0),
                  eYes (1)
            }
    MAX-ACCESS read-only
    STATUS     current
    DESCRIPTION
            "-- empty --"
    ::= { lcsStatusWlanMngmtApConfIbeaconProfileEntry 2 }

-- {COLUMN} 1.3.6.1.4.1.2356.11.1.73.2.26.1.3
lcsStatusWlanMngmtApConfIbeaconProfileEntryMajor OBJECT-TYPE
    SYNTAX     Integer32 (0..65535)
    MAX-ACCESS read-only
    STATUS     current
    DESCRIPTION
            "-- empty --"
    ::= { lcsStatusWlanMngmtApConfIbeaconProfileEntry 3 }

-- {COLUMN} 1.3.6.1.4.1.2356.11.1.73.2.26.1.4
lcsStatusWlanMngmtApConfIbeaconProfileEntryUuid OBJECT-TYPE
    SYNTAX     DisplayString (SIZE(0..36))
    MAX-ACCESS read-only
    STATUS     current
    DESCRIPTION
            "-- empty --"
    ::= { lcsStatusWlanMngmtApConfIbeaconProfileEntry 4 }

-- {NODE} 1.3.6.1.4.1.2356.11.1.73.2.27
lcsStatusWlanMngmtApConfLepsU OBJECT IDENTIFIER ::= { lcsStatusWlanMngmtApConf 27 }

-- {TABLE} 1.3.6.1.4.1.2356.11.1.73.2.27.1
lcsStatusWlanMngmtApConfLepsUProfilesTable OBJECT-TYPE
    SYNTAX     SEQUENCE OF LcsStatusWlanMngmtApConfLepsUProfilesEntry
    MAX-ACCESS not-accessible
    STATUS     current
    DESCRIPTION
            "-- empty --"
    ::= { lcsStatusWlanMngmtApConfLepsU 1 }

-- {ROW} 1.3.6.1.4.1.2356.11.1.73.2.27.1.1
lcsStatusWlanMngmtApConfLepsUProfilesEntry OBJECT-TYPE
    SYNTAX     LcsStatusWlanMngmtApConfLepsUProfilesEntry
    MAX-ACCESS not-accessible
    STATUS     current
    DESCRIPTION
            ""
    INDEX {
            lcsStatusWlanMngmtApConfLepsUProfilesEntryName
          }
    ::= { lcsStatusWlanMngmtApConfLepsUProfilesTable 1 }

LcsStatusWlanMngmtApConfLepsUProfilesEntry ::= SEQUENCE {
            lcsStatusWlanMngmtApConfLepsUProfilesEntryName DisplayString,
            lcsStatusWlanMngmtApConfLepsUProfilesEntryNetworkprofile DisplayString,
            lcsStatusWlanMngmtApConfLepsUProfilesEntryPerClientTxLimit Integer32,
            lcsStatusWlanMngmtApConfLepsUProfilesEntryPerClientRxLimit Integer32,
            lcsStatusWlanMngmtApConfLepsUProfilesEntryVlanIdnew Integer32
    }

-- {COLUMN} 1.3.6.1.4.1.2356.11.1.73.2.27.1.1.1
lcsStatusWlanMngmtApConfLepsUProfilesEntryName OBJECT-TYPE
    SYNTAX     DisplayString (SIZE(0..32))
    MAX-ACCESS read-only
    STATUS     current
    DESCRIPTION
            "-- empty --"
    ::= { lcsStatusWlanMngmtApConfLepsUProfilesEntry 1 }

-- {COLUMN} 1.3.6.1.4.1.2356.11.1.73.2.27.1.1.2
lcsStatusWlanMngmtApConfLepsUProfilesEntryNetworkprofile OBJECT-TYPE
    SYNTAX     DisplayString (SIZE(0..31))
    MAX-ACCESS read-only
    STATUS     current
    DESCRIPTION
            "-- empty --"
    ::= { lcsStatusWlanMngmtApConfLepsUProfilesEntry 2 }

-- {COLUMN} 1.3.6.1.4.1.2356.11.1.73.2.27.1.1.3
lcsStatusWlanMngmtApConfLepsUProfilesEntryPerClientTxLimit OBJECT-TYPE
    SYNTAX     Integer32 (0..2147483647)
    MAX-ACCESS read-only
    STATUS     current
    DESCRIPTION
            "-- empty --"
    ::= { lcsStatusWlanMngmtApConfLepsUProfilesEntry 3 }

-- {COLUMN} 1.3.6.1.4.1.2356.11.1.73.2.27.1.1.4
lcsStatusWlanMngmtApConfLepsUProfilesEntryPerClientRxLimit OBJECT-TYPE
    SYNTAX     Integer32 (0..2147483647)
    MAX-ACCESS read-only
    STATUS     current
    DESCRIPTION
            "-- empty --"
    ::= { lcsStatusWlanMngmtApConfLepsUProfilesEntry 4 }

-- {COLUMN} 1.3.6.1.4.1.2356.11.1.73.2.27.1.1.5
lcsStatusWlanMngmtApConfLepsUProfilesEntryVlanIdnew OBJECT-TYPE
    SYNTAX     Integer32 (0..65535)
    MAX-ACCESS read-only
    STATUS     current
    DESCRIPTION
            ""
    ::= { lcsStatusWlanMngmtApConfLepsUProfilesEntry 5 }

-- {TABLE} 1.3.6.1.4.1.2356.11.1.73.2.27.2
lcsStatusWlanMngmtApConfLepsUUsersTable OBJECT-TYPE
    SYNTAX     SEQUENCE OF LcsStatusWlanMngmtApConfLepsUUsersEntry
    MAX-ACCESS not-accessible
    STATUS     current
    DESCRIPTION
            "-- empty --"
    ::= { lcsStatusWlanMngmtApConfLepsU 2 }

-- {ROW} 1.3.6.1.4.1.2356.11.1.73.2.27.2.1
lcsStatusWlanMngmtApConfLepsUUsersEntry OBJECT-TYPE
    SYNTAX     LcsStatusWlanMngmtApConfLepsUUsersEntry
    MAX-ACCESS not-accessible
    STATUS     current
    DESCRIPTION
            ""
    INDEX {
            lcsStatusWlanMngmtApConfLepsUUsersEntryName
          }
    ::= { lcsStatusWlanMngmtApConfLepsUUsersTable 1 }

LcsStatusWlanMngmtApConfLepsUUsersEntry ::= SEQUENCE {
            lcsStatusWlanMngmtApConfLepsUUsersEntryName DisplayString,
            lcsStatusWlanMngmtApConfLepsUUsersEntryProfile DisplayString,
            lcsStatusWlanMngmtApConfLepsUUsersEntryWpaPassphrase DisplayString,
            lcsStatusWlanMngmtApConfLepsUUsersEntryPerClientTxLimit Integer32,
            lcsStatusWlanMngmtApConfLepsUUsersEntryPerClientRxLimit Integer32,
            lcsStatusWlanMngmtApConfLepsUUsersEntryVlanIdnew Integer32
    }

-- {COLUMN} 1.3.6.1.4.1.2356.11.1.73.2.27.2.1.1
lcsStatusWlanMngmtApConfLepsUUsersEntryName OBJECT-TYPE
    SYNTAX     DisplayString (SIZE(0..32))
    MAX-ACCESS read-only
    STATUS     current
    DESCRIPTION
            "-- empty --"
    ::= { lcsStatusWlanMngmtApConfLepsUUsersEntry 1 }

-- {COLUMN} 1.3.6.1.4.1.2356.11.1.73.2.27.2.1.2
lcsStatusWlanMngmtApConfLepsUUsersEntryProfile OBJECT-TYPE
    SYNTAX     DisplayString (SIZE(0..32))
    MAX-ACCESS read-only
    STATUS     current
    DESCRIPTION
            "-- empty --"
    ::= { lcsStatusWlanMngmtApConfLepsUUsersEntry 2 }

-- {COLUMN} 1.3.6.1.4.1.2356.11.1.73.2.27.2.1.3
lcsStatusWlanMngmtApConfLepsUUsersEntryWpaPassphrase OBJECT-TYPE
    SYNTAX     DisplayString (SIZE(0..63))
    MAX-ACCESS read-only
    STATUS     current
    DESCRIPTION
            "-- empty --"
    ::= { lcsStatusWlanMngmtApConfLepsUUsersEntry 3 }

-- {COLUMN} 1.3.6.1.4.1.2356.11.1.73.2.27.2.1.4
lcsStatusWlanMngmtApConfLepsUUsersEntryPerClientTxLimit OBJECT-TYPE
    SYNTAX     Integer32 (0..2147483647)
    MAX-ACCESS read-only
    STATUS     current
    DESCRIPTION
            "-- empty --"
    ::= { lcsStatusWlanMngmtApConfLepsUUsersEntry 4 }

-- {COLUMN} 1.3.6.1.4.1.2356.11.1.73.2.27.2.1.5
lcsStatusWlanMngmtApConfLepsUUsersEntryPerClientRxLimit OBJECT-TYPE
    SYNTAX     Integer32 (0..2147483647)
    MAX-ACCESS read-only
    STATUS     current
    DESCRIPTION
            "-- empty --"
    ::= { lcsStatusWlanMngmtApConfLepsUUsersEntry 5 }

-- {COLUMN} 1.3.6.1.4.1.2356.11.1.73.2.27.2.1.6
lcsStatusWlanMngmtApConfLepsUUsersEntryVlanIdnew OBJECT-TYPE
    SYNTAX     Integer32 (0..65535)
    MAX-ACCESS read-only
    STATUS     current
    DESCRIPTION
            ""
    ::= { lcsStatusWlanMngmtApConfLepsUUsersEntry 6 }

-- {TABLE} 1.3.6.1.4.1.2356.11.1.73.2.27.3
lcsStatusWlanMngmtApConfLepsUUsrCfErrTable OBJECT-TYPE
    SYNTAX     SEQUENCE OF LcsStatusWlanMngmtApConfLepsUUsrCfErrEntry
    MAX-ACCESS not-accessible
    STATUS     current
    DESCRIPTION
            ""
    ::= { lcsStatusWlanMngmtApConfLepsU 3 }

-- {ROW} 1.3.6.1.4.1.2356.11.1.73.2.27.3.1
lcsStatusWlanMngmtApConfLepsUUsrCfErrEntry OBJECT-TYPE
    SYNTAX     LcsStatusWlanMngmtApConfLepsUUsrCfErrEntry
    MAX-ACCESS not-accessible
    STATUS     current
    DESCRIPTION
            ""
    INDEX {
            lcsStatusWlanMngmtApConfLepsUUsrCfErrEntryIndex
          }
    ::= { lcsStatusWlanMngmtApConfLepsUUsrCfErrTable 1 }

LcsStatusWlanMngmtApConfLepsUUsrCfErrEntry ::= SEQUENCE {
            lcsStatusWlanMngmtApConfLepsUUsrCfErrEntryIndex Integer32,
            lcsStatusWlanMngmtApConfLepsUUsrCfErrEntryName DisplayString,
            lcsStatusWlanMngmtApConfLepsUUsrCfErrEntryError INTEGER,
            lcsStatusWlanMngmtApConfLepsUUsrCfErrEntryNetworkApParameters DisplayString
    }

-- {COLUMN} 1.3.6.1.4.1.2356.11.1.73.2.27.3.1.1
lcsStatusWlanMngmtApConfLepsUUsrCfErrEntryIndex OBJECT-TYPE
    SYNTAX     Integer32 (0..2147483647)
    MAX-ACCESS read-only
    STATUS     current
    DESCRIPTION
            "-- empty --"
    ::= { lcsStatusWlanMngmtApConfLepsUUsrCfErrEntry 1 }

-- {COLUMN} 1.3.6.1.4.1.2356.11.1.73.2.27.3.1.2
lcsStatusWlanMngmtApConfLepsUUsrCfErrEntryName OBJECT-TYPE
    SYNTAX     DisplayString (SIZE(0..31))
    MAX-ACCESS read-only
    STATUS     current
    DESCRIPTION
            "-- empty --"
    ::= { lcsStatusWlanMngmtApConfLepsUUsrCfErrEntry 2 }

-- {COLUMN} 1.3.6.1.4.1.2356.11.1.73.2.27.3.1.3
lcsStatusWlanMngmtApConfLepsUUsrCfErrEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eWlanProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20),
                  eAutowdsSsidNotUnique (21),
                  eAutowdsProfileNotUnique (22),
                  eAutowdsSsidNotDefined (23),
                  eLepsUProfileIsMissing (24)
            }
    MAX-ACCESS read-only
    STATUS     current
    DESCRIPTION
            "-- empty --"
    ::= { lcsStatusWlanMngmtApConfLepsUUsrCfErrEntry 3 }

-- {COLUMN} 1.3.6.1.4.1.2356.11.1.73.2.27.3.1.4
lcsStatusWlanMngmtApConfLepsUUsrCfErrEntryNetworkApParameters OBJECT-TYPE
    SYNTAX     DisplayString (SIZE(0..31))
    MAX-ACCESS read-only
    STATUS     current
    DESCRIPTION
            ""
    ::= { lcsStatusWlanMngmtApConfLepsUUsrCfErrEntry 4 }

-- {SCALAR} 1.3.6.1.4.1.2356.11.1.73.3
lcsStatusWlanMngmtNumberOfApConnections OBJECT-TYPE
    SYNTAX     Integer32 (0..2147483647)
    MAX-ACCESS read-only
    STATUS     current
    DESCRIPTION
            ""
    ::= { lcsStatusWlanMngmt 3 }

-- {TABLE} 1.3.6.1.4.1.2356.11.1.73.4
lcsStatusWlanMngmtApConnectionsTable OBJECT-TYPE
    SYNTAX     SEQUENCE OF LcsStatusWlanMngmtApConnectionsEntry
    MAX-ACCESS not-accessible
    STATUS     current
    DESCRIPTION
            ""
    ::= { lcsStatusWlanMngmt 4 }

-- {ROW} 1.3.6.1.4.1.2356.11.1.73.4.1
lcsStatusWlanMngmtApConnectionsEntry OBJECT-TYPE
    SYNTAX     LcsStatusWlanMngmtApConnectionsEntry
    MAX-ACCESS not-accessible
    STATUS     current
    DESCRIPTION
            ""
    INDEX {
            lcsStatusWlanMngmtApConnectionsEntryJob
          }
    ::= { lcsStatusWlanMngmtApConnectionsTable 1 }

LcsStatusWlanMngmtApConnectionsEntry ::= SEQUENCE {
            lcsStatusWlanMngmtApConnectionsEntryJob Integer32,
            lcsStatusWlanMngmtApConnectionsEntryJobId DisplayString,
            lcsStatusWlanMngmtApConnectionsEntryApLanMac MacAddress,
            lcsStatusWlanMngmtApConnectionsEntryIpAddress IpAddress,
            lcsStatusWlanMngmtApConnectionsEntryAuthorized INTEGER,
            lcsStatusWlanMngmtApConnectionsEntryState INTEGER,
            lcsStatusWlanMngmtApConnectionsEntryConfiguration INTEGER,
            lcsStatusWlanMngmtApConnectionsEntryEncrypted INTEGER,
            lcsStatusWlanMngmtApConnectionsEntryPmtu Integer32,
            lcsStatusWlanMngmtApConnectionsEntryDscpForControlPackets INTEGER,
            lcsStatusWlanMngmtApConnectionsEntryDscpForDataPackets INTEGER,
            lcsStatusWlanMngmtApConnectionsEntryRetransmissions Integer32,
            lcsStatusWlanMngmtApConnectionsEntryFwManagementSupported INTEGER
    }

-- {COLUMN} 1.3.6.1.4.1.2356.11.1.73.4.1.1
lcsStatusWlanMngmtApConnectionsEntryJob OBJECT-TYPE
    SYNTAX     Integer32 (0..2147483647)
    MAX-ACCESS read-only
    STATUS     current
    DESCRIPTION
            ""
    ::= { lcsStatusWlanMngmtApConnectionsEntry 1 }

-- {COLUMN} 1.3.6.1.4.1.2356.11.1.73.4.1.2
lcsStatusWlanMngmtApConnectionsEntryJobId OBJECT-TYPE
    SYNTAX     DisplayString (SIZE(0..2))
    MAX-ACCESS read-only
    STATUS     current
    DESCRIPTION
            ""
    ::= { lcsStatusWlanMngmtApConnectionsEntry 2 }

-- {COLUMN} 1.3.6.1.4.1.2356.11.1.73.4.1.3
lcsStatusWlanMngmtApConnectionsEntryApLanMac OBJECT-TYPE
    SYNTAX     MacAddress
    MAX-ACCESS read-only
    STATUS     current
    DESCRIPTION
            ""
    ::= { lcsStatusWlanMngmtApConnectionsEntry 3 }

-- {COLUMN} 1.3.6.1.4.1.2356.11.1.73.4.1.4
lcsStatusWlanMngmtApConnectionsEntryIpAddress OBJECT-TYPE
    SYNTAX     IpAddress
    MAX-ACCESS read-only
    STATUS     current
    DESCRIPTION
            ""
    ::= { lcsStatusWlanMngmtApConnectionsEntry 4 }

-- {COLUMN} 1.3.6.1.4.1.2356.11.1.73.4.1.5
lcsStatusWlanMngmtApConnectionsEntryAuthorized OBJECT-TYPE
    SYNTAX     INTEGER {
                  eUnknown (0),
                  eYes (1),
                  eNo (2)
            }
    MAX-ACCESS read-only
    STATUS     current
    DESCRIPTION
            ""
    ::= { lcsStatusWlanMngmtApConnectionsEntry 5 }

-- {COLUMN} 1.3.6.1.4.1.2356.11.1.73.4.1.6
lcsStatusWlanMngmtApConnectionsEntryState OBJECT-TYPE
    SYNTAX     INTEGER {
                  eUnknown (0),
                  eIdle (5),
                  eDiscovery (10),
                  eDtlsSetup (15),
                  eJoin (20),
                  eConfigure (25),
                  eImageData (30),
                  eReset (35),
                  eDtlsTeardown (40),
                  eSulking (45),
                  eRun (100)
            }
    MAX-ACCESS read-only
    STATUS     current
    DESCRIPTION
            ""
    ::= { lcsStatusWlanMngmtApConnectionsEntry 6 }

-- {COLUMN} 1.3.6.1.4.1.2356.11.1.73.4.1.7
lcsStatusWlanMngmtApConnectionsEntryConfiguration OBJECT-TYPE
    SYNTAX     INTEGER {
                  eNo (0),
                  eYes (1),
                  eDefault (2)
            }
    MAX-ACCESS read-only
    STATUS     current
    DESCRIPTION
            ""
    ::= { lcsStatusWlanMngmtApConnectionsEntry 7 }

-- {COLUMN} 1.3.6.1.4.1.2356.11.1.73.4.1.8
lcsStatusWlanMngmtApConnectionsEntryEncrypted OBJECT-TYPE
    SYNTAX     INTEGER {
                  eNo (0),
                  eYes (1)
            }
    MAX-ACCESS read-only
    STATUS     current
    DESCRIPTION
            ""
    ::= { lcsStatusWlanMngmtApConnectionsEntry 8 }

-- {COLUMN} 1.3.6.1.4.1.2356.11.1.73.4.1.9
lcsStatusWlanMngmtApConnectionsEntryPmtu OBJECT-TYPE
    SYNTAX     Integer32 (0..2147483647)
    MAX-ACCESS read-only
    STATUS     current
    DESCRIPTION
            ""
    ::= { lcsStatusWlanMngmtApConnectionsEntry 9 }

-- {COLUMN} 1.3.6.1.4.1.2356.11.1.73.4.1.10
lcsStatusWlanMngmtApConnectionsEntryDscpForControlPackets OBJECT-TYPE
    SYNTAX     INTEGER {
                  eBestEffort (0),
                  eAssuredForwarding11 (40),
                  eAssuredForwarding12 (48),
                  eAssuredForwarding13 (56),
                  eAssuredForwarding21 (72),
                  eAssuredForwarding22 (80),
                  eAssuredForwarding23 (88),
                  eAssuredForwarding31 (104),
                  eAssuredForwarding32 (112),
                  eAssuredForwarding33 (120),
                  eAssuredForwarding41 (136),
                  eAssuredForwarding42 (144),
                  eAssuredForwarding43 (152),
                  eExpeditedForwarding (184)
            }
    MAX-ACCESS read-only
    STATUS     current
    DESCRIPTION
            ""
    ::= { lcsStatusWlanMngmtApConnectionsEntry 10 }

-- {COLUMN} 1.3.6.1.4.1.2356.11.1.73.4.1.11
lcsStatusWlanMngmtApConnectionsEntryDscpForDataPackets OBJECT-TYPE
    SYNTAX     INTEGER {
                  eBestEffort (0),
                  eAssuredForwarding11 (40),
                  eAssuredForwarding12 (48),
                  eAssuredForwarding13 (56),
                  eAssuredForwarding21 (72),
                  eAssuredForwarding22 (80),
                  eAssuredForwarding23 (88),
                  eAssuredForwarding31 (104),
                  eAssuredForwarding32 (112),
                  eAssuredForwarding33 (120),
                  eAssuredForwarding41 (136),
                  eAssuredForwarding42 (144),
                  eAssuredForwarding43 (152),
                  eExpeditedForwarding (184)
            }
    MAX-ACCESS read-only
    STATUS     current
    DESCRIPTION
            ""
    ::= { lcsStatusWlanMngmtApConnectionsEntry 11 }

-- {COLUMN} 1.3.6.1.4.1.2356.11.1.73.4.1.12
lcsStatusWlanMngmtApConnectionsEntryRetransmissions OBJECT-TYPE
    SYNTAX     Integer32 (0..2147483647)
    MAX-ACCESS read-only
    STATUS     current
    DESCRIPTION
            "-- empty --"
    ::= { lcsStatusWlanMngmtApConnectionsEntry 12 }

-- {COLUMN} 1.3.6.1.4.1.2356.11.1.73.4.1.13
lcsStatusWlanMngmtApConnectionsEntryFwManagementSupported OBJECT-TYPE
    SYNTAX     INTEGER {
                  eNo (0),
                  eYes (1)
            }
    MAX-ACCESS read-only
    STATUS     current
    DESCRIPTION
            "-- empty --"
    ::= { lcsStatusWlanMngmtApConnectionsEntry 13 }

-- {SCALAR} 1.3.6.1.4.1.2356.11.1.73.5
lcsStatusWlanMngmtExpectedAp OBJECT-TYPE
    SYNTAX     Integer32 (0..2147483647)
    MAX-ACCESS read-only
    STATUS     current
    DESCRIPTION
            ""
    ::= { lcsStatusWlanMngmt 5 }

-- {SCALAR} 1.3.6.1.4.1.2356.11.1.73.6
lcsStatusWlanMngmtConnectedExpectedAp OBJECT-TYPE
    SYNTAX     Integer32 (0..2147483647)
    MAX-ACCESS read-only
    STATUS     current
    DESCRIPTION
            ""
    ::= { lcsStatusWlanMngmt 6 }

-- {SCALAR} 1.3.6.1.4.1.2356.11.1.73.7
lcsStatusWlanMngmtConnectedManagedAp OBJECT-TYPE
    SYNTAX     Integer32 (0..2147483647)
    MAX-ACCESS read-only
    STATUS     current
    DESCRIPTION
            ""
    ::= { lcsStatusWlanMngmt 7 }

-- {SCALAR} 1.3.6.1.4.1.2356.11.1.73.8
lcsStatusWlanMngmtConnectedNewAp OBJECT-TYPE
    SYNTAX     Integer32 (0..2147483647)
    MAX-ACCESS read-only
    STATUS     current
    DESCRIPTION
            ""
    ::= { lcsStatusWlanMngmt 8 }

-- {NODE} 1.3.6.1.4.1.2356.11.1.73.9
lcsStatusWlanMngmtApStatus OBJECT IDENTIFIER ::= { lcsStatusWlanMngmt 9 }

-- {TABLE} 1.3.6.1.4.1.2356.11.1.73.9.1
lcsStatusWlanMngmtApStatusMissingApTable OBJECT-TYPE
    SYNTAX     SEQUENCE OF LcsStatusWlanMngmtApStatusMissingApEntry
    MAX-ACCESS not-accessible
    STATUS     current
    DESCRIPTION
            ""
    ::= { lcsStatusWlanMngmtApStatus 1 }

-- {ROW} 1.3.6.1.4.1.2356.11.1.73.9.1.1
lcsStatusWlanMngmtApStatusMissingApEntry OBJECT-TYPE
    SYNTAX     LcsStatusWlanMngmtApStatusMissingApEntry
    MAX-ACCESS not-accessible
    STATUS     current
    DESCRIPTION
            ""
    INDEX {
            lcsStatusWlanMngmtApStatusMissingApEntryApLanMac
          }
    ::= { lcsStatusWlanMngmtApStatusMissingApTable 1 }

LcsStatusWlanMngmtApStatusMissingApEntry ::= SEQUENCE {
            lcsStatusWlanMngmtApStatusMissingApEntryApLanMac MacAddress,
            lcsStatusWlanMngmtApStatusMissingApEntryIpAddress IpAddress,
            lcsStatusWlanMngmtApStatusMissingApEntryName DisplayString,
            lcsStatusWlanMngmtApStatusMissingApEntryLocation DisplayString,
            lcsStatusWlanMngmtApStatusMissingApEntryValid INTEGER,
            lcsStatusWlanMngmtApStatusMissingApEntryModule DisplayString,
            lcsStatusWlanMngmtApStatusMissingApEntryGroups DisplayString
    }

-- {COLUMN} 1.3.6.1.4.1.2356.11.1.73.9.1.1.1
lcsStatusWlanMngmtApStatusMissingApEntryApLanMac OBJECT-TYPE
    SYNTAX     MacAddress
    MAX-ACCESS read-only
    STATUS     current
    DESCRIPTION
            ""
    ::= { lcsStatusWlanMngmtApStatusMissingApEntry 1 }

-- {COLUMN} 1.3.6.1.4.1.2356.11.1.73.9.1.1.2
lcsStatusWlanMngmtApStatusMissingApEntryIpAddress OBJECT-TYPE
    SYNTAX     IpAddress
    MAX-ACCESS read-only
    STATUS     current
    DESCRIPTION
            ""
    ::= { lcsStatusWlanMngmtApStatusMissingApEntry 2 }

-- {COLUMN} 1.3.6.1.4.1.2356.11.1.73.9.1.1.3
lcsStatusWlanMngmtApStatusMissingApEntryName OBJECT-TYPE
    SYNTAX     DisplayString (SIZE(0..82))
    MAX-ACCESS read-only
    STATUS     current
    DESCRIPTION
            ""
    ::= { lcsStatusWlanMngmtApStatusMissingApEntry 3 }

-- {COLUMN} 1.3.6.1.4.1.2356.11.1.73.9.1.1.4
lcsStatusWlanMngmtApStatusMissingApEntryLocation OBJECT-TYPE
    SYNTAX     DisplayString (SIZE(0..251))
    MAX-ACCESS read-only
    STATUS     current
    DESCRIPTION
            ""
    ::= { lcsStatusWlanMngmtApStatusMissingApEntry 4 }

-- {COLUMN} 1.3.6.1.4.1.2356.11.1.73.9.1.1.5
lcsStatusWlanMngmtApStatusMissingApEntryValid OBJECT-TYPE
    SYNTAX     INTEGER {
                  eNo (0),
                  eYes (1)
            }
    MAX-ACCESS read-only
    STATUS     current
    DESCRIPTION
            ""
    ::= { lcsStatusWlanMngmtApStatusMissingApEntry 5 }

-- {COLUMN} 1.3.6.1.4.1.2356.11.1.73.9.1.1.21
lcsStatusWlanMngmtApStatusMissingApEntryModule OBJECT-TYPE
    SYNTAX     DisplayString (SIZE(0..64))
    MAX-ACCESS read-only
    STATUS     current
    DESCRIPTION
            ""
    ::= { lcsStatusWlanMngmtApStatusMissingApEntry 21 }

-- {COLUMN} 1.3.6.1.4.1.2356.11.1.73.9.1.1.31
lcsStatusWlanMngmtApStatusMissingApEntryGroups OBJECT-TYPE
    SYNTAX     DisplayString (SIZE(0..251))
    MAX-ACCESS read-only
    STATUS     current
    DESCRIPTION
            "-- empty --"
    ::= { lcsStatusWlanMngmtApStatusMissingApEntry 31 }

-- {TABLE} 1.3.6.1.4.1.2356.11.1.73.9.2
lcsStatusWlanMngmtApStatusActiveRadiosTable OBJECT-TYPE
    SYNTAX     SEQUENCE OF LcsStatusWlanMngmtApStatusActiveRadiosEntry
    MAX-ACCESS not-accessible
    STATUS     current
    DESCRIPTION
            ""
    ::= { lcsStatusWlanMngmtApStatus 2 }

-- {ROW} 1.3.6.1.4.1.2356.11.1.73.9.2.1
lcsStatusWlanMngmtApStatusActiveRadiosEntry OBJECT-TYPE
    SYNTAX     LcsStatusWlanMngmtApStatusActiveRadiosEntry
    MAX-ACCESS not-accessible
    STATUS     current
    DESCRIPTION
            ""
    INDEX {
            lcsStatusWlanMngmtApStatusActiveRadiosEntryApLanMac,
            lcsStatusWlanMngmtApStatusActiveRadiosEntryIfc
          }
    ::= { lcsStatusWlanMngmtApStatusActiveRadiosTable 1 }

LcsStatusWlanMngmtApStatusActiveRadiosEntry ::= SEQUENCE {
            lcsStatusWlanMngmtApStatusActiveRadiosEntryApLanMac MacAddress,
            lcsStatusWlanMngmtApStatusActiveRadiosEntryIpAddress IpAddress,
            lcsStatusWlanMngmtApStatusActiveRadiosEntryName DisplayString,
            lcsStatusWlanMngmtApStatusActiveRadiosEntryLocation DisplayString,
            lcsStatusWlanMngmtApStatusActiveRadiosEntryValid INTEGER,
            lcsStatusWlanMngmtApStatusActiveRadiosEntryApWlanMac MacAddress,
            lcsStatusWlanMngmtApStatusActiveRadiosEntryIfc Integer32,
            lcsStatusWlanMngmtApStatusActiveRadiosEntryRadioBand Integer32,
            lcsStatusWlanMngmtApStatusActiveRadiosEntryRadioChannel Integer32,
            lcsStatusWlanMngmtApStatusActiveRadiosEntryClientCount Integer32,
            lcsStatusWlanMngmtApStatusActiveRadiosEntryBackgroundScan Integer32,
            lcsStatusWlanMngmtApStatusActiveRadiosEntryCardId DisplayString,
            lcsStatusWlanMngmtApStatusActiveRadiosEntryCardFirmwareVersion DisplayString,
            lcsStatusWlanMngmtApStatusActiveRadiosEntryCardSerialNumber DisplayString,
            lcsStatusWlanMngmtApStatusActiveRadiosEntryOperating INTEGER,
            lcsStatusWlanMngmtApStatusActiveRadiosEntryTransmitPower DisplayString,
            lcsStatusWlanMngmtApStatusActiveRadiosEntryEirp DisplayString,
            lcsStatusWlanMngmtApStatusActiveRadiosEntryExcEirp Integer32,
            lcsStatusWlanMngmtApStatusActiveRadiosEntryInternal INTEGER,
            lcsStatusWlanMngmtApStatusActiveRadiosEntryRadios Integer32,
            lcsStatusWlanMngmtApStatusActiveRadiosEntryModule DisplayString,
            lcsStatusWlanMngmtApStatusActiveRadiosEntrySerialNumber DisplayString,
            lcsStatusWlanMngmtApStatusActiveRadiosEntryVersion DisplayString,
            lcsStatusWlanMngmtApStatusActiveRadiosEntryCardState INTEGER,
            lcsStatusWlanMngmtApStatusActiveRadiosEntryRadioFldOpt INTEGER,
            lcsStatusWlanMngmtApStatusActiveRadiosEntryMinimalModemLoad Integer32,
            lcsStatusWlanMngmtApStatusActiveRadiosEntryMaximalModemLoad Integer32,
            lcsStatusWlanMngmtApStatusActiveRadiosEntryAverageModemLoad Integer32,
            lcsStatusWlanMngmtApStatusActiveRadiosEntryApConnection INTEGER,
            lcsStatusWlanMngmtApStatusActiveRadiosEntryGroups DisplayString,
            lcsStatusWlanMngmtApStatusActiveRadiosEntryAdaptRfOptLastHour Integer32,
            lcsStatusWlanMngmtApStatusActiveRadiosEntryAdaptRfOptLast5Hours Integer32,
            lcsStatusWlanMngmtApStatusActiveRadiosEntryAdaptRfOptLast24Hours Integer32,
            lcsStatusWlanMngmtApStatusActiveRadiosEntryRxErrorRatio Integer32,
            lcsStatusWlanMngmtApStatusActiveRadiosEntryTxErrorRatio Integer32,
            lcsStatusWlanMngmtApStatusActiveRadiosEntryIdsOperational INTEGER,
            lcsStatusWlanMngmtApStatusActiveRadiosEntryChannelBandwidth INTEGER,
            lcsStatusWlanMngmtApStatusActiveRadiosEntryLepsUUserLimit Integer32,
            lcsStatusWlanMngmtApStatusActiveRadiosEntryWpaKeyTypes BITS,
            lcsStatusWlanMngmtApStatusActiveRadiosEntryBssidCount Integer32,
            lcsStatusWlanMngmtApStatusActiveRadiosEntryOperatingSystem INTEGER
    }

-- {COLUMN} 1.3.6.1.4.1.2356.11.1.73.9.2.1.1
lcsStatusWlanMngmtApStatusActiveRadiosEntryApLanMac OBJECT-TYPE
    SYNTAX     MacAddress
    MAX-ACCESS read-only
    STATUS     current
    DESCRIPTION
            ""
    ::= { lcsStatusWlanMngmtApStatusActiveRadiosEntry 1 }

-- {COLUMN} 1.3.6.1.4.1.2356.11.1.73.9.2.1.2
lcsStatusWlanMngmtApStatusActiveRadiosEntryIpAddress OBJECT-TYPE
    SYNTAX     IpAddress
    MAX-ACCESS read-only
    STATUS     current
    DESCRIPTION
            ""
    ::= { lcsStatusWlanMngmtApStatusActiveRadiosEntry 2 }

-- {COLUMN} 1.3.6.1.4.1.2356.11.1.73.9.2.1.3
lcsStatusWlanMngmtApStatusActiveRadiosEntryName OBJECT-TYPE
    SYNTAX     DisplayString (SIZE(0..82))
    MAX-ACCESS read-only
    STATUS     current
    DESCRIPTION
            ""
    ::= { lcsStatusWlanMngmtApStatusActiveRadiosEntry 3 }

-- {COLUMN} 1.3.6.1.4.1.2356.11.1.73.9.2.1.4
lcsStatusWlanMngmtApStatusActiveRadiosEntryLocation OBJECT-TYPE
    SYNTAX     DisplayString (SIZE(0..251))
    MAX-ACCESS read-only
    STATUS     current
    DESCRIPTION
            ""
    ::= { lcsStatusWlanMngmtApStatusActiveRadiosEntry 4 }

-- {COLUMN} 1.3.6.1.4.1.2356.11.1.73.9.2.1.5
lcsStatusWlanMngmtApStatusActiveRadiosEntryValid OBJECT-TYPE
    SYNTAX     INTEGER {
                  eNo (0),
                  eYes (1)
            }
    MAX-ACCESS read-only
    STATUS     current
    DESCRIPTION
            ""
    ::= { lcsStatusWlanMngmtApStatusActiveRadiosEntry 5 }

-- {COLUMN} 1.3.6.1.4.1.2356.11.1.73.9.2.1.6
lcsStatusWlanMngmtApStatusActiveRadiosEntryApWlanMac OBJECT-TYPE
    SYNTAX     MacAddress
    MAX-ACCESS read-only
    STATUS     current
    DESCRIPTION
            ""
    ::= { lcsStatusWlanMngmtApStatusActiveRadiosEntry 6 }

-- {COLUMN} 1.3.6.1.4.1.2356.11.1.73.9.2.1.7
lcsStatusWlanMngmtApStatusActiveRadiosEntryIfc OBJECT-TYPE
    SYNTAX     Integer32 (0..255)
    MAX-ACCESS read-only
    STATUS     current
    DESCRIPTION
            ""
    ::= { lcsStatusWlanMngmtApStatusActiveRadiosEntry 7 }

-- {COLUMN} 1.3.6.1.4.1.2356.11.1.73.9.2.1.8
lcsStatusWlanMngmtApStatusActiveRadiosEntryRadioBand OBJECT-TYPE
    SYNTAX     Integer32 (0..255)
    MAX-ACCESS read-only
    STATUS     current
    DESCRIPTION
            ""
    ::= { lcsStatusWlanMngmtApStatusActiveRadiosEntry 8 }

-- {COLUMN} 1.3.6.1.4.1.2356.11.1.73.9.2.1.9
lcsStatusWlanMngmtApStatusActiveRadiosEntryRadioChannel OBJECT-TYPE
    SYNTAX     Integer32 (0..255)
    MAX-ACCESS read-only
    STATUS     current
    DESCRIPTION
            ""
    ::= { lcsStatusWlanMngmtApStatusActiveRadiosEntry 9 }

-- {COLUMN} 1.3.6.1.4.1.2356.11.1.73.9.2.1.10
lcsStatusWlanMngmtApStatusActiveRadiosEntryClientCount OBJECT-TYPE
    SYNTAX     Integer32 (0..65535)
    MAX-ACCESS read-only
    STATUS     current
    DESCRIPTION
            ""
    ::= { lcsStatusWlanMngmtApStatusActiveRadiosEntry 10 }

-- {COLUMN} 1.3.6.1.4.1.2356.11.1.73.9.2.1.11
lcsStatusWlanMngmtApStatusActiveRadiosEntryBackgroundScan OBJECT-TYPE
    SYNTAX     Integer32 (0..2147483647)
    MAX-ACCESS read-only
    STATUS     current
    DESCRIPTION
            ""
    ::= { lcsStatusWlanMngmtApStatusActiveRadiosEntry 11 }

-- {COLUMN} 1.3.6.1.4.1.2356.11.1.73.9.2.1.12
lcsStatusWlanMngmtApStatusActiveRadiosEntryCardId OBJECT-TYPE
    SYNTAX     DisplayString (SIZE(0..90))
    MAX-ACCESS read-only
    STATUS     current
    DESCRIPTION
            ""
    ::= { lcsStatusWlanMngmtApStatusActiveRadiosEntry 12 }

-- {COLUMN} 1.3.6.1.4.1.2356.11.1.73.9.2.1.13
lcsStatusWlanMngmtApStatusActiveRadiosEntryCardFirmwareVersion OBJECT-TYPE
    SYNTAX     DisplayString (SIZE(0..32))
    MAX-ACCESS read-only
    STATUS     current
    DESCRIPTION
            ""
    ::= { lcsStatusWlanMngmtApStatusActiveRadiosEntry 13 }

-- {COLUMN} 1.3.6.1.4.1.2356.11.1.73.9.2.1.14
lcsStatusWlanMngmtApStatusActiveRadiosEntryCardSerialNumber OBJECT-TYPE
    SYNTAX     DisplayString (SIZE(0..32))
    MAX-ACCESS read-only
    STATUS     current
    DESCRIPTION
            ""
    ::= { lcsStatusWlanMngmtApStatusActiveRadiosEntry 14 }

-- {COLUMN} 1.3.6.1.4.1.2356.11.1.73.9.2.1.15
lcsStatusWlanMngmtApStatusActiveRadiosEntryOperating OBJECT-TYPE
    SYNTAX     INTEGER {
                  eNo (0),
                  eYes (1)
            }
    MAX-ACCESS read-only
    STATUS     current
    DESCRIPTION
            ""
    ::= { lcsStatusWlanMngmtApStatusActiveRadiosEntry 15 }

-- {COLUMN} 1.3.6.1.4.1.2356.11.1.73.9.2.1.16
lcsStatusWlanMngmtApStatusActiveRadiosEntryTransmitPower OBJECT-TYPE
    SYNTAX     DisplayString (SIZE(0..255))
    MAX-ACCESS read-only
    STATUS     current
    DESCRIPTION
            ""
    ::= { lcsStatusWlanMngmtApStatusActiveRadiosEntry 16 }

-- {COLUMN} 1.3.6.1.4.1.2356.11.1.73.9.2.1.17
lcsStatusWlanMngmtApStatusActiveRadiosEntryEirp OBJECT-TYPE
    SYNTAX     DisplayString (SIZE(0..255))
    MAX-ACCESS read-only
    STATUS     current
    DESCRIPTION
            ""
    ::= { lcsStatusWlanMngmtApStatusActiveRadiosEntry 17 }

-- {COLUMN} 1.3.6.1.4.1.2356.11.1.73.9.2.1.18
lcsStatusWlanMngmtApStatusActiveRadiosEntryExcEirp OBJECT-TYPE
    SYNTAX     Integer32 (0..255)
    MAX-ACCESS read-only
    STATUS     current
    DESCRIPTION
            ""
    ::= { lcsStatusWlanMngmtApStatusActiveRadiosEntry 18 }

-- {COLUMN} 1.3.6.1.4.1.2356.11.1.73.9.2.1.19
lcsStatusWlanMngmtApStatusActiveRadiosEntryInternal OBJECT-TYPE
    SYNTAX     INTEGER {
                  eNo (0),
                  eYes (1)
            }
    MAX-ACCESS read-only
    STATUS     current
    DESCRIPTION
            ""
    ::= { lcsStatusWlanMngmtApStatusActiveRadiosEntry 19 }

-- {COLUMN} 1.3.6.1.4.1.2356.11.1.73.9.2.1.20
lcsStatusWlanMngmtApStatusActiveRadiosEntryRadios OBJECT-TYPE
    SYNTAX     Integer32 (0..255)
    MAX-ACCESS read-only
    STATUS     current
    DESCRIPTION
            ""
    ::= { lcsStatusWlanMngmtApStatusActiveRadiosEntry 20 }

-- {COLUMN} 1.3.6.1.4.1.2356.11.1.73.9.2.1.21
lcsStatusWlanMngmtApStatusActiveRadiosEntryModule OBJECT-TYPE
    SYNTAX     DisplayString (SIZE(0..64))
    MAX-ACCESS read-only
    STATUS     current
    DESCRIPTION
            ""
    ::= { lcsStatusWlanMngmtApStatusActiveRadiosEntry 21 }

-- {COLUMN} 1.3.6.1.4.1.2356.11.1.73.9.2.1.22
lcsStatusWlanMngmtApStatusActiveRadiosEntrySerialNumber OBJECT-TYPE
    SYNTAX     DisplayString (SIZE(0..18))
    MAX-ACCESS read-only
    STATUS     current
    DESCRIPTION
            ""
    ::= { lcsStatusWlanMngmtApStatusActiveRadiosEntry 22 }

-- {COLUMN} 1.3.6.1.4.1.2356.11.1.73.9.2.1.23
lcsStatusWlanMngmtApStatusActiveRadiosEntryVersion OBJECT-TYPE
    SYNTAX     DisplayString (SIZE(0..25))
    MAX-ACCESS read-only
    STATUS     current
    DESCRIPTION
            ""
    ::= { lcsStatusWlanMngmtApStatusActiveRadiosEntry 23 }

-- {COLUMN} 1.3.6.1.4.1.2356.11.1.73.9.2.1.24
lcsStatusWlanMngmtApStatusActiveRadiosEntryCardState OBJECT-TYPE
    SYNTAX     INTEGER {
                  eNormal (0),
                  eFailure (1),
                  eInitalizing (2),
                  eNoCard (4)
            }
    MAX-ACCESS read-only
    STATUS     current
    DESCRIPTION
            ""
    ::= { lcsStatusWlanMngmtApStatusActiveRadiosEntry 24 }

-- {COLUMN} 1.3.6.1.4.1.2356.11.1.73.9.2.1.25
lcsStatusWlanMngmtApStatusActiveRadiosEntryRadioFldOpt OBJECT-TYPE
    SYNTAX     INTEGER {
                  eInactive (0),
                  eWaiting (1),
                  eScanning (2)
            }
    MAX-ACCESS read-only
    STATUS     current
    DESCRIPTION
            "radio field optimization"
    ::= { lcsStatusWlanMngmtApStatusActiveRadiosEntry 25 }

-- {COLUMN} 1.3.6.1.4.1.2356.11.1.73.9.2.1.26
lcsStatusWlanMngmtApStatusActiveRadiosEntryMinimalModemLoad OBJECT-TYPE
    SYNTAX     Integer32 (0..2147483647)
    MAX-ACCESS read-only
    STATUS     current
    DESCRIPTION
            ""
    ::= { lcsStatusWlanMngmtApStatusActiveRadiosEntry 26 }

-- {COLUMN} 1.3.6.1.4.1.2356.11.1.73.9.2.1.27
lcsStatusWlanMngmtApStatusActiveRadiosEntryMaximalModemLoad OBJECT-TYPE
    SYNTAX     Integer32 (0..2147483647)
    MAX-ACCESS read-only
    STATUS     current
    DESCRIPTION
            ""
    ::= { lcsStatusWlanMngmtApStatusActiveRadiosEntry 27 }

-- {COLUMN} 1.3.6.1.4.1.2356.11.1.73.9.2.1.28
lcsStatusWlanMngmtApStatusActiveRadiosEntryAverageModemLoad OBJECT-TYPE
    SYNTAX     Integer32 (0..2147483647)
    MAX-ACCESS read-only
    STATUS     current
    DESCRIPTION
            ""
    ::= { lcsStatusWlanMngmtApStatusActiveRadiosEntry 28 }

-- {COLUMN} 1.3.6.1.4.1.2356.11.1.73.9.2.1.29
lcsStatusWlanMngmtApStatusActiveRadiosEntryApConnection OBJECT-TYPE
    SYNTAX     INTEGER {
                  eLan (0),
                  eWlanClient (1),
                  eWlanAutowds (2)
            }
    MAX-ACCESS read-only
    STATUS     current
    DESCRIPTION
            "-- empty --"
    ::= { lcsStatusWlanMngmtApStatusActiveRadiosEntry 29 }

-- {COLUMN} 1.3.6.1.4.1.2356.11.1.73.9.2.1.31
lcsStatusWlanMngmtApStatusActiveRadiosEntryGroups OBJECT-TYPE
    SYNTAX     DisplayString (SIZE(0..251))
    MAX-ACCESS read-only
    STATUS     current
    DESCRIPTION
            "-- empty --"
    ::= { lcsStatusWlanMngmtApStatusActiveRadiosEntry 31 }

-- {COLUMN} 1.3.6.1.4.1.2356.11.1.73.9.2.1.32
lcsStatusWlanMngmtApStatusActiveRadiosEntryAdaptRfOptLastHour OBJECT-TYPE
    SYNTAX     Integer32 (0..2147483647)
    MAX-ACCESS read-only
    STATUS     current
    DESCRIPTION
            "-- empty --"
    ::= { lcsStatusWlanMngmtApStatusActiveRadiosEntry 32 }

-- {COLUMN} 1.3.6.1.4.1.2356.11.1.73.9.2.1.33
lcsStatusWlanMngmtApStatusActiveRadiosEntryAdaptRfOptLast5Hours OBJECT-TYPE
    SYNTAX     Integer32 (0..2147483647)
    MAX-ACCESS read-only
    STATUS     current
    DESCRIPTION
            "-- empty --"
    ::= { lcsStatusWlanMngmtApStatusActiveRadiosEntry 33 }

-- {COLUMN} 1.3.6.1.4.1.2356.11.1.73.9.2.1.34
lcsStatusWlanMngmtApStatusActiveRadiosEntryAdaptRfOptLast24Hours OBJECT-TYPE
    SYNTAX     Integer32 (0..2147483647)
    MAX-ACCESS read-only
    STATUS     current
    DESCRIPTION
            "-- empty --"
    ::= { lcsStatusWlanMngmtApStatusActiveRadiosEntry 34 }

-- {COLUMN} 1.3.6.1.4.1.2356.11.1.73.9.2.1.35
lcsStatusWlanMngmtApStatusActiveRadiosEntryRxErrorRatio OBJECT-TYPE
    SYNTAX     Integer32 (0..2147483647)
    MAX-ACCESS read-only
    STATUS     current
    DESCRIPTION
            "-- empty --"
    ::= { lcsStatusWlanMngmtApStatusActiveRadiosEntry 35 }

-- {COLUMN} 1.3.6.1.4.1.2356.11.1.73.9.2.1.36
lcsStatusWlanMngmtApStatusActiveRadiosEntryTxErrorRatio OBJECT-TYPE
    SYNTAX     Integer32 (0..2147483647)
    MAX-ACCESS read-only
    STATUS     current
    DESCRIPTION
            "-- empty --"
    ::= { lcsStatusWlanMngmtApStatusActiveRadiosEntry 36 }

-- {COLUMN} 1.3.6.1.4.1.2356.11.1.73.9.2.1.37
lcsStatusWlanMngmtApStatusActiveRadiosEntryIdsOperational OBJECT-TYPE
    SYNTAX     INTEGER {
                  eNo (0),
                  eYes (1)
            }
    MAX-ACCESS read-only
    STATUS     current
    DESCRIPTION
            "-- empty --"
    ::= { lcsStatusWlanMngmtApStatusActiveRadiosEntry 37 }

-- {COLUMN} 1.3.6.1.4.1.2356.11.1.73.9.2.1.38
lcsStatusWlanMngmtApStatusActiveRadiosEntryChannelBandwidth OBJECT-TYPE
    SYNTAX     INTEGER {
                  e20mhz (0),
                  e40mhz (1),
                  e80mhz (2),
                  e160mhz (3),
                  e80Plus80mhz (4),
                  e40mhzTurbo (5),
                  eNotDefined (254),
                  eAuto (255)
            }
    MAX-ACCESS read-only
    STATUS     current
    DESCRIPTION
            "-- empty --"
    ::= { lcsStatusWlanMngmtApStatusActiveRadiosEntry 38 }

-- {COLUMN} 1.3.6.1.4.1.2356.11.1.73.9.2.1.39
lcsStatusWlanMngmtApStatusActiveRadiosEntryLepsUUserLimit OBJECT-TYPE
    SYNTAX     Integer32 (0..2147483647)
    MAX-ACCESS read-only
    STATUS     current
    DESCRIPTION
            "-- empty --"
    ::= { lcsStatusWlanMngmtApStatusActiveRadiosEntry 39 }

-- {COLUMN} 1.3.6.1.4.1.2356.11.1.73.9.2.1.40
lcsStatusWlanMngmtApStatusActiveRadiosEntryWpaKeyTypes OBJECT-TYPE
    SYNTAX     BITS {
                  eAesOcb (2),
                  eAesGcmp256 (3),
                  eAesGcmp128 (4),
                  eAesCcmp256 (5),
                  eAesCcm (6),
                  eTkip (7)
            }
    MAX-ACCESS read-only
    STATUS     current
    DESCRIPTION
            "-- empty --"
    ::= { lcsStatusWlanMngmtApStatusActiveRadiosEntry 40 }

-- {COLUMN} 1.3.6.1.4.1.2356.11.1.73.9.2.1.41
lcsStatusWlanMngmtApStatusActiveRadiosEntryBssidCount OBJECT-TYPE
    SYNTAX     Integer32 (0..2147483647)
    MAX-ACCESS read-only
    STATUS     current
    DESCRIPTION
            "-- empty --"
    ::= { lcsStatusWlanMngmtApStatusActiveRadiosEntry 41 }

-- {COLUMN} 1.3.6.1.4.1.2356.11.1.73.9.2.1.42
lcsStatusWlanMngmtApStatusActiveRadiosEntryOperatingSystem OBJECT-TYPE
    SYNTAX     INTEGER {
                  eLcos (0),
                  eLcosLx (1)
            }
    MAX-ACCESS read-only
    STATUS     current
    DESCRIPTION
            "-- empty --"
    ::= { lcsStatusWlanMngmtApStatusActiveRadiosEntry 42 }

-- {TABLE} 1.3.6.1.4.1.2356.11.1.73.9.3
lcsStatusWlanMngmtApStatusNewApTable OBJECT-TYPE
    SYNTAX     SEQUENCE OF LcsStatusWlanMngmtApStatusNewApEntry
    MAX-ACCESS not-accessible
    STATUS     current
    DESCRIPTION
            ""
    ::= { lcsStatusWlanMngmtApStatus 3 }

-- {ROW} 1.3.6.1.4.1.2356.11.1.73.9.3.1
lcsStatusWlanMngmtApStatusNewApEntry OBJECT-TYPE
    SYNTAX     LcsStatusWlanMngmtApStatusNewApEntry
    MAX-ACCESS not-accessible
    STATUS     current
    DESCRIPTION
            ""
    INDEX {
            lcsStatusWlanMngmtApStatusNewApEntryApLanMac
          }
    ::= { lcsStatusWlanMngmtApStatusNewApTable 1 }

LcsStatusWlanMngmtApStatusNewApEntry ::= SEQUENCE {
            lcsStatusWlanMngmtApStatusNewApEntryApLanMac MacAddress,
            lcsStatusWlanMngmtApStatusNewApEntryIpAddress IpAddress,
            lcsStatusWlanMngmtApStatusNewApEntryName DisplayString,
            lcsStatusWlanMngmtApStatusNewApEntryLocation DisplayString,
            lcsStatusWlanMngmtApStatusNewApEntryValid INTEGER,
            lcsStatusWlanMngmtApStatusNewApEntryConfiguration INTEGER,
            lcsStatusWlanMngmtApStatusNewApEntryAutowdsIntegration INTEGER,
            lcsStatusWlanMngmtApStatusNewApEntryGroups DisplayString,
            lcsStatusWlanMngmtApStatusNewApEntryCertificateState INTEGER
    }

-- {COLUMN} 1.3.6.1.4.1.2356.11.1.73.9.3.1.1
lcsStatusWlanMngmtApStatusNewApEntryApLanMac OBJECT-TYPE
    SYNTAX     MacAddress
    MAX-ACCESS read-only
    STATUS     current
    DESCRIPTION
            ""
    ::= { lcsStatusWlanMngmtApStatusNewApEntry 1 }

-- {COLUMN} 1.3.6.1.4.1.2356.11.1.73.9.3.1.2
lcsStatusWlanMngmtApStatusNewApEntryIpAddress OBJECT-TYPE
    SYNTAX     IpAddress
    MAX-ACCESS read-only
    STATUS     current
    DESCRIPTION
            ""
    ::= { lcsStatusWlanMngmtApStatusNewApEntry 2 }

-- {COLUMN} 1.3.6.1.4.1.2356.11.1.73.9.3.1.3
lcsStatusWlanMngmtApStatusNewApEntryName OBJECT-TYPE
    SYNTAX     DisplayString (SIZE(0..82))
    MAX-ACCESS read-only
    STATUS     current
    DESCRIPTION
            ""
    ::= { lcsStatusWlanMngmtApStatusNewApEntry 3 }

-- {COLUMN} 1.3.6.1.4.1.2356.11.1.73.9.3.1.4
lcsStatusWlanMngmtApStatusNewApEntryLocation OBJECT-TYPE
    SYNTAX     DisplayString (SIZE(0..251))
    MAX-ACCESS read-only
    STATUS     current
    DESCRIPTION
            ""
    ::= { lcsStatusWlanMngmtApStatusNewApEntry 4 }

-- {COLUMN} 1.3.6.1.4.1.2356.11.1.73.9.3.1.5
lcsStatusWlanMngmtApStatusNewApEntryValid OBJECT-TYPE
    SYNTAX     INTEGER {
                  eNo (0),
                  eYes (1)
            }
    MAX-ACCESS read-only
    STATUS     current
    DESCRIPTION
            ""
    ::= { lcsStatusWlanMngmtApStatusNewApEntry 5 }

-- {COLUMN} 1.3.6.1.4.1.2356.11.1.73.9.3.1.6
lcsStatusWlanMngmtApStatusNewApEntryConfiguration OBJECT-TYPE
    SYNTAX     INTEGER {
                  eNo (0),
                  eYes (1)
            }
    MAX-ACCESS read-only
    STATUS     current
    DESCRIPTION
            ""
    ::= { lcsStatusWlanMngmtApStatusNewApEntry 6 }

-- {COLUMN} 1.3.6.1.4.1.2356.11.1.73.9.3.1.7
lcsStatusWlanMngmtApStatusNewApEntryAutowdsIntegration OBJECT-TYPE
    SYNTAX     INTEGER {
                  eNone (0),
                  eExpress (1),
                  ePreconfigured (2)
            }
    MAX-ACCESS read-only
    STATUS     current
    DESCRIPTION
            "-- empty --"
    ::= { lcsStatusWlanMngmtApStatusNewApEntry 7 }

-- {COLUMN} 1.3.6.1.4.1.2356.11.1.73.9.3.1.8
lcsStatusWlanMngmtApStatusNewApEntryGroups OBJECT-TYPE
    SYNTAX     DisplayString (SIZE(0..251))
    MAX-ACCESS read-only
    STATUS     current
    DESCRIPTION
            "-- empty --"
    ::= { lcsStatusWlanMngmtApStatusNewApEntry 8 }

-- {COLUMN} 1.3.6.1.4.1.2356.11.1.73.9.3.1.9
lcsStatusWlanMngmtApStatusNewApEntryCertificateState OBJECT-TYPE
    SYNTAX     INTEGER {
                  eUnknown (0),
                  eMissing (1),
                  eExpired (2),
                  eIncompatible (3),
                  eNotYetValid (4),
                  eValid (5)
            }
    MAX-ACCESS read-only
    STATUS     current
    DESCRIPTION
            "-- empty --"
    ::= { lcsStatusWlanMngmtApStatusNewApEntry 9 }

-- {TABLE} 1.3.6.1.4.1.2356.11.1.73.9.4
lcsStatusWlanMngmtApStatusNextdoorApTable OBJECT-TYPE
    SYNTAX     SEQUENCE OF LcsStatusWlanMngmtApStatusNextdoorApEntry
    MAX-ACCESS not-accessible
    STATUS     current
    DESCRIPTION
            ""
    ::= { lcsStatusWlanMngmtApStatus 4 }

-- {ROW} 1.3.6.1.4.1.2356.11.1.73.9.4.1
lcsStatusWlanMngmtApStatusNextdoorApEntry OBJECT-TYPE
    SYNTAX     LcsStatusWlanMngmtApStatusNextdoorApEntry
    MAX-ACCESS not-accessible
    STATUS     current
    DESCRIPTION
            ""
    INDEX {
            lcsStatusWlanMngmtApStatusNextdoorApEntryApLanMac
          }
    ::= { lcsStatusWlanMngmtApStatusNextdoorApTable 1 }

LcsStatusWlanMngmtApStatusNextdoorApEntry ::= SEQUENCE {
            lcsStatusWlanMngmtApStatusNextdoorApEntryApLanMac MacAddress,
            lcsStatusWlanMngmtApStatusNextdoorApEntryIpAddress IpAddress,
            lcsStatusWlanMngmtApStatusNextdoorApEntryName DisplayString,
            lcsStatusWlanMngmtApStatusNextdoorApEntryLocation DisplayString,
            lcsStatusWlanMngmtApStatusNextdoorApEntryValid INTEGER,
            lcsStatusWlanMngmtApStatusNextdoorApEntryWlcName DisplayString,
            lcsStatusWlanMngmtApStatusNextdoorApEntryWlcLanMac MacAddress,
            lcsStatusWlanMngmtApStatusNextdoorApEntryGroups DisplayString
    }

-- {COLUMN} 1.3.6.1.4.1.2356.11.1.73.9.4.1.1
lcsStatusWlanMngmtApStatusNextdoorApEntryApLanMac OBJECT-TYPE
    SYNTAX     MacAddress
    MAX-ACCESS read-only
    STATUS     current
    DESCRIPTION
            ""
    ::= { lcsStatusWlanMngmtApStatusNextdoorApEntry 1 }

-- {COLUMN} 1.3.6.1.4.1.2356.11.1.73.9.4.1.2
lcsStatusWlanMngmtApStatusNextdoorApEntryIpAddress OBJECT-TYPE
    SYNTAX     IpAddress
    MAX-ACCESS read-only
    STATUS     current
    DESCRIPTION
            ""
    ::= { lcsStatusWlanMngmtApStatusNextdoorApEntry 2 }

-- {COLUMN} 1.3.6.1.4.1.2356.11.1.73.9.4.1.3
lcsStatusWlanMngmtApStatusNextdoorApEntryName OBJECT-TYPE
    SYNTAX     DisplayString (SIZE(0..82))
    MAX-ACCESS read-only
    STATUS     current
    DESCRIPTION
            ""
    ::= { lcsStatusWlanMngmtApStatusNextdoorApEntry 3 }

-- {COLUMN} 1.3.6.1.4.1.2356.11.1.73.9.4.1.4
lcsStatusWlanMngmtApStatusNextdoorApEntryLocation OBJECT-TYPE
    SYNTAX     DisplayString (SIZE(0..251))
    MAX-ACCESS read-only
    STATUS     current
    DESCRIPTION
            ""
    ::= { lcsStatusWlanMngmtApStatusNextdoorApEntry 4 }

-- {COLUMN} 1.3.6.1.4.1.2356.11.1.73.9.4.1.5
lcsStatusWlanMngmtApStatusNextdoorApEntryValid OBJECT-TYPE
    SYNTAX     INTEGER {
                  eNo (0),
                  eYes (1)
            }
    MAX-ACCESS read-only
    STATUS     current
    DESCRIPTION
            ""
    ::= { lcsStatusWlanMngmtApStatusNextdoorApEntry 5 }

-- {COLUMN} 1.3.6.1.4.1.2356.11.1.73.9.4.1.6
lcsStatusWlanMngmtApStatusNextdoorApEntryWlcName OBJECT-TYPE
    SYNTAX     DisplayString (SIZE(0..82))
    MAX-ACCESS read-only
    STATUS     current
    DESCRIPTION
            ""
    ::= { lcsStatusWlanMngmtApStatusNextdoorApEntry 6 }

-- {COLUMN} 1.3.6.1.4.1.2356.11.1.73.9.4.1.7
lcsStatusWlanMngmtApStatusNextdoorApEntryWlcLanMac OBJECT-TYPE
    SYNTAX     MacAddress
    MAX-ACCESS read-only
    STATUS     current
    DESCRIPTION
            ""
    ::= { lcsStatusWlanMngmtApStatusNextdoorApEntry 7 }

-- {COLUMN} 1.3.6.1.4.1.2356.11.1.73.9.4.1.31
lcsStatusWlanMngmtApStatusNextdoorApEntryGroups OBJECT-TYPE
    SYNTAX     DisplayString (SIZE(0..251))
    MAX-ACCESS read-only
    STATUS     current
    DESCRIPTION
            "-- empty --"
    ::= { lcsStatusWlanMngmtApStatusNextdoorApEntry 31 }

-- {TABLE} 1.3.6.1.4.1.2356.11.1.73.9.5
lcsStatusWlanMngmtApStatusApStatisticsTable OBJECT-TYPE
    SYNTAX     SEQUENCE OF LcsStatusWlanMngmtApStatusApStatisticsEntry
    MAX-ACCESS not-accessible
    STATUS     current
    DESCRIPTION
            "-- empty --"
    ::= { lcsStatusWlanMngmtApStatus 5 }

-- {ROW} 1.3.6.1.4.1.2356.11.1.73.9.5.1
lcsStatusWlanMngmtApStatusApStatisticsEntry OBJECT-TYPE
    SYNTAX     LcsStatusWlanMngmtApStatusApStatisticsEntry
    MAX-ACCESS not-accessible
    STATUS     current
    DESCRIPTION
            ""
    INDEX {
            lcsStatusWlanMngmtApStatusApStatisticsEntryApLanMac
          }
    ::= { lcsStatusWlanMngmtApStatusApStatisticsTable 1 }

LcsStatusWlanMngmtApStatusApStatisticsEntry ::= SEQUENCE {
            lcsStatusWlanMngmtApStatusApStatisticsEntryApLanMac MacAddress,
            lcsStatusWlanMngmtApStatusApStatisticsEntryIpAddress IpAddress,
            lcsStatusWlanMngmtApStatusApStatisticsEntryName DisplayString,
            lcsStatusWlanMngmtApStatusApStatisticsEntryLocation DisplayString,
            lcsStatusWlanMngmtApStatusApStatisticsEntryRebootCount Integer32,
            lcsStatusWlanMngmtApStatusApStatisticsEntryACInitRebootCnt Integer32,
            lcsStatusWlanMngmtApStatusApStatisticsEntryLinkFailureCount Integer32,
            lcsStatusWlanMngmtApStatusApStatisticsEntrySoftwareFailureCount Integer32,
            lcsStatusWlanMngmtApStatusApStatisticsEntryHardwareFailureCount Integer32,
            lcsStatusWlanMngmtApStatusApStatisticsEntryOtherFailureCount Integer32,
            lcsStatusWlanMngmtApStatusApStatisticsEntryUnknownFailureCount Integer32,
            lcsStatusWlanMngmtApStatusApStatisticsEntryLastFailure INTEGER
    }

-- {COLUMN} 1.3.6.1.4.1.2356.11.1.73.9.5.1.1
lcsStatusWlanMngmtApStatusApStatisticsEntryApLanMac OBJECT-TYPE
    SYNTAX     MacAddress
    MAX-ACCESS read-only
    STATUS     current
    DESCRIPTION
            "-- empty --"
    ::= { lcsStatusWlanMngmtApStatusApStatisticsEntry 1 }

-- {COLUMN} 1.3.6.1.4.1.2356.11.1.73.9.5.1.2
lcsStatusWlanMngmtApStatusApStatisticsEntryIpAddress OBJECT-TYPE
    SYNTAX     IpAddress
    MAX-ACCESS read-only
    STATUS     current
    DESCRIPTION
            "-- empty --"
    ::= { lcsStatusWlanMngmtApStatusApStatisticsEntry 2 }

-- {COLUMN} 1.3.6.1.4.1.2356.11.1.73.9.5.1.3
lcsStatusWlanMngmtApStatusApStatisticsEntryName OBJECT-TYPE
    SYNTAX     DisplayString (SIZE(0..82))
    MAX-ACCESS read-only
    STATUS     current
    DESCRIPTION
            "-- empty --"
    ::= { lcsStatusWlanMngmtApStatusApStatisticsEntry 3 }

-- {COLUMN} 1.3.6.1.4.1.2356.11.1.73.9.5.1.4
lcsStatusWlanMngmtApStatusApStatisticsEntryLocation OBJECT-TYPE
    SYNTAX     DisplayString (SIZE(0..251))
    MAX-ACCESS read-only
    STATUS     current
    DESCRIPTION
            "-- empty --"
    ::= { lcsStatusWlanMngmtApStatusApStatisticsEntry 4 }

-- {COLUMN} 1.3.6.1.4.1.2356.11.1.73.9.5.1.5
lcsStatusWlanMngmtApStatusApStatisticsEntryRebootCount OBJECT-TYPE
    SYNTAX     Integer32 (0..65535)
    MAX-ACCESS read-only
    STATUS     current
    DESCRIPTION
            "-- empty --"
    ::= { lcsStatusWlanMngmtApStatusApStatisticsEntry 5 }

-- {COLUMN} 1.3.6.1.4.1.2356.11.1.73.9.5.1.6
lcsStatusWlanMngmtApStatusApStatisticsEntryACInitRebootCnt OBJECT-TYPE
    SYNTAX     Integer32 (0..65535)
    MAX-ACCESS read-only
    STATUS     current
    DESCRIPTION
            ""
    ::= { lcsStatusWlanMngmtApStatusApStatisticsEntry 6 }

-- {COLUMN} 1.3.6.1.4.1.2356.11.1.73.9.5.1.7
lcsStatusWlanMngmtApStatusApStatisticsEntryLinkFailureCount OBJECT-TYPE
    SYNTAX     Integer32 (0..65535)
    MAX-ACCESS read-only
    STATUS     current
    DESCRIPTION
            "-- empty --"
    ::= { lcsStatusWlanMngmtApStatusApStatisticsEntry 7 }

-- {COLUMN} 1.3.6.1.4.1.2356.11.1.73.9.5.1.8
lcsStatusWlanMngmtApStatusApStatisticsEntrySoftwareFailureCount OBJECT-TYPE
    SYNTAX     Integer32 (0..65535)
    MAX-ACCESS read-only
    STATUS     current
    DESCRIPTION
            "-- empty --"
    ::= { lcsStatusWlanMngmtApStatusApStatisticsEntry 8 }

-- {COLUMN} 1.3.6.1.4.1.2356.11.1.73.9.5.1.9
lcsStatusWlanMngmtApStatusApStatisticsEntryHardwareFailureCount OBJECT-TYPE
    SYNTAX     Integer32 (0..65535)
    MAX-ACCESS read-only
    STATUS     current
    DESCRIPTION
            "-- empty --"
    ::= { lcsStatusWlanMngmtApStatusApStatisticsEntry 9 }

-- {COLUMN} 1.3.6.1.4.1.2356.11.1.73.9.5.1.10
lcsStatusWlanMngmtApStatusApStatisticsEntryOtherFailureCount OBJECT-TYPE
    SYNTAX     Integer32 (0..65535)
    MAX-ACCESS read-only
    STATUS     current
    DESCRIPTION
            "-- empty --"
    ::= { lcsStatusWlanMngmtApStatusApStatisticsEntry 10 }

-- {COLUMN} 1.3.6.1.4.1.2356.11.1.73.9.5.1.11
lcsStatusWlanMngmtApStatusApStatisticsEntryUnknownFailureCount OBJECT-TYPE
    SYNTAX     Integer32 (0..65535)
    MAX-ACCESS read-only
    STATUS     current
    DESCRIPTION
            "-- empty --"
    ::= { lcsStatusWlanMngmtApStatusApStatisticsEntry 11 }

-- {COLUMN} 1.3.6.1.4.1.2356.11.1.73.9.5.1.12
lcsStatusWlanMngmtApStatusApStatisticsEntryLastFailure OBJECT-TYPE
    SYNTAX     INTEGER {
                  eNotSupported (0),
                  eAcInitiated (1),
                  eLinkFailure (2),
                  eSoftwareFailure (3),
                  eHardwareFailure (4),
                  eOtherFailure (5),
                  eUnknownFailure (255)
            }
    MAX-ACCESS read-only
    STATUS     current
    DESCRIPTION
            "-- empty --"
    ::= { lcsStatusWlanMngmtApStatusApStatisticsEntry 12 }

-- {SCALAR} 1.3.6.1.4.1.2356.11.1.73.10
lcsStatusWlanMngmtAcceptAp OBJECT-TYPE
    SYNTAX     DisplayString
    MAX-ACCESS read-write
    STATUS     current
    DESCRIPTION
            ""
    ::= { lcsStatusWlanMngmt 10 }

-- {SCALAR} 1.3.6.1.4.1.2356.11.1.73.11
lcsStatusWlanMngmtDisconnectAp OBJECT-TYPE
    SYNTAX     DisplayString
    MAX-ACCESS read-write
    STATUS     current
    DESCRIPTION
            ""
    ::= { lcsStatusWlanMngmt 11 }

-- {NODE} 1.3.6.1.4.1.2356.11.1.73.20
lcsStatusWlanMngmtCentralFwMngmt OBJECT IDENTIFIER ::= { lcsStatusWlanMngmt 20 }

-- {TABLE} 1.3.6.1.4.1.2356.11.1.73.20.12
lcsStatusWlanMngmtCentralFwMngmtAvailFwTable OBJECT-TYPE
    SYNTAX     SEQUENCE OF LcsStatusWlanMngmtCentralFwMngmtAvailFwEntry
    MAX-ACCESS not-accessible
    STATUS     current
    DESCRIPTION
            "available firmwares"
    ::= { lcsStatusWlanMngmtCentralFwMngmt 12 }

-- {ROW} 1.3.6.1.4.1.2356.11.1.73.20.12.1
lcsStatusWlanMngmtCentralFwMngmtAvailFwEntry OBJECT-TYPE
    SYNTAX     LcsStatusWlanMngmtCentralFwMngmtAvailFwEntry
    MAX-ACCESS not-accessible
    STATUS     current
    DESCRIPTION
            ""
    INDEX {
            lcsStatusWlanMngmtCentralFwMngmtAvailFwEntryIndex
          }
    ::= { lcsStatusWlanMngmtCentralFwMngmtAvailFwTable 1 }

LcsStatusWlanMngmtCentralFwMngmtAvailFwEntry ::= SEQUENCE {
            lcsStatusWlanMngmtCentralFwMngmtAvailFwEntryIndex Integer32,
            lcsStatusWlanMngmtCentralFwMngmtAvailFwEntryDevice DisplayString,
            lcsStatusWlanMngmtCentralFwMngmtAvailFwEntryVersion DisplayString,
            lcsStatusWlanMngmtCentralFwMngmtAvailFwEntryDate DisplayString,
            lcsStatusWlanMngmtCentralFwMngmtAvailFwEntryDescription DisplayString,
            lcsStatusWlanMngmtCentralFwMngmtAvailFwEntryFileType INTEGER,
            lcsStatusWlanMngmtCentralFwMngmtAvailFwEntryFilesize Integer32,
            lcsStatusWlanMngmtCentralFwMngmtAvailFwEntryLoaded INTEGER,
            lcsStatusWlanMngmtCentralFwMngmtAvailFwEntryRunningUpdates Integer32,
            lcsStatusWlanMngmtCentralFwMngmtAvailFwEntryCompatibilityId Integer32
    }

-- {COLUMN} 1.3.6.1.4.1.2356.11.1.73.20.12.1.1
lcsStatusWlanMngmtCentralFwMngmtAvailFwEntryIndex OBJECT-TYPE
    SYNTAX     Integer32 (0..2147483647)
    MAX-ACCESS read-only
    STATUS     current
    DESCRIPTION
            ""
    ::= { lcsStatusWlanMngmtCentralFwMngmtAvailFwEntry 1 }

-- {COLUMN} 1.3.6.1.4.1.2356.11.1.73.20.12.1.2
lcsStatusWlanMngmtCentralFwMngmtAvailFwEntryDevice OBJECT-TYPE
    SYNTAX     DisplayString (SIZE(0..255))
    MAX-ACCESS read-only
    STATUS     current
    DESCRIPTION
            ""
    ::= { lcsStatusWlanMngmtCentralFwMngmtAvailFwEntry 2 }

-- {COLUMN} 1.3.6.1.4.1.2356.11.1.73.20.12.1.3
lcsStatusWlanMngmtCentralFwMngmtAvailFwEntryVersion OBJECT-TYPE
    SYNTAX     DisplayString (SIZE(0..255))
    MAX-ACCESS read-only
    STATUS     current
    DESCRIPTION
            ""
    ::= { lcsStatusWlanMngmtCentralFwMngmtAvailFwEntry 3 }

-- {COLUMN} 1.3.6.1.4.1.2356.11.1.73.20.12.1.4
lcsStatusWlanMngmtCentralFwMngmtAvailFwEntryDate OBJECT-TYPE
    SYNTAX     DisplayString (SIZE(0..255))
    MAX-ACCESS read-only
    STATUS     current
    DESCRIPTION
            ""
    ::= { lcsStatusWlanMngmtCentralFwMngmtAvailFwEntry 4 }

-- {COLUMN} 1.3.6.1.4.1.2356.11.1.73.20.12.1.5
lcsStatusWlanMngmtCentralFwMngmtAvailFwEntryDescription OBJECT-TYPE
    SYNTAX     DisplayString (SIZE(0..255))
    MAX-ACCESS read-only
    STATUS     current
    DESCRIPTION
            ""
    ::= { lcsStatusWlanMngmtCentralFwMngmtAvailFwEntry 5 }

-- {COLUMN} 1.3.6.1.4.1.2356.11.1.73.20.12.1.6
lcsStatusWlanMngmtCentralFwMngmtAvailFwEntryFileType OBJECT-TYPE
    SYNTAX     INTEGER {
                  eUnknown (0),
                  eFirmware (1),
                  eLoader (2),
                  eOemFile (3),
                  eConverter (4),
                  eMiniFirmware (5)
            }
    MAX-ACCESS read-only
    STATUS     current
    DESCRIPTION
            ""
    ::= { lcsStatusWlanMngmtCentralFwMngmtAvailFwEntry 6 }

-- {COLUMN} 1.3.6.1.4.1.2356.11.1.73.20.12.1.7
lcsStatusWlanMngmtCentralFwMngmtAvailFwEntryFilesize OBJECT-TYPE
    SYNTAX     Integer32 (0..2147483647)
    MAX-ACCESS read-only
    STATUS     current
    DESCRIPTION
            ""
    ::= { lcsStatusWlanMngmtCentralFwMngmtAvailFwEntry 7 }

-- {COLUMN} 1.3.6.1.4.1.2356.11.1.73.20.12.1.8
lcsStatusWlanMngmtCentralFwMngmtAvailFwEntryLoaded OBJECT-TYPE
    SYNTAX     INTEGER {
                  eNo (0),
                  eYes (1)
            }
    MAX-ACCESS read-only
    STATUS     current
    DESCRIPTION
            ""
    ::= { lcsStatusWlanMngmtCentralFwMngmtAvailFwEntry 8 }

-- {COLUMN} 1.3.6.1.4.1.2356.11.1.73.20.12.1.9
lcsStatusWlanMngmtCentralFwMngmtAvailFwEntryRunningUpdates OBJECT-TYPE
    SYNTAX     Integer32 (0..2147483647)
    MAX-ACCESS read-only
    STATUS     current
    DESCRIPTION
            ""
    ::= { lcsStatusWlanMngmtCentralFwMngmtAvailFwEntry 9 }

-- {COLUMN} 1.3.6.1.4.1.2356.11.1.73.20.12.1.10
lcsStatusWlanMngmtCentralFwMngmtAvailFwEntryCompatibilityId OBJECT-TYPE
    SYNTAX     Integer32 (0..65535)
    MAX-ACCESS read-only
    STATUS     current
    DESCRIPTION
            ""
    ::= { lcsStatusWlanMngmtCentralFwMngmtAvailFwEntry 10 }

-- {TABLE} 1.3.6.1.4.1.2356.11.1.73.20.13
lcsStatusWlanMngmtCentralFwMngmtAvailableScriptsTable OBJECT-TYPE
    SYNTAX     SEQUENCE OF LcsStatusWlanMngmtCentralFwMngmtAvailableScriptsEntry
    MAX-ACCESS not-accessible
    STATUS     current
    DESCRIPTION
            ""
    ::= { lcsStatusWlanMngmtCentralFwMngmt 13 }

-- {ROW} 1.3.6.1.4.1.2356.11.1.73.20.13.1
lcsStatusWlanMngmtCentralFwMngmtAvailableScriptsEntry OBJECT-TYPE
    SYNTAX     LcsStatusWlanMngmtCentralFwMngmtAvailableScriptsEntry
    MAX-ACCESS not-accessible
    STATUS     current
    DESCRIPTION
            ""
    INDEX {
            lcsStatusWlanMngmtCentralFwMngmtAvailableScriptsEntryIndex
          }
    ::= { lcsStatusWlanMngmtCentralFwMngmtAvailableScriptsTable 1 }

LcsStatusWlanMngmtCentralFwMngmtAvailableScriptsEntry ::= SEQUENCE {
            lcsStatusWlanMngmtCentralFwMngmtAvailableScriptsEntryIndex Integer32,
            lcsStatusWlanMngmtCentralFwMngmtAvailableScriptsEntryName DisplayString,
            lcsStatusWlanMngmtCentralFwMngmtAvailableScriptsEntryFilesize Integer32,
            lcsStatusWlanMngmtCentralFwMngmtAvailableScriptsEntryCommentary DisplayString,
            lcsStatusWlanMngmtCentralFwMngmtAvailableScriptsEntryRunTransm Integer32
    }

-- {COLUMN} 1.3.6.1.4.1.2356.11.1.73.20.13.1.1
lcsStatusWlanMngmtCentralFwMngmtAvailableScriptsEntryIndex OBJECT-TYPE
    SYNTAX     Integer32 (0..2147483647)
    MAX-ACCESS read-only
    STATUS     current
    DESCRIPTION
            ""
    ::= { lcsStatusWlanMngmtCentralFwMngmtAvailableScriptsEntry 1 }

-- {COLUMN} 1.3.6.1.4.1.2356.11.1.73.20.13.1.2
lcsStatusWlanMngmtCentralFwMngmtAvailableScriptsEntryName OBJECT-TYPE
    SYNTAX     DisplayString (SIZE(0..255))
    MAX-ACCESS read-only
    STATUS     current
    DESCRIPTION
            ""
    ::= { lcsStatusWlanMngmtCentralFwMngmtAvailableScriptsEntry 2 }

-- {COLUMN} 1.3.6.1.4.1.2356.11.1.73.20.13.1.3
lcsStatusWlanMngmtCentralFwMngmtAvailableScriptsEntryFilesize OBJECT-TYPE
    SYNTAX     Integer32 (0..2147483647)
    MAX-ACCESS read-only
    STATUS     current
    DESCRIPTION
            ""
    ::= { lcsStatusWlanMngmtCentralFwMngmtAvailableScriptsEntry 3 }

-- {COLUMN} 1.3.6.1.4.1.2356.11.1.73.20.13.1.4
lcsStatusWlanMngmtCentralFwMngmtAvailableScriptsEntryCommentary OBJECT-TYPE
    SYNTAX     DisplayString (SIZE(0..255))
    MAX-ACCESS read-only
    STATUS     current
    DESCRIPTION
            ""
    ::= { lcsStatusWlanMngmtCentralFwMngmtAvailableScriptsEntry 4 }

-- {COLUMN} 1.3.6.1.4.1.2356.11.1.73.20.13.1.5
lcsStatusWlanMngmtCentralFwMngmtAvailableScriptsEntryRunTransm OBJECT-TYPE
    SYNTAX     Integer32 (0..2147483647)
    MAX-ACCESS read-only
    STATUS     current
    DESCRIPTION
            "running transmissions"
    ::= { lcsStatusWlanMngmtCentralFwMngmtAvailableScriptsEntry 5 }

-- {SCALAR} 1.3.6.1.4.1.2356.11.1.73.20.14
lcsStatusWlanMngmtCentralFwMngmtFetchJobStatus OBJECT-TYPE
    SYNTAX     INTEGER {
                  eIdle (0),
                  eBadUrl (1),
                  eHttpTimeOut (2),
                  eNoMemory (3),
                  eValidUrlFound (4),
                  eHttpError (5),
                  eDownloadIsRunning (6),
                  eFetchJobIsBusy (7),
                  eReceivedFileTooBig (8),
                  eBroken (9),
                  eInvalidFilesize (10),
                  eConnError (11),
                  eTooSlow (12),
                  eReadFailed (13),
                  eConnectionError (14),
                  eDnsError (15),
                  eProtocolError (16)
            }
    MAX-ACCESS read-only
    STATUS     current
    DESCRIPTION
            ""
    ::= { lcsStatusWlanMngmtCentralFwMngmt 14 }

-- {SCALAR} 1.3.6.1.4.1.2356.11.1.73.20.15
lcsStatusWlanMngmtCentralFwMngmtLoadedFirmwares OBJECT-TYPE
    SYNTAX     Integer32 (0..2147483647)
    MAX-ACCESS read-only
    STATUS     current
    DESCRIPTION
            ""
    ::= { lcsStatusWlanMngmtCentralFwMngmt 15 }

-- {SCALAR} 1.3.6.1.4.1.2356.11.1.73.20.16
lcsStatusWlanMngmtCentralFwMngmtUsedMemory OBJECT-TYPE
    SYNTAX     Integer32 (0..2147483647)
    MAX-ACCESS read-only
    STATUS     current
    DESCRIPTION
            ""
    ::= { lcsStatusWlanMngmtCentralFwMngmt 16 }

-- {SCALAR} 1.3.6.1.4.1.2356.11.1.73.20.17
lcsStatusWlanMngmtCentralFwMngmtUpdFwScriptInfo OBJECT-TYPE
    SYNTAX     DisplayString
    MAX-ACCESS read-write
    STATUS     current
    DESCRIPTION
            "update firmware and script information"
    ::= { lcsStatusWlanMngmtCentralFwMngmt 17 }

-- {SCALAR} 1.3.6.1.4.1.2356.11.1.73.20.18
lcsStatusWlanMngmtCentralFwMngmtRebootUpdatedAps OBJECT-TYPE
    SYNTAX     DisplayString
    MAX-ACCESS read-write
    STATUS     current
    DESCRIPTION
            ""
    ::= { lcsStatusWlanMngmtCentralFwMngmt 18 }

-- {TABLE} 1.3.6.1.4.1.2356.11.1.73.20.19
lcsStatusWlanMngmtCentralFwMngmtApStatusTable OBJECT-TYPE
    SYNTAX     SEQUENCE OF LcsStatusWlanMngmtCentralFwMngmtApStatusEntry
    MAX-ACCESS not-accessible
    STATUS     current
    DESCRIPTION
            "-- empty --"
    ::= { lcsStatusWlanMngmtCentralFwMngmt 19 }

-- {ROW} 1.3.6.1.4.1.2356.11.1.73.20.19.1
lcsStatusWlanMngmtCentralFwMngmtApStatusEntry OBJECT-TYPE
    SYNTAX     LcsStatusWlanMngmtCentralFwMngmtApStatusEntry
    MAX-ACCESS not-accessible
    STATUS     current
    DESCRIPTION
            ""
    INDEX {
            lcsStatusWlanMngmtCentralFwMngmtApStatusEntryApLanMac
          }
    ::= { lcsStatusWlanMngmtCentralFwMngmtApStatusTable 1 }

LcsStatusWlanMngmtCentralFwMngmtApStatusEntry ::= SEQUENCE {
            lcsStatusWlanMngmtCentralFwMngmtApStatusEntryApLanMac MacAddress,
            lcsStatusWlanMngmtCentralFwMngmtApStatusEntryJob Unsigned32,
            lcsStatusWlanMngmtCentralFwMngmtApStatusEntryIpAddress IpAddress,
            lcsStatusWlanMngmtCentralFwMngmtApStatusEntryName DisplayString,
            lcsStatusWlanMngmtCentralFwMngmtApStatusEntryLocation DisplayString,
            lcsStatusWlanMngmtCentralFwMngmtApStatusEntryActiveFirmware DisplayString,
            lcsStatusWlanMngmtCentralFwMngmtApStatusEntryAlternativeFirmware DisplayString,
            lcsStatusWlanMngmtCentralFwMngmtApStatusEntryLoader DisplayString,
            lcsStatusWlanMngmtCentralFwMngmtApStatusEntryApStatus INTEGER,
            lcsStatusWlanMngmtCentralFwMngmtApStatusEntryTargetVersion DisplayString
    }

-- {COLUMN} 1.3.6.1.4.1.2356.11.1.73.20.19.1.1
lcsStatusWlanMngmtCentralFwMngmtApStatusEntryApLanMac OBJECT-TYPE
    SYNTAX     MacAddress
    MAX-ACCESS read-only
    STATUS     current
    DESCRIPTION
            "-- empty --"
    ::= { lcsStatusWlanMngmtCentralFwMngmtApStatusEntry 1 }

-- {COLUMN} 1.3.6.1.4.1.2356.11.1.73.20.19.1.2
lcsStatusWlanMngmtCentralFwMngmtApStatusEntryJob OBJECT-TYPE
    SYNTAX     Unsigned32 (0..4294967295)
    MAX-ACCESS read-only
    STATUS     current
    DESCRIPTION
            "-- empty --"
    ::= { lcsStatusWlanMngmtCentralFwMngmtApStatusEntry 2 }

-- {COLUMN} 1.3.6.1.4.1.2356.11.1.73.20.19.1.3
lcsStatusWlanMngmtCentralFwMngmtApStatusEntryIpAddress OBJECT-TYPE
    SYNTAX     IpAddress
    MAX-ACCESS read-only
    STATUS     current
    DESCRIPTION
            "-- empty --"
    ::= { lcsStatusWlanMngmtCentralFwMngmtApStatusEntry 3 }

-- {COLUMN} 1.3.6.1.4.1.2356.11.1.73.20.19.1.4
lcsStatusWlanMngmtCentralFwMngmtApStatusEntryName OBJECT-TYPE
    SYNTAX     DisplayString (SIZE(0..83))
    MAX-ACCESS read-only
    STATUS     current
    DESCRIPTION
            "-- empty --"
    ::= { lcsStatusWlanMngmtCentralFwMngmtApStatusEntry 4 }

-- {COLUMN} 1.3.6.1.4.1.2356.11.1.73.20.19.1.5
lcsStatusWlanMngmtCentralFwMngmtApStatusEntryLocation OBJECT-TYPE
    SYNTAX     DisplayString (SIZE(0..252))
    MAX-ACCESS read-only
    STATUS     current
    DESCRIPTION
            "-- empty --"
    ::= { lcsStatusWlanMngmtCentralFwMngmtApStatusEntry 5 }

-- {COLUMN} 1.3.6.1.4.1.2356.11.1.73.20.19.1.6
lcsStatusWlanMngmtCentralFwMngmtApStatusEntryActiveFirmware OBJECT-TYPE
    SYNTAX     DisplayString (SIZE(0..32))
    MAX-ACCESS read-only
    STATUS     current
    DESCRIPTION
            "-- empty --"
    ::= { lcsStatusWlanMngmtCentralFwMngmtApStatusEntry 6 }

-- {COLUMN} 1.3.6.1.4.1.2356.11.1.73.20.19.1.7
lcsStatusWlanMngmtCentralFwMngmtApStatusEntryAlternativeFirmware OBJECT-TYPE
    SYNTAX     DisplayString (SIZE(0..32))
    MAX-ACCESS read-only
    STATUS     current
    DESCRIPTION
            "-- empty --"
    ::= { lcsStatusWlanMngmtCentralFwMngmtApStatusEntry 7 }

-- {COLUMN} 1.3.6.1.4.1.2356.11.1.73.20.19.1.8
lcsStatusWlanMngmtCentralFwMngmtApStatusEntryLoader OBJECT-TYPE
    SYNTAX     DisplayString (SIZE(0..32))
    MAX-ACCESS read-only
    STATUS     current
    DESCRIPTION
            "-- empty --"
    ::= { lcsStatusWlanMngmtCentralFwMngmtApStatusEntry 8 }

-- {COLUMN} 1.3.6.1.4.1.2356.11.1.73.20.19.1.9
lcsStatusWlanMngmtCentralFwMngmtApStatusEntryApStatus OBJECT-TYPE
    SYNTAX     INTEGER {
                  eUnknown (0),
                  eDisabled (1),
                  eFoundMiniFw (2),
                  eFoundFw (3),
                  eFoundLd (4),
                  eNoUploadRequired (5),
                  eApInfoMissing (6),
                  eStartingUpload (7),
                  eWaitingForImage (8),
                  eDisabledDueToError (9),
                  eMiniFwRequired (10),
                  eRebootRequired (11),
                  eUploading (12)
            }
    MAX-ACCESS read-only
    STATUS     current
    DESCRIPTION
            "-- empty --"
    ::= { lcsStatusWlanMngmtCentralFwMngmtApStatusEntry 9 }

-- {COLUMN} 1.3.6.1.4.1.2356.11.1.73.20.19.1.10
lcsStatusWlanMngmtCentralFwMngmtApStatusEntryTargetVersion OBJECT-TYPE
    SYNTAX     DisplayString (SIZE(0..32))
    MAX-ACCESS read-only
    STATUS     current
    DESCRIPTION
            "-- empty --"
    ::= { lcsStatusWlanMngmtCentralFwMngmtApStatusEntry 10 }

-- {SCALAR} 1.3.6.1.4.1.2356.11.1.73.32
lcsStatusWlanMngmtLicenseCount OBJECT-TYPE
    SYNTAX     Integer32 (0..2147483647)
    MAX-ACCESS read-only
    STATUS     current
    DESCRIPTION
            ""
    ::= { lcsStatusWlanMngmt 32 }

-- {SCALAR} 1.3.6.1.4.1.2356.11.1.73.33
lcsStatusWlanMngmtLicenseLimit OBJECT-TYPE
    SYNTAX     Integer32 (0..2147483647)
    MAX-ACCESS read-only
    STATUS     current
    DESCRIPTION
            ""
    ::= { lcsStatusWlanMngmt 33 }

-- {SCALAR} 1.3.6.1.4.1.2356.11.1.73.34
lcsStatusWlanMngmtQueueBlockErrors OBJECT-TYPE
    SYNTAX     Integer32 (0..2147483647)
    MAX-ACCESS read-only
    STATUS     current
    DESCRIPTION
            ""
    ::= { lcsStatusWlanMngmt 34 }

-- {SCALAR} 1.3.6.1.4.1.2356.11.1.73.35
lcsStatusWlanMngmtClientCount OBJECT-TYPE
    SYNTAX     Integer32 (0..2147483647)
    MAX-ACCESS read-only
    STATUS     current
    DESCRIPTION
            ""
    ::= { lcsStatusWlanMngmt 35 }

-- {TABLE} 1.3.6.1.4.1.2356.11.1.73.36
lcsStatusWlanMngmtWlcBridgeInterfacesTable OBJECT-TYPE
    SYNTAX     SEQUENCE OF LcsStatusWlanMngmtWlcBridgeInterfacesEntry
    MAX-ACCESS not-accessible
    STATUS     current
    DESCRIPTION
            ""
    ::= { lcsStatusWlanMngmt 36 }

-- {ROW} 1.3.6.1.4.1.2356.11.1.73.36.1
lcsStatusWlanMngmtWlcBridgeInterfacesEntry OBJECT-TYPE
    SYNTAX     LcsStatusWlanMngmtWlcBridgeInterfacesEntry
    MAX-ACCESS not-accessible
    STATUS     current
    DESCRIPTION
            ""
    INDEX {
            lcsStatusWlanMngmtWlcBridgeInterfacesEntryBridgeInterface
          }
    ::= { lcsStatusWlanMngmtWlcBridgeInterfacesTable 1 }

LcsStatusWlanMngmtWlcBridgeInterfacesEntry ::= SEQUENCE {
            lcsStatusWlanMngmtWlcBridgeInterfacesEntryBridgeInterface INTEGER,
            lcsStatusWlanMngmtWlcBridgeInterfacesEntryRegisteredConnections Integer32,
            lcsStatusWlanMngmtWlcBridgeInterfacesEntryRecvUnicasts Integer32,
            lcsStatusWlanMngmtWlcBridgeInterfacesEntryRecvMulticasts Integer32,
            lcsStatusWlanMngmtWlcBridgeInterfacesEntryRecvBroadcasts Integer32,
            lcsStatusWlanMngmtWlcBridgeInterfacesEntryTransUnicastPackets Integer32,
            lcsStatusWlanMngmtWlcBridgeInterfacesEntryTransMultiBroadPckts Integer32,
            lcsStatusWlanMngmtWlcBridgeInterfacesEntryDroppedPackets Integer32,
            lcsStatusWlanMngmtWlcBridgeInterfacesEntryUnicastConnections Integer32,
            lcsStatusWlanMngmtWlcBridgeInterfacesEntryTxBytes Counter64,
            lcsStatusWlanMngmtWlcBridgeInterfacesEntryRxBytes Counter64,
            lcsStatusWlanMngmtWlcBridgeInterfacesEntryThroughput DisplayString,
            lcsStatusWlanMngmtWlcBridgeInterfacesEntryMaxThroughput DisplayString
    }

-- {COLUMN} 1.3.6.1.4.1.2356.11.1.73.36.1.1
lcsStatusWlanMngmtWlcBridgeInterfacesEntryBridgeInterface OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-only
    STATUS     current
    DESCRIPTION
            ""
    ::= { lcsStatusWlanMngmtWlcBridgeInterfacesEntry 1 }

-- {COLUMN} 1.3.6.1.4.1.2356.11.1.73.36.1.2
lcsStatusWlanMngmtWlcBridgeInterfacesEntryRegisteredConnections OBJECT-TYPE
    SYNTAX     Integer32 (0..2147483647)
    MAX-ACCESS read-only
    STATUS     current
    DESCRIPTION
            ""
    ::= { lcsStatusWlanMngmtWlcBridgeInterfacesEntry 2 }

-- {COLUMN} 1.3.6.1.4.1.2356.11.1.73.36.1.3
lcsStatusWlanMngmtWlcBridgeInterfacesEntryRecvUnicasts OBJECT-TYPE
    SYNTAX     Integer32 (0..2147483647)
    MAX-ACCESS read-only
    STATUS     current
    DESCRIPTION
            ""
    ::= { lcsStatusWlanMngmtWlcBridgeInterfacesEntry 3 }

-- {COLUMN} 1.3.6.1.4.1.2356.11.1.73.36.1.4
lcsStatusWlanMngmtWlcBridgeInterfacesEntryRecvMulticasts OBJECT-TYPE
    SYNTAX     Integer32 (0..2147483647)
    MAX-ACCESS read-only
    STATUS     current
    DESCRIPTION
            ""
    ::= { lcsStatusWlanMngmtWlcBridgeInterfacesEntry 4 }

-- {COLUMN} 1.3.6.1.4.1.2356.11.1.73.36.1.5
lcsStatusWlanMngmtWlcBridgeInterfacesEntryRecvBroadcasts OBJECT-TYPE
    SYNTAX     Integer32 (0..2147483647)
    MAX-ACCESS read-only
    STATUS     current
    DESCRIPTION
            ""
    ::= { lcsStatusWlanMngmtWlcBridgeInterfacesEntry 5 }

-- {COLUMN} 1.3.6.1.4.1.2356.11.1.73.36.1.6
lcsStatusWlanMngmtWlcBridgeInterfacesEntryTransUnicastPackets OBJECT-TYPE
    SYNTAX     Integer32 (0..2147483647)
    MAX-ACCESS read-only
    STATUS     current
    DESCRIPTION
            ""
    ::= { lcsStatusWlanMngmtWlcBridgeInterfacesEntry 6 }

-- {COLUMN} 1.3.6.1.4.1.2356.11.1.73.36.1.7
lcsStatusWlanMngmtWlcBridgeInterfacesEntryTransMultiBroadPckts OBJECT-TYPE
    SYNTAX     Integer32 (0..2147483647)
    MAX-ACCESS read-only
    STATUS     current
    DESCRIPTION
            ""
    ::= { lcsStatusWlanMngmtWlcBridgeInterfacesEntry 7 }

-- {COLUMN} 1.3.6.1.4.1.2356.11.1.73.36.1.8
lcsStatusWlanMngmtWlcBridgeInterfacesEntryDroppedPackets OBJECT-TYPE
    SYNTAX     Integer32 (0..2147483647)
    MAX-ACCESS read-only
    STATUS     current
    DESCRIPTION
            ""
    ::= { lcsStatusWlanMngmtWlcBridgeInterfacesEntry 8 }

-- {COLUMN} 1.3.6.1.4.1.2356.11.1.73.36.1.9
lcsStatusWlanMngmtWlcBridgeInterfacesEntryUnicastConnections OBJECT-TYPE
    SYNTAX     Integer32 (0..2147483647)
    MAX-ACCESS read-only
    STATUS     current
    DESCRIPTION
            ""
    ::= { lcsStatusWlanMngmtWlcBridgeInterfacesEntry 9 }

-- {COLUMN} 1.3.6.1.4.1.2356.11.1.73.36.1.10
lcsStatusWlanMngmtWlcBridgeInterfacesEntryTxBytes OBJECT-TYPE
    SYNTAX     Counter64
    MAX-ACCESS read-only
    STATUS     current
    DESCRIPTION
            "-- empty --"
    ::= { lcsStatusWlanMngmtWlcBridgeInterfacesEntry 10 }

-- {COLUMN} 1.3.6.1.4.1.2356.11.1.73.36.1.11
lcsStatusWlanMngmtWlcBridgeInterfacesEntryRxBytes OBJECT-TYPE
    SYNTAX     Counter64
    MAX-ACCESS read-only
    STATUS     current
    DESCRIPTION
            "-- empty --"
    ::= { lcsStatusWlanMngmtWlcBridgeInterfacesEntry 11 }

-- {COLUMN} 1.3.6.1.4.1.2356.11.1.73.36.1.12
lcsStatusWlanMngmtWlcBridgeInterfacesEntryThroughput OBJECT-TYPE
    SYNTAX     DisplayString (SIZE(0..255))
    MAX-ACCESS read-only
    STATUS     current
    DESCRIPTION
            "-- empty --"
    ::= { lcsStatusWlanMngmtWlcBridgeInterfacesEntry 12 }

-- {COLUMN} 1.3.6.1.4.1.2356.11.1.73.36.1.13
lcsStatusWlanMngmtWlcBridgeInterfacesEntryMaxThroughput OBJECT-TYPE
    SYNTAX     DisplayString (SIZE(0..255))
    MAX-ACCESS read-only
    STATUS     current
    DESCRIPTION
            "-- empty --"
    ::= { lcsStatusWlanMngmtWlcBridgeInterfacesEntry 13 }

-- {SCALAR} 1.3.6.1.4.1.2356.11.1.73.37
lcsStatusWlanMngmtPreference OBJECT-TYPE
    SYNTAX     Integer32 (0..255)
    MAX-ACCESS read-only
    STATUS     current
    DESCRIPTION
            "-- empty --"
    ::= { lcsStatusWlanMngmt 37 }

-- {NODE} 1.3.6.1.4.1.2356.11.1.73.40
lcsStatusWlanMngmtWlcTunnels OBJECT IDENTIFIER ::= { lcsStatusWlanMngmt 40 }

-- {SCALAR} 1.3.6.1.4.1.2356.11.1.73.40.2
lcsStatusWlanMngmtWlcTunnelsWlcDataTunnelActive OBJECT-TYPE
    SYNTAX     INTEGER {
                  eNo (0),
                  eYes (1)
            }
    MAX-ACCESS read-only
    STATUS     current
    DESCRIPTION
            ""
    ::= { lcsStatusWlanMngmtWlcTunnels 2 }

-- {SCALAR} 1.3.6.1.4.1.2356.11.1.73.40.4
lcsStatusWlanMngmtWlcTunnelsNumberOfWlcConn OBJECT-TYPE
    SYNTAX     Integer32 (0..2147483647)
    MAX-ACCESS read-only
    STATUS     current
    DESCRIPTION
            ""
    ::= { lcsStatusWlanMngmtWlcTunnels 4 }

-- {SCALAR} 1.3.6.1.4.1.2356.11.1.73.40.5
lcsStatusWlanMngmtWlcTunnelsActiveConnections OBJECT-TYPE
    SYNTAX     Integer32 (0..2147483647)
    MAX-ACCESS read-only
    STATUS     current
    DESCRIPTION
            ""
    ::= { lcsStatusWlanMngmtWlcTunnels 5 }

-- {TABLE} 1.3.6.1.4.1.2356.11.1.73.40.6
lcsStatusWlanMngmtWlcTunnelsWlcConnectionsTable OBJECT-TYPE
    SYNTAX     SEQUENCE OF LcsStatusWlanMngmtWlcTunnelsWlcConnectionsEntry
    MAX-ACCESS not-accessible
    STATUS     current
    DESCRIPTION
            ""
    ::= { lcsStatusWlanMngmtWlcTunnels 6 }

-- {ROW} 1.3.6.1.4.1.2356.11.1.73.40.6.1
lcsStatusWlanMngmtWlcTunnelsWlcConnectionsEntry OBJECT-TYPE
    SYNTAX     LcsStatusWlanMngmtWlcTunnelsWlcConnectionsEntry
    MAX-ACCESS not-accessible
    STATUS     current
    DESCRIPTION
            ""
    INDEX {
            lcsStatusWlanMngmtWlcTunnelsWlcConnectionsEntryConnId
          }
    ::= { lcsStatusWlanMngmtWlcTunnelsWlcConnectionsTable 1 }

LcsStatusWlanMngmtWlcTunnelsWlcConnectionsEntry ::= SEQUENCE {
            lcsStatusWlanMngmtWlcTunnelsWlcConnectionsEntryConnId Integer32,
            lcsStatusWlanMngmtWlcTunnelsWlcConnectionsEntryIpAddress IpAddress,
            lcsStatusWlanMngmtWlcTunnelsWlcConnectionsEntryPort Integer32,
            lcsStatusWlanMngmtWlcTunnelsWlcConnectionsEntryResult INTEGER,
            lcsStatusWlanMngmtWlcTunnelsWlcConnectionsEntryName DisplayString,
            lcsStatusWlanMngmtWlcTunnelsWlcConnectionsEntryState INTEGER,
            lcsStatusWlanMngmtWlcTunnelsWlcConnectionsEntryValid INTEGER,
            lcsStatusWlanMngmtWlcTunnelsWlcConnectionsEntryMacAddress Integer32,
            lcsStatusWlanMngmtWlcTunnelsWlcConnectionsEntryFirmwareVersion DisplayString,
            lcsStatusWlanMngmtWlcTunnelsWlcConnectionsEntryPmtu Integer32
    }

-- {COLUMN} 1.3.6.1.4.1.2356.11.1.73.40.6.1.1
lcsStatusWlanMngmtWlcTunnelsWlcConnectionsEntryConnId OBJECT-TYPE
    SYNTAX     Integer32 (0..2147483647)
    MAX-ACCESS read-only
    STATUS     current
    DESCRIPTION
            ""
    ::= { lcsStatusWlanMngmtWlcTunnelsWlcConnectionsEntry 1 }

-- {COLUMN} 1.3.6.1.4.1.2356.11.1.73.40.6.1.2
lcsStatusWlanMngmtWlcTunnelsWlcConnectionsEntryIpAddress OBJECT-TYPE
    SYNTAX     IpAddress
    MAX-ACCESS read-only
    STATUS     current
    DESCRIPTION
            ""
    ::= { lcsStatusWlanMngmtWlcTunnelsWlcConnectionsEntry 2 }

-- {COLUMN} 1.3.6.1.4.1.2356.11.1.73.40.6.1.3
lcsStatusWlanMngmtWlcTunnelsWlcConnectionsEntryPort OBJECT-TYPE
    SYNTAX     Integer32 (0..65535)
    MAX-ACCESS read-only
    STATUS     current
    DESCRIPTION
            ""
    ::= { lcsStatusWlanMngmtWlcTunnelsWlcConnectionsEntry 3 }

-- {COLUMN} 1.3.6.1.4.1.2356.11.1.73.40.6.1.4
lcsStatusWlanMngmtWlcTunnelsWlcConnectionsEntryResult OBJECT-TYPE
    SYNTAX     INTEGER {
                  eSuccess (0),
                  eFailure (1),
                  eSuccessNat (2),
                  eJoinFailUnspecified (3),
                  eJoinFailResourceDepletion (4),
                  eJoinFailUnknwnSrc (5),
                  eJoinFailIncorrectData (6),
                  eJoinFailSessionIdInUse (7),
                  eJoinFailWtpNotSupported (8),
                  eJoinFailBindingNotSupp (9),
                  eResetFailUnableToReset (10),
                  eResetFailFirmwWriteErr (11),
                  eConfigurationErrorServProvAnyhow (12),
                  eConfigurationErrorServNotProv (13),
                  eImageDataErrorChecksum (14),
                  eImageDataErrorLength (15),
                  eImageDataErrorOther (16),
                  eImageDataErrorAlrPresent (17),
                  eMessageUnexpectedInvalid (18),
                  eMessageUnexpectedUnrecognized (19),
                  eFailMissingMandMsgElem (20),
                  eFailUnrecognizedMsgElem (21),
                  eUnsupportedLoaderVersion (300),
                  eUnsupportedFirmwareVersion (301),
                  eUnknown (302),
                  eJoinFailAlreadyConnected (303)
            }
    MAX-ACCESS read-only
    STATUS     current
    DESCRIPTION
            ""
    ::= { lcsStatusWlanMngmtWlcTunnelsWlcConnectionsEntry 4 }

-- {COLUMN} 1.3.6.1.4.1.2356.11.1.73.40.6.1.5
lcsStatusWlanMngmtWlcTunnelsWlcConnectionsEntryName OBJECT-TYPE
    SYNTAX     DisplayString (SIZE(0..31))
    MAX-ACCESS read-only
    STATUS     current
    DESCRIPTION
            ""
    ::= { lcsStatusWlanMngmtWlcTunnelsWlcConnectionsEntry 5 }

-- {COLUMN} 1.3.6.1.4.1.2356.11.1.73.40.6.1.6
lcsStatusWlanMngmtWlcTunnelsWlcConnectionsEntryState OBJECT-TYPE
    SYNTAX     INTEGER {
                  eUnknown (0),
                  eIdle (5),
                  eDiscovery (10),
                  eDtlsSetup (15),
                  eJoin (20),
                  eConfigure (25),
                  eImageData (30),
                  eReset (35),
                  eDtlsTeardown (40),
                  eSulking (45),
                  eRun (100)
            }
    MAX-ACCESS read-only
    STATUS     current
    DESCRIPTION
            ""
    ::= { lcsStatusWlanMngmtWlcTunnelsWlcConnectionsEntry 6 }

-- {COLUMN} 1.3.6.1.4.1.2356.11.1.73.40.6.1.7
lcsStatusWlanMngmtWlcTunnelsWlcConnectionsEntryValid OBJECT-TYPE
    SYNTAX     INTEGER {
                  eNo (0),
                  eYes (1)
            }
    MAX-ACCESS read-only
    STATUS     current
    DESCRIPTION
            ""
    ::= { lcsStatusWlanMngmtWlcTunnelsWlcConnectionsEntry 7 }

-- {COLUMN} 1.3.6.1.4.1.2356.11.1.73.40.6.1.8
lcsStatusWlanMngmtWlcTunnelsWlcConnectionsEntryMacAddress OBJECT-TYPE
    SYNTAX     Integer32 (0..2147483647)
    MAX-ACCESS read-only
    STATUS     current
    DESCRIPTION
            ""
    ::= { lcsStatusWlanMngmtWlcTunnelsWlcConnectionsEntry 8 }

-- {COLUMN} 1.3.6.1.4.1.2356.11.1.73.40.6.1.9
lcsStatusWlanMngmtWlcTunnelsWlcConnectionsEntryFirmwareVersion OBJECT-TYPE
    SYNTAX     DisplayString (SIZE(0..31))
    MAX-ACCESS read-only
    STATUS     current
    DESCRIPTION
            ""
    ::= { lcsStatusWlanMngmtWlcTunnelsWlcConnectionsEntry 9 }

-- {COLUMN} 1.3.6.1.4.1.2356.11.1.73.40.6.1.10
lcsStatusWlanMngmtWlcTunnelsWlcConnectionsEntryPmtu OBJECT-TYPE
    SYNTAX     Integer32 (0..2147483647)
    MAX-ACCESS read-only
    STATUS     current
    DESCRIPTION
            ""
    ::= { lcsStatusWlanMngmtWlcTunnelsWlcConnectionsEntry 10 }

-- {TABLE} 1.3.6.1.4.1.2356.11.1.73.40.7
lcsStatusWlanMngmtWlcTunnelsWlcDiscoveryTable OBJECT-TYPE
    SYNTAX     SEQUENCE OF LcsStatusWlanMngmtWlcTunnelsWlcDiscoveryEntry
    MAX-ACCESS not-accessible
    STATUS     current
    DESCRIPTION
            ""
    ::= { lcsStatusWlanMngmtWlcTunnels 7 }

-- {ROW} 1.3.6.1.4.1.2356.11.1.73.40.7.1
lcsStatusWlanMngmtWlcTunnelsWlcDiscoveryEntry OBJECT-TYPE
    SYNTAX     LcsStatusWlanMngmtWlcTunnelsWlcDiscoveryEntry
    MAX-ACCESS not-accessible
    STATUS     current
    DESCRIPTION
            ""
    INDEX {
            lcsStatusWlanMngmtWlcTunnelsWlcDiscoveryEntryNetwork
          }
    ::= { lcsStatusWlanMngmtWlcTunnelsWlcDiscoveryTable 1 }

LcsStatusWlanMngmtWlcTunnelsWlcDiscoveryEntry ::= SEQUENCE {
            lcsStatusWlanMngmtWlcTunnelsWlcDiscoveryEntryNetwork DisplayString,
            lcsStatusWlanMngmtWlcTunnelsWlcDiscoveryEntryActive INTEGER,
            lcsStatusWlanMngmtWlcTunnelsWlcDiscoveryEntryPort Integer32
    }

-- {COLUMN} 1.3.6.1.4.1.2356.11.1.73.40.7.1.1
lcsStatusWlanMngmtWlcTunnelsWlcDiscoveryEntryNetwork OBJECT-TYPE
    SYNTAX     DisplayString (SIZE(0..16))
    MAX-ACCESS read-only
    STATUS     current
    DESCRIPTION
            ""
    ::= { lcsStatusWlanMngmtWlcTunnelsWlcDiscoveryEntry 1 }

-- {COLUMN} 1.3.6.1.4.1.2356.11.1.73.40.7.1.2
lcsStatusWlanMngmtWlcTunnelsWlcDiscoveryEntryActive OBJECT-TYPE
    SYNTAX     INTEGER {
                  eNo (0),
                  eYes (1)
            }
    MAX-ACCESS read-only
    STATUS     current
    DESCRIPTION
            ""
    ::= { lcsStatusWlanMngmtWlcTunnelsWlcDiscoveryEntry 2 }

-- {COLUMN} 1.3.6.1.4.1.2356.11.1.73.40.7.1.3
lcsStatusWlanMngmtWlcTunnelsWlcDiscoveryEntryPort OBJECT-TYPE
    SYNTAX     Integer32 (0..65535)
    MAX-ACCESS read-only
    STATUS     current
    DESCRIPTION
            "-- empty --"
    ::= { lcsStatusWlanMngmtWlcTunnelsWlcDiscoveryEntry 3 }

-- {SCALAR} 1.3.6.1.4.1.2356.11.1.73.40.8
lcsStatusWlanMngmtWlcTunnelsWlcTunnelActive OBJECT-TYPE
    SYNTAX     INTEGER {
                  eNo (0),
                  eYes (1)
            }
    MAX-ACCESS read-only
    STATUS     current
    DESCRIPTION
            "-- empty --"
    ::= { lcsStatusWlanMngmtWlcTunnels 8 }

-- {SCALAR} 1.3.6.1.4.1.2356.11.1.73.41
lcsStatusWlanMngmtNextdoorAp OBJECT-TYPE
    SYNTAX     Integer32 (0..2147483647)
    MAX-ACCESS read-only
    STATUS     current
    DESCRIPTION
            ""
    ::= { lcsStatusWlanMngmt 41 }

-- {SCALAR} 1.3.6.1.4.1.2356.11.1.73.50
lcsStatusWlanMngmtWtpCount OBJECT-TYPE
    SYNTAX     Integer32 (0..2147483647)
    MAX-ACCESS read-only
    STATUS     current
    DESCRIPTION
            "-- empty --"
    ::= { lcsStatusWlanMngmt 50 }

-- {SCALAR} 1.3.6.1.4.1.2356.11.1.73.51
lcsStatusWlanMngmtClientCount24ghz OBJECT-TYPE
    SYNTAX     Integer32 (0..2147483647)
    MAX-ACCESS read-only
    STATUS     current
    DESCRIPTION
            "-- empty --"
    ::= { lcsStatusWlanMngmt 51 }

-- {SCALAR} 1.3.6.1.4.1.2356.11.1.73.52
lcsStatusWlanMngmtClientCount5ghz OBJECT-TYPE
    SYNTAX     Integer32 (0..2147483647)
    MAX-ACCESS read-only
    STATUS     current
    DESCRIPTION
            "-- empty --"
    ::= { lcsStatusWlanMngmt 52 }

-- {TABLE} 1.3.6.1.4.1.2356.11.1.73.100
lcsStatusWlanMngmtStationTableTable OBJECT-TYPE
    SYNTAX     SEQUENCE OF LcsStatusWlanMngmtStationTableEntry
    MAX-ACCESS not-accessible
    STATUS     current
    DESCRIPTION
            ""
    ::= { lcsStatusWlanMngmt 100 }

-- {ROW} 1.3.6.1.4.1.2356.11.1.73.100.1
lcsStatusWlanMngmtStationTableEntry OBJECT-TYPE
    SYNTAX     LcsStatusWlanMngmtStationTableEntry
    MAX-ACCESS not-accessible
    STATUS     current
    DESCRIPTION
            ""
    INDEX {
            lcsStatusWlanMngmtStationTableEntryClientMac,
            lcsStatusWlanMngmtStationTableEntryApWlanMac
          }
    ::= { lcsStatusWlanMngmtStationTableTable 1 }

LcsStatusWlanMngmtStationTableEntry ::= SEQUENCE {
            lcsStatusWlanMngmtStationTableEntryClientMac MacAddress,
            lcsStatusWlanMngmtStationTableEntryApWlanMac MacAddress,
            lcsStatusWlanMngmtStationTableEntryIdentification DisplayString,
            lcsStatusWlanMngmtStationTableEntryTrap Unsigned32,
            lcsStatusWlanMngmtStationTableEntryPhySignal Unsigned32,
            lcsStatusWlanMngmtStationTableEntryTxRate INTEGER,
            lcsStatusWlanMngmtStationTableEntryRxRate INTEGER,
            lcsStatusWlanMngmtStationTableEntryNetworkName DisplayString,
            lcsStatusWlanMngmtStationTableEntryKeyType INTEGER,
            lcsStatusWlanMngmtStationTableEntryWpaVersion INTEGER,
            lcsStatusWlanMngmtStationTableEntryState INTEGER,
            lcsStatusWlanMngmtStationTableEntryLastError INTEGER,
            lcsStatusWlanMngmtStationTableEntryIpAddress IpAddress,
            lcsStatusWlanMngmtStationTableEntryInterface INTEGER,
            lcsStatusWlanMngmtStationTableEntryThroughput Unsigned32,
            lcsStatusWlanMngmtStationTableEntryCompression Unsigned32,
            lcsStatusWlanMngmtStationTableEntryApLanMac MacAddress,
            lcsStatusWlanMngmtStationTableEntryApName DisplayString,
            lcsStatusWlanMngmtStationTableEntryValid INTEGER,
            lcsStatusWlanMngmtStationTableEntryEffTxRate Unsigned32,
            lcsStatusWlanMngmtStationTableEntryEffRxRate Unsigned32,
            lcsStatusWlanMngmtStationTableEntryBssid MacAddress,
            lcsStatusWlanMngmtStationTableEntryClientSteering INTEGER,
            lcsStatusWlanMngmtStationTableEntryOperationMode INTEGER,
            lcsStatusWlanMngmtStationTableEntryFastRoaming INTEGER,
            lcsStatusWlanMngmtStationTableEntryUserName DisplayString,
            lcsStatusWlanMngmtStationTableEntryRadioBand INTEGER,
            lcsStatusWlanMngmtStationTableEntryRadioChannel Unsigned32,
            lcsStatusWlanMngmtStationTableEntry11acBeamforming DisplayString,
            lcsStatusWlanMngmtStationTableEntryDhcpHostname DisplayString
    }

-- {COLUMN} 1.3.6.1.4.1.2356.11.1.73.100.1.1
lcsStatusWlanMngmtStationTableEntryClientMac OBJECT-TYPE
    SYNTAX     MacAddress
    MAX-ACCESS read-only
    STATUS     current
    DESCRIPTION
            ""
    ::= { lcsStatusWlanMngmtStationTableEntry 1 }

-- {COLUMN} 1.3.6.1.4.1.2356.11.1.73.100.1.2
lcsStatusWlanMngmtStationTableEntryApWlanMac OBJECT-TYPE
    SYNTAX     MacAddress
    MAX-ACCESS read-only
    STATUS     current
    DESCRIPTION
            ""
    ::= { lcsStatusWlanMngmtStationTableEntry 2 }

-- {COLUMN} 1.3.6.1.4.1.2356.11.1.73.100.1.3
lcsStatusWlanMngmtStationTableEntryIdentification OBJECT-TYPE
    SYNTAX     DisplayString (SIZE(0..33))
    MAX-ACCESS read-only
    STATUS     current
    DESCRIPTION
            ""
    ::= { lcsStatusWlanMngmtStationTableEntry 3 }

-- {COLUMN} 1.3.6.1.4.1.2356.11.1.73.100.1.4
lcsStatusWlanMngmtStationTableEntryTrap OBJECT-TYPE
    SYNTAX     Unsigned32 (0..65535)
    MAX-ACCESS read-only
    STATUS     current
    DESCRIPTION
            ""
    ::= { lcsStatusWlanMngmtStationTableEntry 4 }

-- {COLUMN} 1.3.6.1.4.1.2356.11.1.73.100.1.5
lcsStatusWlanMngmtStationTableEntryPhySignal OBJECT-TYPE
    SYNTAX     Unsigned32 (0..65535)
    MAX-ACCESS read-only
    STATUS     current
    DESCRIPTION
            ""
    ::= { lcsStatusWlanMngmtStationTableEntry 5 }

-- {COLUMN} 1.3.6.1.4.1.2356.11.1.73.100.1.6
lcsStatusWlanMngmtStationTableEntryTxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eXR0M5 (16),
                  eXR1M (17),
                  eXR2M (18),
                  eXR3M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            ""
    ::= { lcsStatusWlanMngmtStationTableEntry 6 }

-- {COLUMN} 1.3.6.1.4.1.2356.11.1.73.100.1.7
lcsStatusWlanMngmtStationTableEntryRxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eXR0M5 (16),
                  eXR1M (17),
                  eXR2M (18),
                  eXR3M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            ""
    ::= { lcsStatusWlanMngmtStationTableEntry 7 }

-- {COLUMN} 1.3.6.1.4.1.2356.11.1.73.100.1.8
lcsStatusWlanMngmtStationTableEntryNetworkName OBJECT-TYPE
    SYNTAX     DisplayString (SIZE(0..32))
    MAX-ACCESS read-only
    STATUS     current
    DESCRIPTION
            ""
    ::= { lcsStatusWlanMngmtStationTableEntry 8 }

-- {COLUMN} 1.3.6.1.4.1.2356.11.1.73.100.1.9
lcsStatusWlanMngmtStationTableEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eAesCcmp256 (67),
                  eBip (68),
                  eBipCmac256 (69),
                  eAesGcmp128 (70),
                  eAesGcmp256 (71),
                  eBipGmac128 (72),
                  eBipGmac256 (73)
            }
    MAX-ACCESS read-only
    STATUS     current
    DESCRIPTION
            ""
    ::= { lcsStatusWlanMngmtStationTableEntry 9 }

-- {COLUMN} 1.3.6.1.4.1.2356.11.1.73.100.1.10
lcsStatusWlanMngmtStationTableEntryWpaVersion OBJECT-TYPE
    SYNTAX     INTEGER {
                  eNone (0),
                  eWpa1 (1),
                  eWpa2 (2),
                  eWpa3 (3)
            }
    MAX-ACCESS read-only
    STATUS     current
    DESCRIPTION
            ""
    ::= { lcsStatusWlanMngmtStationTableEntry 10 }

-- {COLUMN} 1.3.6.1.4.1.2356.11.1.73.100.1.11
lcsStatusWlanMngmtStationTableEntryState OBJECT-TYPE
    SYNTAX     INTEGER {
                  eNone (0),
                  eAdhoc (1),
                  eAuthenticated (2),
                  eConnected (3),
                  eMacCheck (4),
                  eKeyHandshake (8),
                  eAssociated (9),
                  e1xNegotiation (10),
                  eWpsNegotiation (11)
            }
    MAX-ACCESS read-only
    STATUS     current
    DESCRIPTION
            ""
    ::= { lcsStatusWlanMngmtStationTableEntry 11 }

-- {COLUMN} 1.3.6.1.4.1.2356.11.1.73.100.1.12
lcsStatusWlanMngmtStationTableEntryLastError OBJECT-TYPE
    SYNTAX     INTEGER {
                  eNone (0),
                  eAuthSuccess (1),
                  eDeauth (2),
                  eAssocSuccess (3),
                  eReassocSuccess (4),
                  eDisassoc (5),
                  eRadiusSuccess (6),
                  eAuthReject (7),
                  eAssocReject (8),
                  eKeyhandshakeSuccess (9),
                  eKeyhandshakeTimeout (10),
                  eKeyhandshakeFailure (11),
                  eRadiusReject (12),
                  eSupervision (13),
                  e8021xSuccess (14),
                  e8021xFailure (15),
                  eIdleTimeout (16),
                  eAdminDeassoc (17),
                  eRoamed (18)
            }
    MAX-ACCESS read-only
    STATUS     current
    DESCRIPTION
            ""
    ::= { lcsStatusWlanMngmtStationTableEntry 12 }

-- {COLUMN} 1.3.6.1.4.1.2356.11.1.73.100.1.13
lcsStatusWlanMngmtStationTableEntryIpAddress OBJECT-TYPE
    SYNTAX     IpAddress
    MAX-ACCESS read-only
    STATUS     current
    DESCRIPTION
            ""
    ::= { lcsStatusWlanMngmtStationTableEntry 13 }

-- {COLUMN} 1.3.6.1.4.1.2356.11.1.73.100.1.14
lcsStatusWlanMngmtStationTableEntryInterface OBJECT-TYPE
    SYNTAX     INTEGER {
                  eWlan1 (0),
                  eWlan2 (1),
                  eWlan3 (2),
                  eWlan4 (3)
            }
    MAX-ACCESS read-only
    STATUS     current
    DESCRIPTION
            ""
    ::= { lcsStatusWlanMngmtStationTableEntry 14 }

-- {COLUMN} 1.3.6.1.4.1.2356.11.1.73.100.1.15
lcsStatusWlanMngmtStationTableEntryThroughput OBJECT-TYPE
    SYNTAX     Unsigned32 (0..4294967295)
    MAX-ACCESS read-only
    STATUS     current
    DESCRIPTION
            ""
    ::= { lcsStatusWlanMngmtStationTableEntry 15 }

-- {COLUMN} 1.3.6.1.4.1.2356.11.1.73.100.1.16
lcsStatusWlanMngmtStationTableEntryCompression OBJECT-TYPE
    SYNTAX     Unsigned32 (0..255)
    MAX-ACCESS read-only
    STATUS     current
    DESCRIPTION
            ""
    ::= { lcsStatusWlanMngmtStationTableEntry 16 }

-- {COLUMN} 1.3.6.1.4.1.2356.11.1.73.100.1.17
lcsStatusWlanMngmtStationTableEntryApLanMac OBJECT-TYPE
    SYNTAX     MacAddress
    MAX-ACCESS read-only
    STATUS     current
    DESCRIPTION
            ""
    ::= { lcsStatusWlanMngmtStationTableEntry 17 }

-- {COLUMN} 1.3.6.1.4.1.2356.11.1.73.100.1.18
lcsStatusWlanMngmtStationTableEntryApName OBJECT-TYPE
    SYNTAX     DisplayString (SIZE(0..65))
    MAX-ACCESS read-only
    STATUS     current
    DESCRIPTION
            ""
    ::= { lcsStatusWlanMngmtStationTableEntry 18 }

-- {COLUMN} 1.3.6.1.4.1.2356.11.1.73.100.1.19
lcsStatusWlanMngmtStationTableEntryValid OBJECT-TYPE
    SYNTAX     INTEGER {
                  eNo (0),
                  eYes (1)
            }
    MAX-ACCESS read-only
    STATUS     current
    DESCRIPTION
            ""
    ::= { lcsStatusWlanMngmtStationTableEntry 19 }

-- {COLUMN} 1.3.6.1.4.1.2356.11.1.73.100.1.20
lcsStatusWlanMngmtStationTableEntryEffTxRate OBJECT-TYPE
    SYNTAX     Unsigned32 (0..65535)
    MAX-ACCESS read-only
    STATUS     current
    DESCRIPTION
            ""
    ::= { lcsStatusWlanMngmtStationTableEntry 20 }

-- {COLUMN} 1.3.6.1.4.1.2356.11.1.73.100.1.21
lcsStatusWlanMngmtStationTableEntryEffRxRate OBJECT-TYPE
    SYNTAX     Unsigned32 (0..65535)
    MAX-ACCESS read-only
    STATUS     current
    DESCRIPTION
            ""
    ::= { lcsStatusWlanMngmtStationTableEntry 21 }

-- {COLUMN} 1.3.6.1.4.1.2356.11.1.73.100.1.22
lcsStatusWlanMngmtStationTableEntryBssid OBJECT-TYPE
    SYNTAX     MacAddress
    MAX-ACCESS read-only
    STATUS     current
    DESCRIPTION
            "-- empty --"
    ::= { lcsStatusWlanMngmtStationTableEntry 22 }

-- {COLUMN} 1.3.6.1.4.1.2356.11.1.73.100.1.23
lcsStatusWlanMngmtStationTableEntryClientSteering OBJECT-TYPE
    SYNTAX     INTEGER {
                  ePending (0),
                  eClientSteeringOk (1),
                  eUnsteerable (2),
                  eNoInfo (3)
            }
    MAX-ACCESS read-only
    STATUS     current
    DESCRIPTION
            "-- empty --"
    ::= { lcsStatusWlanMngmtStationTableEntry 23 }

-- {COLUMN} 1.3.6.1.4.1.2356.11.1.73.100.1.24
lcsStatusWlanMngmtStationTableEntryOperationMode OBJECT-TYPE
    SYNTAX     INTEGER {
                  eUnknown (0),
                  e11b (1),
                  e11g (2),
                  e11a (3),
                  e11n (4),
                  e11ac (5)
            }
    MAX-ACCESS read-only
    STATUS     current
    DESCRIPTION
            "-- empty --"
    ::= { lcsStatusWlanMngmtStationTableEntry 24 }

-- {COLUMN} 1.3.6.1.4.1.2356.11.1.73.100.1.25
lcsStatusWlanMngmtStationTableEntryFastRoaming OBJECT-TYPE
    SYNTAX     INTEGER {
                  eNo (0),
                  eYes (1)
            }
    MAX-ACCESS read-only
    STATUS     current
    DESCRIPTION
            "-- empty --"
    ::= { lcsStatusWlanMngmtStationTableEntry 25 }

-- {COLUMN} 1.3.6.1.4.1.2356.11.1.73.100.1.26
lcsStatusWlanMngmtStationTableEntryUserName OBJECT-TYPE
    SYNTAX     DisplayString (SIZE(0..64))
    MAX-ACCESS read-only
    STATUS     current
    DESCRIPTION
            "-- empty --"
    ::= { lcsStatusWlanMngmtStationTableEntry 26 }

-- {COLUMN} 1.3.6.1.4.1.2356.11.1.73.100.1.27
lcsStatusWlanMngmtStationTableEntryRadioBand OBJECT-TYPE
    SYNTAX     INTEGER {
                  eUnknown (0),
                  e24ghz (1),
                  e5ghz (2)
            }
    MAX-ACCESS read-only
    STATUS     current
    DESCRIPTION
            "-- empty --"
    ::= { lcsStatusWlanMngmtStationTableEntry 27 }

-- {COLUMN} 1.3.6.1.4.1.2356.11.1.73.100.1.28
lcsStatusWlanMngmtStationTableEntryRadioChannel OBJECT-TYPE
    SYNTAX     Unsigned32 (0..65535)
    MAX-ACCESS read-only
    STATUS     current
    DESCRIPTION
            "-- empty --"
    ::= { lcsStatusWlanMngmtStationTableEntry 28 }

-- {COLUMN} 1.3.6.1.4.1.2356.11.1.73.100.1.29
lcsStatusWlanMngmtStationTableEntry11acBeamforming OBJECT-TYPE
    SYNTAX     DisplayString (SIZE(0..64))
    MAX-ACCESS read-only
    STATUS     current
    DESCRIPTION
            "-- empty --"
    ::= { lcsStatusWlanMngmtStationTableEntry 29 }

-- {COLUMN} 1.3.6.1.4.1.2356.11.1.73.100.1.30
lcsStatusWlanMngmtStationTableEntryDhcpHostname OBJECT-TYPE
    SYNTAX     DisplayString (SIZE(0..33))
    MAX-ACCESS read-only
    STATUS     current
    DESCRIPTION
            "-- empty --"
    ::= { lcsStatusWlanMngmtStationTableEntry 30 }

-- {TABLE} 1.3.6.1.4.1.2356.11.1.73.101
lcsStatusWlanMngmtNetworksTable OBJECT-TYPE
    SYNTAX     SEQUENCE OF LcsStatusWlanMngmtNetworksEntry
    MAX-ACCESS not-accessible
    STATUS     current
    DESCRIPTION
            ""
    ::= { lcsStatusWlanMngmt 101 }

-- {ROW} 1.3.6.1.4.1.2356.11.1.73.101.1
lcsStatusWlanMngmtNetworksEntry OBJECT-TYPE
    SYNTAX     LcsStatusWlanMngmtNetworksEntry
    MAX-ACCESS not-accessible
    STATUS     current
    DESCRIPTION
            ""
    INDEX {
            lcsStatusWlanMngmtNetworksEntryBssid
          }
    ::= { lcsStatusWlanMngmtNetworksTable 1 }

LcsStatusWlanMngmtNetworksEntry ::= SEQUENCE {
            lcsStatusWlanMngmtNetworksEntryBssid MacAddress,
            lcsStatusWlanMngmtNetworksEntryApLanMac MacAddress,
            lcsStatusWlanMngmtNetworksEntryApWlanMac MacAddress,
            lcsStatusWlanMngmtNetworksEntryApName DisplayString,
            lcsStatusWlanMngmtNetworksEntryInterface INTEGER,
            lcsStatusWlanMngmtNetworksEntryNetNumber Unsigned32,
            lcsStatusWlanMngmtNetworksEntryName DisplayString,
            lcsStatusWlanMngmtNetworksEntryClientCount Unsigned32,
            lcsStatusWlanMngmtNetworksEntryValid INTEGER
    }

-- {COLUMN} 1.3.6.1.4.1.2356.11.1.73.101.1.1
lcsStatusWlanMngmtNetworksEntryBssid OBJECT-TYPE
    SYNTAX     MacAddress
    MAX-ACCESS read-only
    STATUS     current
    DESCRIPTION
            ""
    ::= { lcsStatusWlanMngmtNetworksEntry 1 }

-- {COLUMN} 1.3.6.1.4.1.2356.11.1.73.101.1.2
lcsStatusWlanMngmtNetworksEntryApLanMac OBJECT-TYPE
    SYNTAX     MacAddress
    MAX-ACCESS read-only
    STATUS     current
    DESCRIPTION
            ""
    ::= { lcsStatusWlanMngmtNetworksEntry 2 }

-- {COLUMN} 1.3.6.1.4.1.2356.11.1.73.101.1.3
lcsStatusWlanMngmtNetworksEntryApWlanMac OBJECT-TYPE
    SYNTAX     MacAddress
    MAX-ACCESS read-only
    STATUS     current
    DESCRIPTION
            ""
    ::= { lcsStatusWlanMngmtNetworksEntry 3 }

-- {COLUMN} 1.3.6.1.4.1.2356.11.1.73.101.1.4
lcsStatusWlanMngmtNetworksEntryApName OBJECT-TYPE
    SYNTAX     DisplayString (SIZE(0..65))
    MAX-ACCESS read-only
    STATUS     current
    DESCRIPTION
            ""
    ::= { lcsStatusWlanMngmtNetworksEntry 4 }

-- {COLUMN} 1.3.6.1.4.1.2356.11.1.73.101.1.5
lcsStatusWlanMngmtNetworksEntryInterface OBJECT-TYPE
    SYNTAX     INTEGER {
                  eWlan1 (0),
                  eWlan2 (1),
                  eWlan3 (2),
                  eWlan4 (3)
            }
    MAX-ACCESS read-only
    STATUS     current
    DESCRIPTION
            ""
    ::= { lcsStatusWlanMngmtNetworksEntry 5 }

-- {COLUMN} 1.3.6.1.4.1.2356.11.1.73.101.1.6
lcsStatusWlanMngmtNetworksEntryNetNumber OBJECT-TYPE
    SYNTAX     Unsigned32 (0..255)
    MAX-ACCESS read-only
    STATUS     current
    DESCRIPTION
            ""
    ::= { lcsStatusWlanMngmtNetworksEntry 6 }

-- {COLUMN} 1.3.6.1.4.1.2356.11.1.73.101.1.7
lcsStatusWlanMngmtNetworksEntryName OBJECT-TYPE
    SYNTAX     DisplayString (SIZE(0..32))
    MAX-ACCESS read-only
    STATUS     current
    DESCRIPTION
            ""
    ::= { lcsStatusWlanMngmtNetworksEntry 7 }

-- {COLUMN} 1.3.6.1.4.1.2356.11.1.73.101.1.8
lcsStatusWlanMngmtNetworksEntryClientCount OBJECT-TYPE
    SYNTAX     Unsigned32 (0..4294967295)
    MAX-ACCESS read-only
    STATUS     current
    DESCRIPTION
            ""
    ::= { lcsStatusWlanMngmtNetworksEntry 8 }

-- {COLUMN} 1.3.6.1.4.1.2356.11.1.73.101.1.9
lcsStatusWlanMngmtNetworksEntryValid OBJECT-TYPE
    SYNTAX     INTEGER {
                  eNo (0),
                  eYes (1)
            }
    MAX-ACCESS read-only
    STATUS     current
    DESCRIPTION
            ""
    ::= { lcsStatusWlanMngmtNetworksEntry 9 }

-- {TABLE} 1.3.6.1.4.1.2356.11.1.73.102
lcsStatusWlanMngmtNetCountTable OBJECT-TYPE
    SYNTAX     SEQUENCE OF LcsStatusWlanMngmtNetCountEntry
    MAX-ACCESS not-accessible
    STATUS     current
    DESCRIPTION
            ""
    ::= { lcsStatusWlanMngmt 102 }

-- {ROW} 1.3.6.1.4.1.2356.11.1.73.102.1
lcsStatusWlanMngmtNetCountEntry OBJECT-TYPE
    SYNTAX     LcsStatusWlanMngmtNetCountEntry
    MAX-ACCESS not-accessible
    STATUS     current
    DESCRIPTION
            ""
    INDEX {
            lcsStatusWlanMngmtNetCountEntryName
          }
    ::= { lcsStatusWlanMngmtNetCountTable 1 }

LcsStatusWlanMngmtNetCountEntry ::= SEQUENCE {
            lcsStatusWlanMngmtNetCountEntryName DisplayString,
            lcsStatusWlanMngmtNetCountEntryNumRadios Unsigned32,
            lcsStatusWlanMngmtNetCountEntryNumStations Unsigned32,
            lcsStatusWlanMngmtNetCountEntrySsid DisplayString,
            lcsStatusWlanMngmtNetCountEntryBridgeInterface INTEGER
    }

-- {COLUMN} 1.3.6.1.4.1.2356.11.1.73.102.1.1
lcsStatusWlanMngmtNetCountEntryName OBJECT-TYPE
    SYNTAX     DisplayString (SIZE(0..32))
    MAX-ACCESS read-only
    STATUS     current
    DESCRIPTION
            ""
    ::= { lcsStatusWlanMngmtNetCountEntry 1 }

-- {COLUMN} 1.3.6.1.4.1.2356.11.1.73.102.1.2
lcsStatusWlanMngmtNetCountEntryNumRadios OBJECT-TYPE
    SYNTAX     Unsigned32 (0..4294967295)
    MAX-ACCESS read-only
    STATUS     current
    DESCRIPTION
            ""
    ::= { lcsStatusWlanMngmtNetCountEntry 2 }

-- {COLUMN} 1.3.6.1.4.1.2356.11.1.73.102.1.3
lcsStatusWlanMngmtNetCountEntryNumStations OBJECT-TYPE
    SYNTAX     Unsigned32 (0..4294967295)
    MAX-ACCESS read-only
    STATUS     current
    DESCRIPTION
            ""
    ::= { lcsStatusWlanMngmtNetCountEntry 3 }

-- {COLUMN} 1.3.6.1.4.1.2356.11.1.73.102.1.4
lcsStatusWlanMngmtNetCountEntrySsid OBJECT-TYPE
    SYNTAX     DisplayString (SIZE(0..33))
    MAX-ACCESS read-only
    STATUS     current
    DESCRIPTION
            ""
    ::= { lcsStatusWlanMngmtNetCountEntry 4 }

-- {COLUMN} 1.3.6.1.4.1.2356.11.1.73.102.1.5
lcsStatusWlanMngmtNetCountEntryBridgeInterface OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-only
    STATUS     current
    DESCRIPTION
            ""
    ::= { lcsStatusWlanMngmtNetCountEntry 5 }

-- {TABLE} 1.3.6.1.4.1.2356.11.1.73.120
lcsStatusWlanMngmtScanResultsTable OBJECT-TYPE
    SYNTAX     SEQUENCE OF LcsStatusWlanMngmtScanResultsEntry
    MAX-ACCESS not-accessible
    STATUS     current
    DESCRIPTION
            ""
    ::= { lcsStatusWlanMngmt 120 }

-- {ROW} 1.3.6.1.4.1.2356.11.1.73.120.1
lcsStatusWlanMngmtScanResultsEntry OBJECT-TYPE
    SYNTAX     LcsStatusWlanMngmtScanResultsEntry
    MAX-ACCESS not-accessible
    STATUS     current
    DESCRIPTION
            ""
    INDEX {
            lcsStatusWlanMngmtScanResultsEntryBssid
          }
    ::= { lcsStatusWlanMngmtScanResultsTable 1 }

LcsStatusWlanMngmtScanResultsEntry ::= SEQUENCE {
            lcsStatusWlanMngmtScanResultsEntryBssid MacAddress,
            lcsStatusWlanMngmtScanResultsEntryApName DisplayString,
            lcsStatusWlanMngmtScanResultsEntryIpAddress IpAddress,
            lcsStatusWlanMngmtScanResultsEntryApLanMac MacAddress,
            lcsStatusWlanMngmtScanResultsEntryInterface INTEGER,
            lcsStatusWlanMngmtScanResultsEntryNetworkName DisplayString,
            lcsStatusWlanMngmtScanResultsEntryEncryption INTEGER,
            lcsStatusWlanMngmtScanResultsEntryRadioBand INTEGER,
            lcsStatusWlanMngmtScanResultsEntryRadioChannel Unsigned32,
            lcsStatusWlanMngmtScanResultsEntry108mbpsMode Unsigned32,
            lcsStatusWlanMngmtScanResultsEntryPhySignal Integer32,
            lcsStatusWlanMngmtScanResultsEntryNoiseLevel Integer32,
            lcsStatusWlanMngmtScanResultsEntryIdentification DisplayString,
            lcsStatusWlanMngmtScanResultsEntryAge Unsigned32
    }

-- {COLUMN} 1.3.6.1.4.1.2356.11.1.73.120.1.1
lcsStatusWlanMngmtScanResultsEntryBssid OBJECT-TYPE
    SYNTAX     MacAddress
    MAX-ACCESS read-only
    STATUS     current
    DESCRIPTION
            ""
    ::= { lcsStatusWlanMngmtScanResultsEntry 1 }

-- {COLUMN} 1.3.6.1.4.1.2356.11.1.73.120.1.2
lcsStatusWlanMngmtScanResultsEntryApName OBJECT-TYPE
    SYNTAX     DisplayString (SIZE(0..65))
    MAX-ACCESS read-only
    STATUS     current
    DESCRIPTION
            ""
    ::= { lcsStatusWlanMngmtScanResultsEntry 2 }

-- {COLUMN} 1.3.6.1.4.1.2356.11.1.73.120.1.3
lcsStatusWlanMngmtScanResultsEntryIpAddress OBJECT-TYPE
    SYNTAX     IpAddress
    MAX-ACCESS read-only
    STATUS     current
    DESCRIPTION
            ""
    ::= { lcsStatusWlanMngmtScanResultsEntry 3 }

-- {COLUMN} 1.3.6.1.4.1.2356.11.1.73.120.1.4
lcsStatusWlanMngmtScanResultsEntryApLanMac OBJECT-TYPE
    SYNTAX     MacAddress
    MAX-ACCESS read-only
    STATUS     current
    DESCRIPTION
            ""
    ::= { lcsStatusWlanMngmtScanResultsEntry 4 }

-- {COLUMN} 1.3.6.1.4.1.2356.11.1.73.120.1.5
lcsStatusWlanMngmtScanResultsEntryInterface OBJECT-TYPE
    SYNTAX     INTEGER {
                  eWlan1 (0),
                  eWlan2 (1),
                  eWlan3 (2),
                  eWlan4 (3)
            }
    MAX-ACCESS read-only
    STATUS     current
    DESCRIPTION
            ""
    ::= { lcsStatusWlanMngmtScanResultsEntry 5 }

-- {COLUMN} 1.3.6.1.4.1.2356.11.1.73.120.1.6
lcsStatusWlanMngmtScanResultsEntryNetworkName OBJECT-TYPE
    SYNTAX     DisplayString (SIZE(0..32))
    MAX-ACCESS read-only
    STATUS     current
    DESCRIPTION
            ""
    ::= { lcsStatusWlanMngmtScanResultsEntry 6 }

-- {COLUMN} 1.3.6.1.4.1.2356.11.1.73.120.1.7
lcsStatusWlanMngmtScanResultsEntryEncryption OBJECT-TYPE
    SYNTAX     INTEGER {
                  eNone (0),
                  eWep (1),
                  eTkip (2),
                  eAes (3),
                  eAesPlusTkip (4)
            }
    MAX-ACCESS read-only
    STATUS     current
    DESCRIPTION
            ""
    ::= { lcsStatusWlanMngmtScanResultsEntry 7 }

-- {COLUMN} 1.3.6.1.4.1.2356.11.1.73.120.1.8
lcsStatusWlanMngmtScanResultsEntryRadioBand OBJECT-TYPE
    SYNTAX     INTEGER {
                  e24ghz5ghz (0),
                  e24ghz (1),
                  e5ghz (2)
            }
    MAX-ACCESS read-only
    STATUS     current
    DESCRIPTION
            ""
    ::= { lcsStatusWlanMngmtScanResultsEntry 8 }

-- {COLUMN} 1.3.6.1.4.1.2356.11.1.73.120.1.9
lcsStatusWlanMngmtScanResultsEntryRadioChannel OBJECT-TYPE
    SYNTAX     Unsigned32 (0..255)
    MAX-ACCESS read-only
    STATUS     current
    DESCRIPTION
            ""
    ::= { lcsStatusWlanMngmtScanResultsEntry 9 }

-- {COLUMN} 1.3.6.1.4.1.2356.11.1.73.120.1.10
lcsStatusWlanMngmtScanResultsEntry108mbpsMode OBJECT-TYPE
    SYNTAX     Unsigned32 (0..255)
    MAX-ACCESS read-only
    STATUS     current
    DESCRIPTION
            ""
    ::= { lcsStatusWlanMngmtScanResultsEntry 10 }

-- {COLUMN} 1.3.6.1.4.1.2356.11.1.73.120.1.11
lcsStatusWlanMngmtScanResultsEntryPhySignal OBJECT-TYPE
    SYNTAX     Integer32 (-32768..32767)
    MAX-ACCESS read-only
    STATUS     current
    DESCRIPTION
            ""
    ::= { lcsStatusWlanMngmtScanResultsEntry 11 }

-- {COLUMN} 1.3.6.1.4.1.2356.11.1.73.120.1.12
lcsStatusWlanMngmtScanResultsEntryNoiseLevel OBJECT-TYPE
    SYNTAX     Integer32 (-128..127)
    MAX-ACCESS read-only
    STATUS     current
    DESCRIPTION
            ""
    ::= { lcsStatusWlanMngmtScanResultsEntry 12 }

-- {COLUMN} 1.3.6.1.4.1.2356.11.1.73.120.1.13
lcsStatusWlanMngmtScanResultsEntryIdentification OBJECT-TYPE
    SYNTAX     DisplayString (SIZE(0..33))
    MAX-ACCESS read-only
    STATUS     current
    DESCRIPTION
            ""
    ::= { lcsStatusWlanMngmtScanResultsEntry 13 }

-- {COLUMN} 1.3.6.1.4.1.2356.11.1.73.120.1.14
lcsStatusWlanMngmtScanResultsEntryAge OBJECT-TYPE
    SYNTAX     Unsigned32 (0..4294967295)
    MAX-ACCESS read-only
    STATUS     current
    DESCRIPTION
            ""
    ::= { lcsStatusWlanMngmtScanResultsEntry 14 }

-- {TABLE} 1.3.6.1.4.1.2356.11.1.73.121
lcsStatusWlanMngmtSeenClientsTable OBJECT-TYPE
    SYNTAX     SEQUENCE OF LcsStatusWlanMngmtSeenClientsEntry
    MAX-ACCESS not-accessible
    STATUS     current
    DESCRIPTION
            ""
    ::= { lcsStatusWlanMngmt 121 }

-- {ROW} 1.3.6.1.4.1.2356.11.1.73.121.1
lcsStatusWlanMngmtSeenClientsEntry OBJECT-TYPE
    SYNTAX     LcsStatusWlanMngmtSeenClientsEntry
    MAX-ACCESS not-accessible
    STATUS     current
    DESCRIPTION
            ""
    INDEX {
            lcsStatusWlanMngmtSeenClientsEntryClientMac,
            lcsStatusWlanMngmtSeenClientsEntryApLanMac
          }
    ::= { lcsStatusWlanMngmtSeenClientsTable 1 }

LcsStatusWlanMngmtSeenClientsEntry ::= SEQUENCE {
            lcsStatusWlanMngmtSeenClientsEntryClientMac MacAddress,
            lcsStatusWlanMngmtSeenClientsEntryApName DisplayString,
            lcsStatusWlanMngmtSeenClientsEntryIpAddress IpAddress,
            lcsStatusWlanMngmtSeenClientsEntryApLanMac MacAddress,
            lcsStatusWlanMngmtSeenClientsEntryInterface INTEGER,
            lcsStatusWlanMngmtSeenClientsEntryRxPhySignal Unsigned32,
            lcsStatusWlanMngmtSeenClientsEntryAge Unsigned32,
            lcsStatusWlanMngmtSeenClientsEntryNetworkName DisplayString
    }

-- {COLUMN} 1.3.6.1.4.1.2356.11.1.73.121.1.1
lcsStatusWlanMngmtSeenClientsEntryClientMac OBJECT-TYPE
    SYNTAX     MacAddress
    MAX-ACCESS read-only
    STATUS     current
    DESCRIPTION
            ""
    ::= { lcsStatusWlanMngmtSeenClientsEntry 1 }

-- {COLUMN} 1.3.6.1.4.1.2356.11.1.73.121.1.2
lcsStatusWlanMngmtSeenClientsEntryApName OBJECT-TYPE
    SYNTAX     DisplayString (SIZE(0..65))
    MAX-ACCESS read-only
    STATUS     current
    DESCRIPTION
            ""
    ::= { lcsStatusWlanMngmtSeenClientsEntry 2 }

-- {COLUMN} 1.3.6.1.4.1.2356.11.1.73.121.1.3
lcsStatusWlanMngmtSeenClientsEntryIpAddress OBJECT-TYPE
    SYNTAX     IpAddress
    MAX-ACCESS read-only
    STATUS     current
    DESCRIPTION
            ""
    ::= { lcsStatusWlanMngmtSeenClientsEntry 3 }

-- {COLUMN} 1.3.6.1.4.1.2356.11.1.73.121.1.4
lcsStatusWlanMngmtSeenClientsEntryApLanMac OBJECT-TYPE
    SYNTAX     MacAddress
    MAX-ACCESS read-only
    STATUS     current
    DESCRIPTION
            ""
    ::= { lcsStatusWlanMngmtSeenClientsEntry 4 }

-- {COLUMN} 1.3.6.1.4.1.2356.11.1.73.121.1.5
lcsStatusWlanMngmtSeenClientsEntryInterface OBJECT-TYPE
    SYNTAX     INTEGER {
                  eWlan1 (0),
                  eWlan2 (1),
                  eWlan3 (2),
                  eWlan4 (3)
            }
    MAX-ACCESS read-only
    STATUS     current
    DESCRIPTION
            ""
    ::= { lcsStatusWlanMngmtSeenClientsEntry 5 }

-- {COLUMN} 1.3.6.1.4.1.2356.11.1.73.121.1.6
lcsStatusWlanMngmtSeenClientsEntryRxPhySignal OBJECT-TYPE
    SYNTAX     Unsigned32 (0..65535)
    MAX-ACCESS read-only
    STATUS     current
    DESCRIPTION
            ""
    ::= { lcsStatusWlanMngmtSeenClientsEntry 6 }

-- {COLUMN} 1.3.6.1.4.1.2356.11.1.73.121.1.7
lcsStatusWlanMngmtSeenClientsEntryAge OBJECT-TYPE
    SYNTAX     Unsigned32 (0..4294967295)
    MAX-ACCESS read-only
    STATUS     current
    DESCRIPTION
            ""
    ::= { lcsStatusWlanMngmtSeenClientsEntry 7 }

-- {COLUMN} 1.3.6.1.4.1.2356.11.1.73.121.1.8
lcsStatusWlanMngmtSeenClientsEntryNetworkName OBJECT-TYPE
    SYNTAX     DisplayString (SIZE(0..32))
    MAX-ACCESS read-only
    STATUS     current
    DESCRIPTION
            ""
    ::= { lcsStatusWlanMngmtSeenClientsEntry 8 }

-- {TABLE} 1.3.6.1.4.1.2356.11.1.73.122
lcsStatusWlanMngmtPmkCachingTable OBJECT-TYPE
    SYNTAX     SEQUENCE OF LcsStatusWlanMngmtPmkCachingEntry
    MAX-ACCESS not-accessible
    STATUS     current
    DESCRIPTION
            "-- empty --"
    ::= { lcsStatusWlanMngmt 122 }

-- {ROW} 1.3.6.1.4.1.2356.11.1.73.122.1
lcsStatusWlanMngmtPmkCachingEntry OBJECT-TYPE
    SYNTAX     LcsStatusWlanMngmtPmkCachingEntry
    MAX-ACCESS not-accessible
    STATUS     current
    DESCRIPTION
            ""
    INDEX {
            lcsStatusWlanMngmtPmkCachingEntrySupplicant
          }
    ::= { lcsStatusWlanMngmtPmkCachingTable 1 }

LcsStatusWlanMngmtPmkCachingEntry ::= SEQUENCE {
            lcsStatusWlanMngmtPmkCachingEntrySupplicant MacAddress,
            lcsStatusWlanMngmtPmkCachingEntrySsid DisplayString,
            lcsStatusWlanMngmtPmkCachingEntryPmkValue OCTET STRING,
            lcsStatusWlanMngmtPmkCachingEntryPmkLength Integer32,
            lcsStatusWlanMngmtPmkCachingEntryLifetime Integer32,
            lcsStatusWlanMngmtPmkCachingEntryVlanId Integer32,
            lcsStatusWlanMngmtPmkCachingEntryUserName DisplayString,
            lcsStatusWlanMngmtPmkCachingEntryStoreTime Integer32,
            lcsStatusWlanMngmtPmkCachingEntryHeapNode Integer32,
            lcsStatusWlanMngmtPmkCachingEntryWpa2KeyManagement INTEGER
    }

-- {COLUMN} 1.3.6.1.4.1.2356.11.1.73.122.1.1
lcsStatusWlanMngmtPmkCachingEntrySupplicant OBJECT-TYPE
    SYNTAX     MacAddress
    MAX-ACCESS read-only
    STATUS     current
    DESCRIPTION
            "-- empty --"
    ::= { lcsStatusWlanMngmtPmkCachingEntry 1 }

-- {COLUMN} 1.3.6.1.4.1.2356.11.1.73.122.1.3
lcsStatusWlanMngmtPmkCachingEntrySsid OBJECT-TYPE
    SYNTAX     DisplayString (SIZE(0..255))
    MAX-ACCESS read-only
    STATUS     current
    DESCRIPTION
            "-- empty --"
    ::= { lcsStatusWlanMngmtPmkCachingEntry 3 }

-- {COLUMN} 1.3.6.1.4.1.2356.11.1.73.122.1.4
lcsStatusWlanMngmtPmkCachingEntryPmkValue OBJECT-TYPE
    SYNTAX     OCTET STRING
    MAX-ACCESS read-only
    STATUS     current
    DESCRIPTION
            "-- empty --"
    ::= { lcsStatusWlanMngmtPmkCachingEntry 4 }

-- {COLUMN} 1.3.6.1.4.1.2356.11.1.73.122.1.5
lcsStatusWlanMngmtPmkCachingEntryPmkLength OBJECT-TYPE
    SYNTAX     Integer32 (0..255)
    MAX-ACCESS read-only
    STATUS     current
    DESCRIPTION
            "-- empty --"
    ::= { lcsStatusWlanMngmtPmkCachingEntry 5 }

-- {COLUMN} 1.3.6.1.4.1.2356.11.1.73.122.1.6
lcsStatusWlanMngmtPmkCachingEntryLifetime OBJECT-TYPE
    SYNTAX     Integer32 (0..2147483647)
    MAX-ACCESS read-only
    STATUS     current
    DESCRIPTION
            "-- empty --"
    ::= { lcsStatusWlanMngmtPmkCachingEntry 6 }

-- {COLUMN} 1.3.6.1.4.1.2356.11.1.73.122.1.7
lcsStatusWlanMngmtPmkCachingEntryVlanId OBJECT-TYPE
    SYNTAX     Integer32 (0..65535)
    MAX-ACCESS read-only
    STATUS     current
    DESCRIPTION
            "-- empty --"
    ::= { lcsStatusWlanMngmtPmkCachingEntry 7 }

-- {COLUMN} 1.3.6.1.4.1.2356.11.1.73.122.1.8
lcsStatusWlanMngmtPmkCachingEntryUserName OBJECT-TYPE
    SYNTAX     DisplayString (SIZE(0..255))
    MAX-ACCESS read-only
    STATUS     current
    DESCRIPTION
            "-- empty --"
    ::= { lcsStatusWlanMngmtPmkCachingEntry 8 }

-- {COLUMN} 1.3.6.1.4.1.2356.11.1.73.122.1.9
lcsStatusWlanMngmtPmkCachingEntryStoreTime OBJECT-TYPE
    SYNTAX     Integer32 (0..2147483647)
    MAX-ACCESS read-only
    STATUS     current
    DESCRIPTION
            "-- empty --"
    ::= { lcsStatusWlanMngmtPmkCachingEntry 9 }

-- {COLUMN} 1.3.6.1.4.1.2356.11.1.73.122.1.10
lcsStatusWlanMngmtPmkCachingEntryHeapNode OBJECT-TYPE
    SYNTAX     Integer32 (0..2147483647)
    MAX-ACCESS read-only
    STATUS     current
    DESCRIPTION
            "-- empty --"
    ::= { lcsStatusWlanMngmtPmkCachingEntry 10 }

-- {COLUMN} 1.3.6.1.4.1.2356.11.1.73.122.1.11
lcsStatusWlanMngmtPmkCachingEntryWpa2KeyManagement OBJECT-TYPE
    SYNTAX     INTEGER {
                  eStandard (0),
                  eFastRoaming (1),
                  eSha256 (2),
                  eSha384 (3),
                  eFastRoamingSha384 (4),
                  eNone (255)
            }
    MAX-ACCESS read-only
    STATUS     current
    DESCRIPTION
            "-- empty --"
    ::= { lcsStatusWlanMngmtPmkCachingEntry 11 }

-- {NODE} 1.3.6.1.4.1.2356.11.1.73.123
lcsStatusWlanMngmtClSte OBJECT IDENTIFIER ::= { lcsStatusWlanMngmt 123 }

-- {SCALAR} 1.3.6.1.4.1.2356.11.1.73.123.1
lcsStatusWlanMngmtClSteOperating OBJECT-TYPE
    SYNTAX     INTEGER {
                  eNo (0),
                  eYes (1)
            }
    MAX-ACCESS read-only
    STATUS     current
    DESCRIPTION
            "-- empty --"
    ::= { lcsStatusWlanMngmtClSte 1 }

-- {SCALAR} 1.3.6.1.4.1.2356.11.1.73.123.2
lcsStatusWlanMngmtClSteResetStatistics OBJECT-TYPE
    SYNTAX     DisplayString
    MAX-ACCESS read-write
    STATUS     current
    DESCRIPTION
            "-- empty --"
    ::= { lcsStatusWlanMngmtClSte 2 }

-- {SCALAR} 1.3.6.1.4.1.2356.11.1.73.123.3
lcsStatusWlanMngmtClSteRateOfOptimizedConnections OBJECT-TYPE
    SYNTAX     Integer32 (0..2147483647)
    MAX-ACCESS read-only
    STATUS     current
    DESCRIPTION
            "-- empty --"
    ::= { lcsStatusWlanMngmtClSte 3 }

-- {TABLE} 1.3.6.1.4.1.2356.11.1.73.123.4
lcsStatusWlanMngmtClSteClientInfoTable OBJECT-TYPE
    SYNTAX     SEQUENCE OF LcsStatusWlanMngmtClSteClientInfoEntry
    MAX-ACCESS not-accessible
    STATUS     current
    DESCRIPTION
            "-- empty --"
    ::= { lcsStatusWlanMngmtClSte 4 }

-- {ROW} 1.3.6.1.4.1.2356.11.1.73.123.4.1
lcsStatusWlanMngmtClSteClientInfoEntry OBJECT-TYPE
    SYNTAX     LcsStatusWlanMngmtClSteClientInfoEntry
    MAX-ACCESS not-accessible
    STATUS     current
    DESCRIPTION
            ""
    INDEX {
            lcsStatusWlanMngmtClSteClientInfoEntryClientMac
          }
    ::= { lcsStatusWlanMngmtClSteClientInfoTable 1 }

LcsStatusWlanMngmtClSteClientInfoEntry ::= SEQUENCE {
            lcsStatusWlanMngmtClSteClientInfoEntryClientMac MacAddress,
            lcsStatusWlanMngmtClSteClientInfoEntryApsGotOk Integer32,
            lcsStatusWlanMngmtClSteClientInfoEntryState INTEGER,
            lcsStatusWlanMngmtClSteClientInfoEntryOkCount Integer32,
            lcsStatusWlanMngmtClSteClientInfoEntryNokCount Integer32,
            lcsStatusWlanMngmtClSteClientInfoEntryAssociationTime Integer32,
            lcsStatusWlanMngmtClSteClientInfoEntryRoamingTime Integer32
    }

-- {COLUMN} 1.3.6.1.4.1.2356.11.1.73.123.4.1.1
lcsStatusWlanMngmtClSteClientInfoEntryClientMac OBJECT-TYPE
    SYNTAX     MacAddress
    MAX-ACCESS read-only
    STATUS     current
    DESCRIPTION
            "-- empty --"
    ::= { lcsStatusWlanMngmtClSteClientInfoEntry 1 }

-- {COLUMN} 1.3.6.1.4.1.2356.11.1.73.123.4.1.4
lcsStatusWlanMngmtClSteClientInfoEntryApsGotOk OBJECT-TYPE
    SYNTAX     Integer32 (0..2147483647)
    MAX-ACCESS read-only
    STATUS     current
    DESCRIPTION
            "-- empty --"
    ::= { lcsStatusWlanMngmtClSteClientInfoEntry 4 }

-- {COLUMN} 1.3.6.1.4.1.2356.11.1.73.123.4.1.5
lcsStatusWlanMngmtClSteClientInfoEntryState OBJECT-TYPE
    SYNTAX     INTEGER {
                  ePending (0),
                  eClientSteeringOk (1),
                  eUnsteerable (2),
                  eNoInfo (3)
            }
    MAX-ACCESS read-only
    STATUS     current
    DESCRIPTION
            "-- empty --"
    ::= { lcsStatusWlanMngmtClSteClientInfoEntry 5 }

-- {COLUMN} 1.3.6.1.4.1.2356.11.1.73.123.4.1.6
lcsStatusWlanMngmtClSteClientInfoEntryOkCount OBJECT-TYPE
    SYNTAX     Integer32 (0..2147483647)
    MAX-ACCESS read-only
    STATUS     current
    DESCRIPTION
            "-- empty --"
    ::= { lcsStatusWlanMngmtClSteClientInfoEntry 6 }

-- {COLUMN} 1.3.6.1.4.1.2356.11.1.73.123.4.1.7
lcsStatusWlanMngmtClSteClientInfoEntryNokCount OBJECT-TYPE
    SYNTAX     Integer32 (0..2147483647)
    MAX-ACCESS read-only
    STATUS     current
    DESCRIPTION
            "-- empty --"
    ::= { lcsStatusWlanMngmtClSteClientInfoEntry 7 }

-- {COLUMN} 1.3.6.1.4.1.2356.11.1.73.123.4.1.8
lcsStatusWlanMngmtClSteClientInfoEntryAssociationTime OBJECT-TYPE
    SYNTAX     Integer32 (0..2147483647)
    MAX-ACCESS read-only
    STATUS     current
    DESCRIPTION
            "-- empty --"
    ::= { lcsStatusWlanMngmtClSteClientInfoEntry 8 }

-- {COLUMN} 1.3.6.1.4.1.2356.11.1.73.123.4.1.9
lcsStatusWlanMngmtClSteClientInfoEntryRoamingTime OBJECT-TYPE
    SYNTAX     Integer32 (0..2147483647)
    MAX-ACCESS read-only
    STATUS     current
    DESCRIPTION
            "-- empty --"
    ::= { lcsStatusWlanMngmtClSteClientInfoEntry 9 }

-- {TABLE} 1.3.6.1.4.1.2356.11.1.73.123.5
lcsStatusWlanMngmtClSteEvtTabTable OBJECT-TYPE
    SYNTAX     SEQUENCE OF LcsStatusWlanMngmtClSteEvtTabEntry
    MAX-ACCESS not-accessible
    STATUS     current
    DESCRIPTION
            ""
    ::= { lcsStatusWlanMngmtClSte 5 }

-- {ROW} 1.3.6.1.4.1.2356.11.1.73.123.5.1
lcsStatusWlanMngmtClSteEvtTabEntry OBJECT-TYPE
    SYNTAX     LcsStatusWlanMngmtClSteEvtTabEntry
    MAX-ACCESS not-accessible
    STATUS     current
    DESCRIPTION
            ""
    INDEX {
            lcsStatusWlanMngmtClSteEvtTabEntrySystemTime,
            lcsStatusWlanMngmtClSteEvtTabEntryClientMac,
            lcsStatusWlanMngmtClSteEvtTabEntryName,
            lcsStatusWlanMngmtClSteEvtTabEntryApLanMac,
            lcsStatusWlanMngmtClSteEvtTabEntryInterface
          }
    ::= { lcsStatusWlanMngmtClSteEvtTabTable 1 }

LcsStatusWlanMngmtClSteEvtTabEntry ::= SEQUENCE {
            lcsStatusWlanMngmtClSteEvtTabEntrySystemTime Integer32,
            lcsStatusWlanMngmtClSteEvtTabEntryClientMac MacAddress,
            lcsStatusWlanMngmtClSteEvtTabEntryApLanMac MacAddress,
            lcsStatusWlanMngmtClSteEvtTabEntryInterface Integer32,
            lcsStatusWlanMngmtClSteEvtTabEntrySignalStrengthRating Integer32,
            lcsStatusWlanMngmtClSteEvtTabEntryAssociatedClientsRating Integer32,
            lcsStatusWlanMngmtClSteEvtTabEntryFrequencyBandRating Integer32,
            lcsStatusWlanMngmtClSteEvtTabEntryFinalRating Integer32,
            lcsStatusWlanMngmtClSteEvtTabEntryAcceptClient INTEGER,
            lcsStatusWlanMngmtClSteEvtTabEntryClientAssociated INTEGER,
            lcsStatusWlanMngmtClSteEvtTabEntryClientDisassociated INTEGER,
            lcsStatusWlanMngmtClSteEvtTabEntryStubbornClient INTEGER,
            lcsStatusWlanMngmtClSteEvtTabEntrySignalStrength Integer32,
            lcsStatusWlanMngmtClSteEvtTabEntryAssociatedClients Integer32,
            lcsStatusWlanMngmtClSteEvtTabEntryFrequencyBand INTEGER,
            lcsStatusWlanMngmtClSteEvtTabEntryClientSteeringProfile DisplayString,
            lcsStatusWlanMngmtClSteEvtTabEntrySignalStrengthWeighting Integer32,
            lcsStatusWlanMngmtClSteEvtTabEntryAssociatedClientsWeighting Integer32,
            lcsStatusWlanMngmtClSteEvtTabEntryFrequencyBandWeighting Integer32,
            lcsStatusWlanMngmtClSteEvtTabEntryName DisplayString
    }

-- {COLUMN} 1.3.6.1.4.1.2356.11.1.73.123.5.1.1
lcsStatusWlanMngmtClSteEvtTabEntrySystemTime OBJECT-TYPE
    SYNTAX     Integer32 (0..2147483647)
    MAX-ACCESS read-only
    STATUS     current
    DESCRIPTION
            "-- empty --"
    ::= { lcsStatusWlanMngmtClSteEvtTabEntry 1 }

-- {COLUMN} 1.3.6.1.4.1.2356.11.1.73.123.5.1.2
lcsStatusWlanMngmtClSteEvtTabEntryClientMac OBJECT-TYPE
    SYNTAX     MacAddress
    MAX-ACCESS read-only
    STATUS     current
    DESCRIPTION
            "-- empty --"
    ::= { lcsStatusWlanMngmtClSteEvtTabEntry 2 }

-- {COLUMN} 1.3.6.1.4.1.2356.11.1.73.123.5.1.3
lcsStatusWlanMngmtClSteEvtTabEntryApLanMac OBJECT-TYPE
    SYNTAX     MacAddress
    MAX-ACCESS read-only
    STATUS     current
    DESCRIPTION
            "-- empty --"
    ::= { lcsStatusWlanMngmtClSteEvtTabEntry 3 }

-- {COLUMN} 1.3.6.1.4.1.2356.11.1.73.123.5.1.4
lcsStatusWlanMngmtClSteEvtTabEntryInterface OBJECT-TYPE
    SYNTAX     Integer32 (0..255)
    MAX-ACCESS read-only
    STATUS     current
    DESCRIPTION
            "-- empty --"
    ::= { lcsStatusWlanMngmtClSteEvtTabEntry 4 }

-- {COLUMN} 1.3.6.1.4.1.2356.11.1.73.123.5.1.5
lcsStatusWlanMngmtClSteEvtTabEntrySignalStrengthRating OBJECT-TYPE
    SYNTAX     Integer32 (0..2147483647)
    MAX-ACCESS read-only
    STATUS     current
    DESCRIPTION
            "-- empty --"
    ::= { lcsStatusWlanMngmtClSteEvtTabEntry 5 }

-- {COLUMN} 1.3.6.1.4.1.2356.11.1.73.123.5.1.6
lcsStatusWlanMngmtClSteEvtTabEntryAssociatedClientsRating OBJECT-TYPE
    SYNTAX     Integer32 (0..2147483647)
    MAX-ACCESS read-only
    STATUS     current
    DESCRIPTION
            "-- empty --"
    ::= { lcsStatusWlanMngmtClSteEvtTabEntry 6 }

-- {COLUMN} 1.3.6.1.4.1.2356.11.1.73.123.5.1.7
lcsStatusWlanMngmtClSteEvtTabEntryFrequencyBandRating OBJECT-TYPE
    SYNTAX     Integer32 (0..2147483647)
    MAX-ACCESS read-only
    STATUS     current
    DESCRIPTION
            "-- empty --"
    ::= { lcsStatusWlanMngmtClSteEvtTabEntry 7 }

-- {COLUMN} 1.3.6.1.4.1.2356.11.1.73.123.5.1.8
lcsStatusWlanMngmtClSteEvtTabEntryFinalRating OBJECT-TYPE
    SYNTAX     Integer32 (0..2147483647)
    MAX-ACCESS read-only
    STATUS     current
    DESCRIPTION
            "-- empty --"
    ::= { lcsStatusWlanMngmtClSteEvtTabEntry 8 }

-- {COLUMN} 1.3.6.1.4.1.2356.11.1.73.123.5.1.9
lcsStatusWlanMngmtClSteEvtTabEntryAcceptClient OBJECT-TYPE
    SYNTAX     INTEGER {
                  eNo (0),
                  eYes (1)
            }
    MAX-ACCESS read-only
    STATUS     current
    DESCRIPTION
            "-- empty --"
    ::= { lcsStatusWlanMngmtClSteEvtTabEntry 9 }

-- {COLUMN} 1.3.6.1.4.1.2356.11.1.73.123.5.1.10
lcsStatusWlanMngmtClSteEvtTabEntryClientAssociated OBJECT-TYPE
    SYNTAX     INTEGER {
                  eNo (0),
                  eYes (1)
            }
    MAX-ACCESS read-only
    STATUS     current
    DESCRIPTION
            "-- empty --"
    ::= { lcsStatusWlanMngmtClSteEvtTabEntry 10 }

-- {COLUMN} 1.3.6.1.4.1.2356.11.1.73.123.5.1.11
lcsStatusWlanMngmtClSteEvtTabEntryClientDisassociated OBJECT-TYPE
    SYNTAX     INTEGER {
                  eNo (0),
                  eYes (1)
            }
    MAX-ACCESS read-only
    STATUS     current
    DESCRIPTION
            "-- empty --"
    ::= { lcsStatusWlanMngmtClSteEvtTabEntry 11 }

-- {COLUMN} 1.3.6.1.4.1.2356.11.1.73.123.5.1.12
lcsStatusWlanMngmtClSteEvtTabEntryStubbornClient OBJECT-TYPE
    SYNTAX     INTEGER {
                  eNo (0),
                  eYes (1)
            }
    MAX-ACCESS read-only
    STATUS     current
    DESCRIPTION
            "-- empty --"
    ::= { lcsStatusWlanMngmtClSteEvtTabEntry 12 }

-- {COLUMN} 1.3.6.1.4.1.2356.11.1.73.123.5.1.13
lcsStatusWlanMngmtClSteEvtTabEntrySignalStrength OBJECT-TYPE
    SYNTAX     Integer32 (0..2147483647)
    MAX-ACCESS read-only
    STATUS     current
    DESCRIPTION
            "-- empty --"
    ::= { lcsStatusWlanMngmtClSteEvtTabEntry 13 }

-- {COLUMN} 1.3.6.1.4.1.2356.11.1.73.123.5.1.14
lcsStatusWlanMngmtClSteEvtTabEntryAssociatedClients OBJECT-TYPE
    SYNTAX     Integer32 (0..255)
    MAX-ACCESS read-only
    STATUS     current
    DESCRIPTION
            "-- empty --"
    ::= { lcsStatusWlanMngmtClSteEvtTabEntry 14 }

-- {COLUMN} 1.3.6.1.4.1.2356.11.1.73.123.5.1.15
lcsStatusWlanMngmtClSteEvtTabEntryFrequencyBand OBJECT-TYPE
    SYNTAX     INTEGER {
                  eDefaultBand (0),
                  e24ghz (1),
                  e5ghz (2),
                  eOff (3),
                  eUnmanaged (4),
                  eAuto (255)
            }
    MAX-ACCESS read-only
    STATUS     current
    DESCRIPTION
            "-- empty --"
    ::= { lcsStatusWlanMngmtClSteEvtTabEntry 15 }

-- {COLUMN} 1.3.6.1.4.1.2356.11.1.73.123.5.1.16
lcsStatusWlanMngmtClSteEvtTabEntryClientSteeringProfile OBJECT-TYPE
    SYNTAX     DisplayString (SIZE(0..255))
    MAX-ACCESS read-only
    STATUS     current
    DESCRIPTION
            "-- empty --"
    ::= { lcsStatusWlanMngmtClSteEvtTabEntry 16 }

-- {COLUMN} 1.3.6.1.4.1.2356.11.1.73.123.5.1.17
lcsStatusWlanMngmtClSteEvtTabEntrySignalStrengthWeighting OBJECT-TYPE
    SYNTAX     Integer32 (0..2147483647)
    MAX-ACCESS read-only
    STATUS     current
    DESCRIPTION
            "-- empty --"
    ::= { lcsStatusWlanMngmtClSteEvtTabEntry 17 }

-- {COLUMN} 1.3.6.1.4.1.2356.11.1.73.123.5.1.18
lcsStatusWlanMngmtClSteEvtTabEntryAssociatedClientsWeighting OBJECT-TYPE
    SYNTAX     Integer32 (0..2147483647)
    MAX-ACCESS read-only
    STATUS     current
    DESCRIPTION
            "-- empty --"
    ::= { lcsStatusWlanMngmtClSteEvtTabEntry 18 }

-- {COLUMN} 1.3.6.1.4.1.2356.11.1.73.123.5.1.19
lcsStatusWlanMngmtClSteEvtTabEntryFrequencyBandWeighting OBJECT-TYPE
    SYNTAX     Integer32 (0..2147483647)
    MAX-ACCESS read-only
    STATUS     current
    DESCRIPTION
            "-- empty --"
    ::= { lcsStatusWlanMngmtClSteEvtTabEntry 19 }

-- {COLUMN} 1.3.6.1.4.1.2356.11.1.73.123.5.1.20
lcsStatusWlanMngmtClSteEvtTabEntryName OBJECT-TYPE
    SYNTAX     DisplayString (SIZE(0..255))
    MAX-ACCESS read-only
    STATUS     current
    DESCRIPTION
            "-- empty --"
    ::= { lcsStatusWlanMngmtClSteEvtTabEntry 20 }

-- {TABLE} 1.3.6.1.4.1.2356.11.1.73.123.6
lcsStatusWlanMngmtClSteApInfoTable OBJECT-TYPE
    SYNTAX     SEQUENCE OF LcsStatusWlanMngmtClSteApInfoEntry
    MAX-ACCESS not-accessible
    STATUS     current
    DESCRIPTION
            "-- empty --"
    ::= { lcsStatusWlanMngmtClSte 6 }

-- {ROW} 1.3.6.1.4.1.2356.11.1.73.123.6.1
lcsStatusWlanMngmtClSteApInfoEntry OBJECT-TYPE
    SYNTAX     LcsStatusWlanMngmtClSteApInfoEntry
    MAX-ACCESS not-accessible
    STATUS     current
    DESCRIPTION
            ""
    INDEX {
            lcsStatusWlanMngmtClSteApInfoEntryApLanMac,
            lcsStatusWlanMngmtClSteApInfoEntryInterface
          }
    ::= { lcsStatusWlanMngmtClSteApInfoTable 1 }

LcsStatusWlanMngmtClSteApInfoEntry ::= SEQUENCE {
            lcsStatusWlanMngmtClSteApInfoEntryApLanMac MacAddress,
            lcsStatusWlanMngmtClSteApInfoEntryInterface Integer32,
            lcsStatusWlanMngmtClSteApInfoEntryClientSteeringProfile DisplayString,
            lcsStatusWlanMngmtClSteApInfoEntrySignalStrengthWeighting Integer32,
            lcsStatusWlanMngmtClSteApInfoEntryAssociatedClientsWeighting Integer32,
            lcsStatusWlanMngmtClSteApInfoEntryFrequencyBandWeighting Integer32,
            lcsStatusWlanMngmtClSteApInfoEntryAssociatedClients Integer32
    }

-- {COLUMN} 1.3.6.1.4.1.2356.11.1.73.123.6.1.1
lcsStatusWlanMngmtClSteApInfoEntryApLanMac OBJECT-TYPE
    SYNTAX     MacAddress
    MAX-ACCESS read-only
    STATUS     current
    DESCRIPTION
            "-- empty --"
    ::= { lcsStatusWlanMngmtClSteApInfoEntry 1 }

-- {COLUMN} 1.3.6.1.4.1.2356.11.1.73.123.6.1.2
lcsStatusWlanMngmtClSteApInfoEntryInterface OBJECT-TYPE
    SYNTAX     Integer32 (0..255)
    MAX-ACCESS read-only
    STATUS     current
    DESCRIPTION
            "-- empty --"
    ::= { lcsStatusWlanMngmtClSteApInfoEntry 2 }

-- {COLUMN} 1.3.6.1.4.1.2356.11.1.73.123.6.1.3
lcsStatusWlanMngmtClSteApInfoEntryClientSteeringProfile OBJECT-TYPE
    SYNTAX     DisplayString (SIZE(0..255))
    MAX-ACCESS read-only
    STATUS     current
    DESCRIPTION
            "-- empty --"
    ::= { lcsStatusWlanMngmtClSteApInfoEntry 3 }

-- {COLUMN} 1.3.6.1.4.1.2356.11.1.73.123.6.1.4
lcsStatusWlanMngmtClSteApInfoEntrySignalStrengthWeighting OBJECT-TYPE
    SYNTAX     Integer32 (0..2147483647)
    MAX-ACCESS read-only
    STATUS     current
    DESCRIPTION
            "-- empty --"
    ::= { lcsStatusWlanMngmtClSteApInfoEntry 4 }

-- {COLUMN} 1.3.6.1.4.1.2356.11.1.73.123.6.1.5
lcsStatusWlanMngmtClSteApInfoEntryAssociatedClientsWeighting OBJECT-TYPE
    SYNTAX     Integer32 (0..2147483647)
    MAX-ACCESS read-only
    STATUS     current
    DESCRIPTION
            "-- empty --"
    ::= { lcsStatusWlanMngmtClSteApInfoEntry 5 }

-- {COLUMN} 1.3.6.1.4.1.2356.11.1.73.123.6.1.6
lcsStatusWlanMngmtClSteApInfoEntryFrequencyBandWeighting OBJECT-TYPE
    SYNTAX     Integer32 (0..2147483647)
    MAX-ACCESS read-only
    STATUS     current
    DESCRIPTION
            "-- empty --"
    ::= { lcsStatusWlanMngmtClSteApInfoEntry 6 }

-- {COLUMN} 1.3.6.1.4.1.2356.11.1.73.123.6.1.7
lcsStatusWlanMngmtClSteApInfoEntryAssociatedClients OBJECT-TYPE
    SYNTAX     Integer32 (0..255)
    MAX-ACCESS read-only
    STATUS     current
    DESCRIPTION
            "-- empty --"
    ::= { lcsStatusWlanMngmtClSteApInfoEntry 7 }

-- {NODE} 1.3.6.1.4.1.2356.11.1.73.123.7
lcsStatusWlanMngmtClSteAvgStatAll OBJECT IDENTIFIER ::= { lcsStatusWlanMngmtClSte 7 }

-- {SCALAR} 1.3.6.1.4.1.2356.11.1.73.123.7.1
lcsStatusWlanMngmtClSteAvgStatAllMedianAssociationDelay OBJECT-TYPE
    SYNTAX     Integer32 (0..2147483647)
    MAX-ACCESS read-only
    STATUS     current
    DESCRIPTION
            "-- empty --"
    ::= { lcsStatusWlanMngmtClSteAvgStatAll 1 }

-- {SCALAR} 1.3.6.1.4.1.2356.11.1.73.123.7.2
lcsStatusWlanMngmtClSteAvgStatAllMedianRoamingDelay OBJECT-TYPE
    SYNTAX     Integer32 (0..2147483647)
    MAX-ACCESS read-only
    STATUS     current
    DESCRIPTION
            "-- empty --"
    ::= { lcsStatusWlanMngmtClSteAvgStatAll 2 }

-- {SCALAR} 1.3.6.1.4.1.2356.11.1.73.123.7.3
lcsStatusWlanMngmtClSteAvgStatAllMinAssociationDelay OBJECT-TYPE
    SYNTAX     Integer32 (0..2147483647)
    MAX-ACCESS read-only
    STATUS     current
    DESCRIPTION
            "-- empty --"
    ::= { lcsStatusWlanMngmtClSteAvgStatAll 3 }

-- {SCALAR} 1.3.6.1.4.1.2356.11.1.73.123.7.4
lcsStatusWlanMngmtClSteAvgStatAllMaxAssociationDelay OBJECT-TYPE
    SYNTAX     Integer32 (0..2147483647)
    MAX-ACCESS read-only
    STATUS     current
    DESCRIPTION
            "-- empty --"
    ::= { lcsStatusWlanMngmtClSteAvgStatAll 4 }

-- {SCALAR} 1.3.6.1.4.1.2356.11.1.73.123.7.5
lcsStatusWlanMngmtClSteAvgStatAllNumberOfForcedRoamingEvents OBJECT-TYPE
    SYNTAX     Integer32 (0..2147483647)
    MAX-ACCESS read-only
    STATUS     current
    DESCRIPTION
            "-- empty --"
    ::= { lcsStatusWlanMngmtClSteAvgStatAll 5 }

-- {SCALAR} 1.3.6.1.4.1.2356.11.1.73.123.7.6
lcsStatusWlanMngmtClSteAvgStatAllNumberOfUnsteerableAssociations OBJECT-TYPE
    SYNTAX     Integer32 (0..2147483647)
    MAX-ACCESS read-only
    STATUS     current
    DESCRIPTION
            "-- empty --"
    ::= { lcsStatusWlanMngmtClSteAvgStatAll 6 }

-- {SCALAR} 1.3.6.1.4.1.2356.11.1.73.123.7.7
lcsStatusWlanMngmtClSteAvgStatAllAverageSignalStrength OBJECT-TYPE
    SYNTAX     Integer32 (0..2147483647)
    MAX-ACCESS read-only
    STATUS     current
    DESCRIPTION
            "-- empty --"
    ::= { lcsStatusWlanMngmtClSteAvgStatAll 7 }

-- {SCALAR} 1.3.6.1.4.1.2356.11.1.73.123.7.10
lcsStatusWlanMngmtClSteAvgStatAllMinRoamingDelay OBJECT-TYPE
    SYNTAX     Integer32 (0..2147483647)
    MAX-ACCESS read-only
    STATUS     current
    DESCRIPTION
            "-- empty --"
    ::= { lcsStatusWlanMngmtClSteAvgStatAll 10 }

-- {SCALAR} 1.3.6.1.4.1.2356.11.1.73.123.7.11
lcsStatusWlanMngmtClSteAvgStatAllMaxRoamingDelay OBJECT-TYPE
    SYNTAX     Integer32 (0..2147483647)
    MAX-ACCESS read-only
    STATUS     current
    DESCRIPTION
            "-- empty --"
    ::= { lcsStatusWlanMngmtClSteAvgStatAll 11 }

-- {NODE} 1.3.6.1.4.1.2356.11.1.73.123.8
lcsStatusWlanMngmtClSteAvgStatFiv OBJECT IDENTIFIER ::= { lcsStatusWlanMngmtClSte 8 }

-- {SCALAR} 1.3.6.1.4.1.2356.11.1.73.123.8.1
lcsStatusWlanMngmtClSteAvgStatFivMedianAssociationDelay OBJECT-TYPE
    SYNTAX     Integer32 (0..2147483647)
    MAX-ACCESS read-only
    STATUS     current
    DESCRIPTION
            "-- empty --"
    ::= { lcsStatusWlanMngmtClSteAvgStatFiv 1 }

-- {SCALAR} 1.3.6.1.4.1.2356.11.1.73.123.8.2
lcsStatusWlanMngmtClSteAvgStatFivMedianRoamingDelay OBJECT-TYPE
    SYNTAX     Integer32 (0..2147483647)
    MAX-ACCESS read-only
    STATUS     current
    DESCRIPTION
            "-- empty --"
    ::= { lcsStatusWlanMngmtClSteAvgStatFiv 2 }

-- {SCALAR} 1.3.6.1.4.1.2356.11.1.73.123.8.3
lcsStatusWlanMngmtClSteAvgStatFivMinAssociationDelay OBJECT-TYPE
    SYNTAX     Integer32 (0..2147483647)
    MAX-ACCESS read-only
    STATUS     current
    DESCRIPTION
            "-- empty --"
    ::= { lcsStatusWlanMngmtClSteAvgStatFiv 3 }

-- {SCALAR} 1.3.6.1.4.1.2356.11.1.73.123.8.4
lcsStatusWlanMngmtClSteAvgStatFivMaxAssociationDelay OBJECT-TYPE
    SYNTAX     Integer32 (0..2147483647)
    MAX-ACCESS read-only
    STATUS     current
    DESCRIPTION
            "-- empty --"
    ::= { lcsStatusWlanMngmtClSteAvgStatFiv 4 }

-- {SCALAR} 1.3.6.1.4.1.2356.11.1.73.123.8.5
lcsStatusWlanMngmtClSteAvgStatFivNumberOfForcedRoamingEvents OBJECT-TYPE
    SYNTAX     Integer32 (0..2147483647)
    MAX-ACCESS read-only
    STATUS     current
    DESCRIPTION
            "-- empty --"
    ::= { lcsStatusWlanMngmtClSteAvgStatFiv 5 }

-- {SCALAR} 1.3.6.1.4.1.2356.11.1.73.123.8.6
lcsStatusWlanMngmtClSteAvgStatFivNumberOfUnsteerableAssociations OBJECT-TYPE
    SYNTAX     Integer32 (0..2147483647)
    MAX-ACCESS read-only
    STATUS     current
    DESCRIPTION
            "-- empty --"
    ::= { lcsStatusWlanMngmtClSteAvgStatFiv 6 }

-- {SCALAR} 1.3.6.1.4.1.2356.11.1.73.123.8.7
lcsStatusWlanMngmtClSteAvgStatFivAverageSignalStrength OBJECT-TYPE
    SYNTAX     Integer32 (0..2147483647)
    MAX-ACCESS read-only
    STATUS     current
    DESCRIPTION
            "-- empty --"
    ::= { lcsStatusWlanMngmtClSteAvgStatFiv 7 }

-- {SCALAR} 1.3.6.1.4.1.2356.11.1.73.123.8.10
lcsStatusWlanMngmtClSteAvgStatFivMinRoamingDelay OBJECT-TYPE
    SYNTAX     Integer32 (0..2147483647)
    MAX-ACCESS read-only
    STATUS     current
    DESCRIPTION
            "-- empty --"
    ::= { lcsStatusWlanMngmtClSteAvgStatFiv 10 }

-- {SCALAR} 1.3.6.1.4.1.2356.11.1.73.123.8.11
lcsStatusWlanMngmtClSteAvgStatFivMaxRoamingDelay OBJECT-TYPE
    SYNTAX     Integer32 (0..2147483647)
    MAX-ACCESS read-only
    STATUS     current
    DESCRIPTION
            "-- empty --"
    ::= { lcsStatusWlanMngmtClSteAvgStatFiv 11 }

-- {SCALAR} 1.3.6.1.4.1.2356.11.1.73.123.9
lcsStatusWlanMngmtClSteAcquireStatisticalData OBJECT-TYPE
    SYNTAX     INTEGER {
                  eNo (0),
                  eYes (1)
            }
    MAX-ACCESS read-only
    STATUS     current
    DESCRIPTION
            "-- empty --"
    ::= { lcsStatusWlanMngmtClSte 9 }

-- {NODE} 1.3.6.1.4.1.2356.11.1.73.248
lcsStatusWlanMngmtWIds OBJECT IDENTIFIER ::= { lcsStatusWlanMngmt 248 }

-- {TABLE} 1.3.6.1.4.1.2356.11.1.73.248.1
lcsStatusWlanMngmtWIdsEventTableTable OBJECT-TYPE
    SYNTAX     SEQUENCE OF LcsStatusWlanMngmtWIdsEventTableEntry
    MAX-ACCESS not-accessible
    STATUS     current
    DESCRIPTION
            "-- empty --"
    ::= { lcsStatusWlanMngmtWIds 1 }

-- {ROW} 1.3.6.1.4.1.2356.11.1.73.248.1.1
lcsStatusWlanMngmtWIdsEventTableEntry OBJECT-TYPE
    SYNTAX     LcsStatusWlanMngmtWIdsEventTableEntry
    MAX-ACCESS not-accessible
    STATUS     current
    DESCRIPTION
            ""
    INDEX {
            lcsStatusWlanMngmtWIdsEventTableEntryMacAddress,
            lcsStatusWlanMngmtWIdsEventTableEntryEventType,
            lcsStatusWlanMngmtWIdsEventTableEntryId
          }
    ::= { lcsStatusWlanMngmtWIdsEventTableTable 1 }

LcsStatusWlanMngmtWIdsEventTableEntry ::= SEQUENCE {
            lcsStatusWlanMngmtWIdsEventTableEntryMacAddress MacAddress,
            lcsStatusWlanMngmtWIdsEventTableEntryEventType INTEGER,
            lcsStatusWlanMngmtWIdsEventTableEntryId Integer32,
            lcsStatusWlanMngmtWIdsEventTableEntryEventTime DisplayString,
            lcsStatusWlanMngmtWIdsEventTableEntryEventRate Integer32,
            lcsStatusWlanMngmtWIdsEventTableEntryInterface INTEGER,
            lcsStatusWlanMngmtWIdsEventTableEntryName DisplayString,
            lcsStatusWlanMngmtWIdsEventTableEntryLocaltime Integer32,
            lcsStatusWlanMngmtWIdsEventTableEntryAttackerMac MacAddress
    }

-- {COLUMN} 1.3.6.1.4.1.2356.11.1.73.248.1.1.1
lcsStatusWlanMngmtWIdsEventTableEntryMacAddress OBJECT-TYPE
    SYNTAX     MacAddress
    MAX-ACCESS read-only
    STATUS     current
    DESCRIPTION
            "-- empty --"
    ::= { lcsStatusWlanMngmtWIdsEventTableEntry 1 }

-- {COLUMN} 1.3.6.1.4.1.2356.11.1.73.248.1.1.2
lcsStatusWlanMngmtWIdsEventTableEntryEventType OBJECT-TYPE
    SYNTAX     INTEGER {
                  eEapolstart (1),
                  eProbebroad (2),
                  eDeauthenticatebroad (3),
                  eDeauthenticate (4),
                  eAssociatereq (5),
                  eReassociatereq (6),
                  eAuthenticate (7),
                  eDisassociate (8),
                  eBlockackAttack (9),
                  eDelba (10),
                  eNullDataDosAttack (11),
                  eNullDataPSAttack (12),
                  ePSPollAttack (13),
                  eSMPSAttack (14),
                  eDisassociatebroad (15),
                  ePrematureeapolsuccess (16),
                  ePrematureeapolfailure (17),
                  eGenericerror (18)
            }
    MAX-ACCESS read-only
    STATUS     current
    DESCRIPTION
            "-- empty --"
    ::= { lcsStatusWlanMngmtWIdsEventTableEntry 2 }

-- {COLUMN} 1.3.6.1.4.1.2356.11.1.73.248.1.1.3
lcsStatusWlanMngmtWIdsEventTableEntryId OBJECT-TYPE
    SYNTAX     Integer32 (0..2147483647)
    MAX-ACCESS read-only
    STATUS     current
    DESCRIPTION
            "-- empty --"
    ::= { lcsStatusWlanMngmtWIdsEventTableEntry 3 }

-- {COLUMN} 1.3.6.1.4.1.2356.11.1.73.248.1.1.4
lcsStatusWlanMngmtWIdsEventTableEntryEventTime OBJECT-TYPE
    SYNTAX     DisplayString (SIZE(0..255))
    MAX-ACCESS read-only
    STATUS     current
    DESCRIPTION
            "-- empty --"
    ::= { lcsStatusWlanMngmtWIdsEventTableEntry 4 }

-- {COLUMN} 1.3.6.1.4.1.2356.11.1.73.248.1.1.5
lcsStatusWlanMngmtWIdsEventTableEntryEventRate OBJECT-TYPE
    SYNTAX     Integer32 (0..2147483647)
    MAX-ACCESS read-only
    STATUS     current
    DESCRIPTION
            "-- empty --"
    ::= { lcsStatusWlanMngmtWIdsEventTableEntry 5 }

-- {COLUMN} 1.3.6.1.4.1.2356.11.1.73.248.1.1.6
lcsStatusWlanMngmtWIdsEventTableEntryInterface OBJECT-TYPE
    SYNTAX     INTEGER {
                  eWlan1 (0),
                  eWlan2 (1),
                  eAny (255)
            }
    MAX-ACCESS read-only
    STATUS     current
    DESCRIPTION
            "-- empty --"
    ::= { lcsStatusWlanMngmtWIdsEventTableEntry 6 }

-- {COLUMN} 1.3.6.1.4.1.2356.11.1.73.248.1.1.7
lcsStatusWlanMngmtWIdsEventTableEntryName OBJECT-TYPE
    SYNTAX     DisplayString (SIZE(0..255))
    MAX-ACCESS read-only
    STATUS     current
    DESCRIPTION
            "-- empty --"
    ::= { lcsStatusWlanMngmtWIdsEventTableEntry 7 }

-- {COLUMN} 1.3.6.1.4.1.2356.11.1.73.248.1.1.8
lcsStatusWlanMngmtWIdsEventTableEntryLocaltime OBJECT-TYPE
    SYNTAX     Integer32 (0..2147483647)
    MAX-ACCESS read-only
    STATUS     current
    DESCRIPTION
            "-- empty --"
    ::= { lcsStatusWlanMngmtWIdsEventTableEntry 8 }

-- {COLUMN} 1.3.6.1.4.1.2356.11.1.73.248.1.1.9
lcsStatusWlanMngmtWIdsEventTableEntryAttackerMac OBJECT-TYPE
    SYNTAX     MacAddress
    MAX-ACCESS read-only
    STATUS     current
    DESCRIPTION
            "-- empty --"
    ::= { lcsStatusWlanMngmtWIdsEventTableEntry 9 }

-- {TABLE} 1.3.6.1.4.1.2356.11.1.73.248.2
lcsStatusWlanMngmtWIdsAlarmsTable OBJECT-TYPE
    SYNTAX     SEQUENCE OF LcsStatusWlanMngmtWIdsAlarmsEntry
    MAX-ACCESS not-accessible
    STATUS     current
    DESCRIPTION
            "-- empty --"
    ::= { lcsStatusWlanMngmtWIds 2 }

-- {ROW} 1.3.6.1.4.1.2356.11.1.73.248.2.1
lcsStatusWlanMngmtWIdsAlarmsEntry OBJECT-TYPE
    SYNTAX     LcsStatusWlanMngmtWIdsAlarmsEntry
    MAX-ACCESS not-accessible
    STATUS     current
    DESCRIPTION
            ""
    INDEX {
            lcsStatusWlanMngmtWIdsAlarmsEntryMacAddress,
            lcsStatusWlanMngmtWIdsAlarmsEntryIfc,
            lcsStatusWlanMngmtWIdsAlarmsEntrySignature
          }
    ::= { lcsStatusWlanMngmtWIdsAlarmsTable 1 }

LcsStatusWlanMngmtWIdsAlarmsEntry ::= SEQUENCE {
            lcsStatusWlanMngmtWIdsAlarmsEntryMacAddress MacAddress,
            lcsStatusWlanMngmtWIdsAlarmsEntryIfc INTEGER,
            lcsStatusWlanMngmtWIdsAlarmsEntrySignature INTEGER,
            lcsStatusWlanMngmtWIdsAlarmsEntryName DisplayString,
            lcsStatusWlanMngmtWIdsAlarmsEntryCounter Integer32,
            lcsStatusWlanMngmtWIdsAlarmsEntryAlarmState INTEGER
    }

-- {COLUMN} 1.3.6.1.4.1.2356.11.1.73.248.2.1.1
lcsStatusWlanMngmtWIdsAlarmsEntryMacAddress OBJECT-TYPE
    SYNTAX     MacAddress
    MAX-ACCESS read-only
    STATUS     current
    DESCRIPTION
            "-- empty --"
    ::= { lcsStatusWlanMngmtWIdsAlarmsEntry 1 }

-- {COLUMN} 1.3.6.1.4.1.2356.11.1.73.248.2.1.2
lcsStatusWlanMngmtWIdsAlarmsEntryIfc OBJECT-TYPE
    SYNTAX     INTEGER {
                  eWlan1 (0),
                  eWlan2 (1),
                  eWlan3 (2),
                  eWlan4 (3)
            }
    MAX-ACCESS read-only
    STATUS     current
    DESCRIPTION
            "-- empty --"
    ::= { lcsStatusWlanMngmtWIdsAlarmsEntry 2 }

-- {COLUMN} 1.3.6.1.4.1.2356.11.1.73.248.2.1.3
lcsStatusWlanMngmtWIdsAlarmsEntrySignature OBJECT-TYPE
    SYNTAX     INTEGER {
                  eEapolstart (1),
                  eProbebroad (2),
                  eDeauthenticatebroad (3),
                  eDeauthenticate (4),
                  eAssociatereq (5),
                  eReassociatereq (6),
                  eAuthenticate (7),
                  eDisassociate (8),
                  eBlockackAttack (9),
                  eDelba (10),
                  eNullDataDosAttack (11),
                  eNullDataPSAttack (12),
                  ePSPollAttack (13),
                  eSMPSAttack (14),
                  eDisassociatebroad (15),
                  ePrematureeapolsuccess (16),
                  ePrematureeapolfailure (17),
                  eGenericerror (18)
            }
    MAX-ACCESS read-only
    STATUS     current
    DESCRIPTION
            "-- empty --"
    ::= { lcsStatusWlanMngmtWIdsAlarmsEntry 3 }

-- {COLUMN} 1.3.6.1.4.1.2356.11.1.73.248.2.1.4
lcsStatusWlanMngmtWIdsAlarmsEntryName OBJECT-TYPE
    SYNTAX     DisplayString (SIZE(0..64))
    MAX-ACCESS read-only
    STATUS     current
    DESCRIPTION
            "-- empty --"
    ::= { lcsStatusWlanMngmtWIdsAlarmsEntry 4 }

-- {COLUMN} 1.3.6.1.4.1.2356.11.1.73.248.2.1.5
lcsStatusWlanMngmtWIdsAlarmsEntryCounter OBJECT-TYPE
    SYNTAX     Integer32 (0..2147483647)
    MAX-ACCESS read-only
    STATUS     current
    DESCRIPTION
            "-- empty --"
    ::= { lcsStatusWlanMngmtWIdsAlarmsEntry 5 }

-- {COLUMN} 1.3.6.1.4.1.2356.11.1.73.248.2.1.6
lcsStatusWlanMngmtWIdsAlarmsEntryAlarmState OBJECT-TYPE
    SYNTAX     INTEGER {
                  eNone (0),
                  eLimitReached (1)
            }
    MAX-ACCESS read-only
    STATUS     current
    DESCRIPTION
            "-- empty --"
    ::= { lcsStatusWlanMngmtWIdsAlarmsEntry 6 }

-- {NODE} 1.3.6.1.4.1.2356.11.1.74
lcsStatusMcp OBJECT IDENTIFIER ::= { lcsStatus 74 }

-- {SCALAR} 1.3.6.1.4.1.2356.11.1.74.1
lcsStatusMcpMcpUmtsState OBJECT-TYPE
    SYNTAX     INTEGER {
                  eUnknown (0),
                  eWaitForUsbDevice (1),
                  eRemoveUsbDevice (2),
                  eWaitForComPortDevice (3),
                  eRemoveComPortDevice (4),
                  eNormalOperation (5),
                  eRestart (6),
                  eDisabled (7)
            }
    MAX-ACCESS read-only
    STATUS     current
    DESCRIPTION
            ""
    ::= { lcsStatusMcp 1 }

-- {SCALAR} 1.3.6.1.4.1.2356.11.1.74.2
lcsStatusMcpUsbReinitCount OBJECT-TYPE
    SYNTAX     Integer32 (0..2147483647)
    MAX-ACCESS read-only
    STATUS     current
    DESCRIPTION
            ""
    ::= { lcsStatusMcp 2 }

-- {SCALAR} 1.3.6.1.4.1.2356.11.1.74.3
lcsStatusMcpUsbReinitTryCount OBJECT-TYPE
    SYNTAX     Integer32 (0..2147483647)
    MAX-ACCESS read-only
    STATUS     current
    DESCRIPTION
            ""
    ::= { lcsStatusMcp 3 }

-- {NODE} 1.3.6.1.4.1.2356.11.1.75
lcsStatusVdsl OBJECT IDENTIFIER ::= { lcsStatus 75 }

-- {SCALAR} 1.3.6.1.4.1.2356.11.1.75.1
lcsStatusVdslLineState OBJECT-TYPE
    SYNTAX     INTEGER {
                  eUnknown (0),
                  eDown (1),
                  eIdle (2),
                  eHandshake (3),
                  eTraining (4),
                  eShowtime (5),
                  eShutdown (6)
            }
    MAX-ACCESS read-only
    STATUS     current
    DESCRIPTION
            ""
    ::= { lcsStatusVdsl 1 }

-- {SCALAR} 1.3.6.1.4.1.2356.11.1.75.2
lcsStatusVdslLineType OBJECT-TYPE
    SYNTAX     DisplayString
    MAX-ACCESS read-only
    STATUS     current
    DESCRIPTION
            ""
    ::= { lcsStatusVdsl 2 }

-- {SCALAR} 1.3.6.1.4.1.2356.11.1.75.3
lcsStatusVdslStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGFast (42),
                  eAdsl2Lite (54),
                  eGVector (254),
                  eUnknown (255)
            }
    MAX-ACCESS read-only
    STATUS     current
    DESCRIPTION
            ""
    ::= { lcsStatusVdsl 3 }

-- {SCALAR} 1.3.6.1.4.1.2356.11.1.75.4
lcsStatusVdslDataRateUpstreamKbps OBJECT-TYPE
    SYNTAX     Integer32 (0..2147483647)
    MAX-ACCESS read-only
    STATUS     current
    DESCRIPTION
            ""
    ::= { lcsStatusVdsl 4 }

-- {SCALAR} 1.3.6.1.4.1.2356.11.1.75.5
lcsStatusVdslDataRateDownstreamKbps OBJECT-TYPE
    SYNTAX     Integer32 (0..2147483647)
    MAX-ACCESS read-only
    STATUS     current
    DESCRIPTION
            ""
    ::= { lcsStatusVdsl 5 }

-- {SCALAR} 1.3.6.1.4.1.2356.11.1.75.6
lcsStatusVdslSnrDownstreamDb OBJECT-TYPE
    SYNTAX     DisplayString (SIZE(0..3))
    MAX-ACCESS read-only
    STATUS     current
    DESCRIPTION
            ""
    ::= { lcsStatusVdsl 6 }

-- {SCALAR} 1.3.6.1.4.1.2356.11.1.75.7
lcsStatusVdslSnrUpstreamDb OBJECT-TYPE
    SYNTAX     DisplayString (SIZE(0..3))
    MAX-ACCESS read-only
    STATUS     current
    DESCRIPTION
            ""
    ::= { lcsStatusVdsl 7 }

-- {SCALAR} 1.3.6.1.4.1.2356.11.1.75.8
lcsStatusVdslAttenuationDownstreamDb OBJECT-TYPE
    SYNTAX     DisplayString (SIZE(0..3))
    MAX-ACCESS read-only
    STATUS     current
    DESCRIPTION
            ""
    ::= { lcsStatusVdsl 8 }

-- {SCALAR} 1.3.6.1.4.1.2356.11.1.75.9
lcsStatusVdslAttenuationUpstreamDb OBJECT-TYPE
    SYNTAX     DisplayString (SIZE(0..3))
    MAX-ACCESS read-only
    STATUS     current
    DESCRIPTION
            ""
    ::= { lcsStatusVdsl 9 }

-- {SCALAR} 1.3.6.1.4.1.2356.11.1.75.10
lcsStatusVdslInterleaveUpstreamMs OBJECT-TYPE
    SYNTAX     DisplayString
    MAX-ACCESS read-only
    STATUS     current
    DESCRIPTION
            ""
    ::= { lcsStatusVdsl 10 }

-- {SCALAR} 1.3.6.1.4.1.2356.11.1.75.11
lcsStatusVdslInterleaveDownstreamMs OBJECT-TYPE
    SYNTAX     DisplayString
    MAX-ACCESS read-only
    STATUS     current
    DESCRIPTION
            ""
    ::= { lcsStatusVdsl 11 }

-- {TABLE} 1.3.6.1.4.1.2356.11.1.75.12
lcsStatusVdslConnectionHistoryTable OBJECT-TYPE
    SYNTAX     SEQUENCE OF LcsStatusVdslConnectionHistoryEntry
    MAX-ACCESS not-accessible
    STATUS     current
    DESCRIPTION
            ""
    ::= { lcsStatusVdsl 12 }

-- {ROW} 1.3.6.1.4.1.2356.11.1.75.12.1
lcsStatusVdslConnectionHistoryEntry OBJECT-TYPE
    SYNTAX     LcsStatusVdslConnectionHistoryEntry
    MAX-ACCESS not-accessible
    STATUS     current
    DESCRIPTION
            ""
    INDEX {
            lcsStatusVdslConnectionHistoryEntryIndex
          }
    ::= { lcsStatusVdslConnectionHistoryTable 1 }

LcsStatusVdslConnectionHistoryEntry ::= SEQUENCE {
            lcsStatusVdslConnectionHistoryEntrySyncTime Gauge32,
            lcsStatusVdslConnectionHistoryEntryStandard INTEGER,
            lcsStatusVdslConnectionHistoryEntryDsDatarate Integer32,
            lcsStatusVdslConnectionHistoryEntryUsDatarate Integer32,
            lcsStatusVdslConnectionHistoryEntryDsAttenuation DisplayString,
            lcsStatusVdslConnectionHistoryEntryDsSnr DisplayString,
            lcsStatusVdslConnectionHistoryEntryDisconnectTime Gauge32,
            lcsStatusVdslConnectionHistoryEntryIndex Integer32,
            lcsStatusVdslConnectionHistoryEntryReason INTEGER,
            lcsStatusVdslConnectionHistoryEntryUsAttenuation DisplayString,
            lcsStatusVdslConnectionHistoryEntryUsSnr DisplayString,
            lcsStatusVdslConnectionHistoryEntryLinecode DisplayString,
            lcsStatusVdslConnectionHistoryEntryVdslProfile INTEGER,
            lcsStatusVdslConnectionHistoryEntryVectoring INTEGER
    }

-- {COLUMN} 1.3.6.1.4.1.2356.11.1.75.12.1.1
lcsStatusVdslConnectionHistoryEntrySyncTime OBJECT-TYPE
    SYNTAX     Gauge32
    MAX-ACCESS read-only
    STATUS     current
    DESCRIPTION
            ""
    ::= { lcsStatusVdslConnectionHistoryEntry 1 }

-- {COLUMN} 1.3.6.1.4.1.2356.11.1.75.12.1.2
lcsStatusVdslConnectionHistoryEntryStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGFast (42),
                  eAdsl2Lite (54),
                  eGVector (254),
                  eUnknown (255)
            }
    MAX-ACCESS read-only
    STATUS     current
    DESCRIPTION
            ""
    ::= { lcsStatusVdslConnectionHistoryEntry 2 }

-- {COLUMN} 1.3.6.1.4.1.2356.11.1.75.12.1.3
lcsStatusVdslConnectionHistoryEntryDsDatarate OBJECT-TYPE
    SYNTAX     Integer32 (0..2147483647)
    MAX-ACCESS read-only
    STATUS     current
    DESCRIPTION
            ""
    ::= { lcsStatusVdslConnectionHistoryEntry 3 }

-- {COLUMN} 1.3.6.1.4.1.2356.11.1.75.12.1.4
lcsStatusVdslConnectionHistoryEntryUsDatarate OBJECT-TYPE
    SYNTAX     Integer32 (0..2147483647)
    MAX-ACCESS read-only
    STATUS     current
    DESCRIPTION
            ""
    ::= { lcsStatusVdslConnectionHistoryEntry 4 }

-- {COLUMN} 1.3.6.1.4.1.2356.11.1.75.12.1.5
lcsStatusVdslConnectionHistoryEntryDsAttenuation OBJECT-TYPE
    SYNTAX     DisplayString (SIZE(0..1))
    MAX-ACCESS read-only
    STATUS     current
    DESCRIPTION
            ""
    ::= { lcsStatusVdslConnectionHistoryEntry 5 }

-- {COLUMN} 1.3.6.1.4.1.2356.11.1.75.12.1.6
lcsStatusVdslConnectionHistoryEntryDsSnr OBJECT-TYPE
    SYNTAX     DisplayString (SIZE(0..1))
    MAX-ACCESS read-only
    STATUS     current
    DESCRIPTION
            ""
    ::= { lcsStatusVdslConnectionHistoryEntry 6 }

-- {COLUMN} 1.3.6.1.4.1.2356.11.1.75.12.1.7
lcsStatusVdslConnectionHistoryEntryDisconnectTime OBJECT-TYPE
    SYNTAX     Gauge32
    MAX-ACCESS read-only
    STATUS     current
    DESCRIPTION
            ""
    ::= { lcsStatusVdslConnectionHistoryEntry 7 }

-- {COLUMN} 1.3.6.1.4.1.2356.11.1.75.12.1.8
lcsStatusVdslConnectionHistoryEntryIndex OBJECT-TYPE
    SYNTAX     Integer32 (0..2147483647)
    MAX-ACCESS read-only
    STATUS     current
    DESCRIPTION
            ""
    ::= { lcsStatusVdslConnectionHistoryEntry 8 }

-- {COLUMN} 1.3.6.1.4.1.2356.11.1.75.12.1.9
lcsStatusVdslConnectionHistoryEntryReason OBJECT-TYPE
    SYNTAX     INTEGER {
                  eModemReboot (1),
                  eRetrain (2),
                  eSilence (3),
                  eLineError (4),
                  eProtocol (5),
                  eLineType (6),
                  eAutomode (7),
                  eTimeout (8),
                  eVcParameters (13)
            }
    MAX-ACCESS read-only
    STATUS     current
    DESCRIPTION
            ""
    ::= { lcsStatusVdslConnectionHistoryEntry 9 }

-- {COLUMN} 1.3.6.1.4.1.2356.11.1.75.12.1.10
lcsStatusVdslConnectionHistoryEntryUsAttenuation OBJECT-TYPE
    SYNTAX     DisplayString (SIZE(0..1))
    MAX-ACCESS read-only
    STATUS     current
    DESCRIPTION
            ""
    ::= { lcsStatusVdslConnectionHistoryEntry 10 }

-- {COLUMN} 1.3.6.1.4.1.2356.11.1.75.12.1.11
lcsStatusVdslConnectionHistoryEntryUsSnr OBJECT-TYPE
    SYNTAX     DisplayString (SIZE(0..1))
    MAX-ACCESS read-only
    STATUS     current
    DESCRIPTION
            ""
    ::= { lcsStatusVdslConnectionHistoryEntry 11 }

-- {COLUMN} 1.3.6.1.4.1.2356.11.1.75.12.1.12
lcsStatusVdslConnectionHistoryEntryLinecode OBJECT-TYPE
    SYNTAX     DisplayString (SIZE(0..1))
    MAX-ACCESS read-only
    STATUS     current
    DESCRIPTION
            "-- empty --"
    ::= { lcsStatusVdslConnectionHistoryEntry 12 }

-- {COLUMN} 1.3.6.1.4.1.2356.11.1.75.12.1.13
lcsStatusVdslConnectionHistoryEntryVdslProfile OBJECT-TYPE
    SYNTAX     INTEGER {
                  eUnknown (0),
                  e8a (1),
                  e8b (2),
                  e8c (3),
                  e8d (4),
                  e12a (5),
                  e12b (6),
                  e17a (7),
                  e30a (8),
                  e35b (9)
            }
    MAX-ACCESS read-only
    STATUS     current
    DESCRIPTION
            ""
    ::= { lcsStatusVdslConnectionHistoryEntry 13 }

-- {COLUMN} 1.3.6.1.4.1.2356.11.1.75.12.1.14
lcsStatusVdslConnectionHistoryEntryVectoring OBJECT-TYPE
    SYNTAX     INTEGER {
                  eNo (1),
                  eYes (2),
                  eFriendly (3)
            }
    MAX-ACCESS read-only
    STATUS     current
    DESCRIPTION
            "-- empty --"
    ::= { lcsStatusVdslConnectionHistoryEntry 14 }

-- {SCALAR} 1.3.6.1.4.1.2356.11.1.75.13
lcsStatusVdslRetrain OBJECT-TYPE
    SYNTAX     DisplayString
    MAX-ACCESS read-write
    STATUS     current
    DESCRIPTION
            ""
    ::= { lcsStatusVdsl 13 }

-- {SCALAR} 1.3.6.1.4.1.2356.11.1.75.14
lcsStatusVdslDslamChipsetManufacturer OBJECT-TYPE
    SYNTAX     DisplayString (SIZE(0..63))
    MAX-ACCESS read-only
    STATUS     current
    DESCRIPTION
            ""
    ::= { lcsStatusVdsl 14 }

-- {SCALAR} 1.3.6.1.4.1.2356.11.1.75.23
lcsStatusVdslModemType OBJECT-TYPE
    SYNTAX     DisplayString
    MAX-ACCESS read-only
    STATUS     current
    DESCRIPTION
            "-- empty --"
    ::= { lcsStatusVdsl 23 }

-- {NODE} 1.3.6.1.4.1.2356.11.1.75.25
lcsStatusVdslAdvanced OBJECT IDENTIFIER ::= { lcsStatusVdsl 25 }

-- {SCALAR} 1.3.6.1.4.1.2356.11.1.75.25.1
lcsStatusVdslAdvancedLineState OBJECT-TYPE
    SYNTAX     INTEGER {
                  eUnknown (0),
                  eDown (1),
                  eIdle (2),
                  eHandshake (3),
                  eTraining (4),
                  eShowtime (5),
                  eShutdown (6)
            }
    MAX-ACCESS read-only
    STATUS     current
    DESCRIPTION
            ""
    ::= { lcsStatusVdslAdvanced 1 }

-- {SCALAR} 1.3.6.1.4.1.2356.11.1.75.25.2
lcsStatusVdslAdvancedStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGFast (42),
                  eAdsl2Lite (54),
                  eGVector (254),
                  eUnknown (255)
            }
    MAX-ACCESS read-only
    STATUS     current
    DESCRIPTION
            ""
    ::= { lcsStatusVdslAdvanced 2 }

-- {SCALAR} 1.3.6.1.4.1.2356.11.1.75.25.3
lcsStatusVdslAdvancedDsDataRateKbps OBJECT-TYPE
    SYNTAX     Integer32 (0..2147483647)
    MAX-ACCESS read-only
    STATUS     current
    DESCRIPTION
            ""
    ::= { lcsStatusVdslAdvanced 3 }

-- {SCALAR} 1.3.6.1.4.1.2356.11.1.75.25.4
lcsStatusVdslAdvancedDsSnrMarginDb OBJECT-TYPE
    SYNTAX     DisplayString (SIZE(0..3))
    MAX-ACCESS read-only
    STATUS     current
    DESCRIPTION
            ""
    ::= { lcsStatusVdslAdvanced 4 }

-- {SCALAR} 1.3.6.1.4.1.2356.11.1.75.25.5
lcsStatusVdslAdvancedDsLineAttenuationDb OBJECT-TYPE
    SYNTAX     DisplayString (SIZE(0..3))
    MAX-ACCESS read-only
    STATUS     current
    DESCRIPTION
            ""
    ::= { lcsStatusVdslAdvanced 5 }

-- {SCALAR} 1.3.6.1.4.1.2356.11.1.75.25.6
lcsStatusVdslAdvancedDsInterleaveMs OBJECT-TYPE
    SYNTAX     DisplayString
    MAX-ACCESS read-only
    STATUS     current
    DESCRIPTION
            ""
    ::= { lcsStatusVdslAdvanced 6 }

-- {TABLE} 1.3.6.1.4.1.2356.11.1.75.25.13
lcsStatusVdslAdvancedDsBitLoadingTable OBJECT-TYPE
    SYNTAX     SEQUENCE OF LcsStatusVdslAdvancedDsBitLoadingEntry
    MAX-ACCESS not-accessible
    STATUS     current
    DESCRIPTION
            ""
    ::= { lcsStatusVdslAdvanced 13 }

-- {ROW} 1.3.6.1.4.1.2356.11.1.75.25.13.1
lcsStatusVdslAdvancedDsBitLoadingEntry OBJECT-TYPE
    SYNTAX     LcsStatusVdslAdvancedDsBitLoadingEntry
    MAX-ACCESS not-accessible
    STATUS     current
    DESCRIPTION
            ""
    INDEX {
            lcsStatusVdslAdvancedDsBitLoadingEntryBinNumber
          }
    ::= { lcsStatusVdslAdvancedDsBitLoadingTable 1 }

LcsStatusVdslAdvancedDsBitLoadingEntry ::= SEQUENCE {
            lcsStatusVdslAdvancedDsBitLoadingEntryBinNumber DisplayString,
            lcsStatusVdslAdvancedDsBitLoadingEntryX0 Integer32,
            lcsStatusVdslAdvancedDsBitLoadingEntryX1 Integer32,
            lcsStatusVdslAdvancedDsBitLoadingEntryX2 Integer32,
            lcsStatusVdslAdvancedDsBitLoadingEntryX3 Integer32,
            lcsStatusVdslAdvancedDsBitLoadingEntryX4 Integer32,
            lcsStatusVdslAdvancedDsBitLoadingEntryX5 Integer32,
            lcsStatusVdslAdvancedDsBitLoadingEntryX6 Integer32,
            lcsStatusVdslAdvancedDsBitLoadingEntryX7 Integer32,
            lcsStatusVdslAdvancedDsBitLoadingEntryX8 Integer32,
            lcsStatusVdslAdvancedDsBitLoadingEntryX9 Integer32,
            lcsStatusVdslAdvancedDsBitLoadingEntryGraph DisplayString
    }

-- {COLUMN} 1.3.6.1.4.1.2356.11.1.75.25.13.1.1
lcsStatusVdslAdvancedDsBitLoadingEntryBinNumber OBJECT-TYPE
    SYNTAX     DisplayString (SIZE(0..255))
    MAX-ACCESS read-only
    STATUS     current
    DESCRIPTION
            ""
    ::= { lcsStatusVdslAdvancedDsBitLoadingEntry 1 }

-- {COLUMN} 1.3.6.1.4.1.2356.11.1.75.25.13.1.2
lcsStatusVdslAdvancedDsBitLoadingEntryX0 OBJECT-TYPE
    SYNTAX     Integer32 (0..2147483647)
    MAX-ACCESS read-only
    STATUS     current
    DESCRIPTION
            ""
    ::= { lcsStatusVdslAdvancedDsBitLoadingEntry 2 }

-- {COLUMN} 1.3.6.1.4.1.2356.11.1.75.25.13.1.3
lcsStatusVdslAdvancedDsBitLoadingEntryX1 OBJECT-TYPE
    SYNTAX     Integer32 (0..2147483647)
    MAX-ACCESS read-only
    STATUS     current
    DESCRIPTION
            ""
    ::= { lcsStatusVdslAdvancedDsBitLoadingEntry 3 }

-- {COLUMN} 1.3.6.1.4.1.2356.11.1.75.25.13.1.4
lcsStatusVdslAdvancedDsBitLoadingEntryX2 OBJECT-TYPE
    SYNTAX     Integer32 (0..2147483647)
    MAX-ACCESS read-only
    STATUS     current
    DESCRIPTION
            ""
    ::= { lcsStatusVdslAdvancedDsBitLoadingEntry 4 }

-- {COLUMN} 1.3.6.1.4.1.2356.11.1.75.25.13.1.5
lcsStatusVdslAdvancedDsBitLoadingEntryX3 OBJECT-TYPE
    SYNTAX     Integer32 (0..2147483647)
    MAX-ACCESS read-only
    STATUS     current
    DESCRIPTION
            ""
    ::= { lcsStatusVdslAdvancedDsBitLoadingEntry 5 }

-- {COLUMN} 1.3.6.1.4.1.2356.11.1.75.25.13.1.6
lcsStatusVdslAdvancedDsBitLoadingEntryX4 OBJECT-TYPE
    SYNTAX     Integer32 (0..2147483647)
    MAX-ACCESS read-only
    STATUS     current
    DESCRIPTION
            ""
    ::= { lcsStatusVdslAdvancedDsBitLoadingEntry 6 }

-- {COLUMN} 1.3.6.1.4.1.2356.11.1.75.25.13.1.7
lcsStatusVdslAdvancedDsBitLoadingEntryX5 OBJECT-TYPE
    SYNTAX     Integer32 (0..2147483647)
    MAX-ACCESS read-only
    STATUS     current
    DESCRIPTION
            ""
    ::= { lcsStatusVdslAdvancedDsBitLoadingEntry 7 }

-- {COLUMN} 1.3.6.1.4.1.2356.11.1.75.25.13.1.8
lcsStatusVdslAdvancedDsBitLoadingEntryX6 OBJECT-TYPE
    SYNTAX     Integer32 (0..2147483647)
    MAX-ACCESS read-only
    STATUS     current
    DESCRIPTION
            ""
    ::= { lcsStatusVdslAdvancedDsBitLoadingEntry 8 }

-- {COLUMN} 1.3.6.1.4.1.2356.11.1.75.25.13.1.9
lcsStatusVdslAdvancedDsBitLoadingEntryX7 OBJECT-TYPE
    SYNTAX     Integer32 (0..2147483647)
    MAX-ACCESS read-only
    STATUS     current
    DESCRIPTION
            ""
    ::= { lcsStatusVdslAdvancedDsBitLoadingEntry 9 }

-- {COLUMN} 1.3.6.1.4.1.2356.11.1.75.25.13.1.10
lcsStatusVdslAdvancedDsBitLoadingEntryX8 OBJECT-TYPE
    SYNTAX     Integer32 (0..2147483647)
    MAX-ACCESS read-only
    STATUS     current
    DESCRIPTION
            ""
    ::= { lcsStatusVdslAdvancedDsBitLoadingEntry 10 }

-- {COLUMN} 1.3.6.1.4.1.2356.11.1.75.25.13.1.11
lcsStatusVdslAdvancedDsBitLoadingEntryX9 OBJECT-TYPE
    SYNTAX     Integer32 (0..2147483647)
    MAX-ACCESS read-only
    STATUS     current
    DESCRIPTION
            ""
    ::= { lcsStatusVdslAdvancedDsBitLoadingEntry 11 }

-- {COLUMN} 1.3.6.1.4.1.2356.11.1.75.25.13.1.12
lcsStatusVdslAdvancedDsBitLoadingEntryGraph OBJECT-TYPE
    SYNTAX     DisplayString (SIZE(0..255))
    MAX-ACCESS read-only
    STATUS     current
    DESCRIPTION
            ""
    ::= { lcsStatusVdslAdvancedDsBitLoadingEntry 12 }

-- {SCALAR} 1.3.6.1.4.1.2356.11.1.75.25.15
lcsStatusVdslAdvancedUsDataRateKbps OBJECT-TYPE
    SYNTAX     Integer32 (0..2147483647)
    MAX-ACCESS read-only
    STATUS     current
    DESCRIPTION
            ""
    ::= { lcsStatusVdslAdvanced 15 }

-- {SCALAR} 1.3.6.1.4.1.2356.11.1.75.25.16
lcsStatusVdslAdvancedUsSnrMarginDb OBJECT-TYPE
    SYNTAX     DisplayString (SIZE(0..3))
    MAX-ACCESS read-only
    STATUS     current
    DESCRIPTION
            ""
    ::= { lcsStatusVdslAdvanced 16 }

-- {SCALAR} 1.3.6.1.4.1.2356.11.1.75.25.17
lcsStatusVdslAdvancedUsLineAttenuationDb OBJECT-TYPE
    SYNTAX     DisplayString (SIZE(0..3))
    MAX-ACCESS read-only
    STATUS     current
    DESCRIPTION
            ""
    ::= { lcsStatusVdslAdvanced 17 }

-- {SCALAR} 1.3.6.1.4.1.2356.11.1.75.25.18
lcsStatusVdslAdvancedUsInterleaveMs OBJECT-TYPE
    SYNTAX     DisplayString
    MAX-ACCESS read-only
    STATUS     current
    DESCRIPTION
            ""
    ::= { lcsStatusVdslAdvanced 18 }

-- {TABLE} 1.3.6.1.4.1.2356.11.1.75.25.25
lcsStatusVdslAdvancedUsBitLoadingTable OBJECT-TYPE
    SYNTAX     SEQUENCE OF LcsStatusVdslAdvancedUsBitLoadingEntry
    MAX-ACCESS not-accessible
    STATUS     current
    DESCRIPTION
            ""
    ::= { lcsStatusVdslAdvanced 25 }

-- {ROW} 1.3.6.1.4.1.2356.11.1.75.25.25.1
lcsStatusVdslAdvancedUsBitLoadingEntry OBJECT-TYPE
    SYNTAX     LcsStatusVdslAdvancedUsBitLoadingEntry
    MAX-ACCESS not-accessible
    STATUS     current
    DESCRIPTION
            ""
    INDEX {
            lcsStatusVdslAdvancedUsBitLoadingEntryBinNumber
          }
    ::= { lcsStatusVdslAdvancedUsBitLoadingTable 1 }

LcsStatusVdslAdvancedUsBitLoadingEntry ::= SEQUENCE {
            lcsStatusVdslAdvancedUsBitLoadingEntryBinNumber DisplayString,
            lcsStatusVdslAdvancedUsBitLoadingEntryX0 Integer32,
            lcsStatusVdslAdvancedUsBitLoadingEntryX1 Integer32,
            lcsStatusVdslAdvancedUsBitLoadingEntryX2 Integer32,
            lcsStatusVdslAdvancedUsBitLoadingEntryX3 Integer32,
            lcsStatusVdslAdvancedUsBitLoadingEntryX4 Integer32,
            lcsStatusVdslAdvancedUsBitLoadingEntryX5 Integer32,
            lcsStatusVdslAdvancedUsBitLoadingEntryX6 Integer32,
            lcsStatusVdslAdvancedUsBitLoadingEntryX7 Integer32,
            lcsStatusVdslAdvancedUsBitLoadingEntryX8 Integer32,
            lcsStatusVdslAdvancedUsBitLoadingEntryX9 Integer32,
            lcsStatusVdslAdvancedUsBitLoadingEntryGraph DisplayString
    }

-- {COLUMN} 1.3.6.1.4.1.2356.11.1.75.25.25.1.1
lcsStatusVdslAdvancedUsBitLoadingEntryBinNumber OBJECT-TYPE
    SYNTAX     DisplayString (SIZE(0..255))
    MAX-ACCESS read-only
    STATUS     current
    DESCRIPTION
            ""
    ::= { lcsStatusVdslAdvancedUsBitLoadingEntry 1 }

-- {COLUMN} 1.3.6.1.4.1.2356.11.1.75.25.25.1.2
lcsStatusVdslAdvancedUsBitLoadingEntryX0 OBJECT-TYPE
    SYNTAX     Integer32 (0..2147483647)
    MAX-ACCESS read-only
    STATUS     current
    DESCRIPTION
            ""
    ::= { lcsStatusVdslAdvancedUsBitLoadingEntry 2 }

-- {COLUMN} 1.3.6.1.4.1.2356.11.1.75.25.25.1.3
lcsStatusVdslAdvancedUsBitLoadingEntryX1 OBJECT-TYPE
    SYNTAX     Integer32 (0..2147483647)
    MAX-ACCESS read-only
    STATUS     current
    DESCRIPTION
            ""
    ::= { lcsStatusVdslAdvancedUsBitLoadingEntry 3 }

-- {COLUMN} 1.3.6.1.4.1.2356.11.1.75.25.25.1.4
lcsStatusVdslAdvancedUsBitLoadingEntryX2 OBJECT-TYPE
    SYNTAX     Integer32 (0..2147483647)
    MAX-ACCESS read-only
    STATUS     current
    DESCRIPTION
            ""
    ::= { lcsStatusVdslAdvancedUsBitLoadingEntry 4 }

-- {COLUMN} 1.3.6.1.4.1.2356.11.1.75.25.25.1.5
lcsStatusVdslAdvancedUsBitLoadingEntryX3 OBJECT-TYPE
    SYNTAX     Integer32 (0..2147483647)
    MAX-ACCESS read-only
    STATUS     current
    DESCRIPTION
            ""
    ::= { lcsStatusVdslAdvancedUsBitLoadingEntry 5 }

-- {COLUMN} 1.3.6.1.4.1.2356.11.1.75.25.25.1.6
lcsStatusVdslAdvancedUsBitLoadingEntryX4 OBJECT-TYPE
    SYNTAX     Integer32 (0..2147483647)
    MAX-ACCESS read-only
    STATUS     current
    DESCRIPTION
            ""
    ::= { lcsStatusVdslAdvancedUsBitLoadingEntry 6 }

-- {COLUMN} 1.3.6.1.4.1.2356.11.1.75.25.25.1.7
lcsStatusVdslAdvancedUsBitLoadingEntryX5 OBJECT-TYPE
    SYNTAX     Integer32 (0..2147483647)
    MAX-ACCESS read-only
    STATUS     current
    DESCRIPTION
            ""
    ::= { lcsStatusVdslAdvancedUsBitLoadingEntry 7 }

-- {COLUMN} 1.3.6.1.4.1.2356.11.1.75.25.25.1.8
lcsStatusVdslAdvancedUsBitLoadingEntryX6 OBJECT-TYPE
    SYNTAX     Integer32 (0..2147483647)
    MAX-ACCESS read-only
    STATUS     current
    DESCRIPTION
            ""
    ::= { lcsStatusVdslAdvancedUsBitLoadingEntry 8 }

-- {COLUMN} 1.3.6.1.4.1.2356.11.1.75.25.25.1.9
lcsStatusVdslAdvancedUsBitLoadingEntryX7 OBJECT-TYPE
    SYNTAX     Integer32 (0..2147483647)
    MAX-ACCESS read-only
    STATUS     current
    DESCRIPTION
            ""
    ::= { lcsStatusVdslAdvancedUsBitLoadingEntry 9 }

-- {COLUMN} 1.3.6.1.4.1.2356.11.1.75.25.25.1.10
lcsStatusVdslAdvancedUsBitLoadingEntryX8 OBJECT-TYPE
    SYNTAX     Integer32 (0..2147483647)
    MAX-ACCESS read-only
    STATUS     current
    DESCRIPTION
            ""
    ::= { lcsStatusVdslAdvancedUsBitLoadingEntry 10 }

-- {COLUMN} 1.3.6.1.4.1.2356.11.1.75.25.25.1.11
lcsStatusVdslAdvancedUsBitLoadingEntryX9 OBJECT-TYPE
    SYNTAX     Integer32 (0..2147483647)
    MAX-ACCESS read-only
    STATUS     current
    DESCRIPTION
            ""
    ::= { lcsStatusVdslAdvancedUsBitLoadingEntry 11 }

-- {COLUMN} 1.3.6.1.4.1.2356.11.1.75.25.25.1.12
lcsStatusVdslAdvancedUsBitLoadingEntryGraph OBJECT-TYPE
    SYNTAX     DisplayString (SIZE(0..255))
    MAX-ACCESS read-only
    STATUS     current
    DESCRIPTION
            ""
    ::= { lcsStatusVdslAdvancedUsBitLoadingEntry 12 }

-- {SCALAR} 1.3.6.1.4.1.2356.11.1.75.25.26
lcsStatusVdslAdvancedRetrain OBJECT-TYPE
    SYNTAX     DisplayString
    MAX-ACCESS read-write
    STATUS     current
    DESCRIPTION
            ""
    ::= { lcsStatusVdslAdvanced 26 }

-- {SCALAR} 1.3.6.1.4.1.2356.11.1.75.25.29
lcsStatusVdslAdvancedTransmittedAtmCells OBJECT-TYPE
    SYNTAX     Integer32 (0..2147483647)
    MAX-ACCESS read-only
    STATUS     current
    DESCRIPTION
            ""
    ::= { lcsStatusVdslAdvanced 29 }

-- {SCALAR} 1.3.6.1.4.1.2356.11.1.75.25.40
lcsStatusVdslAdvancedVdslProfile OBJECT-TYPE
    SYNTAX     INTEGER {
                  eUnknown (0),
                  e8a (1),
                  e8b (2),
                  e8c (3),
                  e8d (4),
                  e12a (5),
                  e12b (6),
                  e17a (7),
                  e30a (8),
                  e35b (9)
            }
    MAX-ACCESS read-only
    STATUS     current
    DESCRIPTION
            ""
    ::= { lcsStatusVdslAdvanced 40 }

-- {SCALAR} 1.3.6.1.4.1.2356.11.1.75.25.41
lcsStatusVdslAdvancedDslamManufacturer OBJECT-TYPE
    SYNTAX     DisplayString (SIZE(0..63))
    MAX-ACCESS read-only
    STATUS     current
    DESCRIPTION
            ""
    ::= { lcsStatusVdslAdvanced 41 }

-- {SCALAR} 1.3.6.1.4.1.2356.11.1.75.25.42
lcsStatusVdslAdvancedDslamVersion OBJECT-TYPE
    SYNTAX     DisplayString (SIZE(0..34))
    MAX-ACCESS read-only
    STATUS     current
    DESCRIPTION
            ""
    ::= { lcsStatusVdslAdvanced 42 }

-- {SCALAR} 1.3.6.1.4.1.2356.11.1.75.25.43
lcsStatusVdslAdvancedDslamSerialNumber OBJECT-TYPE
    SYNTAX     DisplayString (SIZE(0..66))
    MAX-ACCESS read-only
    STATUS     current
    DESCRIPTION
            ""
    ::= { lcsStatusVdslAdvanced 43 }

-- {SCALAR} 1.3.6.1.4.1.2356.11.1.75.25.44
lcsStatusVdslAdvancedDslamChipsetManufacturer OBJECT-TYPE
    SYNTAX     DisplayString (SIZE(0..63))
    MAX-ACCESS read-only
    STATUS     current
    DESCRIPTION
            ""
    ::= { lcsStatusVdslAdvanced 44 }

-- {SCALAR} 1.3.6.1.4.1.2356.11.1.75.25.45
lcsStatusVdslAdvancedVectoringSupport OBJECT-TYPE
    SYNTAX     INTEGER {
                  eNo (1),
                  eYes (2),
                  eFriendly (3)
            }
    MAX-ACCESS read-only
    STATUS     current
    DESCRIPTION
            "-- empty --"
    ::= { lcsStatusVdslAdvanced 45 }

-- {SCALAR} 1.3.6.1.4.1.2356.11.1.75.25.46
lcsStatusVdslAdvancedVectoring OBJECT-TYPE
    SYNTAX     INTEGER {
                  eNo (1),
                  eYes (2),
                  eFriendly (3)
            }
    MAX-ACCESS read-only
    STATUS     current
    DESCRIPTION
            "-- empty --"
    ::= { lcsStatusVdslAdvanced 46 }

-- {SCALAR} 1.3.6.1.4.1.2356.11.1.75.25.47
lcsStatusVdslAdvancedDslamChipsetManufacturerDump OBJECT-TYPE
    SYNTAX     OCTET STRING
    MAX-ACCESS read-only
    STATUS     current
    DESCRIPTION
            "-- empty --"
    ::= { lcsStatusVdslAdvanced 47 }

-- {SCALAR} 1.3.6.1.4.1.2356.11.1.75.25.48
lcsStatusVdslAdvancedDslamManufacturerDump OBJECT-TYPE
    SYNTAX     OCTET STRING
    MAX-ACCESS read-only
    STATUS     current
    DESCRIPTION
            "-- empty --"
    ::= { lcsStatusVdslAdvanced 48 }

-- {SCALAR} 1.3.6.1.4.1.2356.11.1.75.25.53
lcsStatusVdslAdvancedConnectionCount OBJECT-TYPE
    SYNTAX     Integer32 (0..2147483647)
    MAX-ACCESS read-only
    STATUS     current
    DESCRIPTION
            "-- empty --"
    ::= { lcsStatusVdslAdvanced 53 }

-- {SCALAR} 1.3.6.1.4.1.2356.11.1.75.25.54
lcsStatusVdslAdvancedConnectionDuration OBJECT-TYPE
    SYNTAX     Gauge32
    MAX-ACCESS read-only
    STATUS     current
    DESCRIPTION
            "-- empty --"
    ::= { lcsStatusVdslAdvanced 54 }

-- {SCALAR} 1.3.6.1.4.1.2356.11.1.75.25.100
lcsStatusVdslAdvancedDsAttainableDataRateKbps OBJECT-TYPE
    SYNTAX     Integer32 (0..2147483647)
    MAX-ACCESS read-only
    STATUS     current
    DESCRIPTION
            ""
    ::= { lcsStatusVdslAdvanced 100 }

-- {SCALAR} 1.3.6.1.4.1.2356.11.1.75.25.101
lcsStatusVdslAdvancedDsInpSymbols OBJECT-TYPE
    SYNTAX     DisplayString (SIZE(0..3))
    MAX-ACCESS read-only
    STATUS     current
    DESCRIPTION
            ""
    ::= { lcsStatusVdslAdvanced 101 }

-- {SCALAR} 1.3.6.1.4.1.2356.11.1.75.25.102
lcsStatusVdslAdvancedDsCrcErrors OBJECT-TYPE
    SYNTAX     Integer32 (0..2147483647)
    MAX-ACCESS read-only
    STATUS     current
    DESCRIPTION
            ""
    ::= { lcsStatusVdslAdvanced 102 }

-- {SCALAR} 1.3.6.1.4.1.2356.11.1.75.25.103
lcsStatusVdslAdvancedDsFecErrors OBJECT-TYPE
    SYNTAX     Integer32 (0..2147483647)
    MAX-ACCESS read-only
    STATUS     current
    DESCRIPTION
            ""
    ::= { lcsStatusVdslAdvanced 103 }

-- {SCALAR} 1.3.6.1.4.1.2356.11.1.75.25.104
lcsStatusVdslAdvancedDsAtmHecErrors OBJECT-TYPE
    SYNTAX     Integer32 (0..2147483647)
    MAX-ACCESS read-only
    STATUS     current
    DESCRIPTION
            ""
    ::= { lcsStatusVdslAdvanced 104 }

-- {SCALAR} 1.3.6.1.4.1.2356.11.1.75.25.105
lcsStatusVdslAdvancedDsDataPathCrcpErrors OBJECT-TYPE
    SYNTAX     Integer32 (0..2147483647)
    MAX-ACCESS read-only
    STATUS     current
    DESCRIPTION
            ""
    ::= { lcsStatusVdslAdvanced 105 }

-- {SCALAR} 1.3.6.1.4.1.2356.11.1.75.25.106
lcsStatusVdslAdvancedDsDataPathCrcnpErrors OBJECT-TYPE
    SYNTAX     Integer32 (0..2147483647)
    MAX-ACCESS read-only
    STATUS     current
    DESCRIPTION
            ""
    ::= { lcsStatusVdslAdvanced 106 }

-- {SCALAR} 1.3.6.1.4.1.2356.11.1.75.25.107
lcsStatusVdslAdvancedDsDataPathCvpErrors OBJECT-TYPE
    SYNTAX     Integer32 (0..2147483647)
    MAX-ACCESS read-only
    STATUS     current
    DESCRIPTION
            ""
    ::= { lcsStatusVdslAdvanced 107 }

-- {SCALAR} 1.3.6.1.4.1.2356.11.1.75.25.108
lcsStatusVdslAdvancedDsDataPathCvnpErrors OBJECT-TYPE
    SYNTAX     Integer32 (0..2147483647)
    MAX-ACCESS read-only
    STATUS     current
    DESCRIPTION
            ""
    ::= { lcsStatusVdslAdvanced 108 }

-- {SCALAR} 1.3.6.1.4.1.2356.11.1.75.25.109
lcsStatusVdslAdvancedDsAtmIdleBitErrors OBJECT-TYPE
    SYNTAX     Integer32 (0..2147483647)
    MAX-ACCESS read-only
    STATUS     current
    DESCRIPTION
            ""
    ::= { lcsStatusVdslAdvanced 109 }

-- {SCALAR} 1.3.6.1.4.1.2356.11.1.75.25.110
lcsStatusVdslAdvancedDsAtmCells OBJECT-TYPE
    SYNTAX     Integer32 (0..2147483647)
    MAX-ACCESS read-only
    STATUS     current
    DESCRIPTION
            ""
    ::= { lcsStatusVdslAdvanced 110 }

-- {SCALAR} 1.3.6.1.4.1.2356.11.1.75.25.111
lcsStatusVdslAdvancedDsPacketCount OBJECT-TYPE
    SYNTAX     Integer32 (0..2147483647)
    MAX-ACCESS read-only
    STATUS     current
    DESCRIPTION
            ""
    ::= { lcsStatusVdslAdvanced 111 }

-- {SCALAR} 1.3.6.1.4.1.2356.11.1.75.25.112
lcsStatusVdslAdvancedDsPacketBytes OBJECT-TYPE
    SYNTAX     Integer32 (0..2147483647)
    MAX-ACCESS read-only
    STATUS     current
    DESCRIPTION
            ""
    ::= { lcsStatusVdslAdvanced 112 }

-- {SCALAR} 1.3.6.1.4.1.2356.11.1.75.25.113
lcsStatusVdslAdvancedDsPacketErrors OBJECT-TYPE
    SYNTAX     Integer32 (0..2147483647)
    MAX-ACCESS read-only
    STATUS     current
    DESCRIPTION
            ""
    ::= { lcsStatusVdslAdvanced 113 }

-- {SCALAR} 1.3.6.1.4.1.2356.11.1.75.25.114
lcsStatusVdslAdvancedDsPausePackets OBJECT-TYPE
    SYNTAX     Integer32 (0..2147483647)
    MAX-ACCESS read-only
    STATUS     current
    DESCRIPTION
            ""
    ::= { lcsStatusVdslAdvanced 114 }

-- {SCALAR} 1.3.6.1.4.1.2356.11.1.75.25.115
lcsStatusVdslAdvancedDsPacketFcsErrors OBJECT-TYPE
    SYNTAX     Integer32 (0..2147483647)
    MAX-ACCESS read-only
    STATUS     current
    DESCRIPTION
            ""
    ::= { lcsStatusVdslAdvanced 115 }

-- {SCALAR} 1.3.6.1.4.1.2356.11.1.75.25.116
lcsStatusVdslAdvancedDsPacketAllignmentErrors OBJECT-TYPE
    SYNTAX     Integer32 (0..2147483647)
    MAX-ACCESS read-only
    STATUS     current
    DESCRIPTION
            ""
    ::= { lcsStatusVdslAdvanced 116 }

-- {SCALAR} 1.3.6.1.4.1.2356.11.1.75.25.117
lcsStatusVdslAdvancedDsPacketsTooLong OBJECT-TYPE
    SYNTAX     Integer32 (0..2147483647)
    MAX-ACCESS read-only
    STATUS     current
    DESCRIPTION
            ""
    ::= { lcsStatusVdslAdvanced 117 }

-- {SCALAR} 1.3.6.1.4.1.2356.11.1.75.25.118
lcsStatusVdslAdvancedDsPacketsTooShort OBJECT-TYPE
    SYNTAX     Integer32 (0..2147483647)
    MAX-ACCESS read-only
    STATUS     current
    DESCRIPTION
            ""
    ::= { lcsStatusVdslAdvanced 118 }

-- {SCALAR} 1.3.6.1.4.1.2356.11.1.75.25.120
lcsStatusVdslAdvancedUsAttainableDataRateKbps OBJECT-TYPE
    SYNTAX     Integer32 (0..2147483647)
    MAX-ACCESS read-only
    STATUS     current
    DESCRIPTION
            ""
    ::= { lcsStatusVdslAdvanced 120 }

-- {SCALAR} 1.3.6.1.4.1.2356.11.1.75.25.121
lcsStatusVdslAdvancedUsInpSymbols OBJECT-TYPE
    SYNTAX     DisplayString (SIZE(0..3))
    MAX-ACCESS read-only
    STATUS     current
    DESCRIPTION
            ""
    ::= { lcsStatusVdslAdvanced 121 }

-- {SCALAR} 1.3.6.1.4.1.2356.11.1.75.25.122
lcsStatusVdslAdvancedUsCrcErrors OBJECT-TYPE
    SYNTAX     Integer32 (0..2147483647)
    MAX-ACCESS read-only
    STATUS     current
    DESCRIPTION
            ""
    ::= { lcsStatusVdslAdvanced 122 }

-- {SCALAR} 1.3.6.1.4.1.2356.11.1.75.25.123
lcsStatusVdslAdvancedUsFecErrors OBJECT-TYPE
    SYNTAX     Integer32 (0..2147483647)
    MAX-ACCESS read-only
    STATUS     current
    DESCRIPTION
            ""
    ::= { lcsStatusVdslAdvanced 123 }

-- {SCALAR} 1.3.6.1.4.1.2356.11.1.75.25.124
lcsStatusVdslAdvancedUsAtmHecErrors OBJECT-TYPE
    SYNTAX     Integer32 (0..2147483647)
    MAX-ACCESS read-only
    STATUS     current
    DESCRIPTION
            ""
    ::= { lcsStatusVdslAdvanced 124 }

-- {SCALAR} 1.3.6.1.4.1.2356.11.1.75.25.125
lcsStatusVdslAdvancedUsDataPathCrcpErrors OBJECT-TYPE
    SYNTAX     Integer32 (0..2147483647)
    MAX-ACCESS read-only
    STATUS     current
    DESCRIPTION
            ""
    ::= { lcsStatusVdslAdvanced 125 }

-- {SCALAR} 1.3.6.1.4.1.2356.11.1.75.25.126
lcsStatusVdslAdvancedUsDataPathCrcnpErrors OBJECT-TYPE
    SYNTAX     Integer32 (0..2147483647)
    MAX-ACCESS read-only
    STATUS     current
    DESCRIPTION
            ""
    ::= { lcsStatusVdslAdvanced 126 }

-- {SCALAR} 1.3.6.1.4.1.2356.11.1.75.25.127
lcsStatusVdslAdvancedUsDataPathCvpErrors OBJECT-TYPE
    SYNTAX     Integer32 (0..2147483647)
    MAX-ACCESS read-only
    STATUS     current
    DESCRIPTION
            ""
    ::= { lcsStatusVdslAdvanced 127 }

-- {SCALAR} 1.3.6.1.4.1.2356.11.1.75.25.128
lcsStatusVdslAdvancedUsDataPathCvnpErrors OBJECT-TYPE
    SYNTAX     Integer32 (0..2147483647)
    MAX-ACCESS read-only
    STATUS     current
    DESCRIPTION
            ""
    ::= { lcsStatusVdslAdvanced 128 }

-- {SCALAR} 1.3.6.1.4.1.2356.11.1.75.25.129
lcsStatusVdslAdvancedUsAtmIdleBitErrors OBJECT-TYPE
    SYNTAX     Integer32 (0..2147483647)
    MAX-ACCESS read-only
    STATUS     current
    DESCRIPTION
            ""
    ::= { lcsStatusVdslAdvanced 129 }

-- {SCALAR} 1.3.6.1.4.1.2356.11.1.75.25.130
lcsStatusVdslAdvancedUsAtmCells OBJECT-TYPE
    SYNTAX     Integer32 (0..2147483647)
    MAX-ACCESS read-only
    STATUS     current
    DESCRIPTION
            ""
    ::= { lcsStatusVdslAdvanced 130 }

-- {SCALAR} 1.3.6.1.4.1.2356.11.1.75.25.131
lcsStatusVdslAdvancedUsPacketCount OBJECT-TYPE
    SYNTAX     Integer32 (0..2147483647)
    MAX-ACCESS read-only
    STATUS     current
    DESCRIPTION
            ""
    ::= { lcsStatusVdslAdvanced 131 }

-- {SCALAR} 1.3.6.1.4.1.2356.11.1.75.25.132
lcsStatusVdslAdvancedUsPacketBytes OBJECT-TYPE
    SYNTAX     Integer32 (0..2147483647)
    MAX-ACCESS read-only
    STATUS     current
    DESCRIPTION
            ""
    ::= { lcsStatusVdslAdvanced 132 }

-- {SCALAR} 1.3.6.1.4.1.2356.11.1.75.25.133
lcsStatusVdslAdvancedUsPacketErrors OBJECT-TYPE
    SYNTAX     Integer32 (0..2147483647)
    MAX-ACCESS read-only
    STATUS     current
    DESCRIPTION
            ""
    ::= { lcsStatusVdslAdvanced 133 }

-- {SCALAR} 1.3.6.1.4.1.2356.11.1.75.25.134
lcsStatusVdslAdvancedUsPausePackets OBJECT-TYPE
    SYNTAX     Integer32 (0..2147483647)
    MAX-ACCESS read-only
    STATUS     current
    DESCRIPTION
            ""
    ::= { lcsStatusVdslAdvanced 134 }

-- {SCALAR} 1.3.6.1.4.1.2356.11.1.75.25.140
lcsStatusVdslAdvancedWanTxPacketCount OBJECT-TYPE
    SYNTAX     Integer32 (0..2147483647)
    MAX-ACCESS read-only
    STATUS     current
    DESCRIPTION
            ""
    ::= { lcsStatusVdslAdvanced 140 }

-- {SCALAR} 1.3.6.1.4.1.2356.11.1.75.25.141
lcsStatusVdslAdvancedWanTxPacketBytes OBJECT-TYPE
    SYNTAX     Integer32 (0..2147483647)
    MAX-ACCESS read-only
    STATUS     current
    DESCRIPTION
            ""
    ::= { lcsStatusVdslAdvanced 141 }

-- {SCALAR} 1.3.6.1.4.1.2356.11.1.75.25.142
lcsStatusVdslAdvancedWanTxPacketErrors OBJECT-TYPE
    SYNTAX     Integer32 (0..2147483647)
    MAX-ACCESS read-only
    STATUS     current
    DESCRIPTION
            ""
    ::= { lcsStatusVdslAdvanced 142 }

-- {SCALAR} 1.3.6.1.4.1.2356.11.1.75.25.143
lcsStatusVdslAdvancedWanTxPacketDrops OBJECT-TYPE
    SYNTAX     Integer32 (0..2147483647)
    MAX-ACCESS read-only
    STATUS     current
    DESCRIPTION
            ""
    ::= { lcsStatusVdslAdvanced 143 }

-- {SCALAR} 1.3.6.1.4.1.2356.11.1.75.25.144
lcsStatusVdslAdvancedWanTxOverruns OBJECT-TYPE
    SYNTAX     Integer32 (0..2147483647)
    MAX-ACCESS read-only
    STATUS     current
    DESCRIPTION
            ""
    ::= { lcsStatusVdslAdvanced 144 }

-- {SCALAR} 1.3.6.1.4.1.2356.11.1.75.25.145
lcsStatusVdslAdvancedWanTxDelta OBJECT-TYPE
    SYNTAX     Integer32 (-2147483648..2147483647)
    MAX-ACCESS read-only
    STATUS     current
    DESCRIPTION
            ""
    ::= { lcsStatusVdslAdvanced 145 }

-- {SCALAR} 1.3.6.1.4.1.2356.11.1.75.25.146
lcsStatusVdslAdvancedTxPacketCount OBJECT-TYPE
    SYNTAX     Integer32 (0..2147483647)
    MAX-ACCESS read-only
    STATUS     current
    DESCRIPTION
            "-- empty --"
    ::= { lcsStatusVdslAdvanced 146 }

-- {SCALAR} 1.3.6.1.4.1.2356.11.1.75.25.148
lcsStatusVdslAdvancedUsLineOptions OBJECT-TYPE
    SYNTAX     BITS {
                  eBitswap (4),
                  eTrellis (5),
                  eVirtualNoise (6),
                  eRetransmission (7)
            }
    MAX-ACCESS read-only
    STATUS     current
    DESCRIPTION
            "-- empty --"
    ::= { lcsStatusVdslAdvanced 148 }

-- {SCALAR} 1.3.6.1.4.1.2356.11.1.75.25.149
lcsStatusVdslAdvancedTx-Packet-count-64 OBJECT-TYPE
    SYNTAX     Integer32 (0..2147483647)
    MAX-ACCESS read-only
    STATUS     current
    DESCRIPTION
            ""
    ::= { lcsStatusVdslAdvanced 149 }

-- {SCALAR} 1.3.6.1.4.1.2356.11.1.75.25.150
lcsStatusVdslAdvancedWanRxPacketCount OBJECT-TYPE
    SYNTAX     Integer32 (0..2147483647)
    MAX-ACCESS read-only
    STATUS     current
    DESCRIPTION
            ""
    ::= { lcsStatusVdslAdvanced 150 }

-- {SCALAR} 1.3.6.1.4.1.2356.11.1.75.25.151
lcsStatusVdslAdvancedWanRxPacketBytes OBJECT-TYPE
    SYNTAX     Integer32 (0..2147483647)
    MAX-ACCESS read-only
    STATUS     current
    DESCRIPTION
            ""
    ::= { lcsStatusVdslAdvanced 151 }

-- {SCALAR} 1.3.6.1.4.1.2356.11.1.75.25.152
lcsStatusVdslAdvancedWanRxPacketErrors OBJECT-TYPE
    SYNTAX     Integer32 (0..2147483647)
    MAX-ACCESS read-only
    STATUS     current
    DESCRIPTION
            ""
    ::= { lcsStatusVdslAdvanced 152 }

-- {SCALAR} 1.3.6.1.4.1.2356.11.1.75.25.153
lcsStatusVdslAdvancedWanRxPacketDrops OBJECT-TYPE
    SYNTAX     Integer32 (0..2147483647)
    MAX-ACCESS read-only
    STATUS     current
    DESCRIPTION
            ""
    ::= { lcsStatusVdslAdvanced 153 }

-- {SCALAR} 1.3.6.1.4.1.2356.11.1.75.25.154
lcsStatusVdslAdvancedWanRxOverruns OBJECT-TYPE
    SYNTAX     Integer32 (0..2147483647)
    MAX-ACCESS read-only
    STATUS     current
    DESCRIPTION
            ""
    ::= { lcsStatusVdslAdvanced 154 }

-- {SCALAR} 1.3.6.1.4.1.2356.11.1.75.25.155
lcsStatusVdslAdvancedWanRxDelta OBJECT-TYPE
    SYNTAX     Integer32 (-2147483648..2147483647)
    MAX-ACCESS read-only
    STATUS     current
    DESCRIPTION
            ""
    ::= { lcsStatusVdslAdvanced 155 }

-- {SCALAR} 1.3.6.1.4.1.2356.11.1.75.25.156
lcsStatusVdslAdvancedRxPacketCount OBJECT-TYPE
    SYNTAX     Integer32 (0..2147483647)
    MAX-ACCESS read-only
    STATUS     current
    DESCRIPTION
            "-- empty --"
    ::= { lcsStatusVdslAdvanced 156 }

-- {TABLE} 1.3.6.1.4.1.2356.11.1.75.25.157
lcsStatusVdslAdvancedDsSnrPerSubCarrierTable OBJECT-TYPE
    SYNTAX     SEQUENCE OF LcsStatusVdslAdvancedDsSnrPerSubCarrierEntry
    MAX-ACCESS not-accessible
    STATUS     current
    DESCRIPTION
            "-- empty --"
    ::= { lcsStatusVdslAdvanced 157 }

-- {ROW} 1.3.6.1.4.1.2356.11.1.75.25.157.1
lcsStatusVdslAdvancedDsSnrPerSubCarrierEntry OBJECT-TYPE
    SYNTAX     LcsStatusVdslAdvancedDsSnrPerSubCarrierEntry
    MAX-ACCESS not-accessible
    STATUS     current
    DESCRIPTION
            ""
    INDEX {
            lcsStatusVdslAdvancedDsSnrPerSubCarrierEntrySubCarrier
          }
    ::= { lcsStatusVdslAdvancedDsSnrPerSubCarrierTable 1 }

LcsStatusVdslAdvancedDsSnrPerSubCarrierEntry ::= SEQUENCE {
            lcsStatusVdslAdvancedDsSnrPerSubCarrierEntrySubCarrier DisplayString,
            lcsStatusVdslAdvancedDsSnrPerSubCarrierEntryX0 Integer32,
            lcsStatusVdslAdvancedDsSnrPerSubCarrierEntryX1 Integer32,
            lcsStatusVdslAdvancedDsSnrPerSubCarrierEntryX2 Integer32,
            lcsStatusVdslAdvancedDsSnrPerSubCarrierEntryX3 Integer32,
            lcsStatusVdslAdvancedDsSnrPerSubCarrierEntryX4 Integer32,
            lcsStatusVdslAdvancedDsSnrPerSubCarrierEntryX5 Integer32,
            lcsStatusVdslAdvancedDsSnrPerSubCarrierEntryX6 Integer32,
            lcsStatusVdslAdvancedDsSnrPerSubCarrierEntryX7 Integer32,
            lcsStatusVdslAdvancedDsSnrPerSubCarrierEntryX8 Integer32,
            lcsStatusVdslAdvancedDsSnrPerSubCarrierEntryX9 Integer32
    }

-- {COLUMN} 1.3.6.1.4.1.2356.11.1.75.25.157.1.1
lcsStatusVdslAdvancedDsSnrPerSubCarrierEntrySubCarrier OBJECT-TYPE
    SYNTAX     DisplayString (SIZE(0..255))
    MAX-ACCESS read-only
    STATUS     current
    DESCRIPTION
            "-- empty --"
    ::= { lcsStatusVdslAdvancedDsSnrPerSubCarrierEntry 1 }

-- {COLUMN} 1.3.6.1.4.1.2356.11.1.75.25.157.1.2
lcsStatusVdslAdvancedDsSnrPerSubCarrierEntryX0 OBJECT-TYPE
    SYNTAX     Integer32 (0..2147483647)
    MAX-ACCESS read-only
    STATUS     current
    DESCRIPTION
            "-- empty --"
    ::= { lcsStatusVdslAdvancedDsSnrPerSubCarrierEntry 2 }

-- {COLUMN} 1.3.6.1.4.1.2356.11.1.75.25.157.1.3
lcsStatusVdslAdvancedDsSnrPerSubCarrierEntryX1 OBJECT-TYPE
    SYNTAX     Integer32 (0..2147483647)
    MAX-ACCESS read-only
    STATUS     current
    DESCRIPTION
            "-- empty --"
    ::= { lcsStatusVdslAdvancedDsSnrPerSubCarrierEntry 3 }

-- {COLUMN} 1.3.6.1.4.1.2356.11.1.75.25.157.1.4
lcsStatusVdslAdvancedDsSnrPerSubCarrierEntryX2 OBJECT-TYPE
    SYNTAX     Integer32 (0..2147483647)
    MAX-ACCESS read-only
    STATUS     current
    DESCRIPTION
            "-- empty --"
    ::= { lcsStatusVdslAdvancedDsSnrPerSubCarrierEntry 4 }

-- {COLUMN} 1.3.6.1.4.1.2356.11.1.75.25.157.1.5
lcsStatusVdslAdvancedDsSnrPerSubCarrierEntryX3 OBJECT-TYPE
    SYNTAX     Integer32 (0..2147483647)
    MAX-ACCESS read-only
    STATUS     current
    DESCRIPTION
            "-- empty --"
    ::= { lcsStatusVdslAdvancedDsSnrPerSubCarrierEntry 5 }

-- {COLUMN} 1.3.6.1.4.1.2356.11.1.75.25.157.1.6
lcsStatusVdslAdvancedDsSnrPerSubCarrierEntryX4 OBJECT-TYPE
    SYNTAX     Integer32 (0..2147483647)
    MAX-ACCESS read-only
    STATUS     current
    DESCRIPTION
            "-- empty --"
    ::= { lcsStatusVdslAdvancedDsSnrPerSubCarrierEntry 6 }

-- {COLUMN} 1.3.6.1.4.1.2356.11.1.75.25.157.1.7
lcsStatusVdslAdvancedDsSnrPerSubCarrierEntryX5 OBJECT-TYPE
    SYNTAX     Integer32 (0..2147483647)
    MAX-ACCESS read-only
    STATUS     current
    DESCRIPTION
            "-- empty --"
    ::= { lcsStatusVdslAdvancedDsSnrPerSubCarrierEntry 7 }

-- {COLUMN} 1.3.6.1.4.1.2356.11.1.75.25.157.1.8
lcsStatusVdslAdvancedDsSnrPerSubCarrierEntryX6 OBJECT-TYPE
    SYNTAX     Integer32 (0..2147483647)
    MAX-ACCESS read-only
    STATUS     current
    DESCRIPTION
            "-- empty --"
    ::= { lcsStatusVdslAdvancedDsSnrPerSubCarrierEntry 8 }

-- {COLUMN} 1.3.6.1.4.1.2356.11.1.75.25.157.1.9
lcsStatusVdslAdvancedDsSnrPerSubCarrierEntryX7 OBJECT-TYPE
    SYNTAX     Integer32 (0..2147483647)
    MAX-ACCESS read-only
    STATUS     current
    DESCRIPTION
            "-- empty --"
    ::= { lcsStatusVdslAdvancedDsSnrPerSubCarrierEntry 9 }

-- {COLUMN} 1.3.6.1.4.1.2356.11.1.75.25.157.1.10
lcsStatusVdslAdvancedDsSnrPerSubCarrierEntryX8 OBJECT-TYPE
    SYNTAX     Integer32 (0..2147483647)
    MAX-ACCESS read-only
    STATUS     current
    DESCRIPTION
            "-- empty --"
    ::= { lcsStatusVdslAdvancedDsSnrPerSubCarrierEntry 10 }

-- {COLUMN} 1.3.6.1.4.1.2356.11.1.75.25.157.1.11
lcsStatusVdslAdvancedDsSnrPerSubCarrierEntryX9 OBJECT-TYPE
    SYNTAX     Integer32 (0..2147483647)
    MAX-ACCESS read-only
    STATUS     current
    DESCRIPTION
            "-- empty --"
    ::= { lcsStatusVdslAdvancedDsSnrPerSubCarrierEntry 11 }

-- {SCALAR} 1.3.6.1.4.1.2356.11.1.75.25.158
lcsStatusVdslAdvancedDsLineOptions OBJECT-TYPE
    SYNTAX     BITS {
                  eBitswap (4),
                  eTrellis (5),
                  eVirtualNoise (6),
                  eRetransmission (7)
            }
    MAX-ACCESS read-only
    STATUS     current
    DESCRIPTION
            "-- empty --"
    ::= { lcsStatusVdslAdvanced 158 }

-- {SCALAR} 1.3.6.1.4.1.2356.11.1.75.25.159
lcsStatusVdslAdvancedRx-Packet-count-64 OBJECT-TYPE
    SYNTAX     Integer32 (0..2147483647)
    MAX-ACCESS read-only
    STATUS     current
    DESCRIPTION
            ""
    ::= { lcsStatusVdslAdvanced 159 }

-- {SCALAR} 1.3.6.1.4.1.2356.11.1.75.25.160
lcsStatusVdslAdvancedWAN-Tx-Packet-count-64 OBJECT-TYPE
    SYNTAX     Integer32 (0..2147483647)
    MAX-ACCESS read-only
    STATUS     current
    DESCRIPTION
            ""
    ::= { lcsStatusVdslAdvanced 160 }

-- {SCALAR} 1.3.6.1.4.1.2356.11.1.75.25.161
lcsStatusVdslAdvancedWAN-Tx-Packet-bytes-64 OBJECT-TYPE
    SYNTAX     Integer32 (0..2147483647)
    MAX-ACCESS read-only
    STATUS     current
    DESCRIPTION
            ""
    ::= { lcsStatusVdslAdvanced 161 }

-- {SCALAR} 1.3.6.1.4.1.2356.11.1.75.25.170
lcsStatusVdslAdvancedWAN-Rx-Packet-count-64 OBJECT-TYPE
    SYNTAX     Integer32 (0..2147483647)
    MAX-ACCESS read-only
    STATUS     current
    DESCRIPTION
            ""
    ::= { lcsStatusVdslAdvanced 170 }

-- {SCALAR} 1.3.6.1.4.1.2356.11.1.75.25.171
lcsStatusVdslAdvancedWAN-Rx-Packet-bytes-64 OBJECT-TYPE
    SYNTAX     Integer32 (0..2147483647)
    MAX-ACCESS read-only
    STATUS     current
    DESCRIPTION
            ""
    ::= { lcsStatusVdslAdvanced 171 }

-- {SCALAR} 1.3.6.1.4.1.2356.11.1.75.34
lcsStatusVdslInpDownstreamSymbols OBJECT-TYPE
    SYNTAX     DisplayString (SIZE(0..3))
    MAX-ACCESS read-only
    STATUS     current
    DESCRIPTION
            ""
    ::= { lcsStatusVdsl 34 }

-- {SCALAR} 1.3.6.1.4.1.2356.11.1.75.35
lcsStatusVdslInpUpstreamSymbols OBJECT-TYPE
    SYNTAX     DisplayString (SIZE(0..3))
    MAX-ACCESS read-only
    STATUS     current
    DESCRIPTION
            ""
    ::= { lcsStatusVdsl 35 }

-- {SCALAR} 1.3.6.1.4.1.2356.11.1.75.36
lcsStatusVdslAttainableDataRateDownstreamKbps OBJECT-TYPE
    SYNTAX     Integer32 (0..2147483647)
    MAX-ACCESS read-only
    STATUS     current
    DESCRIPTION
            ""
    ::= { lcsStatusVdsl 36 }

-- {SCALAR} 1.3.6.1.4.1.2356.11.1.75.37
lcsStatusVdslAttainableDataRateUpstreamKbps OBJECT-TYPE
    SYNTAX     Integer32 (0..2147483647)
    MAX-ACCESS read-only
    STATUS     current
    DESCRIPTION
            ""
    ::= { lcsStatusVdsl 37 }

-- {SCALAR} 1.3.6.1.4.1.2356.11.1.75.40
lcsStatusVdslVdslProfile OBJECT-TYPE
    SYNTAX     INTEGER {
                  eUnknown (0),
                  e8a (1),
                  e8b (2),
                  e8c (3),
                  e8d (4),
                  e12a (5),
                  e12b (6),
                  e17a (7),
                  e30a (8),
                  e35b (9)
            }
    MAX-ACCESS read-only
    STATUS     current
    DESCRIPTION
            ""
    ::= { lcsStatusVdsl 40 }

-- {SCALAR} 1.3.6.1.4.1.2356.11.1.75.41
lcsStatusVdslDslamManufacturer OBJECT-TYPE
    SYNTAX     DisplayString (SIZE(0..63))
    MAX-ACCESS read-only
    STATUS     current
    DESCRIPTION
            ""
    ::= { lcsStatusVdsl 41 }

-- {SCALAR} 1.3.6.1.4.1.2356.11.1.75.42
lcsStatusVdslDslamVersion OBJECT-TYPE
    SYNTAX     DisplayString (SIZE(0..34))
    MAX-ACCESS read-only
    STATUS     current
    DESCRIPTION
            ""
    ::= { lcsStatusVdsl 42 }

-- {SCALAR} 1.3.6.1.4.1.2356.11.1.75.43
lcsStatusVdslDslamSerialNumber OBJECT-TYPE
    SYNTAX     DisplayString (SIZE(0..66))
    MAX-ACCESS read-only
    STATUS     current
    DESCRIPTION
            ""
    ::= { lcsStatusVdsl 43 }

-- {SCALAR} 1.3.6.1.4.1.2356.11.1.75.45
lcsStatusVdslVectoringSupport OBJECT-TYPE
    SYNTAX     INTEGER {
                  eNo (1),
                  eYes (2),
                  eFriendly (3)
            }
    MAX-ACCESS read-only
    STATUS     current
    DESCRIPTION
            "-- empty --"
    ::= { lcsStatusVdsl 45 }

-- {SCALAR} 1.3.6.1.4.1.2356.11.1.75.46
lcsStatusVdslVectoring OBJECT-TYPE
    SYNTAX     INTEGER {
                  eNo (1),
                  eYes (2),
                  eFriendly (3)
            }
    MAX-ACCESS read-only
    STATUS     current
    DESCRIPTION
            "-- empty --"
    ::= { lcsStatusVdsl 46 }

-- {SCALAR} 1.3.6.1.4.1.2356.11.1.75.50
lcsStatusVdslAtmVpi OBJECT-TYPE
    SYNTAX     Integer32 (0..2147483647)
    MAX-ACCESS read-only
    STATUS     current
    DESCRIPTION
            ""
    ::= { lcsStatusVdsl 50 }

-- {SCALAR} 1.3.6.1.4.1.2356.11.1.75.51
lcsStatusVdslAtmVci OBJECT-TYPE
    SYNTAX     Integer32 (0..2147483647)
    MAX-ACCESS read-only
    STATUS     current
    DESCRIPTION
            ""
    ::= { lcsStatusVdsl 51 }

-- {SCALAR} 1.3.6.1.4.1.2356.11.1.75.52
lcsStatusVdslAtmMuxmode OBJECT-TYPE
    SYNTAX     INTEGER {
                  eVcMux (0),
                  eLlcMux (1)
            }
    MAX-ACCESS read-only
    STATUS     current
    DESCRIPTION
            ""
    ::= { lcsStatusVdsl 52 }

-- {SCALAR} 1.3.6.1.4.1.2356.11.1.75.53
lcsStatusVdslConnectionCount OBJECT-TYPE
    SYNTAX     Integer32 (0..2147483647)
    MAX-ACCESS read-only
    STATUS     current
    DESCRIPTION
            "-- empty --"
    ::= { lcsStatusVdsl 53 }

-- {SCALAR} 1.3.6.1.4.1.2356.11.1.75.54
lcsStatusVdslConnectionDuration OBJECT-TYPE
    SYNTAX     Gauge32
    MAX-ACCESS read-only
    STATUS     current
    DESCRIPTION
            "-- empty --"
    ::= { lcsStatusVdsl 54 }

-- {SCALAR} 1.3.6.1.4.1.2356.11.1.75.200
lcsStatusVdslWanBridge OBJECT-TYPE
    SYNTAX     INTEGER {
                  eNo (0),
                  eYes (1)
            }
    MAX-ACCESS read-only
    STATUS     current
    DESCRIPTION
            "-- empty --"
    ::= { lcsStatusVdsl 200 }

-- {NODE} 1.3.6.1.4.1.2356.11.1.75.500
lcsStatusVdslModem OBJECT IDENTIFIER ::= { lcsStatusVdsl 500 }

-- {SCALAR} 1.3.6.1.4.1.2356.11.1.75.500.1
lcsStatusVdslModemModemState OBJECT-TYPE
    SYNTAX     INTEGER {
                  eNoCommunicationsPort (0),
                  eError (1),
                  eFileSystem (2),
                  eBootHeader (3),
                  eUploadingBootstrap (4),
                  eUploadingMemoryTest (5),
                  eMemoryTest (6),
                  eOptions (7),
                  eUploadingUBoot (8),
                  eQuickMemoryTest (9),
                  eUploadingKernel (10),
                  eUploadingRamdisk (11),
                  eUploadingFirmware (12),
                  eWaitForHeartbeat (13),
                  eRunning (14),
                  eUploadingGphyFirmware (15),
                  eDisabled (16)
            }
    MAX-ACCESS read-only
    STATUS     current
    DESCRIPTION
            ""
    ::= { lcsStatusVdslModem 1 }

-- {SCALAR} 1.3.6.1.4.1.2356.11.1.75.500.2
lcsStatusVdslModemOptions OBJECT-TYPE
    SYNTAX     Integer32 (0..255)
    MAX-ACCESS read-only
    STATUS     current
    DESCRIPTION
            ""
    ::= { lcsStatusVdslModem 2 }

-- {SCALAR} 1.3.6.1.4.1.2356.11.1.75.500.3
lcsStatusVdslModemMemoryTest OBJECT-TYPE
    SYNTAX     INTEGER {
                  eNotTested (0),
                  eTimeout (1),
                  eFailed (2),
                  eOk (3)
            }
    MAX-ACCESS read-only
    STATUS     current
    DESCRIPTION
            ""
    ::= { lcsStatusVdslModem 3 }

-- {SCALAR} 1.3.6.1.4.1.2356.11.1.75.500.4
lcsStatusVdslModemRebootModem OBJECT-TYPE
    SYNTAX     DisplayString
    MAX-ACCESS read-write
    STATUS     current
    DESCRIPTION
            ""
    ::= { lcsStatusVdslModem 4 }

-- {SCALAR} 1.3.6.1.4.1.2356.11.1.75.500.5
lcsStatusVdslModemLink OBJECT-TYPE
    SYNTAX     Integer32 (0..2147483647)
    MAX-ACCESS read-only
    STATUS     current
    DESCRIPTION
            ""
    ::= { lcsStatusVdslModem 5 }

-- {SCALAR} 1.3.6.1.4.1.2356.11.1.75.500.6
lcsStatusVdslModemLastError OBJECT-TYPE
    SYNTAX     DisplayString (SIZE(0..63))
    MAX-ACCESS read-only
    STATUS     current
    DESCRIPTION
            ""
    ::= { lcsStatusVdslModem 6 }

-- {SCALAR} 1.3.6.1.4.1.2356.11.1.75.500.7
lcsStatusVdslModemVdslFirmware OBJECT-TYPE
    SYNTAX     DisplayString (SIZE(0..63))
    MAX-ACCESS read-only
    STATUS     current
    DESCRIPTION
            ""
    ::= { lcsStatusVdslModem 7 }

-- {SCALAR} 1.3.6.1.4.1.2356.11.1.75.500.8
lcsStatusVdslModemAdslPotsFirmware OBJECT-TYPE
    SYNTAX     DisplayString (SIZE(0..63))
    MAX-ACCESS read-only
    STATUS     current
    DESCRIPTION
            ""
    ::= { lcsStatusVdslModem 8 }

-- {SCALAR} 1.3.6.1.4.1.2356.11.1.75.500.9
lcsStatusVdslModemAdslIsdnFirmware OBJECT-TYPE
    SYNTAX     DisplayString (SIZE(0..63))
    MAX-ACCESS read-only
    STATUS     current
    DESCRIPTION
            ""
    ::= { lcsStatusVdslModem 9 }

-- {SCALAR} 1.3.6.1.4.1.2356.11.1.75.500.10
lcsStatusVdslModemDslApiVersion OBJECT-TYPE
    SYNTAX     DisplayString (SIZE(0..31))
    MAX-ACCESS read-only
    STATUS     current
    DESCRIPTION
            ""
    ::= { lcsStatusVdslModem 10 }

-- {SCALAR} 1.3.6.1.4.1.2356.11.1.75.500.11
lcsStatusVdslModemDspFirmwareVersion OBJECT-TYPE
    SYNTAX     DisplayString (SIZE(0..31))
    MAX-ACCESS read-only
    STATUS     current
    DESCRIPTION
            ""
    ::= { lcsStatusVdslModem 11 }

-- {SCALAR} 1.3.6.1.4.1.2356.11.1.75.500.12
lcsStatusVdslModemHardwareVersion OBJECT-TYPE
    SYNTAX     DisplayString (SIZE(0..31))
    MAX-ACCESS read-only
    STATUS     current
    DESCRIPTION
            ""
    ::= { lcsStatusVdslModem 12 }

-- {SCALAR} 1.3.6.1.4.1.2356.11.1.75.500.13
lcsStatusVdslModemChipsetType OBJECT-TYPE
    SYNTAX     DisplayString (SIZE(0..31))
    MAX-ACCESS read-only
    STATUS     current
    DESCRIPTION
            ""
    ::= { lcsStatusVdslModem 13 }

-- {SCALAR} 1.3.6.1.4.1.2356.11.1.75.500.14
lcsStatusVdslModemDriverVersion OBJECT-TYPE
    SYNTAX     DisplayString (SIZE(0..31))
    MAX-ACCESS read-only
    STATUS     current
    DESCRIPTION
            ""
    ::= { lcsStatusVdslModem 14 }

-- {SCALAR} 1.3.6.1.4.1.2356.11.1.75.500.15
lcsStatusVdslModemBootCount OBJECT-TYPE
    SYNTAX     Integer32 (0..2147483647)
    MAX-ACCESS read-only
    STATUS     current
    DESCRIPTION
            ""
    ::= { lcsStatusVdslModem 15 }

-- {SCALAR} 1.3.6.1.4.1.2356.11.1.75.500.16
lcsStatusVdslModemHybrid OBJECT-TYPE
    SYNTAX     INTEGER {
                  eBJ (0),
                  eInvalid (1),
                  eB (2),
                  eA (3),
                  eUniversal (4),
                  eUnknown (256)
            }
    MAX-ACCESS read-only
    STATUS     current
    DESCRIPTION
            "-- empty --"
    ::= { lcsStatusVdslModem 16 }

-- {SCALAR} 1.3.6.1.4.1.2356.11.1.75.500.17
lcsStatusVdslModemDefaultAtmVpi OBJECT-TYPE
    SYNTAX     Integer32 (0..2147483647)
    MAX-ACCESS read-only
    STATUS     current
    DESCRIPTION
            "-- empty --"
    ::= { lcsStatusVdslModem 17 }

-- {SCALAR} 1.3.6.1.4.1.2356.11.1.75.500.18
lcsStatusVdslModemDefaultAtmVci OBJECT-TYPE
    SYNTAX     Integer32 (0..2147483647)
    MAX-ACCESS read-only
    STATUS     current
    DESCRIPTION
            "-- empty --"
    ::= { lcsStatusVdslModem 18 }

-- {SCALAR} 1.3.6.1.4.1.2356.11.1.75.500.19
lcsStatusVdslModemDefaultAtmMuxmode OBJECT-TYPE
    SYNTAX     INTEGER {
                  eVcMux (0),
                  eLlcMux (1)
            }
    MAX-ACCESS read-only
    STATUS     current
    DESCRIPTION
            "-- empty --"
    ::= { lcsStatusVdslModem 19 }

-- {SCALAR} 1.3.6.1.4.1.2356.11.1.75.500.21
lcsStatusVdslModemLoad OBJECT-TYPE
    SYNTAX     Integer32 (0..2147483647)
    MAX-ACCESS read-only
    STATUS     current
    DESCRIPTION
            "-- empty --"
    ::= { lcsStatusVdslModem 21 }

-- {SCALAR} 1.3.6.1.4.1.2356.11.1.75.500.22
lcsStatusVdslModemLoadUser OBJECT-TYPE
    SYNTAX     Integer32 (0..2147483647)
    MAX-ACCESS read-only
    STATUS     current
    DESCRIPTION
            "-- empty --"
    ::= { lcsStatusVdslModem 22 }

-- {SCALAR} 1.3.6.1.4.1.2356.11.1.75.500.23
lcsStatusVdslModemLoadSystem OBJECT-TYPE
    SYNTAX     Integer32 (0..2147483647)
    MAX-ACCESS read-only
    STATUS     current
    DESCRIPTION
            "-- empty --"
    ::= { lcsStatusVdslModem 23 }

-- {SCALAR} 1.3.6.1.4.1.2356.11.1.75.500.24
lcsStatusVdslModemLoadIdle OBJECT-TYPE
    SYNTAX     Integer32 (0..2147483647)
    MAX-ACCESS read-only
    STATUS     current
    DESCRIPTION
            "-- empty --"
    ::= { lcsStatusVdslModem 24 }

-- {SCALAR} 1.3.6.1.4.1.2356.11.1.75.500.25
lcsStatusVdslModemPotsFirmware OBJECT-TYPE
    SYNTAX     DisplayString (SIZE(0..71))
    MAX-ACCESS read-only
    STATUS     current
    DESCRIPTION
            "-- empty --"
    ::= { lcsStatusVdslModem 25 }

-- {SCALAR} 1.3.6.1.4.1.2356.11.1.75.500.26
lcsStatusVdslModemIsdnFirmware OBJECT-TYPE
    SYNTAX     DisplayString (SIZE(0..71))
    MAX-ACCESS read-only
    STATUS     current
    DESCRIPTION
            "-- empty --"
    ::= { lcsStatusVdslModem 26 }

-- {SCALAR} 1.3.6.1.4.1.2356.11.1.75.500.27
lcsStatusVdslModemTemperatureDegc OBJECT-TYPE
    SYNTAX     DisplayString (SIZE(0..3))
    MAX-ACCESS read-only
    STATUS     current
    DESCRIPTION
            "-- empty --"
    ::= { lcsStatusVdslModem 27 }

-- {SCALAR} 1.3.6.1.4.1.2356.11.1.75.500.28
lcsStatusVdslModemWanAcceleration OBJECT-TYPE
    SYNTAX     INTEGER {
                  eNo (0),
                  eYes (1)
            }
    MAX-ACCESS read-only
    STATUS     current
    DESCRIPTION
            "-- empty --"
    ::= { lcsStatusVdslModem 28 }

-- {NODE} 1.3.6.1.4.1.2356.11.1.77
lcsStatusIpv6 OBJECT IDENTIFIER ::= { lcsStatus 77 }

-- {TABLE} 1.3.6.1.4.1.2356.11.1.77.1
lcsStatusIpv6AddressesTable OBJECT-TYPE
    SYNTAX     SEQUENCE OF LcsStatusIpv6AddressesEntry
    MAX-ACCESS not-accessible
    STATUS     current
    DESCRIPTION
            "-- empty --"
    ::= { lcsStatusIpv6 1 }

-- {ROW} 1.3.6.1.4.1.2356.11.1.77.1.1
lcsStatusIpv6AddressesEntry OBJECT-TYPE
    SYNTAX     LcsStatusIpv6AddressesEntry
    MAX-ACCESS not-accessible
    STATUS     current
    DESCRIPTION
            ""
    INDEX {
            lcsStatusIpv6AddressesEntryInterfaceName,
            lcsStatusIpv6AddressesEntryIpv6Address
          }
    ::= { lcsStatusIpv6AddressesTable 1 }

LcsStatusIpv6AddressesEntry ::= SEQUENCE {
            lcsStatusIpv6AddressesEntryInterfaceName DisplayString,
            lcsStatusIpv6AddressesEntryIpv6Address DisplayString,
            lcsStatusIpv6AddressesEntryStatus DisplayString,
            lcsStatusIpv6AddressesEntryProperties DisplayString,
            lcsStatusIpv6AddressesEntryAddressType DisplayString,
            lcsStatusIpv6AddressesEntryInterfaceType INTEGER
    }

-- {COLUMN} 1.3.6.1.4.1.2356.11.1.77.1.1.1
lcsStatusIpv6AddressesEntryInterfaceName OBJECT-TYPE
    SYNTAX     DisplayString (SIZE(0..25))
    MAX-ACCESS read-only
    STATUS     current
    DESCRIPTION
            "-- empty --"
    ::= { lcsStatusIpv6AddressesEntry 1 }

-- {COLUMN} 1.3.6.1.4.1.2356.11.1.77.1.1.2
lcsStatusIpv6AddressesEntryIpv6Address OBJECT-TYPE
    SYNTAX     DisplayString (SIZE(0..39))
    MAX-ACCESS read-only
    STATUS     current
    DESCRIPTION
            "-- empty --"
    ::= { lcsStatusIpv6AddressesEntry 2 }

-- {COLUMN} 1.3.6.1.4.1.2356.11.1.77.1.1.3
lcsStatusIpv6AddressesEntryStatus OBJECT-TYPE
    SYNTAX     DisplayString (SIZE(0..10))
    MAX-ACCESS read-only
    STATUS     current
    DESCRIPTION
            "-- empty --"
    ::= { lcsStatusIpv6AddressesEntry 3 }

-- {COLUMN} 1.3.6.1.4.1.2356.11.1.77.1.1.4
lcsStatusIpv6AddressesEntryProperties OBJECT-TYPE
    SYNTAX     DisplayString (SIZE(0..57))
    MAX-ACCESS read-only
    STATUS     current
    DESCRIPTION
            "-- empty --"
    ::= { lcsStatusIpv6AddressesEntry 4 }

-- {COLUMN} 1.3.6.1.4.1.2356.11.1.77.1.1.5
lcsStatusIpv6AddressesEntryAddressType OBJECT-TYPE
    SYNTAX     DisplayString (SIZE(0..26))
    MAX-ACCESS read-only
    STATUS     current
    DESCRIPTION
            "-- empty --"
    ::= { lcsStatusIpv6AddressesEntry 5 }

-- {COLUMN} 1.3.6.1.4.1.2356.11.1.77.1.1.6
lcsStatusIpv6AddressesEntryInterfaceType OBJECT-TYPE
    SYNTAX     INTEGER {
                  eLan (0),
                  eWan (1),
                  eLoopback (2)
            }
    MAX-ACCESS read-only
    STATUS     current
    DESCRIPTION
            "-- empty --"
    ::= { lcsStatusIpv6AddressesEntry 6 }

-- {TABLE} 1.3.6.1.4.1.2356.11.1.77.2
lcsStatusIpv6PrefixTable OBJECT-TYPE
    SYNTAX     SEQUENCE OF LcsStatusIpv6PrefixEntry
    MAX-ACCESS not-accessible
    STATUS     current
    DESCRIPTION
            "-- empty --"
    ::= { lcsStatusIpv6 2 }

-- {ROW} 1.3.6.1.4.1.2356.11.1.77.2.1
lcsStatusIpv6PrefixEntry OBJECT-TYPE
    SYNTAX     LcsStatusIpv6PrefixEntry
    MAX-ACCESS not-accessible
    STATUS     current
    DESCRIPTION
            ""
    INDEX {
            lcsStatusIpv6PrefixEntryInterfaceName,
            lcsStatusIpv6PrefixEntryPrefix
          }
    ::= { lcsStatusIpv6PrefixTable 1 }

LcsStatusIpv6PrefixEntry ::= SEQUENCE {
            lcsStatusIpv6PrefixEntryInterfaceName DisplayString,
            lcsStatusIpv6PrefixEntryPrefix DisplayString,
            lcsStatusIpv6PrefixEntryStatus DisplayString,
            lcsStatusIpv6PrefixEntryType DisplayString
    }

-- {COLUMN} 1.3.6.1.4.1.2356.11.1.77.2.1.1
lcsStatusIpv6PrefixEntryInterfaceName OBJECT-TYPE
    SYNTAX     DisplayString (SIZE(0..25))
    MAX-ACCESS read-only
    STATUS     current
    DESCRIPTION
            "-- empty --"
    ::= { lcsStatusIpv6PrefixEntry 1 }

-- {COLUMN} 1.3.6.1.4.1.2356.11.1.77.2.1.2
lcsStatusIpv6PrefixEntryPrefix OBJECT-TYPE
    SYNTAX     DisplayString (SIZE(0..43))
    MAX-ACCESS read-only
    STATUS     current
    DESCRIPTION
            "-- empty --"
    ::= { lcsStatusIpv6PrefixEntry 2 }

-- {COLUMN} 1.3.6.1.4.1.2356.11.1.77.2.1.3
lcsStatusIpv6PrefixEntryStatus OBJECT-TYPE
    SYNTAX     DisplayString (SIZE(0..10))
    MAX-ACCESS read-only
    STATUS     current
    DESCRIPTION
            "-- empty --"
    ::= { lcsStatusIpv6PrefixEntry 3 }

-- {COLUMN} 1.3.6.1.4.1.2356.11.1.77.2.1.4
lcsStatusIpv6PrefixEntryType OBJECT-TYPE
    SYNTAX     DisplayString (SIZE(0..26))
    MAX-ACCESS read-only
    STATUS     current
    DESCRIPTION
            "-- empty --"
    ::= { lcsStatusIpv6PrefixEntry 4 }

-- {NODE} 1.3.6.1.4.1.2356.11.1.77.3
lcsStatusIpv6Dhcpv6 OBJECT IDENTIFIER ::= { lcsStatusIpv6 3 }

-- {NODE} 1.3.6.1.4.1.2356.11.1.77.3.1
lcsStatusIpv6Dhcpv6Server OBJECT IDENTIFIER ::= { lcsStatusIpv6Dhcpv6 1 }

-- {TABLE} 1.3.6.1.4.1.2356.11.1.77.3.1.1
lcsStatusIpv6Dhcpv6ServerAddressBindTable OBJECT-TYPE
    SYNTAX     SEQUENCE OF LcsStatusIpv6Dhcpv6ServerAddressBindEntry
    MAX-ACCESS not-accessible
    STATUS     current
    DESCRIPTION
            ""
    ::= { lcsStatusIpv6Dhcpv6Server 1 }

-- {ROW} 1.3.6.1.4.1.2356.11.1.77.3.1.1.1
lcsStatusIpv6Dhcpv6ServerAddressBindEntry OBJECT-TYPE
    SYNTAX     LcsStatusIpv6Dhcpv6ServerAddressBindEntry
    MAX-ACCESS not-accessible
    STATUS     current
    DESCRIPTION
            ""
    INDEX {
            lcsStatusIpv6Dhcpv6ServerAddressBindEntryInterfaceNameOrRelay,
            lcsStatusIpv6Dhcpv6ServerAddressBindEntryAddress
          }
    ::= { lcsStatusIpv6Dhcpv6ServerAddressBindTable 1 }

LcsStatusIpv6Dhcpv6ServerAddressBindEntry ::= SEQUENCE {
            lcsStatusIpv6Dhcpv6ServerAddressBindEntryInterfaceNameOrRelay DisplayString,
            lcsStatusIpv6Dhcpv6ServerAddressBindEntryAddress DisplayString,
            lcsStatusIpv6Dhcpv6ServerAddressBindEntryPreferredUntilNumerical Counter32,
            lcsStatusIpv6Dhcpv6ServerAddressBindEntryPreferredUntil DisplayString,
            lcsStatusIpv6Dhcpv6ServerAddressBindEntryValidUntilNumerical Counter32,
            lcsStatusIpv6Dhcpv6ServerAddressBindEntryValidUntil DisplayString,
            lcsStatusIpv6Dhcpv6ServerAddressBindEntryClientId DisplayString,
            lcsStatusIpv6Dhcpv6ServerAddressBindEntryIaId Integer32,
            lcsStatusIpv6Dhcpv6ServerAddressBindEntryHostName DisplayString,
            lcsStatusIpv6Dhcpv6ServerAddressBindEntryUpdatedAtNumerical Counter32,
            lcsStatusIpv6Dhcpv6ServerAddressBindEntryUpdatedAt DisplayString
    }

-- {COLUMN} 1.3.6.1.4.1.2356.11.1.77.3.1.1.1.1
lcsStatusIpv6Dhcpv6ServerAddressBindEntryInterfaceNameOrRelay OBJECT-TYPE
    SYNTAX     DisplayString (SIZE(0..255))
    MAX-ACCESS read-only
    STATUS     current
    DESCRIPTION
            "-- empty --"
    ::= { lcsStatusIpv6Dhcpv6ServerAddressBindEntry 1 }

-- {COLUMN} 1.3.6.1.4.1.2356.11.1.77.3.1.1.1.2
lcsStatusIpv6Dhcpv6ServerAddressBindEntryAddress OBJECT-TYPE
    SYNTAX     DisplayString (SIZE(0..255))
    MAX-ACCESS read-only
    STATUS     current
    DESCRIPTION
            "-- empty --"
    ::= { lcsStatusIpv6Dhcpv6ServerAddressBindEntry 2 }

-- {COLUMN} 1.3.6.1.4.1.2356.11.1.77.3.1.1.1.3
lcsStatusIpv6Dhcpv6ServerAddressBindEntryPreferredUntilNumerical OBJECT-TYPE
    SYNTAX     Counter32
    MAX-ACCESS read-only
    STATUS     current
    DESCRIPTION
            "-- empty --"
    ::= { lcsStatusIpv6Dhcpv6ServerAddressBindEntry 3 }

-- {COLUMN} 1.3.6.1.4.1.2356.11.1.77.3.1.1.1.4
lcsStatusIpv6Dhcpv6ServerAddressBindEntryPreferredUntil OBJECT-TYPE
    SYNTAX     DisplayString (SIZE(0..255))
    MAX-ACCESS read-only
    STATUS     current
    DESCRIPTION
            "-- empty --"
    ::= { lcsStatusIpv6Dhcpv6ServerAddressBindEntry 4 }

-- {COLUMN} 1.3.6.1.4.1.2356.11.1.77.3.1.1.1.5
lcsStatusIpv6Dhcpv6ServerAddressBindEntryValidUntilNumerical OBJECT-TYPE
    SYNTAX     Counter32
    MAX-ACCESS read-only
    STATUS     current
    DESCRIPTION
            "-- empty --"
    ::= { lcsStatusIpv6Dhcpv6ServerAddressBindEntry 5 }

-- {COLUMN} 1.3.6.1.4.1.2356.11.1.77.3.1.1.1.6
lcsStatusIpv6Dhcpv6ServerAddressBindEntryValidUntil OBJECT-TYPE
    SYNTAX     DisplayString (SIZE(0..255))
    MAX-ACCESS read-only
    STATUS     current
    DESCRIPTION
            "-- empty --"
    ::= { lcsStatusIpv6Dhcpv6ServerAddressBindEntry 6 }

-- {COLUMN} 1.3.6.1.4.1.2356.11.1.77.3.1.1.1.7
lcsStatusIpv6Dhcpv6ServerAddressBindEntryClientId OBJECT-TYPE
    SYNTAX     DisplayString (SIZE(0..255))
    MAX-ACCESS read-only
    STATUS     current
    DESCRIPTION
            "-- empty --"
    ::= { lcsStatusIpv6Dhcpv6ServerAddressBindEntry 7 }

-- {COLUMN} 1.3.6.1.4.1.2356.11.1.77.3.1.1.1.8
lcsStatusIpv6Dhcpv6ServerAddressBindEntryIaId OBJECT-TYPE
    SYNTAX     Integer32 (0..2147483647)
    MAX-ACCESS read-only
    STATUS     current
    DESCRIPTION
            "-- empty --"
    ::= { lcsStatusIpv6Dhcpv6ServerAddressBindEntry 8 }

-- {COLUMN} 1.3.6.1.4.1.2356.11.1.77.3.1.1.1.9
lcsStatusIpv6Dhcpv6ServerAddressBindEntryHostName OBJECT-TYPE
    SYNTAX     DisplayString (SIZE(0..255))
    MAX-ACCESS read-only
    STATUS     current
    DESCRIPTION
            "-- empty --"
    ::= { lcsStatusIpv6Dhcpv6ServerAddressBindEntry 9 }

-- {COLUMN} 1.3.6.1.4.1.2356.11.1.77.3.1.1.1.10
lcsStatusIpv6Dhcpv6ServerAddressBindEntryUpdatedAtNumerical OBJECT-TYPE
    SYNTAX     Counter32
    MAX-ACCESS read-only
    STATUS     current
    DESCRIPTION
            "-- empty --"
    ::= { lcsStatusIpv6Dhcpv6ServerAddressBindEntry 10 }

-- {COLUMN} 1.3.6.1.4.1.2356.11.1.77.3.1.1.1.11
lcsStatusIpv6Dhcpv6ServerAddressBindEntryUpdatedAt OBJECT-TYPE
    SYNTAX     DisplayString (SIZE(0..255))
    MAX-ACCESS read-only
    STATUS     current
    DESCRIPTION
            "-- empty --"
    ::= { lcsStatusIpv6Dhcpv6ServerAddressBindEntry 11 }

-- {TABLE} 1.3.6.1.4.1.2356.11.1.77.3.1.2
lcsStatusIpv6Dhcpv6ServerPdBindingsTable OBJECT-TYPE
    SYNTAX     SEQUENCE OF LcsStatusIpv6Dhcpv6ServerPdBindingsEntry
    MAX-ACCESS not-accessible
    STATUS     current
    DESCRIPTION
            "-- empty --"
    ::= { lcsStatusIpv6Dhcpv6Server 2 }

-- {ROW} 1.3.6.1.4.1.2356.11.1.77.3.1.2.1
lcsStatusIpv6Dhcpv6ServerPdBindingsEntry OBJECT-TYPE
    SYNTAX     LcsStatusIpv6Dhcpv6ServerPdBindingsEntry
    MAX-ACCESS not-accessible
    STATUS     current
    DESCRIPTION
            ""
    INDEX {
            lcsStatusIpv6Dhcpv6ServerPdBindingsEntryInterfaceNameOrRelay,
            lcsStatusIpv6Dhcpv6ServerPdBindingsEntryPdPrefix
          }
    ::= { lcsStatusIpv6Dhcpv6ServerPdBindingsTable 1 }

LcsStatusIpv6Dhcpv6ServerPdBindingsEntry ::= SEQUENCE {
            lcsStatusIpv6Dhcpv6ServerPdBindingsEntryInterfaceNameOrRelay DisplayString,
            lcsStatusIpv6Dhcpv6ServerPdBindingsEntryPdPrefix DisplayString,
            lcsStatusIpv6Dhcpv6ServerPdBindingsEntryPreferredUntilNumerical Counter32,
            lcsStatusIpv6Dhcpv6ServerPdBindingsEntryPreferredUntil DisplayString,
            lcsStatusIpv6Dhcpv6ServerPdBindingsEntryValidUntilNumerical Counter32,
            lcsStatusIpv6Dhcpv6ServerPdBindingsEntryValidUntil DisplayString,
            lcsStatusIpv6Dhcpv6ServerPdBindingsEntryClientId DisplayString,
            lcsStatusIpv6Dhcpv6ServerPdBindingsEntryIaId Integer32,
            lcsStatusIpv6Dhcpv6ServerPdBindingsEntryHostName DisplayString,
            lcsStatusIpv6Dhcpv6ServerPdBindingsEntryUpdatedAtNumerical Counter32,
            lcsStatusIpv6Dhcpv6ServerPdBindingsEntryUpdatedAt DisplayString
    }

-- {COLUMN} 1.3.6.1.4.1.2356.11.1.77.3.1.2.1.1
lcsStatusIpv6Dhcpv6ServerPdBindingsEntryInterfaceNameOrRelay OBJECT-TYPE
    SYNTAX     DisplayString (SIZE(0..255))
    MAX-ACCESS read-only
    STATUS     current
    DESCRIPTION
            "-- empty --"
    ::= { lcsStatusIpv6Dhcpv6ServerPdBindingsEntry 1 }

-- {COLUMN} 1.3.6.1.4.1.2356.11.1.77.3.1.2.1.2
lcsStatusIpv6Dhcpv6ServerPdBindingsEntryPdPrefix OBJECT-TYPE
    SYNTAX     DisplayString (SIZE(0..255))
    MAX-ACCESS read-only
    STATUS     current
    DESCRIPTION
            "-- empty --"
    ::= { lcsStatusIpv6Dhcpv6ServerPdBindingsEntry 2 }

-- {COLUMN} 1.3.6.1.4.1.2356.11.1.77.3.1.2.1.3
lcsStatusIpv6Dhcpv6ServerPdBindingsEntryPreferredUntilNumerical OBJECT-TYPE
    SYNTAX     Counter32
    MAX-ACCESS read-only
    STATUS     current
    DESCRIPTION
            "-- empty --"
    ::= { lcsStatusIpv6Dhcpv6ServerPdBindingsEntry 3 }

-- {COLUMN} 1.3.6.1.4.1.2356.11.1.77.3.1.2.1.4
lcsStatusIpv6Dhcpv6ServerPdBindingsEntryPreferredUntil OBJECT-TYPE
    SYNTAX     DisplayString (SIZE(0..255))
    MAX-ACCESS read-only
    STATUS     current
    DESCRIPTION
            "-- empty --"
    ::= { lcsStatusIpv6Dhcpv6ServerPdBindingsEntry 4 }

-- {COLUMN} 1.3.6.1.4.1.2356.11.1.77.3.1.2.1.5
lcsStatusIpv6Dhcpv6ServerPdBindingsEntryValidUntilNumerical OBJECT-TYPE
    SYNTAX     Counter32
    MAX-ACCESS read-only
    STATUS     current
    DESCRIPTION
            "-- empty --"
    ::= { lcsStatusIpv6Dhcpv6ServerPdBindingsEntry 5 }

-- {COLUMN} 1.3.6.1.4.1.2356.11.1.77.3.1.2.1.6
lcsStatusIpv6Dhcpv6ServerPdBindingsEntryValidUntil OBJECT-TYPE
    SYNTAX     DisplayString (SIZE(0..255))
    MAX-ACCESS read-only
    STATUS     current
    DESCRIPTION
            "-- empty --"
    ::= { lcsStatusIpv6Dhcpv6ServerPdBindingsEntry 6 }

-- {COLUMN} 1.3.6.1.4.1.2356.11.1.77.3.1.2.1.7
lcsStatusIpv6Dhcpv6ServerPdBindingsEntryClientId OBJECT-TYPE
    SYNTAX     DisplayString (SIZE(0..255))
    MAX-ACCESS read-only
    STATUS     current
    DESCRIPTION
            "-- empty --"
    ::= { lcsStatusIpv6Dhcpv6ServerPdBindingsEntry 7 }

-- {COLUMN} 1.3.6.1.4.1.2356.11.1.77.3.1.2.1.8
lcsStatusIpv6Dhcpv6ServerPdBindingsEntryIaId OBJECT-TYPE
    SYNTAX     Integer32 (0..2147483647)
    MAX-ACCESS read-only
    STATUS     current
    DESCRIPTION
            "-- empty --"
    ::= { lcsStatusIpv6Dhcpv6ServerPdBindingsEntry 8 }

-- {COLUMN} 1.3.6.1.4.1.2356.11.1.77.3.1.2.1.9
lcsStatusIpv6Dhcpv6ServerPdBindingsEntryHostName OBJECT-TYPE
    SYNTAX     DisplayString (SIZE(0..255))
    MAX-ACCESS read-only
    STATUS     current
    DESCRIPTION
            "-- empty --"
    ::= { lcsStatusIpv6Dhcpv6ServerPdBindingsEntry 9 }

-- {COLUMN} 1.3.6.1.4.1.2356.11.1.77.3.1.2.1.10
lcsStatusIpv6Dhcpv6ServerPdBindingsEntryUpdatedAtNumerical OBJECT-TYPE
    SYNTAX     Counter32
    MAX-ACCESS read-only
    STATUS     current
    DESCRIPTION
            "-- empty --"
    ::= { lcsStatusIpv6Dhcpv6ServerPdBindingsEntry 10 }

-- {COLUMN} 1.3.6.1.4.1.2356.11.1.77.3.1.2.1.11
lcsStatusIpv6Dhcpv6ServerPdBindingsEntryUpdatedAt OBJECT-TYPE
    SYNTAX     DisplayString (SIZE(0..255))
    MAX-ACCESS read-only
    STATUS     current
    DESCRIPTION
            "-- empty --"
    ::= { lcsStatusIpv6Dhcpv6ServerPdBindingsEntry 11 }

-- {TABLE} 1.3.6.1.4.1.2356.11.1.77.3.1.3
lcsStatusIpv6Dhcpv6ServerDeclinedAddrTable OBJECT-TYPE
    SYNTAX     SEQUENCE OF LcsStatusIpv6Dhcpv6ServerDeclinedAddrEntry
    MAX-ACCESS not-accessible
    STATUS     current
    DESCRIPTION
            ""
    ::= { lcsStatusIpv6Dhcpv6Server 3 }

-- {ROW} 1.3.6.1.4.1.2356.11.1.77.3.1.3.1
lcsStatusIpv6Dhcpv6ServerDeclinedAddrEntry OBJECT-TYPE
    SYNTAX     LcsStatusIpv6Dhcpv6ServerDeclinedAddrEntry
    MAX-ACCESS not-accessible
    STATUS     current
    DESCRIPTION
            ""
    INDEX {
            lcsStatusIpv6Dhcpv6ServerDeclinedAddrEntryInterfaceNameOrRelay,
            lcsStatusIpv6Dhcpv6ServerDeclinedAddrEntryAddress
          }
    ::= { lcsStatusIpv6Dhcpv6ServerDeclinedAddrTable 1 }

LcsStatusIpv6Dhcpv6ServerDeclinedAddrEntry ::= SEQUENCE {
            lcsStatusIpv6Dhcpv6ServerDeclinedAddrEntryInterfaceNameOrRelay DisplayString,
            lcsStatusIpv6Dhcpv6ServerDeclinedAddrEntryAddress DisplayString,
            lcsStatusIpv6Dhcpv6ServerDeclinedAddrEntryDeclinedAtNumerical Counter32,
            lcsStatusIpv6Dhcpv6ServerDeclinedAddrEntryDeclinedAt DisplayString,
            lcsStatusIpv6Dhcpv6ServerDeclinedAddrEntryClientId DisplayString,
            lcsStatusIpv6Dhcpv6ServerDeclinedAddrEntryIaId Integer32,
            lcsStatusIpv6Dhcpv6ServerDeclinedAddrEntryHostName DisplayString
    }

-- {COLUMN} 1.3.6.1.4.1.2356.11.1.77.3.1.3.1.1
lcsStatusIpv6Dhcpv6ServerDeclinedAddrEntryInterfaceNameOrRelay OBJECT-TYPE
    SYNTAX     DisplayString (SIZE(0..255))
    MAX-ACCESS read-only
    STATUS     current
    DESCRIPTION
            "-- empty --"
    ::= { lcsStatusIpv6Dhcpv6ServerDeclinedAddrEntry 1 }

-- {COLUMN} 1.3.6.1.4.1.2356.11.1.77.3.1.3.1.2
lcsStatusIpv6Dhcpv6ServerDeclinedAddrEntryAddress OBJECT-TYPE
    SYNTAX     DisplayString (SIZE(0..255))
    MAX-ACCESS read-only
    STATUS     current
    DESCRIPTION
            "-- empty --"
    ::= { lcsStatusIpv6Dhcpv6ServerDeclinedAddrEntry 2 }

-- {COLUMN} 1.3.6.1.4.1.2356.11.1.77.3.1.3.1.3
lcsStatusIpv6Dhcpv6ServerDeclinedAddrEntryDeclinedAtNumerical OBJECT-TYPE
    SYNTAX     Counter32
    MAX-ACCESS read-only
    STATUS     current
    DESCRIPTION
            "-- empty --"
    ::= { lcsStatusIpv6Dhcpv6ServerDeclinedAddrEntry 3 }

-- {COLUMN} 1.3.6.1.4.1.2356.11.1.77.3.1.3.1.4
lcsStatusIpv6Dhcpv6ServerDeclinedAddrEntryDeclinedAt OBJECT-TYPE
    SYNTAX     DisplayString (SIZE(0..255))
    MAX-ACCESS read-only
    STATUS     current
    DESCRIPTION
            "-- empty --"
    ::= { lcsStatusIpv6Dhcpv6ServerDeclinedAddrEntry 4 }

-- {COLUMN} 1.3.6.1.4.1.2356.11.1.77.3.1.3.1.5
lcsStatusIpv6Dhcpv6ServerDeclinedAddrEntryClientId OBJECT-TYPE
    SYNTAX     DisplayString (SIZE(0..255))
    MAX-ACCESS read-only
    STATUS     current
    DESCRIPTION
            "-- empty --"
    ::= { lcsStatusIpv6Dhcpv6ServerDeclinedAddrEntry 5 }

-- {COLUMN} 1.3.6.1.4.1.2356.11.1.77.3.1.3.1.6
lcsStatusIpv6Dhcpv6ServerDeclinedAddrEntryIaId OBJECT-TYPE
    SYNTAX     Integer32 (0..2147483647)
    MAX-ACCESS read-only
    STATUS     current
    DESCRIPTION
            "-- empty --"
    ::= { lcsStatusIpv6Dhcpv6ServerDeclinedAddrEntry 6 }

-- {COLUMN} 1.3.6.1.4.1.2356.11.1.77.3.1.3.1.9
lcsStatusIpv6Dhcpv6ServerDeclinedAddrEntryHostName OBJECT-TYPE
    SYNTAX     DisplayString (SIZE(0..255))
    MAX-ACCESS read-only
    STATUS     current
    DESCRIPTION
            "-- empty --"
    ::= { lcsStatusIpv6Dhcpv6ServerDeclinedAddrEntry 9 }

-- {TABLE} 1.3.6.1.4.1.2356.11.1.77.3.1.4
lcsStatusIpv6Dhcpv6ServerInterfaceStateTable OBJECT-TYPE
    SYNTAX     SEQUENCE OF LcsStatusIpv6Dhcpv6ServerInterfaceStateEntry
    MAX-ACCESS not-accessible
    STATUS     current
    DESCRIPTION
            "-- empty --"
    ::= { lcsStatusIpv6Dhcpv6Server 4 }

-- {ROW} 1.3.6.1.4.1.2356.11.1.77.3.1.4.1
lcsStatusIpv6Dhcpv6ServerInterfaceStateEntry OBJECT-TYPE
    SYNTAX     LcsStatusIpv6Dhcpv6ServerInterfaceStateEntry
    MAX-ACCESS not-accessible
    STATUS     current
    DESCRIPTION
            ""
    INDEX {
            lcsStatusIpv6Dhcpv6ServerInterfaceStateEntryInterfaceNameOrRelay
          }
    ::= { lcsStatusIpv6Dhcpv6ServerInterfaceStateTable 1 }

LcsStatusIpv6Dhcpv6ServerInterfaceStateEntry ::= SEQUENCE {
            lcsStatusIpv6Dhcpv6ServerInterfaceStateEntryInterfaceNameOrRelay DisplayString,
            lcsStatusIpv6Dhcpv6ServerInterfaceStateEntryOperating INTEGER,
            lcsStatusIpv6Dhcpv6ServerInterfaceStateEntryMode INTEGER,
            lcsStatusIpv6Dhcpv6ServerInterfaceStateEntryAssignPd INTEGER
    }

-- {COLUMN} 1.3.6.1.4.1.2356.11.1.77.3.1.4.1.1
lcsStatusIpv6Dhcpv6ServerInterfaceStateEntryInterfaceNameOrRelay OBJECT-TYPE
    SYNTAX     DisplayString (SIZE(0..255))
    MAX-ACCESS read-only
    STATUS     current
    DESCRIPTION
            "-- empty --"
    ::= { lcsStatusIpv6Dhcpv6ServerInterfaceStateEntry 1 }

-- {COLUMN} 1.3.6.1.4.1.2356.11.1.77.3.1.4.1.2
lcsStatusIpv6Dhcpv6ServerInterfaceStateEntryOperating OBJECT-TYPE
    SYNTAX     INTEGER {
                  eNo (0),
                  eYes (1)
            }
    MAX-ACCESS read-only
    STATUS     current
    DESCRIPTION
            "-- empty --"
    ::= { lcsStatusIpv6Dhcpv6ServerInterfaceStateEntry 2 }

-- {COLUMN} 1.3.6.1.4.1.2356.11.1.77.3.1.4.1.3
lcsStatusIpv6Dhcpv6ServerInterfaceStateEntryMode OBJECT-TYPE
    SYNTAX     INTEGER {
                  eStateless (0),
                  eStateful (1),
                  eStatic (2)
            }
    MAX-ACCESS read-only
    STATUS     current
    DESCRIPTION
            "-- empty --"
    ::= { lcsStatusIpv6Dhcpv6ServerInterfaceStateEntry 3 }

-- {COLUMN} 1.3.6.1.4.1.2356.11.1.77.3.1.4.1.4
lcsStatusIpv6Dhcpv6ServerInterfaceStateEntryAssignPd OBJECT-TYPE
    SYNTAX     INTEGER {
                  eNo (0),
                  eYes (1)
            }
    MAX-ACCESS read-only
    STATUS     current
    DESCRIPTION
            "-- empty --"
    ::= { lcsStatusIpv6Dhcpv6ServerInterfaceStateEntry 4 }

-- {SCALAR} 1.3.6.1.4.1.2356.11.1.77.3.1.5
lcsStatusIpv6Dhcpv6ServerServerId OBJECT-TYPE
    SYNTAX     DisplayString (SIZE(0..97))
    MAX-ACCESS read-only
    STATUS     current
    DESCRIPTION
            "-- empty --"
    ::= { lcsStatusIpv6Dhcpv6Server 5 }

-- {TABLE} 1.3.6.1.4.1.2356.11.1.77.3.1.6
lcsStatusIpv6Dhcpv6ServerClientsTable OBJECT-TYPE
    SYNTAX     SEQUENCE OF LcsStatusIpv6Dhcpv6ServerClientsEntry
    MAX-ACCESS not-accessible
    STATUS     current
    DESCRIPTION
            "-- empty --"
    ::= { lcsStatusIpv6Dhcpv6Server 6 }

-- {ROW} 1.3.6.1.4.1.2356.11.1.77.3.1.6.1
lcsStatusIpv6Dhcpv6ServerClientsEntry OBJECT-TYPE
    SYNTAX     LcsStatusIpv6Dhcpv6ServerClientsEntry
    MAX-ACCESS not-accessible
    STATUS     current
    DESCRIPTION
            ""
    INDEX {
            lcsStatusIpv6Dhcpv6ServerClientsEntryClientId
          }
    ::= { lcsStatusIpv6Dhcpv6ServerClientsTable 1 }

LcsStatusIpv6Dhcpv6ServerClientsEntry ::= SEQUENCE {
            lcsStatusIpv6Dhcpv6ServerClientsEntryClientId DisplayString,
            lcsStatusIpv6Dhcpv6ServerClientsEntryHostName DisplayString,
            lcsStatusIpv6Dhcpv6ServerClientsEntryReconfNegotiated INTEGER,
            lcsStatusIpv6Dhcpv6ServerClientsEntryReconfNegotiatedAtNumerical Counter32,
            lcsStatusIpv6Dhcpv6ServerClientsEntryReconfNegotiatedAt DisplayString,
            lcsStatusIpv6Dhcpv6ServerClientsEntryReconfigure INTEGER,
            lcsStatusIpv6Dhcpv6ServerClientsEntryMacAddress DisplayString
    }

-- {COLUMN} 1.3.6.1.4.1.2356.11.1.77.3.1.6.1.1
lcsStatusIpv6Dhcpv6ServerClientsEntryClientId OBJECT-TYPE
    SYNTAX     DisplayString (SIZE(0..255))
    MAX-ACCESS read-only
    STATUS     current
    DESCRIPTION
            "-- empty --"
    ::= { lcsStatusIpv6Dhcpv6ServerClientsEntry 1 }

-- {COLUMN} 1.3.6.1.4.1.2356.11.1.77.3.1.6.1.2
lcsStatusIpv6Dhcpv6ServerClientsEntryHostName OBJECT-TYPE
    SYNTAX     DisplayString (SIZE(0..255))
    MAX-ACCESS read-only
    STATUS     current
    DESCRIPTION
            "-- empty --"
    ::= { lcsStatusIpv6Dhcpv6ServerClientsEntry 2 }

-- {COLUMN} 1.3.6.1.4.1.2356.11.1.77.3.1.6.1.3
lcsStatusIpv6Dhcpv6ServerClientsEntryReconfNegotiated OBJECT-TYPE
    SYNTAX     INTEGER {
                  eNo (0),
                  eYes (1),
                  eNotEnoughRandom (2)
            }
    MAX-ACCESS read-only
    STATUS     current
    DESCRIPTION
            "-- empty --"
    ::= { lcsStatusIpv6Dhcpv6ServerClientsEntry 3 }

-- {COLUMN} 1.3.6.1.4.1.2356.11.1.77.3.1.6.1.4
lcsStatusIpv6Dhcpv6ServerClientsEntryReconfNegotiatedAtNumerical OBJECT-TYPE
    SYNTAX     Counter32
    MAX-ACCESS read-only
    STATUS     current
    DESCRIPTION
            "-- empty --"
    ::= { lcsStatusIpv6Dhcpv6ServerClientsEntry 4 }

-- {COLUMN} 1.3.6.1.4.1.2356.11.1.77.3.1.6.1.5
lcsStatusIpv6Dhcpv6ServerClientsEntryReconfNegotiatedAt OBJECT-TYPE
    SYNTAX     DisplayString (SIZE(0..255))
    MAX-ACCESS read-only
    STATUS     current
    DESCRIPTION
            "-- empty --"
    ::= { lcsStatusIpv6Dhcpv6ServerClientsEntry 5 }

-- {COLUMN} 1.3.6.1.4.1.2356.11.1.77.3.1.6.1.6
lcsStatusIpv6Dhcpv6ServerClientsEntryReconfigure OBJECT-TYPE
    SYNTAX     INTEGER {
                  eOff (0),
                  eRunning (1),
                  eSucceeded (2),
                  eFailed (3)
            }
    MAX-ACCESS read-only
    STATUS     current
    DESCRIPTION
            "-- empty --"
    ::= { lcsStatusIpv6Dhcpv6ServerClientsEntry 6 }

-- {COLUMN} 1.3.6.1.4.1.2356.11.1.77.3.1.6.1.7
lcsStatusIpv6Dhcpv6ServerClientsEntryMacAddress OBJECT-TYPE
    SYNTAX     DisplayString (SIZE(0..255))
    MAX-ACCESS read-only
    STATUS     current
    DESCRIPTION
            "-- empty --"
    ::= { lcsStatusIpv6Dhcpv6ServerClientsEntry 7 }

-- {SCALAR} 1.3.6.1.4.1.2356.11.1.77.3.1.7
lcsStatusIpv6Dhcpv6ServerReconfigure OBJECT-TYPE
    SYNTAX     DisplayString
    MAX-ACCESS read-write
    STATUS     current
    DESCRIPTION
            "-- empty --"
    ::= { lcsStatusIpv6Dhcpv6Server 7 }

-- {TABLE} 1.3.6.1.4.1.2356.11.1.77.3.1.8
lcsStatusIpv6Dhcpv6ServerRasInterfacesTable OBJECT-TYPE
    SYNTAX     SEQUENCE OF LcsStatusIpv6Dhcpv6ServerRasInterfacesEntry
    MAX-ACCESS not-accessible
    STATUS     current
    DESCRIPTION
            "-- empty --"
    ::= { lcsStatusIpv6Dhcpv6Server 8 }

-- {ROW} 1.3.6.1.4.1.2356.11.1.77.3.1.8.1
lcsStatusIpv6Dhcpv6ServerRasInterfacesEntry OBJECT-TYPE
    SYNTAX     LcsStatusIpv6Dhcpv6ServerRasInterfacesEntry
    MAX-ACCESS not-accessible
    STATUS     current
    DESCRIPTION
            ""
    INDEX {
            lcsStatusIpv6Dhcpv6ServerRasInterfacesEntryInterfaceName
          }
    ::= { lcsStatusIpv6Dhcpv6ServerRasInterfacesTable 1 }

LcsStatusIpv6Dhcpv6ServerRasInterfacesEntry ::= SEQUENCE {
            lcsStatusIpv6Dhcpv6ServerRasInterfacesEntryInterfaceName OCTET STRING,
            lcsStatusIpv6Dhcpv6ServerRasInterfacesEntryTemplateInterface OCTET STRING,
            lcsStatusIpv6Dhcpv6ServerRasInterfacesEntryRadiusPdPrefixes OCTET STRING
    }

-- {COLUMN} 1.3.6.1.4.1.2356.11.1.77.3.1.8.1.1
lcsStatusIpv6Dhcpv6ServerRasInterfacesEntryInterfaceName OBJECT-TYPE
    SYNTAX     OCTET STRING (SIZE(0..26))
    MAX-ACCESS read-only
    STATUS     current
    DESCRIPTION
            "-- empty --"
    ::= { lcsStatusIpv6Dhcpv6ServerRasInterfacesEntry 1 }

-- {COLUMN} 1.3.6.1.4.1.2356.11.1.77.3.1.8.1.2
lcsStatusIpv6Dhcpv6ServerRasInterfacesEntryTemplateInterface OBJECT-TYPE
    SYNTAX     OCTET STRING (SIZE(0..17))
    MAX-ACCESS read-only
    STATUS     current
    DESCRIPTION
            "-- empty --"
    ::= { lcsStatusIpv6Dhcpv6ServerRasInterfacesEntry 2 }

-- {COLUMN} 1.3.6.1.4.1.2356.11.1.77.3.1.8.1.3
lcsStatusIpv6Dhcpv6ServerRasInterfacesEntryRadiusPdPrefixes OBJECT-TYPE
    SYNTAX     OCTET STRING (SIZE(0..87))
    MAX-ACCESS read-only
    STATUS     current
    DESCRIPTION
            "-- empty --"
    ::= { lcsStatusIpv6Dhcpv6ServerRasInterfacesEntry 3 }

-- {NODE} 1.3.6.1.4.1.2356.11.1.77.3.2
lcsStatusIpv6Dhcpv6Client OBJECT IDENTIFIER ::= { lcsStatusIpv6Dhcpv6 2 }

-- {TABLE} 1.3.6.1.4.1.2356.11.1.77.3.2.1
lcsStatusIpv6Dhcpv6ClientInterfaceListTable OBJECT-TYPE
    SYNTAX     SEQUENCE OF LcsStatusIpv6Dhcpv6ClientInterfaceListEntry
    MAX-ACCESS not-accessible
    STATUS     current
    DESCRIPTION
            "-- empty --"
    ::= { lcsStatusIpv6Dhcpv6Client 1 }

-- {ROW} 1.3.6.1.4.1.2356.11.1.77.3.2.1.1
lcsStatusIpv6Dhcpv6ClientInterfaceListEntry OBJECT-TYPE
    SYNTAX     LcsStatusIpv6Dhcpv6ClientInterfaceListEntry
    MAX-ACCESS not-accessible
    STATUS     current
    DESCRIPTION
            ""
    INDEX {
            lcsStatusIpv6Dhcpv6ClientInterfaceListEntryInterfaceName
          }
    ::= { lcsStatusIpv6Dhcpv6ClientInterfaceListTable 1 }

LcsStatusIpv6Dhcpv6ClientInterfaceListEntry ::= SEQUENCE {
            lcsStatusIpv6Dhcpv6ClientInterfaceListEntryInterfaceName DisplayString,
            lcsStatusIpv6Dhcpv6ClientInterfaceListEntryDnsDefault DisplayString,
            lcsStatusIpv6Dhcpv6ClientInterfaceListEntryDnsBackup DisplayString,
            lcsStatusIpv6Dhcpv6ClientInterfaceListEntryDomainList DisplayString,
            lcsStatusIpv6Dhcpv6ClientInterfaceListEntryAftrNameForDsLite DisplayString,
            lcsStatusIpv6Dhcpv6ClientInterfaceListEntrySntpServers DisplayString
    }

-- {COLUMN} 1.3.6.1.4.1.2356.11.1.77.3.2.1.1.1
lcsStatusIpv6Dhcpv6ClientInterfaceListEntryInterfaceName OBJECT-TYPE
    SYNTAX     DisplayString (SIZE(0..255))
    MAX-ACCESS read-only
    STATUS     current
    DESCRIPTION
            "-- empty --"
    ::= { lcsStatusIpv6Dhcpv6ClientInterfaceListEntry 1 }

-- {COLUMN} 1.3.6.1.4.1.2356.11.1.77.3.2.1.1.2
lcsStatusIpv6Dhcpv6ClientInterfaceListEntryDnsDefault OBJECT-TYPE
    SYNTAX     DisplayString (SIZE(0..255))
    MAX-ACCESS read-only
    STATUS     current
    DESCRIPTION
            "-- empty --"
    ::= { lcsStatusIpv6Dhcpv6ClientInterfaceListEntry 2 }

-- {COLUMN} 1.3.6.1.4.1.2356.11.1.77.3.2.1.1.3
lcsStatusIpv6Dhcpv6ClientInterfaceListEntryDnsBackup OBJECT-TYPE
    SYNTAX     DisplayString (SIZE(0..255))
    MAX-ACCESS read-only
    STATUS     current
    DESCRIPTION
            "-- empty --"
    ::= { lcsStatusIpv6Dhcpv6ClientInterfaceListEntry 3 }

-- {COLUMN} 1.3.6.1.4.1.2356.11.1.77.3.2.1.1.4
lcsStatusIpv6Dhcpv6ClientInterfaceListEntryDomainList OBJECT-TYPE
    SYNTAX     DisplayString (SIZE(0..255))
    MAX-ACCESS read-only
    STATUS     current
    DESCRIPTION
            "-- empty --"
    ::= { lcsStatusIpv6Dhcpv6ClientInterfaceListEntry 4 }

-- {COLUMN} 1.3.6.1.4.1.2356.11.1.77.3.2.1.1.5
lcsStatusIpv6Dhcpv6ClientInterfaceListEntryAftrNameForDsLite OBJECT-TYPE
    SYNTAX     DisplayString (SIZE(0..255))
    MAX-ACCESS read-only
    STATUS     current
    DESCRIPTION
            "-- empty --"
    ::= { lcsStatusIpv6Dhcpv6ClientInterfaceListEntry 5 }

-- {COLUMN} 1.3.6.1.4.1.2356.11.1.77.3.2.1.1.6
lcsStatusIpv6Dhcpv6ClientInterfaceListEntrySntpServers OBJECT-TYPE
    SYNTAX     DisplayString (SIZE(0..255))
    MAX-ACCESS read-only
    STATUS     current
    DESCRIPTION
            "-- empty --"
    ::= { lcsStatusIpv6Dhcpv6ClientInterfaceListEntry 6 }

-- {TABLE} 1.3.6.1.4.1.2356.11.1.77.3.2.2
lcsStatusIpv6Dhcpv6ClientAddressBindTable OBJECT-TYPE
    SYNTAX     SEQUENCE OF LcsStatusIpv6Dhcpv6ClientAddressBindEntry
    MAX-ACCESS not-accessible
    STATUS     current
    DESCRIPTION
            ""
    ::= { lcsStatusIpv6Dhcpv6Client 2 }

-- {ROW} 1.3.6.1.4.1.2356.11.1.77.3.2.2.1
lcsStatusIpv6Dhcpv6ClientAddressBindEntry OBJECT-TYPE
    SYNTAX     LcsStatusIpv6Dhcpv6ClientAddressBindEntry
    MAX-ACCESS not-accessible
    STATUS     current
    DESCRIPTION
            ""
    INDEX {
            lcsStatusIpv6Dhcpv6ClientAddressBindEntryInterfaceName,
            lcsStatusIpv6Dhcpv6ClientAddressBindEntryAddress
          }
    ::= { lcsStatusIpv6Dhcpv6ClientAddressBindTable 1 }

LcsStatusIpv6Dhcpv6ClientAddressBindEntry ::= SEQUENCE {
            lcsStatusIpv6Dhcpv6ClientAddressBindEntryInterfaceName DisplayString,
            lcsStatusIpv6Dhcpv6ClientAddressBindEntryAddress DisplayString,
            lcsStatusIpv6Dhcpv6ClientAddressBindEntryPreferredUntilNumerical Counter32,
            lcsStatusIpv6Dhcpv6ClientAddressBindEntryPreferredUntil DisplayString,
            lcsStatusIpv6Dhcpv6ClientAddressBindEntryValidUntilNumerical Counter32,
            lcsStatusIpv6Dhcpv6ClientAddressBindEntryValidUntil DisplayString
    }

-- {COLUMN} 1.3.6.1.4.1.2356.11.1.77.3.2.2.1.1
lcsStatusIpv6Dhcpv6ClientAddressBindEntryInterfaceName OBJECT-TYPE
    SYNTAX     DisplayString (SIZE(0..255))
    MAX-ACCESS read-only
    STATUS     current
    DESCRIPTION
            "-- empty --"
    ::= { lcsStatusIpv6Dhcpv6ClientAddressBindEntry 1 }

-- {COLUMN} 1.3.6.1.4.1.2356.11.1.77.3.2.2.1.2
lcsStatusIpv6Dhcpv6ClientAddressBindEntryAddress OBJECT-TYPE
    SYNTAX     DisplayString (SIZE(0..255))
    MAX-ACCESS read-only
    STATUS     current
    DESCRIPTION
            "-- empty --"
    ::= { lcsStatusIpv6Dhcpv6ClientAddressBindEntry 2 }

-- {COLUMN} 1.3.6.1.4.1.2356.11.1.77.3.2.2.1.3
lcsStatusIpv6Dhcpv6ClientAddressBindEntryPreferredUntilNumerical OBJECT-TYPE
    SYNTAX     Counter32
    MAX-ACCESS read-only
    STATUS     current
    DESCRIPTION
            "-- empty --"
    ::= { lcsStatusIpv6Dhcpv6ClientAddressBindEntry 3 }

-- {COLUMN} 1.3.6.1.4.1.2356.11.1.77.3.2.2.1.4
lcsStatusIpv6Dhcpv6ClientAddressBindEntryPreferredUntil OBJECT-TYPE
    SYNTAX     DisplayString (SIZE(0..255))
    MAX-ACCESS read-only
    STATUS     current
    DESCRIPTION
            "-- empty --"
    ::= { lcsStatusIpv6Dhcpv6ClientAddressBindEntry 4 }

-- {COLUMN} 1.3.6.1.4.1.2356.11.1.77.3.2.2.1.5
lcsStatusIpv6Dhcpv6ClientAddressBindEntryValidUntilNumerical OBJECT-TYPE
    SYNTAX     Counter32
    MAX-ACCESS read-only
    STATUS     current
    DESCRIPTION
            "-- empty --"
    ::= { lcsStatusIpv6Dhcpv6ClientAddressBindEntry 5 }

-- {COLUMN} 1.3.6.1.4.1.2356.11.1.77.3.2.2.1.6
lcsStatusIpv6Dhcpv6ClientAddressBindEntryValidUntil OBJECT-TYPE
    SYNTAX     DisplayString (SIZE(0..255))
    MAX-ACCESS read-only
    STATUS     current
    DESCRIPTION
            "-- empty --"
    ::= { lcsStatusIpv6Dhcpv6ClientAddressBindEntry 6 }

-- {TABLE} 1.3.6.1.4.1.2356.11.1.77.3.2.3
lcsStatusIpv6Dhcpv6ClientPdBindingsTable OBJECT-TYPE
    SYNTAX     SEQUENCE OF LcsStatusIpv6Dhcpv6ClientPdBindingsEntry
    MAX-ACCESS not-accessible
    STATUS     current
    DESCRIPTION
            "-- empty --"
    ::= { lcsStatusIpv6Dhcpv6Client 3 }

-- {ROW} 1.3.6.1.4.1.2356.11.1.77.3.2.3.1
lcsStatusIpv6Dhcpv6ClientPdBindingsEntry OBJECT-TYPE
    SYNTAX     LcsStatusIpv6Dhcpv6ClientPdBindingsEntry
    MAX-ACCESS not-accessible
    STATUS     current
    DESCRIPTION
            ""
    INDEX {
            lcsStatusIpv6Dhcpv6ClientPdBindingsEntryInterfaceName,
            lcsStatusIpv6Dhcpv6ClientPdBindingsEntryPdPrefix,
            lcsStatusIpv6Dhcpv6ClientPdBindingsEntryExcludedPrefix
          }
    ::= { lcsStatusIpv6Dhcpv6ClientPdBindingsTable 1 }

LcsStatusIpv6Dhcpv6ClientPdBindingsEntry ::= SEQUENCE {
            lcsStatusIpv6Dhcpv6ClientPdBindingsEntryInterfaceName DisplayString,
            lcsStatusIpv6Dhcpv6ClientPdBindingsEntryPdPrefix DisplayString,
            lcsStatusIpv6Dhcpv6ClientPdBindingsEntryPreferredUntilNumerical Counter32,
            lcsStatusIpv6Dhcpv6ClientPdBindingsEntryPreferredUntil DisplayString,
            lcsStatusIpv6Dhcpv6ClientPdBindingsEntryValidUntilNumerical Counter32,
            lcsStatusIpv6Dhcpv6ClientPdBindingsEntryValidUntil DisplayString,
            lcsStatusIpv6Dhcpv6ClientPdBindingsEntryExcludedPrefix DisplayString
    }

-- {COLUMN} 1.3.6.1.4.1.2356.11.1.77.3.2.3.1.1
lcsStatusIpv6Dhcpv6ClientPdBindingsEntryInterfaceName OBJECT-TYPE
    SYNTAX     DisplayString (SIZE(0..255))
    MAX-ACCESS read-only
    STATUS     current
    DESCRIPTION
            "-- empty --"
    ::= { lcsStatusIpv6Dhcpv6ClientPdBindingsEntry 1 }

-- {COLUMN} 1.3.6.1.4.1.2356.11.1.77.3.2.3.1.2
lcsStatusIpv6Dhcpv6ClientPdBindingsEntryPdPrefix OBJECT-TYPE
    SYNTAX     DisplayString (SIZE(0..255))
    MAX-ACCESS read-only
    STATUS     current
    DESCRIPTION
            "-- empty --"
    ::= { lcsStatusIpv6Dhcpv6ClientPdBindingsEntry 2 }

-- {COLUMN} 1.3.6.1.4.1.2356.11.1.77.3.2.3.1.3
lcsStatusIpv6Dhcpv6ClientPdBindingsEntryPreferredUntilNumerical OBJECT-TYPE
    SYNTAX     Counter32
    MAX-ACCESS read-only
    STATUS     current
    DESCRIPTION
            "-- empty --"
    ::= { lcsStatusIpv6Dhcpv6ClientPdBindingsEntry 3 }

-- {COLUMN} 1.3.6.1.4.1.2356.11.1.77.3.2.3.1.4
lcsStatusIpv6Dhcpv6ClientPdBindingsEntryPreferredUntil OBJECT-TYPE
    SYNTAX     DisplayString (SIZE(0..255))
    MAX-ACCESS read-only
    STATUS     current
    DESCRIPTION
            "-- empty --"
    ::= { lcsStatusIpv6Dhcpv6ClientPdBindingsEntry 4 }

-- {COLUMN} 1.3.6.1.4.1.2356.11.1.77.3.2.3.1.5
lcsStatusIpv6Dhcpv6ClientPdBindingsEntryValidUntilNumerical OBJECT-TYPE
    SYNTAX     Counter32
    MAX-ACCESS read-only
    STATUS     current
    DESCRIPTION
            "-- empty --"
    ::= { lcsStatusIpv6Dhcpv6ClientPdBindingsEntry 5 }

-- {COLUMN} 1.3.6.1.4.1.2356.11.1.77.3.2.3.1.6
lcsStatusIpv6Dhcpv6ClientPdBindingsEntryValidUntil OBJECT-TYPE
    SYNTAX     DisplayString (SIZE(0..255))
    MAX-ACCESS read-only
    STATUS     current
    DESCRIPTION
            "-- empty --"
    ::= { lcsStatusIpv6Dhcpv6ClientPdBindingsEntry 6 }

-- {COLUMN} 1.3.6.1.4.1.2356.11.1.77.3.2.3.1.7
lcsStatusIpv6Dhcpv6ClientPdBindingsEntryExcludedPrefix OBJECT-TYPE
    SYNTAX     DisplayString (SIZE(0..255))
    MAX-ACCESS read-only
    STATUS     current
    DESCRIPTION
            "-- empty --"
    ::= { lcsStatusIpv6Dhcpv6ClientPdBindingsEntry 7 }

-- {TABLE} 1.3.6.1.4.1.2356.11.1.77.3.2.4
lcsStatusIpv6Dhcpv6ClientInterfaceStateTable OBJECT-TYPE
    SYNTAX     SEQUENCE OF LcsStatusIpv6Dhcpv6ClientInterfaceStateEntry
    MAX-ACCESS not-accessible
    STATUS     current
    DESCRIPTION
            "-- empty --"
    ::= { lcsStatusIpv6Dhcpv6Client 4 }

-- {ROW} 1.3.6.1.4.1.2356.11.1.77.3.2.4.1
lcsStatusIpv6Dhcpv6ClientInterfaceStateEntry OBJECT-TYPE
    SYNTAX     LcsStatusIpv6Dhcpv6ClientInterfaceStateEntry
    MAX-ACCESS not-accessible
    STATUS     current
    DESCRIPTION
            ""
    INDEX {
            lcsStatusIpv6Dhcpv6ClientInterfaceStateEntryInterfaceName
          }
    ::= { lcsStatusIpv6Dhcpv6ClientInterfaceStateTable 1 }

LcsStatusIpv6Dhcpv6ClientInterfaceStateEntry ::= SEQUENCE {
            lcsStatusIpv6Dhcpv6ClientInterfaceStateEntryInterfaceName DisplayString,
            lcsStatusIpv6Dhcpv6ClientInterfaceStateEntryMode INTEGER,
            lcsStatusIpv6Dhcpv6ClientInterfaceStateEntryRequestPd INTEGER,
            lcsStatusIpv6Dhcpv6ClientInterfaceStateEntryReconfNegotiated INTEGER,
            lcsStatusIpv6Dhcpv6ClientInterfaceStateEntryClientId DisplayString
    }

-- {COLUMN} 1.3.6.1.4.1.2356.11.1.77.3.2.4.1.1
lcsStatusIpv6Dhcpv6ClientInterfaceStateEntryInterfaceName OBJECT-TYPE
    SYNTAX     DisplayString (SIZE(0..255))
    MAX-ACCESS read-only
    STATUS     current
    DESCRIPTION
            "-- empty --"
    ::= { lcsStatusIpv6Dhcpv6ClientInterfaceStateEntry 1 }

-- {COLUMN} 1.3.6.1.4.1.2356.11.1.77.3.2.4.1.2
lcsStatusIpv6Dhcpv6ClientInterfaceStateEntryMode OBJECT-TYPE
    SYNTAX     INTEGER {
                  eStateless (0),
                  eStateful (1),
                  eStatic (2)
            }
    MAX-ACCESS read-only
    STATUS     current
    DESCRIPTION
            "-- empty --"
    ::= { lcsStatusIpv6Dhcpv6ClientInterfaceStateEntry 2 }

-- {COLUMN} 1.3.6.1.4.1.2356.11.1.77.3.2.4.1.3
lcsStatusIpv6Dhcpv6ClientInterfaceStateEntryRequestPd OBJECT-TYPE
    SYNTAX     INTEGER {
                  eNo (0),
                  eYes (1)
            }
    MAX-ACCESS read-only
    STATUS     current
    DESCRIPTION
            "-- empty --"
    ::= { lcsStatusIpv6Dhcpv6ClientInterfaceStateEntry 3 }

-- {COLUMN} 1.3.6.1.4.1.2356.11.1.77.3.2.4.1.4
lcsStatusIpv6Dhcpv6ClientInterfaceStateEntryReconfNegotiated OBJECT-TYPE
    SYNTAX     INTEGER {
                  eNo (0),
                  eYes (1)
            }
    MAX-ACCESS read-only
    STATUS     current
    DESCRIPTION
            "-- empty --"
    ::= { lcsStatusIpv6Dhcpv6ClientInterfaceStateEntry 4 }

-- {COLUMN} 1.3.6.1.4.1.2356.11.1.77.3.2.4.1.5
lcsStatusIpv6Dhcpv6ClientInterfaceStateEntryClientId OBJECT-TYPE
    SYNTAX     DisplayString (SIZE(0..255))
    MAX-ACCESS read-only
    STATUS     current
    DESCRIPTION
            "-- empty --"
    ::= { lcsStatusIpv6Dhcpv6ClientInterfaceStateEntry 5 }

-- {SCALAR} 1.3.6.1.4.1.2356.11.1.77.3.2.5
lcsStatusIpv6Dhcpv6ClientRelease OBJECT-TYPE
    SYNTAX     DisplayString
    MAX-ACCESS read-write
    STATUS     current
    DESCRIPTION
            "-- empty --"
    ::= { lcsStatusIpv6Dhcpv6Client 5 }

-- {SCALAR} 1.3.6.1.4.1.2356.11.1.77.3.2.6
lcsStatusIpv6Dhcpv6ClientClientId OBJECT-TYPE
    SYNTAX     DisplayString (SIZE(0..97))
    MAX-ACCESS read-only
    STATUS     current
    DESCRIPTION
            "-- empty --"
    ::= { lcsStatusIpv6Dhcpv6Client 6 }

-- {NODE} 1.3.6.1.4.1.2356.11.1.77.3.3
lcsStatusIpv6Dhcpv6RelayAgent OBJECT IDENTIFIER ::= { lcsStatusIpv6Dhcpv6 3 }

-- {TABLE} 1.3.6.1.4.1.2356.11.1.77.4
lcsStatusIpv6InterfacesTable OBJECT-TYPE
    SYNTAX     SEQUENCE OF LcsStatusIpv6InterfacesEntry
    MAX-ACCESS not-accessible
    STATUS     current
    DESCRIPTION
            "-- empty --"
    ::= { lcsStatusIpv6 4 }

-- {ROW} 1.3.6.1.4.1.2356.11.1.77.4.1
lcsStatusIpv6InterfacesEntry OBJECT-TYPE
    SYNTAX     LcsStatusIpv6InterfacesEntry
    MAX-ACCESS not-accessible
    STATUS     current
    DESCRIPTION
            ""
    INDEX {
            lcsStatusIpv6InterfacesEntryInterfaceName
          }
    ::= { lcsStatusIpv6InterfacesTable 1 }

LcsStatusIpv6InterfacesEntry ::= SEQUENCE {
            lcsStatusIpv6InterfacesEntryInterfaceName OCTET STRING,
            lcsStatusIpv6InterfacesEntryInterfaceType INTEGER,
            lcsStatusIpv6InterfacesEntryInterfaceStatus INTEGER,
            lcsStatusIpv6InterfacesEntryForwarding INTEGER,
            lcsStatusIpv6InterfacesEntryAutoconf INTEGER,
            lcsStatusIpv6InterfacesEntryAcceptRa INTEGER,
            lcsStatusIpv6InterfacesEntryMtu Unsigned32,
            lcsStatusIpv6InterfacesEntryFirewall INTEGER
    }

-- {COLUMN} 1.3.6.1.4.1.2356.11.1.77.4.1.1
lcsStatusIpv6InterfacesEntryInterfaceName OBJECT-TYPE
    SYNTAX     OCTET STRING (SIZE(0..26))
    MAX-ACCESS read-only
    STATUS     current
    DESCRIPTION
            "-- empty --"
    ::= { lcsStatusIpv6InterfacesEntry 1 }

-- {COLUMN} 1.3.6.1.4.1.2356.11.1.77.4.1.2
lcsStatusIpv6InterfacesEntryInterfaceType OBJECT-TYPE
    SYNTAX     INTEGER {
                  eLan (0),
                  eWan (1),
                  eLoopback (2)
            }
    MAX-ACCESS read-only
    STATUS     current
    DESCRIPTION
            "-- empty --"
    ::= { lcsStatusIpv6InterfacesEntry 2 }

-- {COLUMN} 1.3.6.1.4.1.2356.11.1.77.4.1.3
lcsStatusIpv6InterfacesEntryInterfaceStatus OBJECT-TYPE
    SYNTAX     INTEGER {
                  eUp (1),
                  eDown (2)
            }
    MAX-ACCESS read-only
    STATUS     current
    DESCRIPTION
            "-- empty --"
    ::= { lcsStatusIpv6InterfacesEntry 3 }

-- {COLUMN} 1.3.6.1.4.1.2356.11.1.77.4.1.4
lcsStatusIpv6InterfacesEntryForwarding OBJECT-TYPE
    SYNTAX     INTEGER {
                  eYes (0),
                  eNo (1)
            }
    MAX-ACCESS read-only
    STATUS     current
    DESCRIPTION
            "-- empty --"
    ::= { lcsStatusIpv6InterfacesEntry 4 }

-- {COLUMN} 1.3.6.1.4.1.2356.11.1.77.4.1.5
lcsStatusIpv6InterfacesEntryAutoconf OBJECT-TYPE
    SYNTAX     INTEGER {
                  eYes (0),
                  eNo (1)
            }
    MAX-ACCESS read-only
    STATUS     current
    DESCRIPTION
            "-- empty --"
    ::= { lcsStatusIpv6InterfacesEntry 5 }

-- {COLUMN} 1.3.6.1.4.1.2356.11.1.77.4.1.6
lcsStatusIpv6InterfacesEntryAcceptRa OBJECT-TYPE
    SYNTAX     INTEGER {
                  eYes (0),
                  eNo (1)
            }
    MAX-ACCESS read-only
    STATUS     current
    DESCRIPTION
            "-- empty --"
    ::= { lcsStatusIpv6InterfacesEntry 6 }

-- {COLUMN} 1.3.6.1.4.1.2356.11.1.77.4.1.7
lcsStatusIpv6InterfacesEntryMtu OBJECT-TYPE
    SYNTAX     Unsigned32 (0..65535)
    MAX-ACCESS read-only
    STATUS     current
    DESCRIPTION
            "-- empty --"
    ::= { lcsStatusIpv6InterfacesEntry 7 }

-- {COLUMN} 1.3.6.1.4.1.2356.11.1.77.4.1.8
lcsStatusIpv6InterfacesEntryFirewall OBJECT-TYPE
    SYNTAX     INTEGER {
                  eYes (0),
                  eNo (1)
            }
    MAX-ACCESS read-only
    STATUS     current
    DESCRIPTION
            "-- empty --"
    ::= { lcsStatusIpv6InterfacesEntry 8 }

-- {TABLE} 1.3.6.1.4.1.2356.11.1.77.5
lcsStatusIpv6ActIpRoutingTabTable OBJECT-TYPE
    SYNTAX     SEQUENCE OF LcsStatusIpv6ActIpRoutingTabEntry
    MAX-ACCESS not-accessible
    STATUS     current
    DESCRIPTION
            "-- empty --"
    ::= { lcsStatusIpv6 5 }

-- {ROW} 1.3.6.1.4.1.2356.11.1.77.5.1
lcsStatusIpv6ActIpRoutingTabEntry OBJECT-TYPE
    SYNTAX     LcsStatusIpv6ActIpRoutingTabEntry
    MAX-ACCESS not-accessible
    STATUS     current
    DESCRIPTION
            ""
    INDEX {
            lcsStatusIpv6ActIpRoutingTabEntryPrefix,
            lcsStatusIpv6ActIpRoutingTabEntryRtgTag
          }
    ::= { lcsStatusIpv6ActIpRoutingTabTable 1 }

LcsStatusIpv6ActIpRoutingTabEntry ::= SEQUENCE {
            lcsStatusIpv6ActIpRoutingTabEntryPrefix OCTET STRING,
            lcsStatusIpv6ActIpRoutingTabEntryRtgTag Unsigned32,
            lcsStatusIpv6ActIpRoutingTabEntryNextHop OCTET STRING,
            lcsStatusIpv6ActIpRoutingTabEntryTargetInterface OCTET STRING,
            lcsStatusIpv6ActIpRoutingTabEntryType OCTET STRING
    }

-- {COLUMN} 1.3.6.1.4.1.2356.11.1.77.5.1.1
lcsStatusIpv6ActIpRoutingTabEntryPrefix OBJECT-TYPE
    SYNTAX     OCTET STRING (SIZE(37..37))
    MAX-ACCESS read-only
    STATUS     current
    DESCRIPTION
            "-- empty --"
    ::= { lcsStatusIpv6ActIpRoutingTabEntry 1 }

-- {COLUMN} 1.3.6.1.4.1.2356.11.1.77.5.1.2
lcsStatusIpv6ActIpRoutingTabEntryRtgTag OBJECT-TYPE
    SYNTAX     Unsigned32
    MAX-ACCESS read-only
    STATUS     current
    DESCRIPTION
            "-- empty --"
    ::= { lcsStatusIpv6ActIpRoutingTabEntry 2 }

-- {COLUMN} 1.3.6.1.4.1.2356.11.1.77.5.1.3
lcsStatusIpv6ActIpRoutingTabEntryNextHop OBJECT-TYPE
    SYNTAX     OCTET STRING (SIZE(16..16))
    MAX-ACCESS read-only
    STATUS     current
    DESCRIPTION
            "-- empty --"
    ::= { lcsStatusIpv6ActIpRoutingTabEntry 3 }

-- {COLUMN} 1.3.6.1.4.1.2356.11.1.77.5.1.4
lcsStatusIpv6ActIpRoutingTabEntryTargetInterface OBJECT-TYPE
    SYNTAX     OCTET STRING (SIZE(0..17))
    MAX-ACCESS read-only
    STATUS     current
    DESCRIPTION
            "-- empty --"
    ::= { lcsStatusIpv6ActIpRoutingTabEntry 4 }

-- {COLUMN} 1.3.6.1.4.1.2356.11.1.77.5.1.5
lcsStatusIpv6ActIpRoutingTabEntryType OBJECT-TYPE
    SYNTAX     OCTET STRING (SIZE(0..16))
    MAX-ACCESS read-only
    STATUS     current
    DESCRIPTION
            "-- empty --"
    ::= { lcsStatusIpv6ActIpRoutingTabEntry 5 }

-- {NODE} 1.3.6.1.4.1.2356.11.1.77.6
lcsStatusIpv6Network OBJECT IDENTIFIER ::= { lcsStatusIpv6 6 }

-- {TABLE} 1.3.6.1.4.1.2356.11.1.77.6.1
lcsStatusIpv6NetworkAddressesTable OBJECT-TYPE
    SYNTAX     SEQUENCE OF LcsStatusIpv6NetworkAddressesEntry
    MAX-ACCESS not-accessible
    STATUS     current
    DESCRIPTION
            "-- empty --"
    ::= { lcsStatusIpv6Network 1 }

-- {ROW} 1.3.6.1.4.1.2356.11.1.77.6.1.1
lcsStatusIpv6NetworkAddressesEntry OBJECT-TYPE
    SYNTAX     LcsStatusIpv6NetworkAddressesEntry
    MAX-ACCESS not-accessible
    STATUS     current
    DESCRIPTION
            ""
    INDEX {
            lcsStatusIpv6NetworkAddressesEntryInterfaceName,
            lcsStatusIpv6NetworkAddressesEntryIpv6Address
          }
    ::= { lcsStatusIpv6NetworkAddressesTable 1 }

LcsStatusIpv6NetworkAddressesEntry ::= SEQUENCE {
            lcsStatusIpv6NetworkAddressesEntryInterfaceName OCTET STRING,
            lcsStatusIpv6NetworkAddressesEntryIpv6Address OCTET STRING,
            lcsStatusIpv6NetworkAddressesEntryAddressType INTEGER,
            lcsStatusIpv6NetworkAddressesEntryPrefLifetime Unsigned32,
            lcsStatusIpv6NetworkAddressesEntryValidLifetime Unsigned32,
            lcsStatusIpv6NetworkAddressesEntryInterfaceType INTEGER
    }

-- {COLUMN} 1.3.6.1.4.1.2356.11.1.77.6.1.1.1
lcsStatusIpv6NetworkAddressesEntryInterfaceName OBJECT-TYPE
    SYNTAX     OCTET STRING (SIZE(0..26))
    MAX-ACCESS read-only
    STATUS     current
    DESCRIPTION
            "-- empty --"
    ::= { lcsStatusIpv6NetworkAddressesEntry 1 }

-- {COLUMN} 1.3.6.1.4.1.2356.11.1.77.6.1.1.2
lcsStatusIpv6NetworkAddressesEntryIpv6Address OBJECT-TYPE
    SYNTAX     OCTET STRING (SIZE(16..16))
    MAX-ACCESS read-only
    STATUS     current
    DESCRIPTION
            "-- empty --"
    ::= { lcsStatusIpv6NetworkAddressesEntry 2 }

-- {COLUMN} 1.3.6.1.4.1.2356.11.1.77.6.1.1.3
lcsStatusIpv6NetworkAddressesEntryAddressType OBJECT-TYPE
    SYNTAX     INTEGER {
                  ePrimaryLinkLocalAddress (0),
                  eStaticConfiguration (1),
                  eAutoConfiguration (2),
                  eDhcpv6ClientIaNa (3),
                  eDhcpv6ClientIaPd (4),
                  eSubnetRouterAnycast (5),
                  eLoopback (6),
                  eVpn (7)
            }
    MAX-ACCESS read-only
    STATUS     current
    DESCRIPTION
            "-- empty --"
    ::= { lcsStatusIpv6NetworkAddressesEntry 3 }

-- {COLUMN} 1.3.6.1.4.1.2356.11.1.77.6.1.1.4
lcsStatusIpv6NetworkAddressesEntryPrefLifetime OBJECT-TYPE
    SYNTAX     Unsigned32 (0..4294967295)
    MAX-ACCESS read-only
    STATUS     current
    DESCRIPTION
            "-- empty --"
    ::= { lcsStatusIpv6NetworkAddressesEntry 4 }

-- {COLUMN} 1.3.6.1.4.1.2356.11.1.77.6.1.1.5
lcsStatusIpv6NetworkAddressesEntryValidLifetime OBJECT-TYPE
    SYNTAX     Unsigned32 (0..4294967295)
    MAX-ACCESS read-only
    STATUS     current
    DESCRIPTION
            "-- empty --"
    ::= { lcsStatusIpv6NetworkAddressesEntry 5 }

-- {COLUMN} 1.3.6.1.4.1.2356.11.1.77.6.1.1.6
lcsStatusIpv6NetworkAddressesEntryInterfaceType OBJECT-TYPE
    SYNTAX     INTEGER {
                  eLan (0),
                  eWan (1),
                  eLoopback (2)
            }
    MAX-ACCESS read-only
    STATUS     current
    DESCRIPTION
            "-- empty --"
    ::= { lcsStatusIpv6NetworkAddressesEntry 6 }

-- {TABLE} 1.3.6.1.4.1.2356.11.1.77.6.2
lcsStatusIpv6NetworkParameterTable OBJECT-TYPE
    SYNTAX     SEQUENCE OF LcsStatusIpv6NetworkParameterEntry
    MAX-ACCESS not-accessible
    STATUS     current
    DESCRIPTION
            "-- empty --"
    ::= { lcsStatusIpv6Network 2 }

-- {ROW} 1.3.6.1.4.1.2356.11.1.77.6.2.1
lcsStatusIpv6NetworkParameterEntry OBJECT-TYPE
    SYNTAX     LcsStatusIpv6NetworkParameterEntry
    MAX-ACCESS not-accessible
    STATUS     current
    DESCRIPTION
            ""
    INDEX {
            lcsStatusIpv6NetworkParameterEntryInterfaceName
          }
    ::= { lcsStatusIpv6NetworkParameterTable 1 }

LcsStatusIpv6NetworkParameterEntry ::= SEQUENCE {
            lcsStatusIpv6NetworkParameterEntryInterfaceName OCTET STRING,
            lcsStatusIpv6NetworkParameterEntryPrimaryDns OCTET STRING,
            lcsStatusIpv6NetworkParameterEntrySecondaryDns OCTET STRING
    }

-- {COLUMN} 1.3.6.1.4.1.2356.11.1.77.6.2.1.1
lcsStatusIpv6NetworkParameterEntryInterfaceName OBJECT-TYPE
    SYNTAX     OCTET STRING (SIZE(0..26))
    MAX-ACCESS read-only
    STATUS     current
    DESCRIPTION
            "-- empty --"
    ::= { lcsStatusIpv6NetworkParameterEntry 1 }

-- {COLUMN} 1.3.6.1.4.1.2356.11.1.77.6.2.1.2
lcsStatusIpv6NetworkParameterEntryPrimaryDns OBJECT-TYPE
    SYNTAX     OCTET STRING (SIZE(16..16))
    MAX-ACCESS read-only
    STATUS     current
    DESCRIPTION
            "-- empty --"
    ::= { lcsStatusIpv6NetworkParameterEntry 2 }

-- {COLUMN} 1.3.6.1.4.1.2356.11.1.77.6.2.1.3
lcsStatusIpv6NetworkParameterEntrySecondaryDns OBJECT-TYPE
    SYNTAX     OCTET STRING (SIZE(16..16))
    MAX-ACCESS read-only
    STATUS     current
    DESCRIPTION
            "-- empty --"
    ::= { lcsStatusIpv6NetworkParameterEntry 3 }

-- {NODE} 1.3.6.1.4.1.2356.11.1.77.7
lcsStatusIpv6RouterAdv OBJECT IDENTIFIER ::= { lcsStatusIpv6 7 }

-- {TABLE} 1.3.6.1.4.1.2356.11.1.77.7.1
lcsStatusIpv6RouterAdvInterfaceOptionsTable OBJECT-TYPE
    SYNTAX     SEQUENCE OF LcsStatusIpv6RouterAdvInterfaceOptionsEntry
    MAX-ACCESS not-accessible
    STATUS     current
    DESCRIPTION
            "-- empty --"
    ::= { lcsStatusIpv6RouterAdv 1 }

-- {ROW} 1.3.6.1.4.1.2356.11.1.77.7.1.1
lcsStatusIpv6RouterAdvInterfaceOptionsEntry OBJECT-TYPE
    SYNTAX     LcsStatusIpv6RouterAdvInterfaceOptionsEntry
    MAX-ACCESS not-accessible
    STATUS     current
    DESCRIPTION
            ""
    INDEX {
            lcsStatusIpv6RouterAdvInterfaceOptionsEntryInterfaceName
          }
    ::= { lcsStatusIpv6RouterAdvInterfaceOptionsTable 1 }

LcsStatusIpv6RouterAdvInterfaceOptionsEntry ::= SEQUENCE {
            lcsStatusIpv6RouterAdvInterfaceOptionsEntryInterfaceName OCTET STRING,
            lcsStatusIpv6RouterAdvInterfaceOptionsEntrySendAdverts INTEGER,
            lcsStatusIpv6RouterAdvInterfaceOptionsEntryManagedFlag INTEGER,
            lcsStatusIpv6RouterAdvInterfaceOptionsEntryOtherConfigFlag INTEGER,
            lcsStatusIpv6RouterAdvInterfaceOptionsEntryLinkMtu Unsigned32,
            lcsStatusIpv6RouterAdvInterfaceOptionsEntryDefaultLifetime Unsigned32
    }

-- {COLUMN} 1.3.6.1.4.1.2356.11.1.77.7.1.1.1
lcsStatusIpv6RouterAdvInterfaceOptionsEntryInterfaceName OBJECT-TYPE
    SYNTAX     OCTET STRING (SIZE(0..26))
    MAX-ACCESS read-only
    STATUS     current
    DESCRIPTION
            "-- empty --"
    ::= { lcsStatusIpv6RouterAdvInterfaceOptionsEntry 1 }

-- {COLUMN} 1.3.6.1.4.1.2356.11.1.77.7.1.1.2
lcsStatusIpv6RouterAdvInterfaceOptionsEntrySendAdverts OBJECT-TYPE
    SYNTAX     INTEGER {
                  eYes (0),
                  eNo (1)
            }
    MAX-ACCESS read-only
    STATUS     current
    DESCRIPTION
            "-- empty --"
    ::= { lcsStatusIpv6RouterAdvInterfaceOptionsEntry 2 }

-- {COLUMN} 1.3.6.1.4.1.2356.11.1.77.7.1.1.3
lcsStatusIpv6RouterAdvInterfaceOptionsEntryManagedFlag OBJECT-TYPE
    SYNTAX     INTEGER {
                  eYes (0),
                  eNo (1)
            }
    MAX-ACCESS read-only
    STATUS     current
    DESCRIPTION
            "-- empty --"
    ::= { lcsStatusIpv6RouterAdvInterfaceOptionsEntry 3 }

-- {COLUMN} 1.3.6.1.4.1.2356.11.1.77.7.1.1.4
lcsStatusIpv6RouterAdvInterfaceOptionsEntryOtherConfigFlag OBJECT-TYPE
    SYNTAX     INTEGER {
                  eYes (0),
                  eNo (1)
            }
    MAX-ACCESS read-only
    STATUS     current
    DESCRIPTION
            "-- empty --"
    ::= { lcsStatusIpv6RouterAdvInterfaceOptionsEntry 4 }

-- {COLUMN} 1.3.6.1.4.1.2356.11.1.77.7.1.1.5
lcsStatusIpv6RouterAdvInterfaceOptionsEntryLinkMtu OBJECT-TYPE
    SYNTAX     Unsigned32 (0..4294967295)
    MAX-ACCESS read-only
    STATUS     current
    DESCRIPTION
            "-- empty --"
    ::= { lcsStatusIpv6RouterAdvInterfaceOptionsEntry 5 }

-- {COLUMN} 1.3.6.1.4.1.2356.11.1.77.7.1.1.6
lcsStatusIpv6RouterAdvInterfaceOptionsEntryDefaultLifetime OBJECT-TYPE
    SYNTAX     Unsigned32 (0..4294967295)
    MAX-ACCESS read-only
    STATUS     current
    DESCRIPTION
            "-- empty --"
    ::= { lcsStatusIpv6RouterAdvInterfaceOptionsEntry 6 }

-- {TABLE} 1.3.6.1.4.1.2356.11.1.77.7.2
lcsStatusIpv6RouterAdvPrefixOptionsTable OBJECT-TYPE
    SYNTAX     SEQUENCE OF LcsStatusIpv6RouterAdvPrefixOptionsEntry
    MAX-ACCESS not-accessible
    STATUS     current
    DESCRIPTION
            "-- empty --"
    ::= { lcsStatusIpv6RouterAdv 2 }

-- {ROW} 1.3.6.1.4.1.2356.11.1.77.7.2.1
lcsStatusIpv6RouterAdvPrefixOptionsEntry OBJECT-TYPE
    SYNTAX     LcsStatusIpv6RouterAdvPrefixOptionsEntry
    MAX-ACCESS not-accessible
    STATUS     current
    DESCRIPTION
            ""
    INDEX {
            lcsStatusIpv6RouterAdvPrefixOptionsEntryInterfaceName,
            lcsStatusIpv6RouterAdvPrefixOptionsEntryPrefix
          }
    ::= { lcsStatusIpv6RouterAdvPrefixOptionsTable 1 }

LcsStatusIpv6RouterAdvPrefixOptionsEntry ::= SEQUENCE {
            lcsStatusIpv6RouterAdvPrefixOptionsEntryInterfaceName OCTET STRING,
            lcsStatusIpv6RouterAdvPrefixOptionsEntryPrefix OCTET STRING,
            lcsStatusIpv6RouterAdvPrefixOptionsEntryAdvOnlink INTEGER,
            lcsStatusIpv6RouterAdvPrefixOptionsEntryAdvAutonomous INTEGER,
            lcsStatusIpv6RouterAdvPrefixOptionsEntryAdvPrefLifetime Unsigned32,
            lcsStatusIpv6RouterAdvPrefixOptionsEntryAdvValidLifetime Unsigned32,
            lcsStatusIpv6RouterAdvPrefixOptionsEntryType INTEGER
    }

-- {COLUMN} 1.3.6.1.4.1.2356.11.1.77.7.2.1.1
lcsStatusIpv6RouterAdvPrefixOptionsEntryInterfaceName OBJECT-TYPE
    SYNTAX     OCTET STRING (SIZE(0..26))
    MAX-ACCESS read-only
    STATUS     current
    DESCRIPTION
            "-- empty --"
    ::= { lcsStatusIpv6RouterAdvPrefixOptionsEntry 1 }

-- {COLUMN} 1.3.6.1.4.1.2356.11.1.77.7.2.1.2
lcsStatusIpv6RouterAdvPrefixOptionsEntryPrefix OBJECT-TYPE
    SYNTAX     OCTET STRING (SIZE(17..17))
    MAX-ACCESS read-only
    STATUS     current
    DESCRIPTION
            "-- empty --"
    ::= { lcsStatusIpv6RouterAdvPrefixOptionsEntry 2 }

-- {COLUMN} 1.3.6.1.4.1.2356.11.1.77.7.2.1.3
lcsStatusIpv6RouterAdvPrefixOptionsEntryAdvOnlink OBJECT-TYPE
    SYNTAX     INTEGER {
                  eYes (0),
                  eNo (1)
            }
    MAX-ACCESS read-only
    STATUS     current
    DESCRIPTION
            "-- empty --"
    ::= { lcsStatusIpv6RouterAdvPrefixOptionsEntry 3 }

-- {COLUMN} 1.3.6.1.4.1.2356.11.1.77.7.2.1.4
lcsStatusIpv6RouterAdvPrefixOptionsEntryAdvAutonomous OBJECT-TYPE
    SYNTAX     INTEGER {
                  eYes (0),
                  eNo (1)
            }
    MAX-ACCESS read-only
    STATUS     current
    DESCRIPTION
            "-- empty --"
    ::= { lcsStatusIpv6RouterAdvPrefixOptionsEntry 4 }

-- {COLUMN} 1.3.6.1.4.1.2356.11.1.77.7.2.1.5
lcsStatusIpv6RouterAdvPrefixOptionsEntryAdvPrefLifetime OBJECT-TYPE
    SYNTAX     Unsigned32 (0..4294967295)
    MAX-ACCESS read-only
    STATUS     current
    DESCRIPTION
            "-- empty --"
    ::= { lcsStatusIpv6RouterAdvPrefixOptionsEntry 5 }

-- {COLUMN} 1.3.6.1.4.1.2356.11.1.77.7.2.1.6
lcsStatusIpv6RouterAdvPrefixOptionsEntryAdvValidLifetime OBJECT-TYPE
    SYNTAX     Unsigned32 (0..4294967295)
    MAX-ACCESS read-only
    STATUS     current
    DESCRIPTION
            "-- empty --"
    ::= { lcsStatusIpv6RouterAdvPrefixOptionsEntry 6 }

-- {COLUMN} 1.3.6.1.4.1.2356.11.1.77.7.2.1.7
lcsStatusIpv6RouterAdvPrefixOptionsEntryType OBJECT-TYPE
    SYNTAX     INTEGER {
                  eTunnel (0),
                  eAutoConfiguration (1),
                  eDhcpv6ClientIaPd (2),
                  eStaticConfiguration (3)
            }
    MAX-ACCESS read-only
    STATUS     current
    DESCRIPTION
            "-- empty --"
    ::= { lcsStatusIpv6RouterAdvPrefixOptionsEntry 7 }

-- {NODE} 1.3.6.1.4.1.2356.11.1.77.8
lcsStatusIpv6Tunnel OBJECT IDENTIFIER ::= { lcsStatusIpv6 8 }

-- {TABLE} 1.3.6.1.4.1.2356.11.1.77.8.1
lcsStatusIpv6Tunnel6in4Table OBJECT-TYPE
    SYNTAX     SEQUENCE OF LcsStatusIpv6Tunnel6in4Entry
    MAX-ACCESS not-accessible
    STATUS     current
    DESCRIPTION
            "-- empty --"
    ::= { lcsStatusIpv6Tunnel 1 }

-- {ROW} 1.3.6.1.4.1.2356.11.1.77.8.1.1
lcsStatusIpv6Tunnel6in4Entry OBJECT-TYPE
    SYNTAX     LcsStatusIpv6Tunnel6in4Entry
    MAX-ACCESS not-accessible
    STATUS     current
    DESCRIPTION
            ""
    INDEX {
            lcsStatusIpv6Tunnel6in4EntryPeerName
          }
    ::= { lcsStatusIpv6Tunnel6in4Table 1 }

LcsStatusIpv6Tunnel6in4Entry ::= SEQUENCE {
            lcsStatusIpv6Tunnel6in4EntryPeerName OCTET STRING,
            lcsStatusIpv6Tunnel6in4EntryInterfaceStatus INTEGER,
            lcsStatusIpv6Tunnel6in4EntryGatewayAddress OCTET STRING,
            lcsStatusIpv6Tunnel6in4EntryGatewayIpv6Address OCTET STRING,
            lcsStatusIpv6Tunnel6in4EntryLocalIpv6Address OCTET STRING,
            lcsStatusIpv6Tunnel6in4EntryRoutedIpv6Prefix OCTET STRING,
            lcsStatusIpv6Tunnel6in4EntryFirewall INTEGER
    }

-- {COLUMN} 1.3.6.1.4.1.2356.11.1.77.8.1.1.1
lcsStatusIpv6Tunnel6in4EntryPeerName OBJECT-TYPE
    SYNTAX     OCTET STRING (SIZE(0..17))
    MAX-ACCESS read-only
    STATUS     current
    DESCRIPTION
            "-- empty --"
    ::= { lcsStatusIpv6Tunnel6in4Entry 1 }

-- {COLUMN} 1.3.6.1.4.1.2356.11.1.77.8.1.1.2
lcsStatusIpv6Tunnel6in4EntryInterfaceStatus OBJECT-TYPE
    SYNTAX     INTEGER {
                  eUp (1),
                  eDown (2)
            }
    MAX-ACCESS read-only
    STATUS     current
    DESCRIPTION
            "-- empty --"
    ::= { lcsStatusIpv6Tunnel6in4Entry 2 }

-- {COLUMN} 1.3.6.1.4.1.2356.11.1.77.8.1.1.3
lcsStatusIpv6Tunnel6in4EntryGatewayAddress OBJECT-TYPE
    SYNTAX     OCTET STRING (SIZE(0..65))
    MAX-ACCESS read-only
    STATUS     current
    DESCRIPTION
            "-- empty --"
    ::= { lcsStatusIpv6Tunnel6in4Entry 3 }

-- {COLUMN} 1.3.6.1.4.1.2356.11.1.77.8.1.1.4
lcsStatusIpv6Tunnel6in4EntryGatewayIpv6Address OBJECT-TYPE
    SYNTAX     OCTET STRING (SIZE(17..17))
    MAX-ACCESS read-only
    STATUS     current
    DESCRIPTION
            "-- empty --"
    ::= { lcsStatusIpv6Tunnel6in4Entry 4 }

-- {COLUMN} 1.3.6.1.4.1.2356.11.1.77.8.1.1.5
lcsStatusIpv6Tunnel6in4EntryLocalIpv6Address OBJECT-TYPE
    SYNTAX     OCTET STRING (SIZE(16..16))
    MAX-ACCESS read-only
    STATUS     current
    DESCRIPTION
            "-- empty --"
    ::= { lcsStatusIpv6Tunnel6in4Entry 5 }

-- {COLUMN} 1.3.6.1.4.1.2356.11.1.77.8.1.1.6
lcsStatusIpv6Tunnel6in4EntryRoutedIpv6Prefix OBJECT-TYPE
    SYNTAX     OCTET STRING (SIZE(17..17))
    MAX-ACCESS read-only
    STATUS     current
    DESCRIPTION
            "-- empty --"
    ::= { lcsStatusIpv6Tunnel6in4Entry 6 }

-- {COLUMN} 1.3.6.1.4.1.2356.11.1.77.8.1.1.7
lcsStatusIpv6Tunnel6in4EntryFirewall OBJECT-TYPE
    SYNTAX     INTEGER {
                  eYes (0),
                  eNo (1)
            }
    MAX-ACCESS read-only
    STATUS     current
    DESCRIPTION
            "-- empty --"
    ::= { lcsStatusIpv6Tunnel6in4Entry 7 }

-- {TABLE} 1.3.6.1.4.1.2356.11.1.77.8.2
lcsStatusIpv6Tunnel6rdTable OBJECT-TYPE
    SYNTAX     SEQUENCE OF LcsStatusIpv6Tunnel6rdEntry
    MAX-ACCESS not-accessible
    STATUS     current
    DESCRIPTION
            "-- empty --"
    ::= { lcsStatusIpv6Tunnel 2 }

-- {ROW} 1.3.6.1.4.1.2356.11.1.77.8.2.1
lcsStatusIpv6Tunnel6rdEntry OBJECT-TYPE
    SYNTAX     LcsStatusIpv6Tunnel6rdEntry
    MAX-ACCESS not-accessible
    STATUS     current
    DESCRIPTION
            ""
    INDEX {
            lcsStatusIpv6Tunnel6rdEntryPeerName
          }
    ::= { lcsStatusIpv6Tunnel6rdTable 1 }

LcsStatusIpv6Tunnel6rdEntry ::= SEQUENCE {
            lcsStatusIpv6Tunnel6rdEntryPeerName OCTET STRING,
            lcsStatusIpv6Tunnel6rdEntryInterfaceStatus INTEGER,
            lcsStatusIpv6Tunnel6rdEntryBorderRelayAddress OCTET STRING,
            lcsStatusIpv6Tunnel6rdEntry6rdPrefix OCTET STRING,
            lcsStatusIpv6Tunnel6rdEntryIpv4MaskLength Unsigned32,
            lcsStatusIpv6Tunnel6rdEntryFirewall INTEGER
    }

-- {COLUMN} 1.3.6.1.4.1.2356.11.1.77.8.2.1.1
lcsStatusIpv6Tunnel6rdEntryPeerName OBJECT-TYPE
    SYNTAX     OCTET STRING (SIZE(0..17))
    MAX-ACCESS read-only
    STATUS     current
    DESCRIPTION
            "-- empty --"
    ::= { lcsStatusIpv6Tunnel6rdEntry 1 }

-- {COLUMN} 1.3.6.1.4.1.2356.11.1.77.8.2.1.2
lcsStatusIpv6Tunnel6rdEntryInterfaceStatus OBJECT-TYPE
    SYNTAX     INTEGER {
                  eUp (1),
                  eDown (2)
            }
    MAX-ACCESS read-only
    STATUS     current
    DESCRIPTION
            "-- empty --"
    ::= { lcsStatusIpv6Tunnel6rdEntry 2 }

-- {COLUMN} 1.3.6.1.4.1.2356.11.1.77.8.2.1.3
lcsStatusIpv6Tunnel6rdEntryBorderRelayAddress OBJECT-TYPE
    SYNTAX     OCTET STRING (SIZE(0..65))
    MAX-ACCESS read-only
    STATUS     current
    DESCRIPTION
            "-- empty --"
    ::= { lcsStatusIpv6Tunnel6rdEntry 3 }

-- {COLUMN} 1.3.6.1.4.1.2356.11.1.77.8.2.1.4
lcsStatusIpv6Tunnel6rdEntry6rdPrefix OBJECT-TYPE
    SYNTAX     OCTET STRING (SIZE(17..17))
    MAX-ACCESS read-only
    STATUS     current
    DESCRIPTION
            "-- empty --"
    ::= { lcsStatusIpv6Tunnel6rdEntry 4 }

-- {COLUMN} 1.3.6.1.4.1.2356.11.1.77.8.2.1.5
lcsStatusIpv6Tunnel6rdEntryIpv4MaskLength OBJECT-TYPE
    SYNTAX     Unsigned32 (0..65535)
    MAX-ACCESS read-only
    STATUS     current
    DESCRIPTION
            "-- empty --"
    ::= { lcsStatusIpv6Tunnel6rdEntry 5 }

-- {COLUMN} 1.3.6.1.4.1.2356.11.1.77.8.2.1.6
lcsStatusIpv6Tunnel6rdEntryFirewall OBJECT-TYPE
    SYNTAX     INTEGER {
                  eYes (0),
                  eNo (1)
            }
    MAX-ACCESS read-only
    STATUS     current
    DESCRIPTION
            "-- empty --"
    ::= { lcsStatusIpv6Tunnel6rdEntry 6 }

-- {TABLE} 1.3.6.1.4.1.2356.11.1.77.8.3
lcsStatusIpv6Tunnel6rdBorderRelayTable OBJECT-TYPE
    SYNTAX     SEQUENCE OF LcsStatusIpv6Tunnel6rdBorderRelayEntry
    MAX-ACCESS not-accessible
    STATUS     current
    DESCRIPTION
            "-- empty --"
    ::= { lcsStatusIpv6Tunnel 3 }

-- {ROW} 1.3.6.1.4.1.2356.11.1.77.8.3.1
lcsStatusIpv6Tunnel6rdBorderRelayEntry OBJECT-TYPE
    SYNTAX     LcsStatusIpv6Tunnel6rdBorderRelayEntry
    MAX-ACCESS not-accessible
    STATUS     current
    DESCRIPTION
            ""
    INDEX {
            lcsStatusIpv6Tunnel6rdBorderRelayEntryPeerName
          }
    ::= { lcsStatusIpv6Tunnel6rdBorderRelayTable 1 }

LcsStatusIpv6Tunnel6rdBorderRelayEntry ::= SEQUENCE {
            lcsStatusIpv6Tunnel6rdBorderRelayEntryPeerName OCTET STRING,
            lcsStatusIpv6Tunnel6rdBorderRelayEntryInterfaceStatus INTEGER,
            lcsStatusIpv6Tunnel6rdBorderRelayEntryIpv4LoopbackAddress OCTET STRING,
            lcsStatusIpv6Tunnel6rdBorderRelayEntry6rdPrefix OCTET STRING,
            lcsStatusIpv6Tunnel6rdBorderRelayEntryIpv4MaskLength Unsigned32,
            lcsStatusIpv6Tunnel6rdBorderRelayEntryDhcpv4Propagate INTEGER,
            lcsStatusIpv6Tunnel6rdBorderRelayEntryFirewall INTEGER
    }

-- {COLUMN} 1.3.6.1.4.1.2356.11.1.77.8.3.1.1
lcsStatusIpv6Tunnel6rdBorderRelayEntryPeerName OBJECT-TYPE
    SYNTAX     OCTET STRING (SIZE(0..17))
    MAX-ACCESS read-only
    STATUS     current
    DESCRIPTION
            "-- empty --"
    ::= { lcsStatusIpv6Tunnel6rdBorderRelayEntry 1 }

-- {COLUMN} 1.3.6.1.4.1.2356.11.1.77.8.3.1.2
lcsStatusIpv6Tunnel6rdBorderRelayEntryInterfaceStatus OBJECT-TYPE
    SYNTAX     INTEGER {
                  eUp (1),
                  eDown (2)
            }
    MAX-ACCESS read-only
    STATUS     current
    DESCRIPTION
            "-- empty --"
    ::= { lcsStatusIpv6Tunnel6rdBorderRelayEntry 2 }

-- {COLUMN} 1.3.6.1.4.1.2356.11.1.77.8.3.1.3
lcsStatusIpv6Tunnel6rdBorderRelayEntryIpv4LoopbackAddress OBJECT-TYPE
    SYNTAX     OCTET STRING (SIZE(0..22))
    MAX-ACCESS read-only
    STATUS     current
    DESCRIPTION
            "-- empty --"
    ::= { lcsStatusIpv6Tunnel6rdBorderRelayEntry 3 }

-- {COLUMN} 1.3.6.1.4.1.2356.11.1.77.8.3.1.4
lcsStatusIpv6Tunnel6rdBorderRelayEntry6rdPrefix OBJECT-TYPE
    SYNTAX     OCTET STRING (SIZE(17..17))
    MAX-ACCESS read-only
    STATUS     current
    DESCRIPTION
            "-- empty --"
    ::= { lcsStatusIpv6Tunnel6rdBorderRelayEntry 4 }

-- {COLUMN} 1.3.6.1.4.1.2356.11.1.77.8.3.1.5
lcsStatusIpv6Tunnel6rdBorderRelayEntryIpv4MaskLength OBJECT-TYPE
    SYNTAX     Unsigned32 (0..65535)
    MAX-ACCESS read-only
    STATUS     current
    DESCRIPTION
            "-- empty --"
    ::= { lcsStatusIpv6Tunnel6rdBorderRelayEntry 5 }

-- {COLUMN} 1.3.6.1.4.1.2356.11.1.77.8.3.1.6
lcsStatusIpv6Tunnel6rdBorderRelayEntryDhcpv4Propagate OBJECT-TYPE
    SYNTAX     INTEGER {
                  eYes (0),
                  eNo (1)
            }
    MAX-ACCESS read-only
    STATUS     current
    DESCRIPTION
            "-- empty --"
    ::= { lcsStatusIpv6Tunnel6rdBorderRelayEntry 6 }

-- {COLUMN} 1.3.6.1.4.1.2356.11.1.77.8.3.1.7
lcsStatusIpv6Tunnel6rdBorderRelayEntryFirewall OBJECT-TYPE
    SYNTAX     INTEGER {
                  eYes (0),
                  eNo (1)
            }
    MAX-ACCESS read-only
    STATUS     current
    DESCRIPTION
            "-- empty --"
    ::= { lcsStatusIpv6Tunnel6rdBorderRelayEntry 7 }

-- {TABLE} 1.3.6.1.4.1.2356.11.1.77.8.4
lcsStatusIpv6Tunnel6to4Table OBJECT-TYPE
    SYNTAX     SEQUENCE OF LcsStatusIpv6Tunnel6to4Entry
    MAX-ACCESS not-accessible
    STATUS     current
    DESCRIPTION
            "-- empty --"
    ::= { lcsStatusIpv6Tunnel 4 }

-- {ROW} 1.3.6.1.4.1.2356.11.1.77.8.4.1
lcsStatusIpv6Tunnel6to4Entry OBJECT-TYPE
    SYNTAX     LcsStatusIpv6Tunnel6to4Entry
    MAX-ACCESS not-accessible
    STATUS     current
    DESCRIPTION
            ""
    INDEX {
            lcsStatusIpv6Tunnel6to4EntryPeerName
          }
    ::= { lcsStatusIpv6Tunnel6to4Table 1 }

LcsStatusIpv6Tunnel6to4Entry ::= SEQUENCE {
            lcsStatusIpv6Tunnel6to4EntryPeerName OCTET STRING,
            lcsStatusIpv6Tunnel6to4EntryInterfaceStatus INTEGER,
            lcsStatusIpv6Tunnel6to4EntryGatewayAddress OCTET STRING,
            lcsStatusIpv6Tunnel6to4EntryFirewall INTEGER
    }

-- {COLUMN} 1.3.6.1.4.1.2356.11.1.77.8.4.1.1
lcsStatusIpv6Tunnel6to4EntryPeerName OBJECT-TYPE
    SYNTAX     OCTET STRING (SIZE(0..17))
    MAX-ACCESS read-only
    STATUS     current
    DESCRIPTION
            "-- empty --"
    ::= { lcsStatusIpv6Tunnel6to4Entry 1 }

-- {COLUMN} 1.3.6.1.4.1.2356.11.1.77.8.4.1.2
lcsStatusIpv6Tunnel6to4EntryInterfaceStatus OBJECT-TYPE
    SYNTAX     INTEGER {
                  eUp (1),
                  eDown (2)
            }
    MAX-ACCESS read-only
    STATUS     current
    DESCRIPTION
            "-- empty --"
    ::= { lcsStatusIpv6Tunnel6to4Entry 2 }

-- {COLUMN} 1.3.6.1.4.1.2356.11.1.77.8.4.1.3
lcsStatusIpv6Tunnel6to4EntryGatewayAddress OBJECT-TYPE
    SYNTAX     OCTET STRING (SIZE(0..65))
    MAX-ACCESS read-only
    STATUS     current
    DESCRIPTION
            "-- empty --"
    ::= { lcsStatusIpv6Tunnel6to4Entry 3 }

-- {COLUMN} 1.3.6.1.4.1.2356.11.1.77.8.4.1.4
lcsStatusIpv6Tunnel6to4EntryFirewall OBJECT-TYPE
    SYNTAX     INTEGER {
                  eYes (0),
                  eNo (1)
            }
    MAX-ACCESS read-only
    STATUS     current
    DESCRIPTION
            "-- empty --"
    ::= { lcsStatusIpv6Tunnel6to4Entry 4 }

-- {NODE} 1.3.6.1.4.1.2356.11.1.77.9
lcsStatusIpv6Firewall OBJECT IDENTIFIER ::= { lcsStatusIpv6 9 }

-- {TABLE} 1.3.6.1.4.1.2356.11.1.77.9.1
lcsStatusIpv6FirewallLogTableTable OBJECT-TYPE
    SYNTAX     SEQUENCE OF LcsStatusIpv6FirewallLogTableEntry
    MAX-ACCESS not-accessible
    STATUS     current
    DESCRIPTION
            "-- empty --"
    ::= { lcsStatusIpv6Firewall 1 }

-- {ROW} 1.3.6.1.4.1.2356.11.1.77.9.1.1
lcsStatusIpv6FirewallLogTableEntry OBJECT-TYPE
    SYNTAX     LcsStatusIpv6FirewallLogTableEntry
    MAX-ACCESS not-accessible
    STATUS     current
    DESCRIPTION
            ""
    INDEX {
            lcsStatusIpv6FirewallLogTableEntryIdx
          }
    ::= { lcsStatusIpv6FirewallLogTableTable 1 }

LcsStatusIpv6FirewallLogTableEntry ::= SEQUENCE {
            lcsStatusIpv6FirewallLogTableEntryIdx Integer32,
            lcsStatusIpv6FirewallLogTableEntrySystemTime DisplayString,
            lcsStatusIpv6FirewallLogTableEntrySrcAddress DisplayString,
            lcsStatusIpv6FirewallLogTableEntryDstAddress DisplayString,
            lcsStatusIpv6FirewallLogTableEntryProt Integer32,
            lcsStatusIpv6FirewallLogTableEntrySrcPort Integer32,
            lcsStatusIpv6FirewallLogTableEntryDstPort Integer32,
            lcsStatusIpv6FirewallLogTableEntryFilterRule DisplayString,
            lcsStatusIpv6FirewallLogTableEntryLimit Integer32,
            lcsStatusIpv6FirewallLogTableEntryThreshold Integer32,
            lcsStatusIpv6FirewallLogTableEntryAction Integer32
    }

-- {COLUMN} 1.3.6.1.4.1.2356.11.1.77.9.1.1.1
lcsStatusIpv6FirewallLogTableEntryIdx OBJECT-TYPE
    SYNTAX     Integer32 (0..65535)
    MAX-ACCESS read-only
    STATUS     current
    DESCRIPTION
            "-- empty --"
    ::= { lcsStatusIpv6FirewallLogTableEntry 1 }

-- {COLUMN} 1.3.6.1.4.1.2356.11.1.77.9.1.1.2
lcsStatusIpv6FirewallLogTableEntrySystemTime OBJECT-TYPE
    SYNTAX     DisplayString (SIZE(0..19))
    MAX-ACCESS read-only
    STATUS     current
    DESCRIPTION
            "-- empty --"
    ::= { lcsStatusIpv6FirewallLogTableEntry 2 }

-- {COLUMN} 1.3.6.1.4.1.2356.11.1.77.9.1.1.3
lcsStatusIpv6FirewallLogTableEntrySrcAddress OBJECT-TYPE
    SYNTAX     DisplayString (SIZE(0..255))
    MAX-ACCESS read-only
    STATUS     current
    DESCRIPTION
            "-- empty --"
    ::= { lcsStatusIpv6FirewallLogTableEntry 3 }

-- {COLUMN} 1.3.6.1.4.1.2356.11.1.77.9.1.1.4
lcsStatusIpv6FirewallLogTableEntryDstAddress OBJECT-TYPE
    SYNTAX     DisplayString (SIZE(0..255))
    MAX-ACCESS read-only
    STATUS     current
    DESCRIPTION
            "-- empty --"
    ::= { lcsStatusIpv6FirewallLogTableEntry 4 }

-- {COLUMN} 1.3.6.1.4.1.2356.11.1.77.9.1.1.5
lcsStatusIpv6FirewallLogTableEntryProt OBJECT-TYPE
    SYNTAX     Integer32 (0..255)
    MAX-ACCESS read-only
    STATUS     current
    DESCRIPTION
            "-- empty --"
    ::= { lcsStatusIpv6FirewallLogTableEntry 5 }

-- {COLUMN} 1.3.6.1.4.1.2356.11.1.77.9.1.1.6
lcsStatusIpv6FirewallLogTableEntrySrcPort OBJECT-TYPE
    SYNTAX     Integer32 (0..65535)
    MAX-ACCESS read-only
    STATUS     current
    DESCRIPTION
            "-- empty --"
    ::= { lcsStatusIpv6FirewallLogTableEntry 6 }

-- {COLUMN} 1.3.6.1.4.1.2356.11.1.77.9.1.1.7
lcsStatusIpv6FirewallLogTableEntryDstPort OBJECT-TYPE
    SYNTAX     Integer32 (0..65535)
    MAX-ACCESS read-only
    STATUS     current
    DESCRIPTION
            "-- empty --"
    ::= { lcsStatusIpv6FirewallLogTableEntry 7 }

-- {COLUMN} 1.3.6.1.4.1.2356.11.1.77.9.1.1.8
lcsStatusIpv6FirewallLogTableEntryFilterRule OBJECT-TYPE
    SYNTAX     DisplayString (SIZE(0..69))
    MAX-ACCESS read-only
    STATUS     current
    DESCRIPTION
            "-- empty --"
    ::= { lcsStatusIpv6FirewallLogTableEntry 8 }

-- {COLUMN} 1.3.6.1.4.1.2356.11.1.77.9.1.1.9
lcsStatusIpv6FirewallLogTableEntryLimit OBJECT-TYPE
    SYNTAX     Integer32 (0..2147483647)
    MAX-ACCESS read-only
    STATUS     current
    DESCRIPTION
            "-- empty --"
    ::= { lcsStatusIpv6FirewallLogTableEntry 9 }

-- {COLUMN} 1.3.6.1.4.1.2356.11.1.77.9.1.1.10
lcsStatusIpv6FirewallLogTableEntryThreshold OBJECT-TYPE
    SYNTAX     Integer32 (0..2147483647)
    MAX-ACCESS read-only
    STATUS     current
    DESCRIPTION
            "-- empty --"
    ::= { lcsStatusIpv6FirewallLogTableEntry 10 }

-- {COLUMN} 1.3.6.1.4.1.2356.11.1.77.9.1.1.11
lcsStatusIpv6FirewallLogTableEntryAction OBJECT-TYPE
    SYNTAX     Integer32 (0..2147483647)
    MAX-ACCESS read-only
    STATUS     current
    DESCRIPTION
            "-- empty --"
    ::= { lcsStatusIpv6FirewallLogTableEntry 11 }

-- {TABLE} 1.3.6.1.4.1.2356.11.1.77.9.2
lcsStatusIpv6FirewallForwardingFilterTable OBJECT-TYPE
    SYNTAX     SEQUENCE OF LcsStatusIpv6FirewallForwardingFilterEntry
    MAX-ACCESS not-accessible
    STATUS     current
    DESCRIPTION
            "-- empty --"
    ::= { lcsStatusIpv6Firewall 2 }

-- {ROW} 1.3.6.1.4.1.2356.11.1.77.9.2.1
lcsStatusIpv6FirewallForwardingFilterEntry OBJECT-TYPE
    SYNTAX     LcsStatusIpv6FirewallForwardingFilterEntry
    MAX-ACCESS not-accessible
    STATUS     current
    DESCRIPTION
            ""
    INDEX {
            lcsStatusIpv6FirewallForwardingFilterEntryIdx
          }
    ::= { lcsStatusIpv6FirewallForwardingFilterTable 1 }

LcsStatusIpv6FirewallForwardingFilterEntry ::= SEQUENCE {
            lcsStatusIpv6FirewallForwardingFilterEntryIdx Unsigned32,
            lcsStatusIpv6FirewallForwardingFilterEntryProt Unsigned32,
            lcsStatusIpv6FirewallForwardingFilterEntrySourceNetwork OCTET STRING,
            lcsStatusIpv6FirewallForwardingFilterEntrySrcInterface OCTET STRING,
            lcsStatusIpv6FirewallForwardingFilterEntrySSt Unsigned32,
            lcsStatusIpv6FirewallForwardingFilterEntrySEnd Unsigned32,
            lcsStatusIpv6FirewallForwardingFilterEntryDestinationNetwork OCTET STRING,
            lcsStatusIpv6FirewallForwardingFilterEntryDstInterface OCTET STRING,
            lcsStatusIpv6FirewallForwardingFilterEntryDSt Unsigned32,
            lcsStatusIpv6FirewallForwardingFilterEntryDEnd Unsigned32,
            lcsStatusIpv6FirewallForwardingFilterEntryAction OCTET STRING,
            lcsStatusIpv6FirewallForwardingFilterEntryLinked INTEGER,
            lcsStatusIpv6FirewallForwardingFilterEntryPrio Unsigned32,
            lcsStatusIpv6FirewallForwardingFilterEntryRtgTag Unsigned32,
            lcsStatusIpv6FirewallForwardingFilterEntryFilterRule OCTET STRING,
            lcsStatusIpv6FirewallForwardingFilterEntrySrcTag Unsigned32
    }

-- {COLUMN} 1.3.6.1.4.1.2356.11.1.77.9.2.1.1
lcsStatusIpv6FirewallForwardingFilterEntryIdx OBJECT-TYPE
    SYNTAX     Unsigned32 (0..4294967295)
    MAX-ACCESS read-only
    STATUS     current
    DESCRIPTION
            "-- empty --"
    ::= { lcsStatusIpv6FirewallForwardingFilterEntry 1 }

-- {COLUMN} 1.3.6.1.4.1.2356.11.1.77.9.2.1.2
lcsStatusIpv6FirewallForwardingFilterEntryProt OBJECT-TYPE
    SYNTAX     Unsigned32 (0..65535)
    MAX-ACCESS read-only
    STATUS     current
    DESCRIPTION
            "-- empty --"
    ::= { lcsStatusIpv6FirewallForwardingFilterEntry 2 }

-- {COLUMN} 1.3.6.1.4.1.2356.11.1.77.9.2.1.4
lcsStatusIpv6FirewallForwardingFilterEntrySourceNetwork OBJECT-TYPE
    SYNTAX     OCTET STRING (SIZE(17..17))
    MAX-ACCESS read-only
    STATUS     current
    DESCRIPTION
            "-- empty --"
    ::= { lcsStatusIpv6FirewallForwardingFilterEntry 4 }

-- {COLUMN} 1.3.6.1.4.1.2356.11.1.77.9.2.1.5
lcsStatusIpv6FirewallForwardingFilterEntrySrcInterface OBJECT-TYPE
    SYNTAX     OCTET STRING (SIZE(0..25))
    MAX-ACCESS read-only
    STATUS     current
    DESCRIPTION
            "-- empty --"
    ::= { lcsStatusIpv6FirewallForwardingFilterEntry 5 }

-- {COLUMN} 1.3.6.1.4.1.2356.11.1.77.9.2.1.6
lcsStatusIpv6FirewallForwardingFilterEntrySSt OBJECT-TYPE
    SYNTAX     Unsigned32 (0..65535)
    MAX-ACCESS read-only
    STATUS     current
    DESCRIPTION
            "-- empty --"
    ::= { lcsStatusIpv6FirewallForwardingFilterEntry 6 }

-- {COLUMN} 1.3.6.1.4.1.2356.11.1.77.9.2.1.7
lcsStatusIpv6FirewallForwardingFilterEntrySEnd OBJECT-TYPE
    SYNTAX     Unsigned32 (0..65535)
    MAX-ACCESS read-only
    STATUS     current
    DESCRIPTION
            "-- empty --"
    ::= { lcsStatusIpv6FirewallForwardingFilterEntry 7 }

-- {COLUMN} 1.3.6.1.4.1.2356.11.1.77.9.2.1.9
lcsStatusIpv6FirewallForwardingFilterEntryDestinationNetwork OBJECT-TYPE
    SYNTAX     OCTET STRING (SIZE(0..43))
    MAX-ACCESS read-only
    STATUS     current
    DESCRIPTION
            "-- empty --"
    ::= { lcsStatusIpv6FirewallForwardingFilterEntry 9 }

-- {COLUMN} 1.3.6.1.4.1.2356.11.1.77.9.2.1.10
lcsStatusIpv6FirewallForwardingFilterEntryDstInterface OBJECT-TYPE
    SYNTAX     OCTET STRING (SIZE(0..25))
    MAX-ACCESS read-only
    STATUS     current
    DESCRIPTION
            "-- empty --"
    ::= { lcsStatusIpv6FirewallForwardingFilterEntry 10 }

-- {COLUMN} 1.3.6.1.4.1.2356.11.1.77.9.2.1.11
lcsStatusIpv6FirewallForwardingFilterEntryDSt OBJECT-TYPE
    SYNTAX     Unsigned32 (0..65535)
    MAX-ACCESS read-only
    STATUS     current
    DESCRIPTION
            "-- empty --"
    ::= { lcsStatusIpv6FirewallForwardingFilterEntry 11 }

-- {COLUMN} 1.3.6.1.4.1.2356.11.1.77.9.2.1.12
lcsStatusIpv6FirewallForwardingFilterEntryDEnd OBJECT-TYPE
    SYNTAX     Unsigned32 (0..65535)
    MAX-ACCESS read-only
    STATUS     current
    DESCRIPTION
            "-- empty --"
    ::= { lcsStatusIpv6FirewallForwardingFilterEntry 12 }

-- {COLUMN} 1.3.6.1.4.1.2356.11.1.77.9.2.1.13
lcsStatusIpv6FirewallForwardingFilterEntryAction OBJECT-TYPE
    SYNTAX     OCTET STRING (SIZE(0..32))
    MAX-ACCESS read-only
    STATUS     current
    DESCRIPTION
            "-- empty --"
    ::= { lcsStatusIpv6FirewallForwardingFilterEntry 13 }

-- {COLUMN} 1.3.6.1.4.1.2356.11.1.77.9.2.1.14
lcsStatusIpv6FirewallForwardingFilterEntryLinked OBJECT-TYPE
    SYNTAX     INTEGER {
                  eNo (0),
                  eYes (1)
            }
    MAX-ACCESS read-only
    STATUS     current
    DESCRIPTION
            "-- empty --"
    ::= { lcsStatusIpv6FirewallForwardingFilterEntry 14 }

-- {COLUMN} 1.3.6.1.4.1.2356.11.1.77.9.2.1.15
lcsStatusIpv6FirewallForwardingFilterEntryPrio OBJECT-TYPE
    SYNTAX     Unsigned32 (0..65535)
    MAX-ACCESS read-only
    STATUS     current
    DESCRIPTION
            "-- empty --"
    ::= { lcsStatusIpv6FirewallForwardingFilterEntry 15 }

-- {COLUMN} 1.3.6.1.4.1.2356.11.1.77.9.2.1.16
lcsStatusIpv6FirewallForwardingFilterEntryRtgTag OBJECT-TYPE
    SYNTAX     Unsigned32 (0..65535)
    MAX-ACCESS read-only
    STATUS     current
    DESCRIPTION
            "-- empty --"
    ::= { lcsStatusIpv6FirewallForwardingFilterEntry 16 }

-- {COLUMN} 1.3.6.1.4.1.2356.11.1.77.9.2.1.17
lcsStatusIpv6FirewallForwardingFilterEntryFilterRule OBJECT-TYPE
    SYNTAX     OCTET STRING (SIZE(0..69))
    MAX-ACCESS read-only
    STATUS     current
    DESCRIPTION
            "-- empty --"
    ::= { lcsStatusIpv6FirewallForwardingFilterEntry 17 }

-- {COLUMN} 1.3.6.1.4.1.2356.11.1.77.9.2.1.18
lcsStatusIpv6FirewallForwardingFilterEntrySrcTag OBJECT-TYPE
    SYNTAX     Unsigned32 (0..65535)
    MAX-ACCESS read-only
    STATUS     current
    DESCRIPTION
            "-- empty --"
    ::= { lcsStatusIpv6FirewallForwardingFilterEntry 18 }

-- {TABLE} 1.3.6.1.4.1.2356.11.1.77.9.3
lcsStatusIpv6FirewallInboundFilterTable OBJECT-TYPE
    SYNTAX     SEQUENCE OF LcsStatusIpv6FirewallInboundFilterEntry
    MAX-ACCESS not-accessible
    STATUS     current
    DESCRIPTION
            "-- empty --"
    ::= { lcsStatusIpv6Firewall 3 }

-- {ROW} 1.3.6.1.4.1.2356.11.1.77.9.3.1
lcsStatusIpv6FirewallInboundFilterEntry OBJECT-TYPE
    SYNTAX     LcsStatusIpv6FirewallInboundFilterEntry
    MAX-ACCESS not-accessible
    STATUS     current
    DESCRIPTION
            ""
    INDEX {
            lcsStatusIpv6FirewallInboundFilterEntryIdx
          }
    ::= { lcsStatusIpv6FirewallInboundFilterTable 1 }

LcsStatusIpv6FirewallInboundFilterEntry ::= SEQUENCE {
            lcsStatusIpv6FirewallInboundFilterEntryIdx Unsigned32,
            lcsStatusIpv6FirewallInboundFilterEntryProt Unsigned32,
            lcsStatusIpv6FirewallInboundFilterEntrySourceNetwork OCTET STRING,
            lcsStatusIpv6FirewallInboundFilterEntrySrcInterface OCTET STRING,
            lcsStatusIpv6FirewallInboundFilterEntrySSt Unsigned32,
            lcsStatusIpv6FirewallInboundFilterEntrySEnd Unsigned32,
            lcsStatusIpv6FirewallInboundFilterEntryDSt Unsigned32,
            lcsStatusIpv6FirewallInboundFilterEntryDEnd Unsigned32,
            lcsStatusIpv6FirewallInboundFilterEntryAction OCTET STRING,
            lcsStatusIpv6FirewallInboundFilterEntryPrio Unsigned32,
            lcsStatusIpv6FirewallInboundFilterEntryFilterRule OCTET STRING,
            lcsStatusIpv6FirewallInboundFilterEntrySrcTag Unsigned32
    }

-- {COLUMN} 1.3.6.1.4.1.2356.11.1.77.9.3.1.1
lcsStatusIpv6FirewallInboundFilterEntryIdx OBJECT-TYPE
    SYNTAX     Unsigned32 (0..4294967295)
    MAX-ACCESS read-only
    STATUS     current
    DESCRIPTION
            "-- empty --"
    ::= { lcsStatusIpv6FirewallInboundFilterEntry 1 }

-- {COLUMN} 1.3.6.1.4.1.2356.11.1.77.9.3.1.2
lcsStatusIpv6FirewallInboundFilterEntryProt OBJECT-TYPE
    SYNTAX     Unsigned32 (0..65535)
    MAX-ACCESS read-only
    STATUS     current
    DESCRIPTION
            "-- empty --"
    ::= { lcsStatusIpv6FirewallInboundFilterEntry 2 }

-- {COLUMN} 1.3.6.1.4.1.2356.11.1.77.9.3.1.4
lcsStatusIpv6FirewallInboundFilterEntrySourceNetwork OBJECT-TYPE
    SYNTAX     OCTET STRING (SIZE(17..17))
    MAX-ACCESS read-only
    STATUS     current
    DESCRIPTION
            "-- empty --"
    ::= { lcsStatusIpv6FirewallInboundFilterEntry 4 }

-- {COLUMN} 1.3.6.1.4.1.2356.11.1.77.9.3.1.5
lcsStatusIpv6FirewallInboundFilterEntrySrcInterface OBJECT-TYPE
    SYNTAX     OCTET STRING (SIZE(0..25))
    MAX-ACCESS read-only
    STATUS     current
    DESCRIPTION
            "-- empty --"
    ::= { lcsStatusIpv6FirewallInboundFilterEntry 5 }

-- {COLUMN} 1.3.6.1.4.1.2356.11.1.77.9.3.1.6
lcsStatusIpv6FirewallInboundFilterEntrySSt OBJECT-TYPE
    SYNTAX     Unsigned32 (0..65535)
    MAX-ACCESS read-only
    STATUS     current
    DESCRIPTION
            "-- empty --"
    ::= { lcsStatusIpv6FirewallInboundFilterEntry 6 }

-- {COLUMN} 1.3.6.1.4.1.2356.11.1.77.9.3.1.7
lcsStatusIpv6FirewallInboundFilterEntrySEnd OBJECT-TYPE
    SYNTAX     Unsigned32 (0..65535)
    MAX-ACCESS read-only
    STATUS     current
    DESCRIPTION
            "-- empty --"
    ::= { lcsStatusIpv6FirewallInboundFilterEntry 7 }

-- {COLUMN} 1.3.6.1.4.1.2356.11.1.77.9.3.1.9
lcsStatusIpv6FirewallInboundFilterEntryDSt OBJECT-TYPE
    SYNTAX     Unsigned32 (0..65535)
    MAX-ACCESS read-only
    STATUS     current
    DESCRIPTION
            "-- empty --"
    ::= { lcsStatusIpv6FirewallInboundFilterEntry 9 }

-- {COLUMN} 1.3.6.1.4.1.2356.11.1.77.9.3.1.10
lcsStatusIpv6FirewallInboundFilterEntryDEnd OBJECT-TYPE
    SYNTAX     Unsigned32 (0..65535)
    MAX-ACCESS read-only
    STATUS     current
    DESCRIPTION
            "-- empty --"
    ::= { lcsStatusIpv6FirewallInboundFilterEntry 10 }

-- {COLUMN} 1.3.6.1.4.1.2356.11.1.77.9.3.1.11
lcsStatusIpv6FirewallInboundFilterEntryAction OBJECT-TYPE
    SYNTAX     OCTET STRING (SIZE(0..32))
    MAX-ACCESS read-only
    STATUS     current
    DESCRIPTION
            "-- empty --"
    ::= { lcsStatusIpv6FirewallInboundFilterEntry 11 }

-- {COLUMN} 1.3.6.1.4.1.2356.11.1.77.9.3.1.12
lcsStatusIpv6FirewallInboundFilterEntryPrio OBJECT-TYPE
    SYNTAX     Unsigned32 (0..65535)
    MAX-ACCESS read-only
    STATUS     current
    DESCRIPTION
            "-- empty --"
    ::= { lcsStatusIpv6FirewallInboundFilterEntry 12 }

-- {COLUMN} 1.3.6.1.4.1.2356.11.1.77.9.3.1.13
lcsStatusIpv6FirewallInboundFilterEntryFilterRule OBJECT-TYPE
    SYNTAX     OCTET STRING (SIZE(0..69))
    MAX-ACCESS read-only
    STATUS     current
    DESCRIPTION
            "-- empty --"
    ::= { lcsStatusIpv6FirewallInboundFilterEntry 13 }

-- {COLUMN} 1.3.6.1.4.1.2356.11.1.77.9.3.1.14
lcsStatusIpv6FirewallInboundFilterEntrySrcTag OBJECT-TYPE
    SYNTAX     Unsigned32 (0..65535)
    MAX-ACCESS read-only
    STATUS     current
    DESCRIPTION
            "-- empty --"
    ::= { lcsStatusIpv6FirewallInboundFilterEntry 14 }

-- {TABLE} 1.3.6.1.4.1.2356.11.1.77.9.4
lcsStatusIpv6FirewallForwardingSessionsTable OBJECT-TYPE
    SYNTAX     SEQUENCE OF LcsStatusIpv6FirewallForwardingSessionsEntry
    MAX-ACCESS not-accessible
    STATUS     current
    DESCRIPTION
            "-- empty --"
    ::= { lcsStatusIpv6Firewall 4 }

-- {ROW} 1.3.6.1.4.1.2356.11.1.77.9.4.1
lcsStatusIpv6FirewallForwardingSessionsEntry OBJECT-TYPE
    SYNTAX     LcsStatusIpv6FirewallForwardingSessionsEntry
    MAX-ACCESS not-accessible
    STATUS     current
    DESCRIPTION
            ""
    INDEX {
            lcsStatusIpv6FirewallForwardingSessionsEntrySrcAddress,
            lcsStatusIpv6FirewallForwardingSessionsEntryDstAddress,
            lcsStatusIpv6FirewallForwardingSessionsEntryProt,
            lcsStatusIpv6FirewallForwardingSessionsEntrySrcPort,
            lcsStatusIpv6FirewallForwardingSessionsEntryDstPort,
            lcsStatusIpv6FirewallForwardingSessionsEntrySrcInterface
          }
    ::= { lcsStatusIpv6FirewallForwardingSessionsTable 1 }

LcsStatusIpv6FirewallForwardingSessionsEntry ::= SEQUENCE {
            lcsStatusIpv6FirewallForwardingSessionsEntrySrcAddress OCTET STRING,
            lcsStatusIpv6FirewallForwardingSessionsEntryDstAddress OCTET STRING,
            lcsStatusIpv6FirewallForwardingSessionsEntryProt Unsigned32,
            lcsStatusIpv6FirewallForwardingSessionsEntrySrcPort Unsigned32,
            lcsStatusIpv6FirewallForwardingSessionsEntryDstPort Unsigned32,
            lcsStatusIpv6FirewallForwardingSessionsEntrySrcInterface OCTET STRING,
            lcsStatusIpv6FirewallForwardingSessionsEntryDstInterface OCTET STRING,
            lcsStatusIpv6FirewallForwardingSessionsEntryRtgTag Unsigned32,
            lcsStatusIpv6FirewallForwardingSessionsEntryTimeout Unsigned32,
            lcsStatusIpv6FirewallForwardingSessionsEntryFilterRule OCTET STRING
    }

-- {COLUMN} 1.3.6.1.4.1.2356.11.1.77.9.4.1.1
lcsStatusIpv6FirewallForwardingSessionsEntrySrcAddress OBJECT-TYPE
    SYNTAX     OCTET STRING (SIZE(16..16))
    MAX-ACCESS read-only
    STATUS     current
    DESCRIPTION
            "-- empty --"
    ::= { lcsStatusIpv6FirewallForwardingSessionsEntry 1 }

-- {COLUMN} 1.3.6.1.4.1.2356.11.1.77.9.4.1.2
lcsStatusIpv6FirewallForwardingSessionsEntryDstAddress OBJECT-TYPE
    SYNTAX     OCTET STRING (SIZE(16..16))
    MAX-ACCESS read-only
    STATUS     current
    DESCRIPTION
            "-- empty --"
    ::= { lcsStatusIpv6FirewallForwardingSessionsEntry 2 }

-- {COLUMN} 1.3.6.1.4.1.2356.11.1.77.9.4.1.3
lcsStatusIpv6FirewallForwardingSessionsEntryProt OBJECT-TYPE
    SYNTAX     Unsigned32 (0..65535)
    MAX-ACCESS read-only
    STATUS     current
    DESCRIPTION
            "-- empty --"
    ::= { lcsStatusIpv6FirewallForwardingSessionsEntry 3 }

-- {COLUMN} 1.3.6.1.4.1.2356.11.1.77.9.4.1.4
lcsStatusIpv6FirewallForwardingSessionsEntrySrcPort OBJECT-TYPE
    SYNTAX     Unsigned32 (0..65535)
    MAX-ACCESS read-only
    STATUS     current
    DESCRIPTION
            "-- empty --"
    ::= { lcsStatusIpv6FirewallForwardingSessionsEntry 4 }

-- {COLUMN} 1.3.6.1.4.1.2356.11.1.77.9.4.1.5
lcsStatusIpv6FirewallForwardingSessionsEntryDstPort OBJECT-TYPE
    SYNTAX     Unsigned32 (0..65535)
    MAX-ACCESS read-only
    STATUS     current
    DESCRIPTION
            "-- empty --"
    ::= { lcsStatusIpv6FirewallForwardingSessionsEntry 5 }

-- {COLUMN} 1.3.6.1.4.1.2356.11.1.77.9.4.1.6
lcsStatusIpv6FirewallForwardingSessionsEntrySrcInterface OBJECT-TYPE
    SYNTAX     OCTET STRING (SIZE(0..25))
    MAX-ACCESS read-only
    STATUS     current
    DESCRIPTION
            "-- empty --"
    ::= { lcsStatusIpv6FirewallForwardingSessionsEntry 6 }

-- {COLUMN} 1.3.6.1.4.1.2356.11.1.77.9.4.1.7
lcsStatusIpv6FirewallForwardingSessionsEntryDstInterface OBJECT-TYPE
    SYNTAX     OCTET STRING (SIZE(0..25))
    MAX-ACCESS read-only
    STATUS     current
    DESCRIPTION
            "-- empty --"
    ::= { lcsStatusIpv6FirewallForwardingSessionsEntry 7 }

-- {COLUMN} 1.3.6.1.4.1.2356.11.1.77.9.4.1.8
lcsStatusIpv6FirewallForwardingSessionsEntryRtgTag OBJECT-TYPE
    SYNTAX     Unsigned32 (0..65535)
    MAX-ACCESS read-only
    STATUS     current
    DESCRIPTION
            "-- empty --"
    ::= { lcsStatusIpv6FirewallForwardingSessionsEntry 8 }

-- {COLUMN} 1.3.6.1.4.1.2356.11.1.77.9.4.1.9
lcsStatusIpv6FirewallForwardingSessionsEntryTimeout OBJECT-TYPE
    SYNTAX     Unsigned32 (0..4294967295)
    MAX-ACCESS read-only
    STATUS     current
    DESCRIPTION
            "-- empty --"
    ::= { lcsStatusIpv6FirewallForwardingSessionsEntry 9 }

-- {COLUMN} 1.3.6.1.4.1.2356.11.1.77.9.4.1.11
lcsStatusIpv6FirewallForwardingSessionsEntryFilterRule OBJECT-TYPE
    SYNTAX     OCTET STRING (SIZE(0..69))
    MAX-ACCESS read-only
    STATUS     current
    DESCRIPTION
            "-- empty --"
    ::= { lcsStatusIpv6FirewallForwardingSessionsEntry 11 }

-- {TABLE} 1.3.6.1.4.1.2356.11.1.77.9.5
lcsStatusIpv6FirewallInboundSessionsTable OBJECT-TYPE
    SYNTAX     SEQUENCE OF LcsStatusIpv6FirewallInboundSessionsEntry
    MAX-ACCESS not-accessible
    STATUS     current
    DESCRIPTION
            "-- empty --"
    ::= { lcsStatusIpv6Firewall 5 }

-- {ROW} 1.3.6.1.4.1.2356.11.1.77.9.5.1
lcsStatusIpv6FirewallInboundSessionsEntry OBJECT-TYPE
    SYNTAX     LcsStatusIpv6FirewallInboundSessionsEntry
    MAX-ACCESS not-accessible
    STATUS     current
    DESCRIPTION
            ""
    INDEX {
            lcsStatusIpv6FirewallInboundSessionsEntrySrcAddress,
            lcsStatusIpv6FirewallInboundSessionsEntryDstAddress,
            lcsStatusIpv6FirewallInboundSessionsEntryProt,
            lcsStatusIpv6FirewallInboundSessionsEntrySrcPort,
            lcsStatusIpv6FirewallInboundSessionsEntryDstPort,
            lcsStatusIpv6FirewallInboundSessionsEntrySrcInterface
          }
    ::= { lcsStatusIpv6FirewallInboundSessionsTable 1 }

LcsStatusIpv6FirewallInboundSessionsEntry ::= SEQUENCE {
            lcsStatusIpv6FirewallInboundSessionsEntrySrcAddress OCTET STRING,
            lcsStatusIpv6FirewallInboundSessionsEntryDstAddress OCTET STRING,
            lcsStatusIpv6FirewallInboundSessionsEntryProt Unsigned32,
            lcsStatusIpv6FirewallInboundSessionsEntrySrcPort Unsigned32,
            lcsStatusIpv6FirewallInboundSessionsEntryDstPort Unsigned32,
            lcsStatusIpv6FirewallInboundSessionsEntrySrcInterface OCTET STRING,
            lcsStatusIpv6FirewallInboundSessionsEntryTimeout Unsigned32,
            lcsStatusIpv6FirewallInboundSessionsEntryFilterRule OCTET STRING
    }

-- {COLUMN} 1.3.6.1.4.1.2356.11.1.77.9.5.1.1
lcsStatusIpv6FirewallInboundSessionsEntrySrcAddress OBJECT-TYPE
    SYNTAX     OCTET STRING (SIZE(16..16))
    MAX-ACCESS read-only
    STATUS     current
    DESCRIPTION
            "-- empty --"
    ::= { lcsStatusIpv6FirewallInboundSessionsEntry 1 }

-- {COLUMN} 1.3.6.1.4.1.2356.11.1.77.9.5.1.2
lcsStatusIpv6FirewallInboundSessionsEntryDstAddress OBJECT-TYPE
    SYNTAX     OCTET STRING (SIZE(16..16))
    MAX-ACCESS read-only
    STATUS     current
    DESCRIPTION
            "-- empty --"
    ::= { lcsStatusIpv6FirewallInboundSessionsEntry 2 }

-- {COLUMN} 1.3.6.1.4.1.2356.11.1.77.9.5.1.3
lcsStatusIpv6FirewallInboundSessionsEntryProt OBJECT-TYPE
    SYNTAX     Unsigned32 (0..65535)
    MAX-ACCESS read-only
    STATUS     current
    DESCRIPTION
            "-- empty --"
    ::= { lcsStatusIpv6FirewallInboundSessionsEntry 3 }

-- {COLUMN} 1.3.6.1.4.1.2356.11.1.77.9.5.1.4
lcsStatusIpv6FirewallInboundSessionsEntrySrcPort OBJECT-TYPE
    SYNTAX     Unsigned32 (0..65535)
    MAX-ACCESS read-only
    STATUS     current
    DESCRIPTION
            "-- empty --"
    ::= { lcsStatusIpv6FirewallInboundSessionsEntry 4 }

-- {COLUMN} 1.3.6.1.4.1.2356.11.1.77.9.5.1.5
lcsStatusIpv6FirewallInboundSessionsEntryDstPort OBJECT-TYPE
    SYNTAX     Unsigned32 (0..65535)
    MAX-ACCESS read-only
    STATUS     current
    DESCRIPTION
            "-- empty --"
    ::= { lcsStatusIpv6FirewallInboundSessionsEntry 5 }

-- {COLUMN} 1.3.6.1.4.1.2356.11.1.77.9.5.1.6
lcsStatusIpv6FirewallInboundSessionsEntrySrcInterface OBJECT-TYPE
    SYNTAX     OCTET STRING (SIZE(0..25))
    MAX-ACCESS read-only
    STATUS     current
    DESCRIPTION
            "-- empty --"
    ::= { lcsStatusIpv6FirewallInboundSessionsEntry 6 }

-- {COLUMN} 1.3.6.1.4.1.2356.11.1.77.9.5.1.7
lcsStatusIpv6FirewallInboundSessionsEntryTimeout OBJECT-TYPE
    SYNTAX     Unsigned32 (0..4294967295)
    MAX-ACCESS read-only
    STATUS     current
    DESCRIPTION
            "-- empty --"
    ::= { lcsStatusIpv6FirewallInboundSessionsEntry 7 }

-- {COLUMN} 1.3.6.1.4.1.2356.11.1.77.9.5.1.9
lcsStatusIpv6FirewallInboundSessionsEntryFilterRule OBJECT-TYPE
    SYNTAX     OCTET STRING (SIZE(0..69))
    MAX-ACCESS read-only
    STATUS     current
    DESCRIPTION
            "-- empty --"
    ::= { lcsStatusIpv6FirewallInboundSessionsEntry 9 }

-- {TABLE} 1.3.6.1.4.1.2356.11.1.77.9.6
lcsStatusIpv6FirewallForwardingOpenPortsTable OBJECT-TYPE
    SYNTAX     SEQUENCE OF LcsStatusIpv6FirewallForwardingOpenPortsEntry
    MAX-ACCESS not-accessible
    STATUS     current
    DESCRIPTION
            "-- empty --"
    ::= { lcsStatusIpv6Firewall 6 }

-- {ROW} 1.3.6.1.4.1.2356.11.1.77.9.6.1
lcsStatusIpv6FirewallForwardingOpenPortsEntry OBJECT-TYPE
    SYNTAX     LcsStatusIpv6FirewallForwardingOpenPortsEntry
    MAX-ACCESS not-accessible
    STATUS     current
    DESCRIPTION
            ""
    INDEX {
            lcsStatusIpv6FirewallForwardingOpenPortsEntrySrcAddress,
            lcsStatusIpv6FirewallForwardingOpenPortsEntryDstAddress,
            lcsStatusIpv6FirewallForwardingOpenPortsEntryProt,
            lcsStatusIpv6FirewallForwardingOpenPortsEntryDstPort,
            lcsStatusIpv6FirewallForwardingOpenPortsEntrySrcInterface
          }
    ::= { lcsStatusIpv6FirewallForwardingOpenPortsTable 1 }

LcsStatusIpv6FirewallForwardingOpenPortsEntry ::= SEQUENCE {
            lcsStatusIpv6FirewallForwardingOpenPortsEntrySrcAddress OCTET STRING,
            lcsStatusIpv6FirewallForwardingOpenPortsEntryDstAddress OCTET STRING,
            lcsStatusIpv6FirewallForwardingOpenPortsEntryProt Unsigned32,
            lcsStatusIpv6FirewallForwardingOpenPortsEntryDstPort Unsigned32,
            lcsStatusIpv6FirewallForwardingOpenPortsEntrySrcInterface OCTET STRING,
            lcsStatusIpv6FirewallForwardingOpenPortsEntryTimeout Unsigned32,
            lcsStatusIpv6FirewallForwardingOpenPortsEntryFilterRule OCTET STRING
    }

-- {COLUMN} 1.3.6.1.4.1.2356.11.1.77.9.6.1.1
lcsStatusIpv6FirewallForwardingOpenPortsEntrySrcAddress OBJECT-TYPE
    SYNTAX     OCTET STRING (SIZE(16..16))
    MAX-ACCESS read-only
    STATUS     current
    DESCRIPTION
            "-- empty --"
    ::= { lcsStatusIpv6FirewallForwardingOpenPortsEntry 1 }

-- {COLUMN} 1.3.6.1.4.1.2356.11.1.77.9.6.1.2
lcsStatusIpv6FirewallForwardingOpenPortsEntryDstAddress OBJECT-TYPE
    SYNTAX     OCTET STRING (SIZE(16..16))
    MAX-ACCESS read-only
    STATUS     current
    DESCRIPTION
            "-- empty --"
    ::= { lcsStatusIpv6FirewallForwardingOpenPortsEntry 2 }

-- {COLUMN} 1.3.6.1.4.1.2356.11.1.77.9.6.1.3
lcsStatusIpv6FirewallForwardingOpenPortsEntryProt OBJECT-TYPE
    SYNTAX     Unsigned32 (0..65535)
    MAX-ACCESS read-only
    STATUS     current
    DESCRIPTION
            "-- empty --"
    ::= { lcsStatusIpv6FirewallForwardingOpenPortsEntry 3 }

-- {COLUMN} 1.3.6.1.4.1.2356.11.1.77.9.6.1.4
lcsStatusIpv6FirewallForwardingOpenPortsEntryDstPort OBJECT-TYPE
    SYNTAX     Unsigned32 (0..65535)
    MAX-ACCESS read-only
    STATUS     current
    DESCRIPTION
            "-- empty --"
    ::= { lcsStatusIpv6FirewallForwardingOpenPortsEntry 4 }

-- {COLUMN} 1.3.6.1.4.1.2356.11.1.77.9.6.1.5
lcsStatusIpv6FirewallForwardingOpenPortsEntrySrcInterface OBJECT-TYPE
    SYNTAX     OCTET STRING (SIZE(0..25))
    MAX-ACCESS read-only
    STATUS     current
    DESCRIPTION
            "-- empty --"
    ::= { lcsStatusIpv6FirewallForwardingOpenPortsEntry 5 }

-- {COLUMN} 1.3.6.1.4.1.2356.11.1.77.9.6.1.6
lcsStatusIpv6FirewallForwardingOpenPortsEntryTimeout OBJECT-TYPE
    SYNTAX     Unsigned32 (0..4294967295)
    MAX-ACCESS read-only
    STATUS     current
    DESCRIPTION
            "-- empty --"
    ::= { lcsStatusIpv6FirewallForwardingOpenPortsEntry 6 }

-- {COLUMN} 1.3.6.1.4.1.2356.11.1.77.9.6.1.7
lcsStatusIpv6FirewallForwardingOpenPortsEntryFilterRule OBJECT-TYPE
    SYNTAX     OCTET STRING (SIZE(0..69))
    MAX-ACCESS read-only
    STATUS     current
    DESCRIPTION
            "-- empty --"
    ::= { lcsStatusIpv6FirewallForwardingOpenPortsEntry 7 }

-- {TABLE} 1.3.6.1.4.1.2356.11.1.77.9.7
lcsStatusIpv6FirewallHostBlockListTable OBJECT-TYPE
    SYNTAX     SEQUENCE OF LcsStatusIpv6FirewallHostBlockListEntry
    MAX-ACCESS not-accessible
    STATUS     current
    DESCRIPTION
            "-- empty --"
    ::= { lcsStatusIpv6Firewall 7 }

-- {ROW} 1.3.6.1.4.1.2356.11.1.77.9.7.1
lcsStatusIpv6FirewallHostBlockListEntry OBJECT-TYPE
    SYNTAX     LcsStatusIpv6FirewallHostBlockListEntry
    MAX-ACCESS not-accessible
    STATUS     current
    DESCRIPTION
            ""
    INDEX {
            lcsStatusIpv6FirewallHostBlockListEntrySrcAddress
          }
    ::= { lcsStatusIpv6FirewallHostBlockListTable 1 }

LcsStatusIpv6FirewallHostBlockListEntry ::= SEQUENCE {
            lcsStatusIpv6FirewallHostBlockListEntrySrcAddress OCTET STRING,
            lcsStatusIpv6FirewallHostBlockListEntryTimeout Unsigned32,
            lcsStatusIpv6FirewallHostBlockListEntryFilterRule OCTET STRING
    }

-- {COLUMN} 1.3.6.1.4.1.2356.11.1.77.9.7.1.1
lcsStatusIpv6FirewallHostBlockListEntrySrcAddress OBJECT-TYPE
    SYNTAX     OCTET STRING (SIZE(16..16))
    MAX-ACCESS read-only
    STATUS     current
    DESCRIPTION
            "-- empty --"
    ::= { lcsStatusIpv6FirewallHostBlockListEntry 1 }

-- {COLUMN} 1.3.6.1.4.1.2356.11.1.77.9.7.1.2
lcsStatusIpv6FirewallHostBlockListEntryTimeout OBJECT-TYPE
    SYNTAX     Unsigned32 (0..4294967295)
    MAX-ACCESS read-only
    STATUS     current
    DESCRIPTION
            "-- empty --"
    ::= { lcsStatusIpv6FirewallHostBlockListEntry 2 }

-- {COLUMN} 1.3.6.1.4.1.2356.11.1.77.9.7.1.3
lcsStatusIpv6FirewallHostBlockListEntryFilterRule OBJECT-TYPE
    SYNTAX     OCTET STRING (SIZE(0..69))
    MAX-ACCESS read-only
    STATUS     current
    DESCRIPTION
            "-- empty --"
    ::= { lcsStatusIpv6FirewallHostBlockListEntry 3 }

-- {TABLE} 1.3.6.1.4.1.2356.11.1.77.9.8
lcsStatusIpv6FirewallPortBlockListTable OBJECT-TYPE
    SYNTAX     SEQUENCE OF LcsStatusIpv6FirewallPortBlockListEntry
    MAX-ACCESS not-accessible
    STATUS     current
    DESCRIPTION
            "-- empty --"
    ::= { lcsStatusIpv6Firewall 8 }

-- {ROW} 1.3.6.1.4.1.2356.11.1.77.9.8.1
lcsStatusIpv6FirewallPortBlockListEntry OBJECT-TYPE
    SYNTAX     LcsStatusIpv6FirewallPortBlockListEntry
    MAX-ACCESS not-accessible
    STATUS     current
    DESCRIPTION
            ""
    INDEX {
            lcsStatusIpv6FirewallPortBlockListEntryDstAddress,
            lcsStatusIpv6FirewallPortBlockListEntryProt,
            lcsStatusIpv6FirewallPortBlockListEntryDstPort
          }
    ::= { lcsStatusIpv6FirewallPortBlockListTable 1 }

LcsStatusIpv6FirewallPortBlockListEntry ::= SEQUENCE {
            lcsStatusIpv6FirewallPortBlockListEntryDstAddress OCTET STRING,
            lcsStatusIpv6FirewallPortBlockListEntryProt Unsigned32,
            lcsStatusIpv6FirewallPortBlockListEntryDstPort Unsigned32,
            lcsStatusIpv6FirewallPortBlockListEntryTimeout Unsigned32,
            lcsStatusIpv6FirewallPortBlockListEntryFilterRule OCTET STRING
    }

-- {COLUMN} 1.3.6.1.4.1.2356.11.1.77.9.8.1.1
lcsStatusIpv6FirewallPortBlockListEntryDstAddress OBJECT-TYPE
    SYNTAX     OCTET STRING (SIZE(16..16))
    MAX-ACCESS read-only
    STATUS     current
    DESCRIPTION
            "-- empty --"
    ::= { lcsStatusIpv6FirewallPortBlockListEntry 1 }

-- {COLUMN} 1.3.6.1.4.1.2356.11.1.77.9.8.1.2
lcsStatusIpv6FirewallPortBlockListEntryProt OBJECT-TYPE
    SYNTAX     Unsigned32 (0..65535)
    MAX-ACCESS read-only
    STATUS     current
    DESCRIPTION
            "-- empty --"
    ::= { lcsStatusIpv6FirewallPortBlockListEntry 2 }

-- {COLUMN} 1.3.6.1.4.1.2356.11.1.77.9.8.1.3
lcsStatusIpv6FirewallPortBlockListEntryDstPort OBJECT-TYPE
    SYNTAX     Unsigned32 (0..65535)
    MAX-ACCESS read-only
    STATUS     current
    DESCRIPTION
            "-- empty --"
    ::= { lcsStatusIpv6FirewallPortBlockListEntry 3 }

-- {COLUMN} 1.3.6.1.4.1.2356.11.1.77.9.8.1.4
lcsStatusIpv6FirewallPortBlockListEntryTimeout OBJECT-TYPE
    SYNTAX     Unsigned32 (0..4294967295)
    MAX-ACCESS read-only
    STATUS     current
    DESCRIPTION
            "-- empty --"
    ::= { lcsStatusIpv6FirewallPortBlockListEntry 4 }

-- {COLUMN} 1.3.6.1.4.1.2356.11.1.77.9.8.1.5
lcsStatusIpv6FirewallPortBlockListEntryFilterRule OBJECT-TYPE
    SYNTAX     OCTET STRING (SIZE(0..69))
    MAX-ACCESS read-only
    STATUS     current
    DESCRIPTION
            "-- empty --"
    ::= { lcsStatusIpv6FirewallPortBlockListEntry 5 }

-- {TABLE} 1.3.6.1.4.1.2356.11.1.77.9.9
lcsStatusIpv6FirewallHalfOpenConnectionsTable OBJECT-TYPE
    SYNTAX     SEQUENCE OF LcsStatusIpv6FirewallHalfOpenConnectionsEntry
    MAX-ACCESS not-accessible
    STATUS     current
    DESCRIPTION
            "-- empty --"
    ::= { lcsStatusIpv6Firewall 9 }

-- {ROW} 1.3.6.1.4.1.2356.11.1.77.9.9.1
lcsStatusIpv6FirewallHalfOpenConnectionsEntry OBJECT-TYPE
    SYNTAX     LcsStatusIpv6FirewallHalfOpenConnectionsEntry
    MAX-ACCESS not-accessible
    STATUS     current
    DESCRIPTION
            ""
    INDEX {
            lcsStatusIpv6FirewallHalfOpenConnectionsEntryDstAddress
          }
    ::= { lcsStatusIpv6FirewallHalfOpenConnectionsTable 1 }

LcsStatusIpv6FirewallHalfOpenConnectionsEntry ::= SEQUENCE {
            lcsStatusIpv6FirewallHalfOpenConnectionsEntryDstAddress OCTET STRING,
            lcsStatusIpv6FirewallHalfOpenConnectionsEntryNumHoConn Unsigned32,
            lcsStatusIpv6FirewallHalfOpenConnectionsEntryTimeout Unsigned32
    }

-- {COLUMN} 1.3.6.1.4.1.2356.11.1.77.9.9.1.1
lcsStatusIpv6FirewallHalfOpenConnectionsEntryDstAddress OBJECT-TYPE
    SYNTAX     OCTET STRING (SIZE(16..16))
    MAX-ACCESS read-only
    STATUS     current
    DESCRIPTION
            "-- empty --"
    ::= { lcsStatusIpv6FirewallHalfOpenConnectionsEntry 1 }

-- {COLUMN} 1.3.6.1.4.1.2356.11.1.77.9.9.1.2
lcsStatusIpv6FirewallHalfOpenConnectionsEntryNumHoConn OBJECT-TYPE
    SYNTAX     Unsigned32 (0..4294967295)
    MAX-ACCESS read-only
    STATUS     current
    DESCRIPTION
            "-- empty --"
    ::= { lcsStatusIpv6FirewallHalfOpenConnectionsEntry 2 }

-- {COLUMN} 1.3.6.1.4.1.2356.11.1.77.9.9.1.3
lcsStatusIpv6FirewallHalfOpenConnectionsEntryTimeout OBJECT-TYPE
    SYNTAX     Unsigned32 (0..4294967295)
    MAX-ACCESS read-only
    STATUS     current
    DESCRIPTION
            "-- empty --"
    ::= { lcsStatusIpv6FirewallHalfOpenConnectionsEntry 3 }

-- {TABLE} 1.3.6.1.4.1.2356.11.1.77.9.10
lcsStatusIpv6FirewallOutboundSessionsTable OBJECT-TYPE
    SYNTAX     SEQUENCE OF LcsStatusIpv6FirewallOutboundSessionsEntry
    MAX-ACCESS not-accessible
    STATUS     current
    DESCRIPTION
            "-- empty --"
    ::= { lcsStatusIpv6Firewall 10 }

-- {ROW} 1.3.6.1.4.1.2356.11.1.77.9.10.1
lcsStatusIpv6FirewallOutboundSessionsEntry OBJECT-TYPE
    SYNTAX     LcsStatusIpv6FirewallOutboundSessionsEntry
    MAX-ACCESS not-accessible
    STATUS     current
    DESCRIPTION
            ""
    INDEX {
            lcsStatusIpv6FirewallOutboundSessionsEntrySrcAddress,
            lcsStatusIpv6FirewallOutboundSessionsEntryDstAddress,
            lcsStatusIpv6FirewallOutboundSessionsEntryProt,
            lcsStatusIpv6FirewallOutboundSessionsEntrySrcPort,
            lcsStatusIpv6FirewallOutboundSessionsEntryDstPort,
            lcsStatusIpv6FirewallOutboundSessionsEntryDstInterface
          }
    ::= { lcsStatusIpv6FirewallOutboundSessionsTable 1 }

LcsStatusIpv6FirewallOutboundSessionsEntry ::= SEQUENCE {
            lcsStatusIpv6FirewallOutboundSessionsEntrySrcAddress OCTET STRING,
            lcsStatusIpv6FirewallOutboundSessionsEntryDstAddress OCTET STRING,
            lcsStatusIpv6FirewallOutboundSessionsEntryProt Unsigned32,
            lcsStatusIpv6FirewallOutboundSessionsEntrySrcPort Unsigned32,
            lcsStatusIpv6FirewallOutboundSessionsEntryDstPort Unsigned32,
            lcsStatusIpv6FirewallOutboundSessionsEntryDstInterface OCTET STRING,
            lcsStatusIpv6FirewallOutboundSessionsEntryTimeout Unsigned32,
            lcsStatusIpv6FirewallOutboundSessionsEntryFilterRule OCTET STRING
    }

-- {COLUMN} 1.3.6.1.4.1.2356.11.1.77.9.10.1.1
lcsStatusIpv6FirewallOutboundSessionsEntrySrcAddress OBJECT-TYPE
    SYNTAX     OCTET STRING (SIZE(16..16))
    MAX-ACCESS read-only
    STATUS     current
    DESCRIPTION
            "-- empty --"
    ::= { lcsStatusIpv6FirewallOutboundSessionsEntry 1 }

-- {COLUMN} 1.3.6.1.4.1.2356.11.1.77.9.10.1.2
lcsStatusIpv6FirewallOutboundSessionsEntryDstAddress OBJECT-TYPE
    SYNTAX     OCTET STRING (SIZE(16..16))
    MAX-ACCESS read-only
    STATUS     current
    DESCRIPTION
            "-- empty --"
    ::= { lcsStatusIpv6FirewallOutboundSessionsEntry 2 }

-- {COLUMN} 1.3.6.1.4.1.2356.11.1.77.9.10.1.3
lcsStatusIpv6FirewallOutboundSessionsEntryProt OBJECT-TYPE
    SYNTAX     Unsigned32 (0..65535)
    MAX-ACCESS read-only
    STATUS     current
    DESCRIPTION
            "-- empty --"
    ::= { lcsStatusIpv6FirewallOutboundSessionsEntry 3 }

-- {COLUMN} 1.3.6.1.4.1.2356.11.1.77.9.10.1.4
lcsStatusIpv6FirewallOutboundSessionsEntrySrcPort OBJECT-TYPE
    SYNTAX     Unsigned32 (0..65535)
    MAX-ACCESS read-only
    STATUS     current
    DESCRIPTION
            "-- empty --"
    ::= { lcsStatusIpv6FirewallOutboundSessionsEntry 4 }

-- {COLUMN} 1.3.6.1.4.1.2356.11.1.77.9.10.1.5
lcsStatusIpv6FirewallOutboundSessionsEntryDstPort OBJECT-TYPE
    SYNTAX     Unsigned32 (0..65535)
    MAX-ACCESS read-only
    STATUS     current
    DESCRIPTION
            "-- empty --"
    ::= { lcsStatusIpv6FirewallOutboundSessionsEntry 5 }

-- {COLUMN} 1.3.6.1.4.1.2356.11.1.77.9.10.1.6
lcsStatusIpv6FirewallOutboundSessionsEntryDstInterface OBJECT-TYPE
    SYNTAX     OCTET STRING (SIZE(0..25))
    MAX-ACCESS read-only
    STATUS     current
    DESCRIPTION
            "-- empty --"
    ::= { lcsStatusIpv6FirewallOutboundSessionsEntry 6 }

-- {COLUMN} 1.3.6.1.4.1.2356.11.1.77.9.10.1.7
lcsStatusIpv6FirewallOutboundSessionsEntryTimeout OBJECT-TYPE
    SYNTAX     Unsigned32 (0..4294967295)
    MAX-ACCESS read-only
    STATUS     current
    DESCRIPTION
            "-- empty --"
    ::= { lcsStatusIpv6FirewallOutboundSessionsEntry 7 }

-- {COLUMN} 1.3.6.1.4.1.2356.11.1.77.9.10.1.9
lcsStatusIpv6FirewallOutboundSessionsEntryFilterRule OBJECT-TYPE
    SYNTAX     OCTET STRING (SIZE(0..32))
    MAX-ACCESS read-only
    STATUS     current
    DESCRIPTION
            "-- empty --"
    ::= { lcsStatusIpv6FirewallOutboundSessionsEntry 9 }

-- {NODE} 1.3.6.1.4.1.2356.11.1.77.10
lcsStatusIpv6Ndp OBJECT IDENTIFIER ::= { lcsStatusIpv6 10 }

-- {TABLE} 1.3.6.1.4.1.2356.11.1.77.10.1
lcsStatusIpv6NdpNdpTableTable OBJECT-TYPE
    SYNTAX     SEQUENCE OF LcsStatusIpv6NdpNdpTableEntry
    MAX-ACCESS not-accessible
    STATUS     current
    DESCRIPTION
            "-- empty --"
    ::= { lcsStatusIpv6Ndp 1 }

-- {ROW} 1.3.6.1.4.1.2356.11.1.77.10.1.1
lcsStatusIpv6NdpNdpTableEntry OBJECT-TYPE
    SYNTAX     LcsStatusIpv6NdpNdpTableEntry
    MAX-ACCESS not-accessible
    STATUS     current
    DESCRIPTION
            ""
    INDEX {
            lcsStatusIpv6NdpNdpTableEntryInterface,
            lcsStatusIpv6NdpNdpTableEntryIpAddress
          }
    ::= { lcsStatusIpv6NdpNdpTableTable 1 }

LcsStatusIpv6NdpNdpTableEntry ::= SEQUENCE {
            lcsStatusIpv6NdpNdpTableEntryInterface OCTET STRING,
            lcsStatusIpv6NdpNdpTableEntryIpAddress OCTET STRING,
            lcsStatusIpv6NdpNdpTableEntryMacAddress MacAddress,
            lcsStatusIpv6NdpNdpTableEntryEthernetPort INTEGER,
            lcsStatusIpv6NdpNdpTableEntryState INTEGER
    }

-- {COLUMN} 1.3.6.1.4.1.2356.11.1.77.10.1.1.1
lcsStatusIpv6NdpNdpTableEntryInterface OBJECT-TYPE
    SYNTAX     OCTET STRING (SIZE(0..26))
    MAX-ACCESS read-only
    STATUS     current
    DESCRIPTION
            "-- empty --"
    ::= { lcsStatusIpv6NdpNdpTableEntry 1 }

-- {COLUMN} 1.3.6.1.4.1.2356.11.1.77.10.1.1.2
lcsStatusIpv6NdpNdpTableEntryIpAddress OBJECT-TYPE
    SYNTAX     OCTET STRING (SIZE(16..16))
    MAX-ACCESS read-only
    STATUS     current
    DESCRIPTION
            "-- empty --"
    ::= { lcsStatusIpv6NdpNdpTableEntry 2 }

-- {COLUMN} 1.3.6.1.4.1.2356.11.1.77.10.1.1.3
lcsStatusIpv6NdpNdpTableEntryMacAddress OBJECT-TYPE
    SYNTAX     MacAddress
    MAX-ACCESS read-only
    STATUS     current
    DESCRIPTION
            "-- empty --"
    ::= { lcsStatusIpv6NdpNdpTableEntry 3 }

-- {COLUMN} 1.3.6.1.4.1.2356.11.1.77.10.1.1.4
lcsStatusIpv6NdpNdpTableEntryEthernetPort OBJECT-TYPE
    SYNTAX     INTEGER {
                  eUnknown (0),
                  eUplink (1),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            "-- empty --"
    ::= { lcsStatusIpv6NdpNdpTableEntry 4 }

-- {COLUMN} 1.3.6.1.4.1.2356.11.1.77.10.1.1.5
lcsStatusIpv6NdpNdpTableEntryState OBJECT-TYPE
    SYNTAX     INTEGER {
                  eIncomplete (0),
                  eReachable (1),
                  eStale (2),
                  eDelay (3),
                  eProbe (4),
                  eUnreachable (5),
                  eInit (6),
                  eStatic (7)
            }
    MAX-ACCESS read-only
    STATUS     current
    DESCRIPTION
            "-- empty --"
    ::= { lcsStatusIpv6NdpNdpTableEntry 5 }

-- {NODE} 1.3.6.1.4.1.2356.11.1.78
lcsStatusPmsInterface OBJECT IDENTIFIER ::= { lcsStatus 78 }

-- {SCALAR} 1.3.6.1.4.1.2356.11.1.78.1
lcsStatusPmsInterfaceConnection OBJECT-TYPE
    SYNTAX     INTEGER {
                  eConnected (0),
                  eClosed (1),
                  eFailed (2),
                  eOff (3),
                  eTryToConnect (4),
                  eInitialisation (5)
            }
    MAX-ACCESS read-only
    STATUS     current
    DESCRIPTION
            "-- empty --"
    ::= { lcsStatusPmsInterface 1 }

-- {TABLE} 1.3.6.1.4.1.2356.11.1.78.2
lcsStatusPmsInterfaceAccountingTable OBJECT-TYPE
    SYNTAX     SEQUENCE OF LcsStatusPmsInterfaceAccountingEntry
    MAX-ACCESS not-accessible
    STATUS     current
    DESCRIPTION
            "-- empty --"
    ::= { lcsStatusPmsInterface 2 }

-- {ROW} 1.3.6.1.4.1.2356.11.1.78.2.1
lcsStatusPmsInterfaceAccountingEntry OBJECT-TYPE
    SYNTAX     LcsStatusPmsInterfaceAccountingEntry
    MAX-ACCESS not-accessible
    STATUS     current
    DESCRIPTION
            ""
    INDEX {
            lcsStatusPmsInterfaceAccountingEntryReservationNumber,
            lcsStatusPmsInterfaceAccountingEntryUserName
          }
    ::= { lcsStatusPmsInterfaceAccountingTable 1 }

LcsStatusPmsInterfaceAccountingEntry ::= SEQUENCE {
            lcsStatusPmsInterfaceAccountingEntryReservationNumber DisplayString,
            lcsStatusPmsInterfaceAccountingEntryUserName DisplayString,
            lcsStatusPmsInterfaceAccountingEntryRoomNumber DisplayString,
            lcsStatusPmsInterfaceAccountingEntryMac DisplayString,
            lcsStatusPmsInterfaceAccountingEntryComment DisplayString,
            lcsStatusPmsInterfaceAccountingEntryTimeBudget Integer32,
            lcsStatusPmsInterfaceAccountingEntryVolumeBudget Integer32,
            lcsStatusPmsInterfaceAccountingEntryTotalVolume Integer32,
            lcsStatusPmsInterfaceAccountingEntryTotalTime Integer32,
            lcsStatusPmsInterfaceAccountingEntryActive Integer32,
            lcsStatusPmsInterfaceAccountingEntryLastUpdated Integer32,
            lcsStatusPmsInterfaceAccountingEntryInitialTotalVolume Integer32,
            lcsStatusPmsInterfaceAccountingEntryInitialTotalTime Integer32,
            lcsStatusPmsInterfaceAccountingEntryDelete Integer32,
            lcsStatusPmsInterfaceAccountingEntryTxBandwidth Integer32,
            lcsStatusPmsInterfaceAccountingEntryRxBandwidth Integer32,
            lcsStatusPmsInterfaceAccountingEntryInterfaceName DisplayString
    }

-- {COLUMN} 1.3.6.1.4.1.2356.11.1.78.2.1.1
lcsStatusPmsInterfaceAccountingEntryReservationNumber OBJECT-TYPE
    SYNTAX     DisplayString (SIZE(0..10))
    MAX-ACCESS read-only
    STATUS     current
    DESCRIPTION
            "-- empty --"
    ::= { lcsStatusPmsInterfaceAccountingEntry 1 }

-- {COLUMN} 1.3.6.1.4.1.2356.11.1.78.2.1.2
lcsStatusPmsInterfaceAccountingEntryUserName OBJECT-TYPE
    SYNTAX     DisplayString (SIZE(0..40))
    MAX-ACCESS read-only
    STATUS     current
    DESCRIPTION
            "-- empty --"
    ::= { lcsStatusPmsInterfaceAccountingEntry 2 }

-- {COLUMN} 1.3.6.1.4.1.2356.11.1.78.2.1.3
lcsStatusPmsInterfaceAccountingEntryRoomNumber OBJECT-TYPE
    SYNTAX     DisplayString (SIZE(0..8))
    MAX-ACCESS read-only
    STATUS     current
    DESCRIPTION
            "-- empty --"
    ::= { lcsStatusPmsInterfaceAccountingEntry 3 }

-- {COLUMN} 1.3.6.1.4.1.2356.11.1.78.2.1.4
lcsStatusPmsInterfaceAccountingEntryMac OBJECT-TYPE
    SYNTAX     DisplayString (SIZE(0..17))
    MAX-ACCESS read-only
    STATUS     current
    DESCRIPTION
            "-- empty --"
    ::= { lcsStatusPmsInterfaceAccountingEntry 4 }

-- {COLUMN} 1.3.6.1.4.1.2356.11.1.78.2.1.5
lcsStatusPmsInterfaceAccountingEntryComment OBJECT-TYPE
    SYNTAX     DisplayString (SIZE(0..254))
    MAX-ACCESS read-only
    STATUS     current
    DESCRIPTION
            "-- empty --"
    ::= { lcsStatusPmsInterfaceAccountingEntry 5 }

-- {COLUMN} 1.3.6.1.4.1.2356.11.1.78.2.1.6
lcsStatusPmsInterfaceAccountingEntryTimeBudget OBJECT-TYPE
    SYNTAX     Integer32 (0..2147483647)
    MAX-ACCESS read-only
    STATUS     current
    DESCRIPTION
            "-- empty --"
    ::= { lcsStatusPmsInterfaceAccountingEntry 6 }

-- {COLUMN} 1.3.6.1.4.1.2356.11.1.78.2.1.7
lcsStatusPmsInterfaceAccountingEntryVolumeBudget OBJECT-TYPE
    SYNTAX     Integer32 (0..2147483647)
    MAX-ACCESS read-only
    STATUS     current
    DESCRIPTION
            "-- empty --"
    ::= { lcsStatusPmsInterfaceAccountingEntry 7 }

-- {COLUMN} 1.3.6.1.4.1.2356.11.1.78.2.1.8
lcsStatusPmsInterfaceAccountingEntryTotalVolume OBJECT-TYPE
    SYNTAX     Integer32 (0..2147483647)
    MAX-ACCESS read-only
    STATUS     current
    DESCRIPTION
            "-- empty --"
    ::= { lcsStatusPmsInterfaceAccountingEntry 8 }

-- {COLUMN} 1.3.6.1.4.1.2356.11.1.78.2.1.9
lcsStatusPmsInterfaceAccountingEntryTotalTime OBJECT-TYPE
    SYNTAX     Integer32 (0..2147483647)
    MAX-ACCESS read-only
    STATUS     current
    DESCRIPTION
            "-- empty --"
    ::= { lcsStatusPmsInterfaceAccountingEntry 9 }

-- {COLUMN} 1.3.6.1.4.1.2356.11.1.78.2.1.10
lcsStatusPmsInterfaceAccountingEntryActive OBJECT-TYPE
    SYNTAX     Integer32 (0..255)
    MAX-ACCESS read-only
    STATUS     current
    DESCRIPTION
            "-- empty --"
    ::= { lcsStatusPmsInterfaceAccountingEntry 10 }

-- {COLUMN} 1.3.6.1.4.1.2356.11.1.78.2.1.11
lcsStatusPmsInterfaceAccountingEntryLastUpdated OBJECT-TYPE
    SYNTAX     Integer32 (0..2147483647)
    MAX-ACCESS read-only
    STATUS     current
    DESCRIPTION
            "-- empty --"
    ::= { lcsStatusPmsInterfaceAccountingEntry 11 }

-- {COLUMN} 1.3.6.1.4.1.2356.11.1.78.2.1.12
lcsStatusPmsInterfaceAccountingEntryInitialTotalVolume OBJECT-TYPE
    SYNTAX     Integer32 (0..2147483647)
    MAX-ACCESS read-only
    STATUS     current
    DESCRIPTION
            "-- empty --"
    ::= { lcsStatusPmsInterfaceAccountingEntry 12 }

-- {COLUMN} 1.3.6.1.4.1.2356.11.1.78.2.1.13
lcsStatusPmsInterfaceAccountingEntryInitialTotalTime OBJECT-TYPE
    SYNTAX     Integer32 (0..2147483647)
    MAX-ACCESS read-only
    STATUS     current
    DESCRIPTION
            "-- empty --"
    ::= { lcsStatusPmsInterfaceAccountingEntry 13 }

-- {COLUMN} 1.3.6.1.4.1.2356.11.1.78.2.1.14
lcsStatusPmsInterfaceAccountingEntryDelete OBJECT-TYPE
    SYNTAX     Integer32 (0..255)
    MAX-ACCESS read-only
    STATUS     current
    DESCRIPTION
            "-- empty --"
    ::= { lcsStatusPmsInterfaceAccountingEntry 14 }

-- {COLUMN} 1.3.6.1.4.1.2356.11.1.78.2.1.15
lcsStatusPmsInterfaceAccountingEntryTxBandwidth OBJECT-TYPE
    SYNTAX     Integer32 (0..2147483647)
    MAX-ACCESS read-only
    STATUS     current
    DESCRIPTION
            "-- empty --"
    ::= { lcsStatusPmsInterfaceAccountingEntry 15 }

-- {COLUMN} 1.3.6.1.4.1.2356.11.1.78.2.1.16
lcsStatusPmsInterfaceAccountingEntryRxBandwidth OBJECT-TYPE
    SYNTAX     Integer32 (0..2147483647)
    MAX-ACCESS read-only
    STATUS     current
    DESCRIPTION
            "-- empty --"
    ::= { lcsStatusPmsInterfaceAccountingEntry 16 }

-- {COLUMN} 1.3.6.1.4.1.2356.11.1.78.2.1.17
lcsStatusPmsInterfaceAccountingEntryInterfaceName OBJECT-TYPE
    SYNTAX     DisplayString (SIZE(0..18))
    MAX-ACCESS read-only
    STATUS     current
    DESCRIPTION
            "-- empty --"
    ::= { lcsStatusPmsInterfaceAccountingEntry 17 }

-- {NODE} 1.3.6.1.4.1.2356.11.1.79
lcsStatusSoftwareInfo OBJECT IDENTIFIER ::= { lcsStatus 79 }

-- {SCALAR} 1.3.6.1.4.1.2356.11.1.79.1
lcsStatusSoftwareInfoSwVersion OBJECT-TYPE
    SYNTAX     DisplayString (SIZE(0..39))
    MAX-ACCESS read-only
    STATUS     current
    DESCRIPTION
            "-- empty --"
    ::= { lcsStatusSoftwareInfo 1 }

-- {SCALAR} 1.3.6.1.4.1.2356.11.1.79.2
lcsStatusSoftwareInfoVpnLicenses OBJECT-TYPE
    SYNTAX     Integer32 (0..2147483647)
    MAX-ACCESS read-only
    STATUS     current
    DESCRIPTION
            "-- empty --"
    ::= { lcsStatusSoftwareInfo 2 }

-- {SCALAR} 1.3.6.1.4.1.2356.11.1.79.3
lcsStatusSoftwareInfoBandwidthLimit OBJECT-TYPE
    SYNTAX     DisplayString
    MAX-ACCESS read-only
    STATUS     current
    DESCRIPTION
            "-- empty --"
    ::= { lcsStatusSoftwareInfo 3 }

-- {SCALAR} 1.3.6.1.4.1.2356.11.1.79.4
lcsStatusSoftwareInfoArfLicenses OBJECT-TYPE
    SYNTAX     Integer32 (0..2147483647)
    MAX-ACCESS read-only
    STATUS     current
    DESCRIPTION
            "-- empty --"
    ::= { lcsStatusSoftwareInfo 4 }

-- {NODE} 1.3.6.1.4.1.2356.11.1.79.5
lcsStatusSoftwareInfoOptions OBJECT IDENTIFIER ::= { lcsStatusSoftwareInfo 5 }

-- {TABLE} 1.3.6.1.4.1.2356.11.1.79.5.1
lcsStatusSoftwareInfoOptionsLicensesTable OBJECT-TYPE
    SYNTAX     SEQUENCE OF LcsStatusSoftwareInfoOptionsLicensesEntry
    MAX-ACCESS not-accessible
    STATUS     current
    DESCRIPTION
            "-- empty --"
    ::= { lcsStatusSoftwareInfoOptions 1 }

-- {ROW} 1.3.6.1.4.1.2356.11.1.79.5.1.1
lcsStatusSoftwareInfoOptionsLicensesEntry OBJECT-TYPE
    SYNTAX     LcsStatusSoftwareInfoOptionsLicensesEntry
    MAX-ACCESS not-accessible
    STATUS     current
    DESCRIPTION
            ""
    INDEX {
            lcsStatusSoftwareInfoOptionsLicensesEntryOption,
            lcsStatusSoftwareInfoOptionsLicensesEntryIndex
          }
    ::= { lcsStatusSoftwareInfoOptionsLicensesTable 1 }

LcsStatusSoftwareInfoOptionsLicensesEntry ::= SEQUENCE {
            lcsStatusSoftwareInfoOptionsLicensesEntryOption INTEGER,
            lcsStatusSoftwareInfoOptionsLicensesEntryExpires DisplayString,
            lcsStatusSoftwareInfoOptionsLicensesEntryExpire Gauge32,
            lcsStatusSoftwareInfoOptionsLicensesEntryState INTEGER,
            lcsStatusSoftwareInfoOptionsLicensesEntryIndex Integer32,
            lcsStatusSoftwareInfoOptionsLicensesEntryCount Gauge32,
            lcsStatusSoftwareInfoOptionsLicensesEntryLicense-count DisplayString,
            lcsStatusSoftwareInfoOptionsLicensesEntryAttributes DisplayString
    }

-- {COLUMN} 1.3.6.1.4.1.2356.11.1.79.5.1.1.1
lcsStatusSoftwareInfoOptionsLicensesEntryOption OBJECT-TYPE
    SYNTAX     INTEGER {
                  eLanBridge (2),
                  eLancapi (3),
                  eLeasedLine (4),
                  eSwitchedLine (5),
                  eDslInterface (6),
                  eFax (7),
                  eModem (8),
                  eVpn5 (9),
                  eVpn25 (10),
                  eCommonCriteria (11),
                  eProductionOk (12),
                  eVpn100 (13),
                  eWlc4025100 (14),
                  eWlanPointToPoint (15),
                  ePublicSpot (16),
                  eVpn200 (17),
                  eVpn500 (18),
                  eVpn1000 (19),
                  eHermes1Wpa (20),
                  eVpn3 (21),
                  eMobileModem (22),
                  eDynamicVpn (23),
                  eWlan5ghz (24),
                  eWlanNoEncryption (25),
                  eAllIp (27),
                  eWlanFccRestrictions (28),
                  eWlc402550 (29),
                  eWlc400612 (30),
                  eContentfilterAdditive (36),
                  eWlcPublicSpot (37),
                  eWlanMonitorMode (38),
                  eWlanNo5ghz (39),
                  eWlcApUpgrade (40),
                  eWlanDfs3 (41),
                  eInProduction (42),
                  eNetioServer (43),
                  eLanWlanBridge (44),
                  eEthernetIp (45),
                  eProfinet (46),
                  eWlanFilteredAveraging (47),
                  eVpn50 (48),
                  eWlcApBasic (49),
                  ePms (50),
                  ePrp (53),
                  eAllIpAdditive (55),
                  eClustering (56),
                  eR8xxEnterpriseOption (57),
                  eArfContexts (58),
                  eVpn (59),
                  eBandwidth (60),
                  eSfpEedataFileAccess (62),
                  eVrouter (63),
                  eSystemtest (64)
            }
    MAX-ACCESS read-only
    STATUS     current
    DESCRIPTION
            "-- empty --"
    ::= { lcsStatusSoftwareInfoOptionsLicensesEntry 1 }

-- {COLUMN} 1.3.6.1.4.1.2356.11.1.79.5.1.1.2
lcsStatusSoftwareInfoOptionsLicensesEntryExpires OBJECT-TYPE
    SYNTAX     DisplayString (SIZE(0..255))
    MAX-ACCESS read-only
    STATUS     current
    DESCRIPTION
            "-- empty --"
    ::= { lcsStatusSoftwareInfoOptionsLicensesEntry 2 }

-- {COLUMN} 1.3.6.1.4.1.2356.11.1.79.5.1.1.3
lcsStatusSoftwareInfoOptionsLicensesEntryExpire OBJECT-TYPE
    SYNTAX     Gauge32
    MAX-ACCESS read-only
    STATUS     current
    DESCRIPTION
            "-- empty --"
    ::= { lcsStatusSoftwareInfoOptionsLicensesEntry 3 }

-- {COLUMN} 1.3.6.1.4.1.2356.11.1.79.5.1.1.4
lcsStatusSoftwareInfoOptionsLicensesEntryState OBJECT-TYPE
    SYNTAX     INTEGER {
                  eLocked (0),
                  eActive (1),
                  eHidden (2),
                  eExpired (3),
                  eUnused (4)
            }
    MAX-ACCESS read-only
    STATUS     current
    DESCRIPTION
            "-- empty --"
    ::= { lcsStatusSoftwareInfoOptionsLicensesEntry 4 }

-- {COLUMN} 1.3.6.1.4.1.2356.11.1.79.5.1.1.5
lcsStatusSoftwareInfoOptionsLicensesEntryIndex OBJECT-TYPE
    SYNTAX     Integer32 (0..2147483647)
    MAX-ACCESS read-only
    STATUS     current
    DESCRIPTION
            "-- empty --"
    ::= { lcsStatusSoftwareInfoOptionsLicensesEntry 5 }

-- {COLUMN} 1.3.6.1.4.1.2356.11.1.79.5.1.1.6
lcsStatusSoftwareInfoOptionsLicensesEntryCount OBJECT-TYPE
    SYNTAX     Gauge32
    MAX-ACCESS read-only
    STATUS     current
    DESCRIPTION
            ""
    ::= { lcsStatusSoftwareInfoOptionsLicensesEntry 6 }

-- {COLUMN} 1.3.6.1.4.1.2356.11.1.79.5.1.1.7
lcsStatusSoftwareInfoOptionsLicensesEntryLicense-count OBJECT-TYPE
    SYNTAX     DisplayString (SIZE(0..255))
    MAX-ACCESS read-only
    STATUS     current
    DESCRIPTION
            ""
    ::= { lcsStatusSoftwareInfoOptionsLicensesEntry 7 }

-- {COLUMN} 1.3.6.1.4.1.2356.11.1.79.5.1.1.8
lcsStatusSoftwareInfoOptionsLicensesEntryAttributes OBJECT-TYPE
    SYNTAX     DisplayString (SIZE(0..255))
    MAX-ACCESS read-only
    STATUS     current
    DESCRIPTION
            "-- empty --"
    ::= { lcsStatusSoftwareInfoOptionsLicensesEntry 8 }

-- {TABLE} 1.3.6.1.4.1.2356.11.1.79.5.2
lcsStatusSoftwareInfoOptionsLicenseFilesTable OBJECT-TYPE
    SYNTAX     SEQUENCE OF LcsStatusSoftwareInfoOptionsLicenseFilesEntry
    MAX-ACCESS not-accessible
    STATUS     current
    DESCRIPTION
            "-- empty --"
    ::= { lcsStatusSoftwareInfoOptions 2 }

-- {ROW} 1.3.6.1.4.1.2356.11.1.79.5.2.1
lcsStatusSoftwareInfoOptionsLicenseFilesEntry OBJECT-TYPE
    SYNTAX     LcsStatusSoftwareInfoOptionsLicenseFilesEntry
    MAX-ACCESS not-accessible
    STATUS     current
    DESCRIPTION
            ""
    INDEX {
            lcsStatusSoftwareInfoOptionsLicenseFilesEntryIndex
          }
    ::= { lcsStatusSoftwareInfoOptionsLicenseFilesTable 1 }

LcsStatusSoftwareInfoOptionsLicenseFilesEntry ::= SEQUENCE {
            lcsStatusSoftwareInfoOptionsLicenseFilesEntryIndex Integer32,
            lcsStatusSoftwareInfoOptionsLicenseFilesEntryTitle DisplayString,
            lcsStatusSoftwareInfoOptionsLicenseFilesEntryExpires DisplayString,
            lcsStatusSoftwareInfoOptionsLicenseFilesEntryNumExpires Gauge32
    }

-- {COLUMN} 1.3.6.1.4.1.2356.11.1.79.5.2.1.1
lcsStatusSoftwareInfoOptionsLicenseFilesEntryIndex OBJECT-TYPE
    SYNTAX     Integer32 (0..2147483647)
    MAX-ACCESS read-only
    STATUS     current
    DESCRIPTION
            "-- empty --"
    ::= { lcsStatusSoftwareInfoOptionsLicenseFilesEntry 1 }

-- {COLUMN} 1.3.6.1.4.1.2356.11.1.79.5.2.1.2
lcsStatusSoftwareInfoOptionsLicenseFilesEntryTitle OBJECT-TYPE
    SYNTAX     DisplayString (SIZE(0..1))
    MAX-ACCESS read-only
    STATUS     current
    DESCRIPTION
            "-- empty --"
    ::= { lcsStatusSoftwareInfoOptionsLicenseFilesEntry 2 }

-- {COLUMN} 1.3.6.1.4.1.2356.11.1.79.5.2.1.3
lcsStatusSoftwareInfoOptionsLicenseFilesEntryExpires OBJECT-TYPE
    SYNTAX     DisplayString (SIZE(0..1))
    MAX-ACCESS read-only
    STATUS     current
    DESCRIPTION
            "-- empty --"
    ::= { lcsStatusSoftwareInfoOptionsLicenseFilesEntry 3 }

-- {COLUMN} 1.3.6.1.4.1.2356.11.1.79.5.2.1.4
lcsStatusSoftwareInfoOptionsLicenseFilesEntryNumExpires OBJECT-TYPE
    SYNTAX     Gauge32
    MAX-ACCESS read-only
    STATUS     current
    DESCRIPTION
            "-- empty --"
    ::= { lcsStatusSoftwareInfoOptionsLicenseFilesEntry 4 }

-- {SCALAR} 1.3.6.1.4.1.2356.11.1.79.5.3
lcsStatusSoftwareInfoOptionsDeviceId OBJECT-TYPE
    SYNTAX     DisplayString (SIZE(0..3))
    MAX-ACCESS read-only
    STATUS     current
    DESCRIPTION
            "-- empty --"
    ::= { lcsStatusSoftwareInfoOptions 3 }

-- {SCALAR} 1.3.6.1.4.1.2356.11.1.79.6
lcsStatusSoftwareInfoPbspotLicenses OBJECT-TYPE
    SYNTAX     DisplayString
    MAX-ACCESS read-only
    STATUS     current
    DESCRIPTION
            "-- empty --"
    ::= { lcsStatusSoftwareInfo 6 }

-- {SCALAR} 1.3.6.1.4.1.2356.11.1.79.7
lcsStatusSoftwareInfoIkev2EapLicense OBJECT-TYPE
    SYNTAX     INTEGER {
                  eRequires25VpnLicenses (0),
                  eAvailable (1)
            }
    MAX-ACCESS read-only
    STATUS     current
    DESCRIPTION
            "-- empty --"
    ::= { lcsStatusSoftwareInfo 7 }

-- {NODE} 1.3.6.1.4.1.2356.11.1.81
lcsStatusDsLite OBJECT IDENTIFIER ::= { lcsStatus 81 }

-- {SCALAR} 1.3.6.1.4.1.2356.11.1.81.1
lcsStatusDsLiteRxPackets OBJECT-TYPE
    SYNTAX     Integer32 (0..2147483647)
    MAX-ACCESS read-only
    STATUS     current
    DESCRIPTION
            "-- empty --"
    ::= { lcsStatusDsLite 1 }

-- {SCALAR} 1.3.6.1.4.1.2356.11.1.81.2
lcsStatusDsLiteTxPackets OBJECT-TYPE
    SYNTAX     Integer32 (0..2147483647)
    MAX-ACCESS read-only
    STATUS     current
    DESCRIPTION
            "-- empty --"
    ::= { lcsStatusDsLite 2 }

-- {SCALAR} 1.3.6.1.4.1.2356.11.1.81.3
lcsStatusDsLiteQueueErrors OBJECT-TYPE
    SYNTAX     Integer32 (0..2147483647)
    MAX-ACCESS read-only
    STATUS     current
    DESCRIPTION
            "-- empty --"
    ::= { lcsStatusDsLite 3 }

-- {TABLE} 1.3.6.1.4.1.2356.11.1.81.4
lcsStatusDsLiteConnectionsTable OBJECT-TYPE
    SYNTAX     SEQUENCE OF LcsStatusDsLiteConnectionsEntry
    MAX-ACCESS not-accessible
    STATUS     current
    DESCRIPTION
            "-- empty --"
    ::= { lcsStatusDsLite 4 }

-- {ROW} 1.3.6.1.4.1.2356.11.1.81.4.1
lcsStatusDsLiteConnectionsEntry OBJECT-TYPE
    SYNTAX     LcsStatusDsLiteConnectionsEntry
    MAX-ACCESS not-accessible
    STATUS     current
    DESCRIPTION
            ""
    INDEX {
            lcsStatusDsLiteConnectionsEntryPeer
          }
    ::= { lcsStatusDsLiteConnectionsTable 1 }

LcsStatusDsLiteConnectionsEntry ::= SEQUENCE {
            lcsStatusDsLiteConnectionsEntryPeer DisplayString,
            lcsStatusDsLiteConnectionsEntryState INTEGER,
            lcsStatusDsLiteConnectionsEntryLastError INTEGER,
            lcsStatusDsLiteConnectionsEntryIpv4Address IpAddress,
            lcsStatusDsLiteConnectionsEntryPhysConn DisplayString,
            lcsStatusDsLiteConnectionsEntryAftrName DisplayString,
            lcsStatusDsLiteConnectionsEntryAftrIpv6Address DisplayString,
            lcsStatusDsLiteConnectionsEntryConnTime Gauge32
    }

-- {COLUMN} 1.3.6.1.4.1.2356.11.1.81.4.1.1
lcsStatusDsLiteConnectionsEntryPeer OBJECT-TYPE
    SYNTAX     DisplayString (SIZE(0..16))
    MAX-ACCESS read-only
    STATUS     current
    DESCRIPTION
            "-- empty --"
    ::= { lcsStatusDsLiteConnectionsEntry 1 }

-- {COLUMN} 1.3.6.1.4.1.2356.11.1.81.4.1.2
lcsStatusDsLiteConnectionsEntryState OBJECT-TYPE
    SYNTAX     INTEGER {
                  eInit (0),
                  eSetupWan (1),
                  eReady (2),
                  eWaitForCb (3),
                  eDial (4),
                  eIncomingCall (5),
                  eProtocol (6),
                  eConnection (7),
                  eDisconnecting (8),
                  eCallBack (9),
                  eBundleConnect (10),
                  eProtocol2 (11),
                  eReserved (12),
                  eBundle (13)
            }
    MAX-ACCESS read-only
    STATUS     current
    DESCRIPTION
            "-- empty --"
    ::= { lcsStatusDsLiteConnectionsEntry 2 }

-- {COLUMN} 1.3.6.1.4.1.2356.11.1.81.4.1.3
lcsStatusDsLiteConnectionsEntryLastError OBJECT-TYPE
    SYNTAX     INTEGER {
                  eNone (0),
                  eIcmpConnError (275),
                  eDnsResolutionFailed (20481),
                  eNoRouteToGateway (20482),
                  eNoGatewayByDhcp (20483),
                  eInvalidGatewayAddress (20484),
                  eMultipleGatewayUsage (20485),
                  eNoIpv6Address (20486)
            }
    MAX-ACCESS read-write
    STATUS     current
    DESCRIPTION
            "-- empty --"
    ::= { lcsStatusDsLiteConnectionsEntry 3 }

-- {COLUMN} 1.3.6.1.4.1.2356.11.1.81.4.1.4
lcsStatusDsLiteConnectionsEntryIpv4Address OBJECT-TYPE
    SYNTAX     IpAddress
    MAX-ACCESS read-only
    STATUS     current
    DESCRIPTION
            "-- empty --"
    ::= { lcsStatusDsLiteConnectionsEntry 4 }

-- {COLUMN} 1.3.6.1.4.1.2356.11.1.81.4.1.5
lcsStatusDsLiteConnectionsEntryPhysConn OBJECT-TYPE
    SYNTAX     DisplayString (SIZE(0..16))
    MAX-ACCESS read-only
    STATUS     current
    DESCRIPTION
            "-- empty --"
    ::= { lcsStatusDsLiteConnectionsEntry 5 }

-- {COLUMN} 1.3.6.1.4.1.2356.11.1.81.4.1.6
lcsStatusDsLiteConnectionsEntryAftrName OBJECT-TYPE
    SYNTAX     DisplayString (SIZE(0..64))
    MAX-ACCESS read-only
    STATUS     current
    DESCRIPTION
            "-- empty --"
    ::= { lcsStatusDsLiteConnectionsEntry 6 }

-- {COLUMN} 1.3.6.1.4.1.2356.11.1.81.4.1.7
lcsStatusDsLiteConnectionsEntryAftrIpv6Address OBJECT-TYPE
    SYNTAX     DisplayString (SIZE(0..255))
    MAX-ACCESS read-only
    STATUS     current
    DESCRIPTION
            "-- empty --"
    ::= { lcsStatusDsLiteConnectionsEntry 7 }

-- {COLUMN} 1.3.6.1.4.1.2356.11.1.81.4.1.8
lcsStatusDsLiteConnectionsEntryConnTime OBJECT-TYPE
    SYNTAX     Gauge32
    MAX-ACCESS read-only
    STATUS     current
    DESCRIPTION
            "-- empty --"
    ::= { lcsStatusDsLiteConnectionsEntry 8 }

-- {SCALAR} 1.3.6.1.4.1.2356.11.1.81.5
lcsStatusDsLiteTunnel OBJECT-TYPE
    SYNTAX     Integer32 (0..2147483647)
    MAX-ACCESS read-only
    STATUS     current
    DESCRIPTION
            "-- empty --"
    ::= { lcsStatusDsLite 5 }

-- {SCALAR} 1.3.6.1.4.1.2356.11.1.81.6
lcsStatusDsLiteDeleteValues OBJECT-TYPE
    SYNTAX     DisplayString
    MAX-ACCESS read-write
    STATUS     current
    DESCRIPTION
            "-- empty --"
    ::= { lcsStatusDsLite 6 }

-- {NODE} 1.3.6.1.4.1.2356.11.1.82
lcsStatusCrypto OBJECT IDENTIFIER ::= { lcsStatus 82 }

-- {NODE} 1.3.6.1.4.1.2356.11.1.82.1
lcsStatusCryptoRng OBJECT IDENTIFIER ::= { lcsStatusCrypto 1 }

-- {SCALAR} 1.3.6.1.4.1.2356.11.1.82.1.1
lcsStatusCryptoRngState OBJECT-TYPE
    SYNTAX     INTEGER {
                  eNone (0),
                  eNotSeeded (1),
                  ePreSeeded (2),
                  eSeeded (3),
                  eNeedsReseed (4),
                  eError (5)
            }
    MAX-ACCESS read-only
    STATUS     current
    DESCRIPTION
            "-- empty --"
    ::= { lcsStatusCryptoRng 1 }

-- {SCALAR} 1.3.6.1.4.1.2356.11.1.82.1.2
lcsStatusCryptoRngCounter OBJECT-TYPE
    SYNTAX     Integer32 (0..2147483647)
    MAX-ACCESS read-only
    STATUS     current
    DESCRIPTION
            "-- empty --"
    ::= { lcsStatusCryptoRng 2 }

-- {SCALAR} 1.3.6.1.4.1.2356.11.1.82.1.3
lcsStatusCryptoRngPercent OBJECT-TYPE
    SYNTAX     Integer32 (0..65535)
    MAX-ACCESS read-only
    STATUS     current
    DESCRIPTION
            "-- empty --"
    ::= { lcsStatusCryptoRng 3 }

-- {SCALAR} 1.3.6.1.4.1.2356.11.1.82.1.4
lcsStatusCryptoRngWriteInterval OBJECT-TYPE
    SYNTAX     Integer32 (0..2147483647)
    MAX-ACCESS read-only
    STATUS     current
    DESCRIPTION
            "-- empty --"
    ::= { lcsStatusCryptoRng 4 }

-- {NODE} 1.3.6.1.4.1.2356.11.1.83
lcsStatusSms OBJECT IDENTIFIER ::= { lcsStatus 83 }

-- {TABLE} 1.3.6.1.4.1.2356.11.1.83.1
lcsStatusSmsInboxTable OBJECT-TYPE
    SYNTAX     SEQUENCE OF LcsStatusSmsInboxEntry
    MAX-ACCESS not-accessible
    STATUS     current
    DESCRIPTION
            "-- empty --"
    ::= { lcsStatusSms 1 }

-- {ROW} 1.3.6.1.4.1.2356.11.1.83.1.1
lcsStatusSmsInboxEntry OBJECT-TYPE
    SYNTAX     LcsStatusSmsInboxEntry
    MAX-ACCESS not-accessible
    STATUS     current
    DESCRIPTION
            ""
    INDEX {
            lcsStatusSmsInboxEntryIdx,
            lcsStatusSmsInboxEntryMsgref,
            lcsStatusSmsInboxEntryPartnr
          }
    ::= { lcsStatusSmsInboxTable 1 }

LcsStatusSmsInboxEntry ::= SEQUENCE {
            lcsStatusSmsInboxEntryIdx Integer32,
            lcsStatusSmsInboxEntryMsgref Integer32,
            lcsStatusSmsInboxEntryPartnr Integer32,
            lcsStatusSmsInboxEntrySender DisplayString,
            lcsStatusSmsInboxEntryStatus INTEGER,
            lcsStatusSmsInboxEntryTimestamp Gauge32,
            lcsStatusSmsInboxEntryContent DisplayString,
            lcsStatusSmsInboxEntryRowstatus INTEGER
    }

-- {COLUMN} 1.3.6.1.4.1.2356.11.1.83.1.1.1
lcsStatusSmsInboxEntryIdx OBJECT-TYPE
    SYNTAX     Integer32 (0..2147483647)
    MAX-ACCESS read-only
    STATUS     current
    DESCRIPTION
            "-- empty --"
    ::= { lcsStatusSmsInboxEntry 1 }

-- {COLUMN} 1.3.6.1.4.1.2356.11.1.83.1.1.2
lcsStatusSmsInboxEntryMsgref OBJECT-TYPE
    SYNTAX     Integer32 (0..2147483647)
    MAX-ACCESS read-only
    STATUS     current
    DESCRIPTION
            "-- empty --"
    ::= { lcsStatusSmsInboxEntry 2 }

-- {COLUMN} 1.3.6.1.4.1.2356.11.1.83.1.1.3
lcsStatusSmsInboxEntryPartnr OBJECT-TYPE
    SYNTAX     Integer32 (0..2147483647)
    MAX-ACCESS read-only
    STATUS     current
    DESCRIPTION
            "-- empty --"
    ::= { lcsStatusSmsInboxEntry 3 }

-- {COLUMN} 1.3.6.1.4.1.2356.11.1.83.1.1.4
lcsStatusSmsInboxEntrySender OBJECT-TYPE
    SYNTAX     DisplayString (SIZE(0..255))
    MAX-ACCESS read-only
    STATUS     current
    DESCRIPTION
            "-- empty --"
    ::= { lcsStatusSmsInboxEntry 4 }

-- {COLUMN} 1.3.6.1.4.1.2356.11.1.83.1.1.5
lcsStatusSmsInboxEntryStatus OBJECT-TYPE
    SYNTAX     INTEGER {
                  eNew (7),
                  eRead (8)
            }
    MAX-ACCESS read-write
    STATUS     current
    DESCRIPTION
            "-- empty --"
    ::= { lcsStatusSmsInboxEntry 5 }

-- {COLUMN} 1.3.6.1.4.1.2356.11.1.83.1.1.6
lcsStatusSmsInboxEntryTimestamp OBJECT-TYPE
    SYNTAX     Gauge32
    MAX-ACCESS read-only
    STATUS     current
    DESCRIPTION
            "-- empty --"
    ::= { lcsStatusSmsInboxEntry 6 }

-- {COLUMN} 1.3.6.1.4.1.2356.11.1.83.1.1.7
lcsStatusSmsInboxEntryContent OBJECT-TYPE
    SYNTAX     DisplayString (SIZE(0..255))
    MAX-ACCESS read-only
    STATUS     current
    DESCRIPTION
            "-- empty --"
    ::= { lcsStatusSmsInboxEntry 7 }

-- {COLUMN} 1.3.6.1.4.1.2356.11.1.83.1.1.8
lcsStatusSmsInboxEntryRowstatus OBJECT-TYPE
    SYNTAX     INTEGER {
                  eActive (1),
                  eNotinservice (2),
                  eNotready (3),
                  eCreateandgo (4),
                  eCreateandwait (5),
                  eDestroy (6)
            }
    MAX-ACCESS read-write
    STATUS     current
    DESCRIPTION
            "-- empty --"
    ::= { lcsStatusSmsInboxEntry 8 }

-- {TABLE} 1.3.6.1.4.1.2356.11.1.83.2
lcsStatusSmsOutboxTable OBJECT-TYPE
    SYNTAX     SEQUENCE OF LcsStatusSmsOutboxEntry
    MAX-ACCESS not-accessible
    STATUS     current
    DESCRIPTION
            "-- empty --"
    ::= { lcsStatusSms 2 }

-- {ROW} 1.3.6.1.4.1.2356.11.1.83.2.1
lcsStatusSmsOutboxEntry OBJECT-TYPE
    SYNTAX     LcsStatusSmsOutboxEntry
    MAX-ACCESS not-accessible
    STATUS     current
    DESCRIPTION
            ""
    INDEX {
            lcsStatusSmsOutboxEntryIdx,
            lcsStatusSmsOutboxEntryMsgref,
            lcsStatusSmsOutboxEntryPartnr
          }
    ::= { lcsStatusSmsOutboxTable 1 }

LcsStatusSmsOutboxEntry ::= SEQUENCE {
            lcsStatusSmsOutboxEntryIdx Integer32,
            lcsStatusSmsOutboxEntryMsgref Integer32,
            lcsStatusSmsOutboxEntryPartnr Integer32,
            lcsStatusSmsOutboxEntryDestination DisplayString,
            lcsStatusSmsOutboxEntryStatus INTEGER,
            lcsStatusSmsOutboxEntryTimestamp Gauge32,
            lcsStatusSmsOutboxEntryContent DisplayString,
            lcsStatusSmsOutboxEntryRowstatus INTEGER,
            lcsStatusSmsOutboxEntrySendAttempts Integer32
    }

-- {COLUMN} 1.3.6.1.4.1.2356.11.1.83.2.1.1
lcsStatusSmsOutboxEntryIdx OBJECT-TYPE
    SYNTAX     Integer32 (0..2147483647)
    MAX-ACCESS read-write
    STATUS     current
    DESCRIPTION
            "-- empty --"
    ::= { lcsStatusSmsOutboxEntry 1 }

-- {COLUMN} 1.3.6.1.4.1.2356.11.1.83.2.1.2
lcsStatusSmsOutboxEntryMsgref OBJECT-TYPE
    SYNTAX     Integer32 (0..2147483647)
    MAX-ACCESS read-write
    STATUS     current
    DESCRIPTION
            "-- empty --"
    ::= { lcsStatusSmsOutboxEntry 2 }

-- {COLUMN} 1.3.6.1.4.1.2356.11.1.83.2.1.3
lcsStatusSmsOutboxEntryPartnr OBJECT-TYPE
    SYNTAX     Integer32 (0..2147483647)
    MAX-ACCESS read-write
    STATUS     current
    DESCRIPTION
            "-- empty --"
    ::= { lcsStatusSmsOutboxEntry 3 }

-- {COLUMN} 1.3.6.1.4.1.2356.11.1.83.2.1.4
lcsStatusSmsOutboxEntryDestination OBJECT-TYPE
    SYNTAX     DisplayString (SIZE(0..255))
    MAX-ACCESS read-write
    STATUS     current
    DESCRIPTION
            "-- empty --"
    ::= { lcsStatusSmsOutboxEntry 4 }

-- {COLUMN} 1.3.6.1.4.1.2356.11.1.83.2.1.5
lcsStatusSmsOutboxEntryStatus OBJECT-TYPE
    SYNTAX     INTEGER {
                  eUnsent (0),
                  ePending (1),
                  eDelivered (2),
                  eUnconfirmed (3),
                  eFailedtrying (4),
                  eFailedpermanent (5),
                  eFailedtemporary (6),
                  eSent (9),
                  eFailedpermanentlocal (10),
                  eFailedtemporarylocal (11)
            }
    MAX-ACCESS read-only
    STATUS     current
    DESCRIPTION
            "-- empty --"
    ::= { lcsStatusSmsOutboxEntry 5 }

-- {COLUMN} 1.3.6.1.4.1.2356.11.1.83.2.1.6
lcsStatusSmsOutboxEntryTimestamp OBJECT-TYPE
    SYNTAX     Gauge32
    MAX-ACCESS read-only
    STATUS     current
    DESCRIPTION
            "-- empty --"
    ::= { lcsStatusSmsOutboxEntry 6 }

-- {COLUMN} 1.3.6.1.4.1.2356.11.1.83.2.1.7
lcsStatusSmsOutboxEntryContent OBJECT-TYPE
    SYNTAX     DisplayString (SIZE(0..255))
    MAX-ACCESS read-write
    STATUS     current
    DESCRIPTION
            "-- empty --"
    ::= { lcsStatusSmsOutboxEntry 7 }

-- {COLUMN} 1.3.6.1.4.1.2356.11.1.83.2.1.8
lcsStatusSmsOutboxEntryRowstatus OBJECT-TYPE
    SYNTAX     INTEGER {
                  eActive (1),
                  eNotinservice (2),
                  eNotready (3),
                  eCreateandgo (4),
                  eCreateandwait (5),
                  eDestroy (6)
            }
    MAX-ACCESS read-write
    STATUS     current
    DESCRIPTION
            "-- empty --"
    ::= { lcsStatusSmsOutboxEntry 8 }

-- {COLUMN} 1.3.6.1.4.1.2356.11.1.83.2.1.9
lcsStatusSmsOutboxEntrySendAttempts OBJECT-TYPE
    SYNTAX     Integer32 (0..2147483647)
    MAX-ACCESS read-only
    STATUS     current
    DESCRIPTION
            "-- empty --"
    ::= { lcsStatusSmsOutboxEntry 9 }

-- {SCALAR} 1.3.6.1.4.1.2356.11.1.83.3
lcsStatusSmsInboxMessages OBJECT-TYPE
    SYNTAX     Integer32 (0..2147483647)
    MAX-ACCESS read-only
    STATUS     current
    DESCRIPTION
            "-- empty --"
    ::= { lcsStatusSms 3 }

-- {SCALAR} 1.3.6.1.4.1.2356.11.1.83.4
lcsStatusSmsUnreadMessages OBJECT-TYPE
    SYNTAX     Integer32 (0..2147483647)
    MAX-ACCESS read-only
    STATUS     current
    DESCRIPTION
            "-- empty --"
    ::= { lcsStatusSms 4 }

-- {SCALAR} 1.3.6.1.4.1.2356.11.1.83.5
lcsStatusSmsOutboxMessages OBJECT-TYPE
    SYNTAX     Integer32 (0..2147483647)
    MAX-ACCESS read-only
    STATUS     current
    DESCRIPTION
            "-- empty --"
    ::= { lcsStatusSms 5 }

-- {SCALAR} 1.3.6.1.4.1.2356.11.1.83.6
lcsStatusSmsSmscAddress OBJECT-TYPE
    SYNTAX     DisplayString (SIZE(0..31))
    MAX-ACCESS read-only
    STATUS     current
    DESCRIPTION
            "-- empty --"
    ::= { lcsStatusSms 6 }

-- {SCALAR} 1.3.6.1.4.1.2356.11.1.83.7
lcsStatusSmsClearInbox OBJECT-TYPE
    SYNTAX     DisplayString
    MAX-ACCESS read-write
    STATUS     current
    DESCRIPTION
            "-- empty --"
    ::= { lcsStatusSms 7 }

-- {SCALAR} 1.3.6.1.4.1.2356.11.1.83.8
lcsStatusSmsClearOutbox OBJECT-TYPE
    SYNTAX     DisplayString
    MAX-ACCESS read-write
    STATUS     current
    DESCRIPTION
            "-- empty --"
    ::= { lcsStatusSms 8 }

-- {SCALAR} 1.3.6.1.4.1.2356.11.1.83.9
lcsStatusSmsMarkReadInbox OBJECT-TYPE
    SYNTAX     DisplayString
    MAX-ACCESS read-write
    STATUS     current
    DESCRIPTION
            "-- empty --"
    ::= { lcsStatusSms 9 }

-- {SCALAR} 1.3.6.1.4.1.2356.11.1.83.10
lcsStatusSmsLimitRemaining OBJECT-TYPE
    SYNTAX     Integer32 (0..2147483647)
    MAX-ACCESS read-only
    STATUS     current
    DESCRIPTION
            "-- empty --"
    ::= { lcsStatusSms 10 }

-- {SCALAR} 1.3.6.1.4.1.2356.11.1.83.11
lcsStatusSmsLimitReset OBJECT-TYPE
    SYNTAX     DisplayString
    MAX-ACCESS read-write
    STATUS     current
    DESCRIPTION
            "-- empty --"
    ::= { lcsStatusSms 11 }

-- {NODE} 1.3.6.1.4.1.2356.11.1.84
lcsStatusL2tp OBJECT IDENTIFIER ::= { lcsStatus 84 }

-- {SCALAR} 1.3.6.1.4.1.2356.11.1.84.1
lcsStatusL2tpRxPackets OBJECT-TYPE
    SYNTAX     Integer32 (0..2147483647)
    MAX-ACCESS read-only
    STATUS     current
    DESCRIPTION
            "-- empty --"
    ::= { lcsStatusL2tp 1 }

-- {SCALAR} 1.3.6.1.4.1.2356.11.1.84.2
lcsStatusL2tpTxPackets OBJECT-TYPE
    SYNTAX     Integer32 (0..2147483647)
    MAX-ACCESS read-only
    STATUS     current
    DESCRIPTION
            "-- empty --"
    ::= { lcsStatusL2tp 2 }

-- {SCALAR} 1.3.6.1.4.1.2356.11.1.84.3
lcsStatusL2tpTxRetries OBJECT-TYPE
    SYNTAX     Integer32 (0..2147483647)
    MAX-ACCESS read-only
    STATUS     current
    DESCRIPTION
            "-- empty --"
    ::= { lcsStatusL2tp 3 }

-- {SCALAR} 1.3.6.1.4.1.2356.11.1.84.4
lcsStatusL2tpCallErrors OBJECT-TYPE
    SYNTAX     Integer32 (0..2147483647)
    MAX-ACCESS read-only
    STATUS     current
    DESCRIPTION
            "-- empty --"
    ::= { lcsStatusL2tp 4 }

-- {TABLE} 1.3.6.1.4.1.2356.11.1.84.5
lcsStatusL2tpEndpointsTable OBJECT-TYPE
    SYNTAX     SEQUENCE OF LcsStatusL2tpEndpointsEntry
    MAX-ACCESS not-accessible
    STATUS     current
    DESCRIPTION
            "-- empty --"
    ::= { lcsStatusL2tp 5 }

-- {ROW} 1.3.6.1.4.1.2356.11.1.84.5.1
lcsStatusL2tpEndpointsEntry OBJECT-TYPE
    SYNTAX     LcsStatusL2tpEndpointsEntry
    MAX-ACCESS not-accessible
    STATUS     current
    DESCRIPTION
            ""
    INDEX {
            lcsStatusL2tpEndpointsEntryL2tpEndpoint
          }
    ::= { lcsStatusL2tpEndpointsTable 1 }

LcsStatusL2tpEndpointsEntry ::= SEQUENCE {
            lcsStatusL2tpEndpointsEntryL2tpEndpoint DisplayString,
            lcsStatusL2tpEndpointsEntryState INTEGER,
            lcsStatusL2tpEndpointsEntryLastError INTEGER,
            lcsStatusL2tpEndpointsEntryMode INTEGER,
            lcsStatusL2tpEndpointsEntryPhysConnection DisplayString,
            lcsStatusL2tpEndpointsEntryGateway DisplayString,
            lcsStatusL2tpEndpointsEntrySessions Integer32,
            lcsStatusL2tpEndpointsEntryConnTime Gauge32,
            lcsStatusL2tpEndpointsEntryEmbeddedErrorMessage DisplayString
    }

-- {COLUMN} 1.3.6.1.4.1.2356.11.1.84.5.1.1
lcsStatusL2tpEndpointsEntryL2tpEndpoint OBJECT-TYPE
    SYNTAX     DisplayString (SIZE(0..16))
    MAX-ACCESS read-only
    STATUS     current
    DESCRIPTION
            "-- empty --"
    ::= { lcsStatusL2tpEndpointsEntry 1 }

-- {COLUMN} 1.3.6.1.4.1.2356.11.1.84.5.1.2
lcsStatusL2tpEndpointsEntryState OBJECT-TYPE
    SYNTAX     INTEGER {
                  eInvalid (-1),
                  eDestroying (0),
                  eIdle (1),
                  eWaitCtlReply (2),
                  eWaitCtlConn (3),
                  eWaitEstablish (4),
                  eEstablished (5),
                  eAuthenticating (6)
            }
    MAX-ACCESS read-only
    STATUS     current
    DESCRIPTION
            "-- empty --"
    ::= { lcsStatusL2tpEndpointsEntry 2 }

-- {COLUMN} 1.3.6.1.4.1.2356.11.1.84.5.1.3
lcsStatusL2tpEndpointsEntryLastError OBJECT-TYPE
    SYNTAX     INTEGER {
                  eNone (0),
                  eDnsResolutionFailed (1),
                  eNoRouteToGateway (2),
                  eInvalidGatewayAddress (3),
                  eNoResponse (4),
                  eMessageTimeout (5),
                  eNoTransportAvailable (6),
                  eTunnelAlreadyExists (19),
                  eAuthorizationFailed (20),
                  eBadProtocolVersion (21),
                  eShuttingDown (22),
                  eStateMachineError (23),
                  eNoTunnelExists (33),
                  eInvalidLength (34),
                  eInvalidValue (35),
                  eNoRessources (36),
                  eInvalidSessionId (37),
                  eVendorSpecificError (38),
                  eTryAnother (39),
                  eUnknownMandatoryAttribute (40),
                  eUnknown (255)
            }
    MAX-ACCESS read-write
    STATUS     current
    DESCRIPTION
            "-- empty --"
    ::= { lcsStatusL2tpEndpointsEntry 3 }

-- {COLUMN} 1.3.6.1.4.1.2356.11.1.84.5.1.4
lcsStatusL2tpEndpointsEntryMode OBJECT-TYPE
    SYNTAX     INTEGER {
                  eLac (0),
                  eLns (1)
            }
    MAX-ACCESS read-only
    STATUS     current
    DESCRIPTION
            "-- empty --"
    ::= { lcsStatusL2tpEndpointsEntry 4 }

-- {COLUMN} 1.3.6.1.4.1.2356.11.1.84.5.1.5
lcsStatusL2tpEndpointsEntryPhysConnection OBJECT-TYPE
    SYNTAX     DisplayString (SIZE(0..16))
    MAX-ACCESS read-only
    STATUS     current
    DESCRIPTION
            "-- empty --"
    ::= { lcsStatusL2tpEndpointsEntry 5 }

-- {COLUMN} 1.3.6.1.4.1.2356.11.1.84.5.1.6
lcsStatusL2tpEndpointsEntryGateway OBJECT-TYPE
    SYNTAX     DisplayString (SIZE(0..39))
    MAX-ACCESS read-only
    STATUS     current
    DESCRIPTION
            "-- empty --"
    ::= { lcsStatusL2tpEndpointsEntry 6 }

-- {COLUMN} 1.3.6.1.4.1.2356.11.1.84.5.1.7
lcsStatusL2tpEndpointsEntrySessions OBJECT-TYPE
    SYNTAX     Integer32 (0..65535)
    MAX-ACCESS read-only
    STATUS     current
    DESCRIPTION
            "-- empty --"
    ::= { lcsStatusL2tpEndpointsEntry 7 }

-- {COLUMN} 1.3.6.1.4.1.2356.11.1.84.5.1.8
lcsStatusL2tpEndpointsEntryConnTime OBJECT-TYPE
    SYNTAX     Gauge32
    MAX-ACCESS read-only
    STATUS     current
    DESCRIPTION
            "-- empty --"
    ::= { lcsStatusL2tpEndpointsEntry 8 }

-- {COLUMN} 1.3.6.1.4.1.2356.11.1.84.5.1.9
lcsStatusL2tpEndpointsEntryEmbeddedErrorMessage OBJECT-TYPE
    SYNTAX     DisplayString (SIZE(0..32))
    MAX-ACCESS read-only
    STATUS     current
    DESCRIPTION
            "-- empty --"
    ::= { lcsStatusL2tpEndpointsEntry 9 }

-- {SCALAR} 1.3.6.1.4.1.2356.11.1.84.6
lcsStatusL2tpNumEndpoints OBJECT-TYPE
    SYNTAX     Integer32 (0..2147483647)
    MAX-ACCESS read-only
    STATUS     current
    DESCRIPTION
            "-- empty --"
    ::= { lcsStatusL2tp 6 }

-- {TABLE} 1.3.6.1.4.1.2356.11.1.84.7
lcsStatusL2tpConnectionsTable OBJECT-TYPE
    SYNTAX     SEQUENCE OF LcsStatusL2tpConnectionsEntry
    MAX-ACCESS not-accessible
    STATUS     current
    DESCRIPTION
            "-- empty --"
    ::= { lcsStatusL2tp 7 }

-- {ROW} 1.3.6.1.4.1.2356.11.1.84.7.1
lcsStatusL2tpConnectionsEntry OBJECT-TYPE
    SYNTAX     LcsStatusL2tpConnectionsEntry
    MAX-ACCESS not-accessible
    STATUS     current
    DESCRIPTION
            ""
    INDEX {
            lcsStatusL2tpConnectionsEntryPeer
          }
    ::= { lcsStatusL2tpConnectionsTable 1 }

LcsStatusL2tpConnectionsEntry ::= SEQUENCE {
            lcsStatusL2tpConnectionsEntryPeer DisplayString,
            lcsStatusL2tpConnectionsEntryState INTEGER,
            lcsStatusL2tpConnectionsEntryLastError INTEGER,
            lcsStatusL2tpConnectionsEntryMode INTEGER,
            lcsStatusL2tpConnectionsEntryShTime Integer32,
            lcsStatusL2tpConnectionsEntryL2tpEndpoint DisplayString,
            lcsStatusL2tpConnectionsEntryPeerAddress IpAddress,
            lcsStatusL2tpConnectionsEntryIpAddress IpAddress,
            lcsStatusL2tpConnectionsEntryDnsDefault IpAddress,
            lcsStatusL2tpConnectionsEntryDnsBackup IpAddress,
            lcsStatusL2tpConnectionsEntryNbnsDefault IpAddress,
            lcsStatusL2tpConnectionsEntryNbnsBackup IpAddress,
            lcsStatusL2tpConnectionsEntryConnTime Gauge32
    }

-- {COLUMN} 1.3.6.1.4.1.2356.11.1.84.7.1.1
lcsStatusL2tpConnectionsEntryPeer OBJECT-TYPE
    SYNTAX     DisplayString (SIZE(0..16))
    MAX-ACCESS read-only
    STATUS     current
    DESCRIPTION
            "-- empty --"
    ::= { lcsStatusL2tpConnectionsEntry 1 }

-- {COLUMN} 1.3.6.1.4.1.2356.11.1.84.7.1.2
lcsStatusL2tpConnectionsEntryState OBJECT-TYPE
    SYNTAX     INTEGER {
                  eInit (0),
                  eSetupWan (1),
                  eReady (2),
                  eWaitForCb (3),
                  eDial (4),
                  eIncomingCall (5),
                  eProtocol (6),
                  eConnection (7),
                  eDisconnecting (8),
                  eCallBack (9),
                  eBundleConnect (10),
                  eProtocol2 (11),
                  eReserved (12),
                  eBundle (13)
            }
    MAX-ACCESS read-only
    STATUS     current
    DESCRIPTION
            "-- empty --"
    ::= { lcsStatusL2tpConnectionsEntry 2 }

-- {COLUMN} 1.3.6.1.4.1.2356.11.1.84.7.1.3
lcsStatusL2tpConnectionsEntryLastError OBJECT-TYPE
    SYNTAX     INTEGER {
                  eNone (0),
                  eRemoteDoubled (267),
                  eIcmpConnError (275),
                  eChargeLocked (283),
                  eRemoteDisconnected (17153),
                  eManualDisconnect (17154),
                  eShortholdExpired (17155),
                  ePhysicalDisconnected (17156),
                  eInvalidPhysicalChannel (17157),
                  eDynamicVpnReconnect (17158),
                  eConfigurationChanged (17159),
                  eRemovedFromConfig (17160),
                  eLcpRejected (32768),
                  eAuthError (32769),
                  eAuthRejected (32770),
                  eLcpConnError (32771),
                  ePapRejected (32784),
                  ePapRxTimeout (32785),
                  ePapTxTimeout (32786),
                  eWrongPapReq (32787),
                  ePapNakReceived (32788),
                  eUnknPapPeer (32789),
                  eChapRejected (32800),
                  eChapRxTimeout (32801),
                  eChapTxTimeout (32802),
                  eWrongChapResp (32803),
                  eChapFailRecvd (32804),
                  eUnknChapPeer (32805),
                  eIpcpRejected (32832),
                  eCcpRejected (32848),
                  eNoNcpAvailable (33008)
            }
    MAX-ACCESS read-write
    STATUS     current
    DESCRIPTION
            "-- empty --"
    ::= { lcsStatusL2tpConnectionsEntry 3 }

-- {COLUMN} 1.3.6.1.4.1.2356.11.1.84.7.1.4
lcsStatusL2tpConnectionsEntryMode OBJECT-TYPE
    SYNTAX     INTEGER {
                  ePassive (0),
                  eActive (128)
            }
    MAX-ACCESS read-only
    STATUS     current
    DESCRIPTION
            "-- empty --"
    ::= { lcsStatusL2tpConnectionsEntry 4 }

-- {COLUMN} 1.3.6.1.4.1.2356.11.1.84.7.1.5
lcsStatusL2tpConnectionsEntryShTime OBJECT-TYPE
    SYNTAX     Integer32 (0..65535)
    MAX-ACCESS read-only
    STATUS     current
    DESCRIPTION
            "-- empty --"
    ::= { lcsStatusL2tpConnectionsEntry 5 }

-- {COLUMN} 1.3.6.1.4.1.2356.11.1.84.7.1.6
lcsStatusL2tpConnectionsEntryL2tpEndpoint OBJECT-TYPE
    SYNTAX     DisplayString (SIZE(0..16))
    MAX-ACCESS read-only
    STATUS     current
    DESCRIPTION
            "-- empty --"
    ::= { lcsStatusL2tpConnectionsEntry 6 }

-- {COLUMN} 1.3.6.1.4.1.2356.11.1.84.7.1.7
lcsStatusL2tpConnectionsEntryPeerAddress OBJECT-TYPE
    SYNTAX     IpAddress
    MAX-ACCESS read-only
    STATUS     current
    DESCRIPTION
            "-- empty --"
    ::= { lcsStatusL2tpConnectionsEntry 7 }

-- {COLUMN} 1.3.6.1.4.1.2356.11.1.84.7.1.8
lcsStatusL2tpConnectionsEntryIpAddress OBJECT-TYPE
    SYNTAX     IpAddress
    MAX-ACCESS read-only
    STATUS     current
    DESCRIPTION
            "-- empty --"
    ::= { lcsStatusL2tpConnectionsEntry 8 }

-- {COLUMN} 1.3.6.1.4.1.2356.11.1.84.7.1.9
lcsStatusL2tpConnectionsEntryDnsDefault OBJECT-TYPE
    SYNTAX     IpAddress
    MAX-ACCESS read-only
    STATUS     current
    DESCRIPTION
            "-- empty --"
    ::= { lcsStatusL2tpConnectionsEntry 9 }

-- {COLUMN} 1.3.6.1.4.1.2356.11.1.84.7.1.10
lcsStatusL2tpConnectionsEntryDnsBackup OBJECT-TYPE
    SYNTAX     IpAddress
    MAX-ACCESS read-only
    STATUS     current
    DESCRIPTION
            "-- empty --"
    ::= { lcsStatusL2tpConnectionsEntry 10 }

-- {COLUMN} 1.3.6.1.4.1.2356.11.1.84.7.1.11
lcsStatusL2tpConnectionsEntryNbnsDefault OBJECT-TYPE
    SYNTAX     IpAddress
    MAX-ACCESS read-only
    STATUS     current
    DESCRIPTION
            "-- empty --"
    ::= { lcsStatusL2tpConnectionsEntry 11 }

-- {COLUMN} 1.3.6.1.4.1.2356.11.1.84.7.1.12
lcsStatusL2tpConnectionsEntryNbnsBackup OBJECT-TYPE
    SYNTAX     IpAddress
    MAX-ACCESS read-only
    STATUS     current
    DESCRIPTION
            "-- empty --"
    ::= { lcsStatusL2tpConnectionsEntry 12 }

-- {COLUMN} 1.3.6.1.4.1.2356.11.1.84.7.1.13
lcsStatusL2tpConnectionsEntryConnTime OBJECT-TYPE
    SYNTAX     Gauge32
    MAX-ACCESS read-only
    STATUS     current
    DESCRIPTION
            "-- empty --"
    ::= { lcsStatusL2tpConnectionsEntry 13 }

-- {SCALAR} 1.3.6.1.4.1.2356.11.1.84.8
lcsStatusL2tpNumConnections OBJECT-TYPE
    SYNTAX     Integer32 (0..2147483647)
    MAX-ACCESS read-only
    STATUS     current
    DESCRIPTION
            "-- empty --"
    ::= { lcsStatusL2tp 8 }

-- {SCALAR} 1.3.6.1.4.1.2356.11.1.84.9
lcsStatusL2tpDeleteValues OBJECT-TYPE
    SYNTAX     DisplayString
    MAX-ACCESS read-write
    STATUS     current
    DESCRIPTION
            "-- empty --"
    ::= { lcsStatusL2tp 9 }

-- {TABLE} 1.3.6.1.4.1.2356.11.1.84.10
lcsStatusL2tpEthernetTable OBJECT-TYPE
    SYNTAX     SEQUENCE OF LcsStatusL2tpEthernetEntry
    MAX-ACCESS not-accessible
    STATUS     current
    DESCRIPTION
            "-- empty --"
    ::= { lcsStatusL2tp 10 }

-- {ROW} 1.3.6.1.4.1.2356.11.1.84.10.1
lcsStatusL2tpEthernetEntry OBJECT-TYPE
    SYNTAX     LcsStatusL2tpEthernetEntry
    MAX-ACCESS not-accessible
    STATUS     current
    DESCRIPTION
            ""
    INDEX {
            lcsStatusL2tpEthernetEntryRemoteEnd,
            lcsStatusL2tpEthernetEntryL2tpEndpoint
          }
    ::= { lcsStatusL2tpEthernetTable 1 }

LcsStatusL2tpEthernetEntry ::= SEQUENCE {
            lcsStatusL2tpEthernetEntryRemoteEnd DisplayString,
            lcsStatusL2tpEthernetEntryL2tpEndpoint DisplayString,
            lcsStatusL2tpEthernetEntryState INTEGER,
            lcsStatusL2tpEthernetEntryMode INTEGER,
            lcsStatusL2tpEthernetEntryInterface INTEGER,
            lcsStatusL2tpEthernetEntryBrgAddr MacAddress,
            lcsStatusL2tpEthernetEntryConnTime Gauge32
    }

-- {COLUMN} 1.3.6.1.4.1.2356.11.1.84.10.1.1
lcsStatusL2tpEthernetEntryRemoteEnd OBJECT-TYPE
    SYNTAX     DisplayString (SIZE(0..32))
    MAX-ACCESS read-only
    STATUS     current
    DESCRIPTION
            "-- empty --"
    ::= { lcsStatusL2tpEthernetEntry 1 }

-- {COLUMN} 1.3.6.1.4.1.2356.11.1.84.10.1.2
lcsStatusL2tpEthernetEntryL2tpEndpoint OBJECT-TYPE
    SYNTAX     DisplayString (SIZE(0..16))
    MAX-ACCESS read-only
    STATUS     current
    DESCRIPTION
            "-- empty --"
    ::= { lcsStatusL2tpEthernetEntry 2 }

-- {COLUMN} 1.3.6.1.4.1.2356.11.1.84.10.1.3
lcsStatusL2tpEthernetEntryState OBJECT-TYPE
    SYNTAX     INTEGER {
                  eIdle (1),
                  eWaitTunnel (2),
                  eWaitIcrp (3),
                  eWaitOcrp (4),
                  eWaitConnect (5),
                  eWaitCsAnswer (6),
                  eWaitEstablish (7),
                  eEstablished (8)
            }
    MAX-ACCESS read-only
    STATUS     current
    DESCRIPTION
            "-- empty --"
    ::= { lcsStatusL2tpEthernetEntry 3 }

-- {COLUMN} 1.3.6.1.4.1.2356.11.1.84.10.1.4
lcsStatusL2tpEthernetEntryMode OBJECT-TYPE
    SYNTAX     INTEGER {
                  ePassive (0),
                  eActive (128)
            }
    MAX-ACCESS read-only
    STATUS     current
    DESCRIPTION
            "-- empty --"
    ::= { lcsStatusL2tpEthernetEntry 4 }

-- {COLUMN} 1.3.6.1.4.1.2356.11.1.84.10.1.5
lcsStatusL2tpEthernetEntryInterface OBJECT-TYPE
    SYNTAX     INTEGER {
                  eL2tpEthernet1 (0),
                  eL2tpEthernet2 (1),
                  eL2tpEthernet3 (2),
                  eL2tpEthernet4 (3),
                  eL2tpEthernet5 (4),
                  eL2tpEthernet6 (5),
                  eL2tpEthernet7 (6),
                  eL2tpEthernet8 (7),
                  eL2tpEthernet9 (8),
                  eL2tpEthernet10 (9),
                  eL2tpEthernet11 (10),
                  eL2tpEthernet12 (11),
                  eL2tpEthernet13 (12),
                  eL2tpEthernet14 (13),
                  eL2tpEthernet15 (14),
                  eL2tpEthernet16 (15),
                  eNone (65535)
            }
    MAX-ACCESS read-only
    STATUS     current
    DESCRIPTION
            "-- empty --"
    ::= { lcsStatusL2tpEthernetEntry 5 }

-- {COLUMN} 1.3.6.1.4.1.2356.11.1.84.10.1.6
lcsStatusL2tpEthernetEntryBrgAddr OBJECT-TYPE
    SYNTAX     MacAddress
    MAX-ACCESS read-only
    STATUS     current
    DESCRIPTION
            "-- empty --"
    ::= { lcsStatusL2tpEthernetEntry 6 }

-- {COLUMN} 1.3.6.1.4.1.2356.11.1.84.10.1.7
lcsStatusL2tpEthernetEntryConnTime OBJECT-TYPE
    SYNTAX     Gauge32
    MAX-ACCESS read-only
    STATUS     current
    DESCRIPTION
            "-- empty --"
    ::= { lcsStatusL2tpEthernetEntry 7 }

-- {SCALAR} 1.3.6.1.4.1.2356.11.1.84.11
lcsStatusL2tpNumEthernet OBJECT-TYPE
    SYNTAX     Integer32 (0..2147483647)
    MAX-ACCESS read-only
    STATUS     current
    DESCRIPTION
            "-- empty --"
    ::= { lcsStatusL2tp 11 }

-- {NODE} 1.3.6.1.4.1.2356.11.1.85
lcsStatusCwmp OBJECT IDENTIFIER ::= { lcsStatus 85 }

-- {SCALAR} 1.3.6.1.4.1.2356.11.1.85.1
lcsStatusCwmpOperating OBJECT-TYPE
    SYNTAX     INTEGER {
                  eNo (0),
                  eYes (1)
            }
    MAX-ACCESS read-only
    STATUS     current
    DESCRIPTION
            "-- empty --"
    ::= { lcsStatusCwmp 1 }

-- {SCALAR} 1.3.6.1.4.1.2356.11.1.85.2
lcsStatusCwmpAllowFileDownload OBJECT-TYPE
    SYNTAX     INTEGER {
                  eNo (0),
                  eYes (1)
            }
    MAX-ACCESS read-only
    STATUS     current
    DESCRIPTION
            "-- empty --"
    ::= { lcsStatusCwmp 2 }

-- {SCALAR} 1.3.6.1.4.1.2356.11.1.85.3
lcsStatusCwmpProvisioningCode OBJECT-TYPE
    SYNTAX     DisplayString (SIZE(0..63))
    MAX-ACCESS read-only
    STATUS     current
    DESCRIPTION
            "-- empty --"
    ::= { lcsStatusCwmp 3 }

-- {SCALAR} 1.3.6.1.4.1.2356.11.1.85.4
lcsStatusCwmpParameterKey OBJECT-TYPE
    SYNTAX     DisplayString (SIZE(0..63))
    MAX-ACCESS read-only
    STATUS     current
    DESCRIPTION
            "-- empty --"
    ::= { lcsStatusCwmp 4 }

-- {SCALAR} 1.3.6.1.4.1.2356.11.1.85.5
lcsStatusCwmpCommandKey OBJECT-TYPE
    SYNTAX     DisplayString (SIZE(0..31))
    MAX-ACCESS read-only
    STATUS     current
    DESCRIPTION
            "-- empty --"
    ::= { lcsStatusCwmp 5 }

-- {SCALAR} 1.3.6.1.4.1.2356.11.1.85.6
lcsStatusCwmpNtpServer1 OBJECT-TYPE
    SYNTAX     DisplayString (SIZE(0..63))
    MAX-ACCESS read-only
    STATUS     current
    DESCRIPTION
            "-- empty --"
    ::= { lcsStatusCwmp 6 }

-- {SCALAR} 1.3.6.1.4.1.2356.11.1.85.7
lcsStatusCwmpNtpServer2 OBJECT-TYPE
    SYNTAX     DisplayString (SIZE(0..63))
    MAX-ACCESS read-only
    STATUS     current
    DESCRIPTION
            "-- empty --"
    ::= { lcsStatusCwmp 7 }

-- {SCALAR} 1.3.6.1.4.1.2356.11.1.85.8
lcsStatusCwmpNtpServer3 OBJECT-TYPE
    SYNTAX     DisplayString (SIZE(0..63))
    MAX-ACCESS read-only
    STATUS     current
    DESCRIPTION
            "-- empty --"
    ::= { lcsStatusCwmp 8 }

-- {SCALAR} 1.3.6.1.4.1.2356.11.1.85.9
lcsStatusCwmpNtpServer4 OBJECT-TYPE
    SYNTAX     DisplayString (SIZE(0..63))
    MAX-ACCESS read-only
    STATUS     current
    DESCRIPTION
            "-- empty --"
    ::= { lcsStatusCwmp 9 }

-- {SCALAR} 1.3.6.1.4.1.2356.11.1.85.10
lcsStatusCwmpNtpServer5 OBJECT-TYPE
    SYNTAX     DisplayString (SIZE(0..63))
    MAX-ACCESS read-only
    STATUS     current
    DESCRIPTION
            "-- empty --"
    ::= { lcsStatusCwmp 10 }

-- {SCALAR} 1.3.6.1.4.1.2356.11.1.85.11
lcsStatusCwmpAllowUserChange OBJECT-TYPE
    SYNTAX     INTEGER {
                  eNo (0),
                  eYes (1)
            }
    MAX-ACCESS read-only
    STATUS     current
    DESCRIPTION
            "-- empty --"
    ::= { lcsStatusCwmp 11 }

-- {SCALAR} 1.3.6.1.4.1.2356.11.1.85.12
lcsStatusCwmpUpgradesManaged OBJECT-TYPE
    SYNTAX     INTEGER {
                  eNo (0),
                  eYes (1)
            }
    MAX-ACCESS read-only
    STATUS     current
    DESCRIPTION
            "-- empty --"
    ::= { lcsStatusCwmp 12 }

-- {SCALAR} 1.3.6.1.4.1.2356.11.1.85.23
lcsStatusCwmpConfigurationManaged OBJECT-TYPE
    SYNTAX     INTEGER {
                  eNo (0),
                  eYes (1)
            }
    MAX-ACCESS read-write
    STATUS     current
    DESCRIPTION
            "-- empty --"
    ::= { lcsStatusCwmp 23 }

-- {NODE} 1.3.6.1.4.1.2356.11.1.85.26
lcsStatusCwmpSslNew OBJECT IDENTIFIER ::= { lcsStatusCwmp 26 }

-- {SCALAR} 1.3.6.1.4.1.2356.11.1.85.26.1
lcsStatusCwmpSslNewVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsStatusCwmpSslNew 1 }

-- {SCALAR} 1.3.6.1.4.1.2356.11.1.85.26.2
lcsStatusCwmpSslNewKeyexAlgorithms OBJECT-TYPE
    SYNTAX     BITS {
                  eEcdhe (27),
                  eDhe (29),
                  eRsa (31)
            }
    MAX-ACCESS read-write
    STATUS     current
    DESCRIPTION
            "-- empty --"
    ::= { lcsStatusCwmpSslNew 2 }

-- {SCALAR} 1.3.6.1.4.1.2356.11.1.85.26.3
lcsStatusCwmpSslNewCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsStatusCwmpSslNew 3 }

-- {SCALAR} 1.3.6.1.4.1.2356.11.1.85.26.4
lcsStatusCwmpSslNewHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsStatusCwmpSslNew 4 }

-- {SCALAR} 1.3.6.1.4.1.2356.11.1.85.26.5
lcsStatusCwmpSslNewPreferPfs OBJECT-TYPE
    SYNTAX     BITS {
                  eNo (0),
                  eYes (7)
            }
    MAX-ACCESS read-write
    STATUS     current
    DESCRIPTION
            "-- empty --"
    ::= { lcsStatusCwmpSslNew 5 }

-- {SCALAR} 1.3.6.1.4.1.2356.11.1.85.26.6
lcsStatusCwmpSslNewRenegotiations OBJECT-TYPE
    SYNTAX     INTEGER {
                  eForbidden (0),
                  eAllowed (1),
                  eIgnored (2)
            }
    MAX-ACCESS read-write
    STATUS     current
    DESCRIPTION
            "-- empty --"
    ::= { lcsStatusCwmpSslNew 6 }

-- {SCALAR} 1.3.6.1.4.1.2356.11.1.85.26.7
lcsStatusCwmpSslNewEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsStatusCwmpSslNew 7 }

-- {SCALAR} 1.3.6.1.4.1.2356.11.1.85.26.21
lcsStatusCwmpSslNewSigHashAlgs OBJECT-TYPE
    SYNTAX     BITS {
                  eSha512Ecdsa (20),
                  eSha384Ecdsa (21),
                  eSha256Ecdsa (22),
                  eSha224Ecdsa (23),
                  eSha1Ecdsa (24),
                  eSha512Rsa (26),
                  eSha384Rsa (27),
                  eSha256Rsa (28),
                  eSha224Rsa (29),
                  eSha1Rsa (30)
            }
    MAX-ACCESS read-write
    STATUS     current
    DESCRIPTION
            "list of allowed signature/hash algorithms"
    ::= { lcsStatusCwmpSslNew 21 }

-- {TABLE} 1.3.6.1.4.1.2356.11.1.86
lcsStatusGreTunnelTable OBJECT-TYPE
    SYNTAX     SEQUENCE OF LcsStatusGreTunnelEntry
    MAX-ACCESS not-accessible
    STATUS     current
    DESCRIPTION
            "-- empty --"
    ::= { lcsStatus 86 }

-- {ROW} 1.3.6.1.4.1.2356.11.1.86.1
lcsStatusGreTunnelEntry OBJECT-TYPE
    SYNTAX     LcsStatusGreTunnelEntry
    MAX-ACCESS not-accessible
    STATUS     current
    DESCRIPTION
            ""
    INDEX {
            lcsStatusGreTunnelEntryPeer
          }
    ::= { lcsStatusGreTunnelTable 1 }

LcsStatusGreTunnelEntry ::= SEQUENCE {
            lcsStatusGreTunnelEntryPeer DisplayString,
            lcsStatusGreTunnelEntryIpAddress DisplayString,
            lcsStatusGreTunnelEntryRtgTag Integer32,
            lcsStatusGreTunnelEntryKeyPresent INTEGER,
            lcsStatusGreTunnelEntryKeyValue Integer32,
            lcsStatusGreTunnelEntryChecksum INTEGER,
            lcsStatusGreTunnelEntrySequencing INTEGER,
            lcsStatusGreTunnelEntryLoopbackAddress DisplayString
    }

-- {COLUMN} 1.3.6.1.4.1.2356.11.1.86.1.1
lcsStatusGreTunnelEntryPeer OBJECT-TYPE
    SYNTAX     DisplayString (SIZE(0..16))
    MAX-ACCESS read-only
    STATUS     current
    DESCRIPTION
            "-- empty --"
    ::= { lcsStatusGreTunnelEntry 1 }

-- {COLUMN} 1.3.6.1.4.1.2356.11.1.86.1.3
lcsStatusGreTunnelEntryIpAddress OBJECT-TYPE
    SYNTAX     DisplayString (SIZE(0..64))
    MAX-ACCESS read-only
    STATUS     current
    DESCRIPTION
            "-- empty --"
    ::= { lcsStatusGreTunnelEntry 3 }

-- {COLUMN} 1.3.6.1.4.1.2356.11.1.86.1.4
lcsStatusGreTunnelEntryRtgTag OBJECT-TYPE
    SYNTAX     Integer32 (0..2147483647)
    MAX-ACCESS read-only
    STATUS     current
    DESCRIPTION
            "-- empty --"
    ::= { lcsStatusGreTunnelEntry 4 }

-- {COLUMN} 1.3.6.1.4.1.2356.11.1.86.1.5
lcsStatusGreTunnelEntryKeyPresent OBJECT-TYPE
    SYNTAX     INTEGER {
                  eNo (0),
                  eYes (1)
            }
    MAX-ACCESS read-only
    STATUS     current
    DESCRIPTION
            "-- empty --"
    ::= { lcsStatusGreTunnelEntry 5 }

-- {COLUMN} 1.3.6.1.4.1.2356.11.1.86.1.6
lcsStatusGreTunnelEntryKeyValue OBJECT-TYPE
    SYNTAX     Integer32 (0..2147483647)
    MAX-ACCESS read-only
    STATUS     current
    DESCRIPTION
            "-- empty --"
    ::= { lcsStatusGreTunnelEntry 6 }

-- {COLUMN} 1.3.6.1.4.1.2356.11.1.86.1.7
lcsStatusGreTunnelEntryChecksum OBJECT-TYPE
    SYNTAX     INTEGER {
                  eNo (0),
                  eYes (1)
            }
    MAX-ACCESS read-only
    STATUS     current
    DESCRIPTION
            "-- empty --"
    ::= { lcsStatusGreTunnelEntry 7 }

-- {COLUMN} 1.3.6.1.4.1.2356.11.1.86.1.8
lcsStatusGreTunnelEntrySequencing OBJECT-TYPE
    SYNTAX     INTEGER {
                  eNo (0),
                  eYes (1)
            }
    MAX-ACCESS read-only
    STATUS     current
    DESCRIPTION
            "-- empty --"
    ::= { lcsStatusGreTunnelEntry 8 }

-- {COLUMN} 1.3.6.1.4.1.2356.11.1.86.1.9
lcsStatusGreTunnelEntryLoopbackAddress OBJECT-TYPE
    SYNTAX     DisplayString (SIZE(0..16))
    MAX-ACCESS read-only
    STATUS     current
    DESCRIPTION
            "-- empty --"
    ::= { lcsStatusGreTunnelEntry 9 }

-- {TABLE} 1.3.6.1.4.1.2356.11.1.87
lcsStatusEogreTunnelTable OBJECT-TYPE
    SYNTAX     SEQUENCE OF LcsStatusEogreTunnelEntry
    MAX-ACCESS not-accessible
    STATUS     current
    DESCRIPTION
            "-- empty --"
    ::= { lcsStatus 87 }

-- {ROW} 1.3.6.1.4.1.2356.11.1.87.1
lcsStatusEogreTunnelEntry OBJECT-TYPE
    SYNTAX     LcsStatusEogreTunnelEntry
    MAX-ACCESS not-accessible
    STATUS     current
    DESCRIPTION
            ""
    INDEX {
            lcsStatusEogreTunnelEntryPort
          }
    ::= { lcsStatusEogreTunnelTable 1 }

LcsStatusEogreTunnelEntry ::= SEQUENCE {
            lcsStatusEogreTunnelEntryPort DisplayString,
            lcsStatusEogreTunnelEntryActive INTEGER,
            lcsStatusEogreTunnelEntryRemoteEndpointAddress DisplayString,
            lcsStatusEogreTunnelEntryRtgTag Integer32,
            lcsStatusEogreTunnelEntryKeyPresent INTEGER,
            lcsStatusEogreTunnelEntryKeyValue Integer32,
            lcsStatusEogreTunnelEntryChecksum INTEGER,
            lcsStatusEogreTunnelEntrySequencing INTEGER,
            lcsStatusEogreTunnelEntryLoopbackAddress DisplayString
    }

-- {COLUMN} 1.3.6.1.4.1.2356.11.1.87.1.1
lcsStatusEogreTunnelEntryPort OBJECT-TYPE
    SYNTAX     DisplayString (SIZE(0..15))
    MAX-ACCESS read-only
    STATUS     current
    DESCRIPTION
            "-- empty --"
    ::= { lcsStatusEogreTunnelEntry 1 }

-- {COLUMN} 1.3.6.1.4.1.2356.11.1.87.1.2
lcsStatusEogreTunnelEntryActive OBJECT-TYPE
    SYNTAX     INTEGER {
                  eNo (0),
                  eYes (1)
            }
    MAX-ACCESS read-only
    STATUS     current
    DESCRIPTION
            "-- empty --"
    ::= { lcsStatusEogreTunnelEntry 2 }

-- {COLUMN} 1.3.6.1.4.1.2356.11.1.87.1.3
lcsStatusEogreTunnelEntryRemoteEndpointAddress OBJECT-TYPE
    SYNTAX     DisplayString (SIZE(0..64))
    MAX-ACCESS read-only
    STATUS     current
    DESCRIPTION
            "-- empty --"
    ::= { lcsStatusEogreTunnelEntry 3 }

-- {COLUMN} 1.3.6.1.4.1.2356.11.1.87.1.4
lcsStatusEogreTunnelEntryRtgTag OBJECT-TYPE
    SYNTAX     Integer32 (0..2147483647)
    MAX-ACCESS read-only
    STATUS     current
    DESCRIPTION
            "-- empty --"
    ::= { lcsStatusEogreTunnelEntry 4 }

-- {COLUMN} 1.3.6.1.4.1.2356.11.1.87.1.5
lcsStatusEogreTunnelEntryKeyPresent OBJECT-TYPE
    SYNTAX     INTEGER {
                  eNo (0),
                  eYes (1)
            }
    MAX-ACCESS read-only
    STATUS     current
    DESCRIPTION
            "-- empty --"
    ::= { lcsStatusEogreTunnelEntry 5 }

-- {COLUMN} 1.3.6.1.4.1.2356.11.1.87.1.6
lcsStatusEogreTunnelEntryKeyValue OBJECT-TYPE
    SYNTAX     Integer32 (0..2147483647)
    MAX-ACCESS read-only
    STATUS     current
    DESCRIPTION
            "-- empty --"
    ::= { lcsStatusEogreTunnelEntry 6 }

-- {COLUMN} 1.3.6.1.4.1.2356.11.1.87.1.7
lcsStatusEogreTunnelEntryChecksum OBJECT-TYPE
    SYNTAX     INTEGER {
                  eNo (0),
                  eYes (1)
            }
    MAX-ACCESS read-only
    STATUS     current
    DESCRIPTION
            "-- empty --"
    ::= { lcsStatusEogreTunnelEntry 7 }

-- {COLUMN} 1.3.6.1.4.1.2356.11.1.87.1.8
lcsStatusEogreTunnelEntrySequencing OBJECT-TYPE
    SYNTAX     INTEGER {
                  eNo (0),
                  eYes (1)
            }
    MAX-ACCESS read-only
    STATUS     current
    DESCRIPTION
            "-- empty --"
    ::= { lcsStatusEogreTunnelEntry 8 }

-- {COLUMN} 1.3.6.1.4.1.2356.11.1.87.1.9
lcsStatusEogreTunnelEntryLoopbackAddress OBJECT-TYPE
    SYNTAX     DisplayString (SIZE(0..16))
    MAX-ACCESS read-only
    STATUS     current
    DESCRIPTION
            "-- empty --"
    ::= { lcsStatusEogreTunnelEntry 9 }

-- {NODE} 1.3.6.1.4.1.2356.11.1.88
lcsStatusWirelessEpaper OBJECT IDENTIFIER ::= { lcsStatus 88 }

-- {SCALAR} 1.3.6.1.4.1.2356.11.1.88.1
lcsStatusWirelessEpaperState OBJECT-TYPE
    SYNTAX     INTEGER {
                  eInactive (1),
                  eWaitingForControllerConnection (2),
                  eRunning (3),
                  eTransmitting (4),
                  eError (5),
                  eWaitingForEpaperModule (6),
                  eRunningDisconnected (7)
            }
    MAX-ACCESS read-only
    STATUS     current
    DESCRIPTION
            "-- empty --"
    ::= { lcsStatusWirelessEpaper 1 }

-- {SCALAR} 1.3.6.1.4.1.2356.11.1.88.2
lcsStatusWirelessEpaperOperating OBJECT-TYPE
    SYNTAX     INTEGER {
                  eNo (0),
                  eYes (1)
            }
    MAX-ACCESS read-only
    STATUS     current
    DESCRIPTION
            "-- empty --"
    ::= { lcsStatusWirelessEpaper 2 }

-- {SCALAR} 1.3.6.1.4.1.2356.11.1.88.3
lcsStatusWirelessEpaperAccesspointId OBJECT-TYPE
    SYNTAX     Integer32 (0..2147483647)
    MAX-ACCESS read-only
    STATUS     current
    DESCRIPTION
            "-- empty --"
    ::= { lcsStatusWirelessEpaper 3 }

-- {SCALAR} 1.3.6.1.4.1.2356.11.1.88.4
lcsStatusWirelessEpaperFirmwareVersion OBJECT-TYPE
    SYNTAX     DisplayString (SIZE(0..13))
    MAX-ACCESS read-only
    STATUS     current
    DESCRIPTION
            "-- empty --"
    ::= { lcsStatusWirelessEpaper 4 }

-- {SCALAR} 1.3.6.1.4.1.2356.11.1.88.5
lcsStatusWirelessEpaperCurrentChannel OBJECT-TYPE
    SYNTAX     INTEGER {
                  e2404mhz (0),
                  e2410mhz (1),
                  e2422mhz (2),
                  e2425mhz (3),
                  e2442mhz (4),
                  e2450mhz (5),
                  e2462mhz (6),
                  e2470mhz (7),
                  e2474mhz (8),
                  e2477mhz (9),
                  e2480mhz (10),
                  eNone (255)
            }
    MAX-ACCESS read-only
    STATUS     current
    DESCRIPTION
            "-- empty --"
    ::= { lcsStatusWirelessEpaper 5 }

-- {NODE} 1.3.6.1.4.1.2356.11.1.88.6
lcsStatusWirelessEpaperStatistics OBJECT IDENTIFIER ::= { lcsStatusWirelessEpaper 6 }

-- {SCALAR} 1.3.6.1.4.1.2356.11.1.88.6.1
lcsStatusWirelessEpaperStatisticsUartErrorCounter OBJECT-TYPE
    SYNTAX     Integer32 (0..2147483647)
    MAX-ACCESS read-only
    STATUS     current
    DESCRIPTION
            "-- empty --"
    ::= { lcsStatusWirelessEpaperStatistics 1 }

-- {SCALAR} 1.3.6.1.4.1.2356.11.1.88.6.2
lcsStatusWirelessEpaperStatisticsControllerLateResponseCounter OBJECT-TYPE
    SYNTAX     Integer32 (0..2147483647)
    MAX-ACCESS read-only
    STATUS     current
    DESCRIPTION
            "-- empty --"
    ::= { lcsStatusWirelessEpaperStatistics 2 }

-- {SCALAR} 1.3.6.1.4.1.2356.11.1.88.6.3
lcsStatusWirelessEpaperStatisticsControllerTimeoutCounter OBJECT-TYPE
    SYNTAX     Integer32 (0..2147483647)
    MAX-ACCESS read-only
    STATUS     current
    DESCRIPTION
            "-- empty --"
    ::= { lcsStatusWirelessEpaperStatistics 3 }

-- {SCALAR} 1.3.6.1.4.1.2356.11.1.88.6.4
lcsStatusWirelessEpaperStatisticsCoexistenceActiveCounter OBJECT-TYPE
    SYNTAX     Integer32 (0..2147483647)
    MAX-ACCESS read-only
    STATUS     current
    DESCRIPTION
            "-- empty --"
    ::= { lcsStatusWirelessEpaperStatistics 4 }

-- {SCALAR} 1.3.6.1.4.1.2356.11.1.88.6.5
lcsStatusWirelessEpaperStatisticsCoexistenceStuckCounter OBJECT-TYPE
    SYNTAX     Integer32 (0..2147483647)
    MAX-ACCESS read-only
    STATUS     current
    DESCRIPTION
            "-- empty --"
    ::= { lcsStatusWirelessEpaperStatistics 5 }

-- {SCALAR} 1.3.6.1.4.1.2356.11.1.88.7
lcsStatusWirelessEpaperControllerIp OBJECT-TYPE
    SYNTAX     DisplayString (SIZE(0..63))
    MAX-ACCESS read-only
    STATUS     current
    DESCRIPTION
            "-- empty --"
    ::= { lcsStatusWirelessEpaper 7 }

-- {SCALAR} 1.3.6.1.4.1.2356.11.1.88.8
lcsStatusWirelessEpaperPort OBJECT-TYPE
    SYNTAX     Integer32 (0..65535)
    MAX-ACCESS read-only
    STATUS     current
    DESCRIPTION
            "-- empty --"
    ::= { lcsStatusWirelessEpaper 8 }

-- {NODE} 1.3.6.1.4.1.2356.11.1.88.9
lcsStatusWirelessEpaperCoord OBJECT IDENTIFIER ::= { lcsStatusWirelessEpaper 9 }

-- {TABLE} 1.3.6.1.4.1.2356.11.1.88.9.1
lcsStatusWirelessEpaperCoordPeerTableTable OBJECT-TYPE
    SYNTAX     SEQUENCE OF LcsStatusWirelessEpaperCoordPeerTableEntry
    MAX-ACCESS not-accessible
    STATUS     current
    DESCRIPTION
            "-- empty --"
    ::= { lcsStatusWirelessEpaperCoord 1 }

-- {ROW} 1.3.6.1.4.1.2356.11.1.88.9.1.1
lcsStatusWirelessEpaperCoordPeerTableEntry OBJECT-TYPE
    SYNTAX     LcsStatusWirelessEpaperCoordPeerTableEntry
    MAX-ACCESS not-accessible
    STATUS     current
    DESCRIPTION
            ""
    INDEX {
            lcsStatusWirelessEpaperCoordPeerTableEntryId
          }
    ::= { lcsStatusWirelessEpaperCoordPeerTableTable 1 }

LcsStatusWirelessEpaperCoordPeerTableEntry ::= SEQUENCE {
            lcsStatusWirelessEpaperCoordPeerTableEntryId Unsigned32,
            lcsStatusWirelessEpaperCoordPeerTableEntryState INTEGER,
            lcsStatusWirelessEpaperCoordPeerTableEntryIpAddress OCTET STRING,
            lcsStatusWirelessEpaperCoordPeerTableEntryRtgTag Unsigned32,
            lcsStatusWirelessEpaperCoordPeerTableEntryConnected INTEGER,
            lcsStatusWirelessEpaperCoordPeerTableEntryAssessment OCTET STRING,
            lcsStatusWirelessEpaperCoordPeerTableEntryAssignment Unsigned32
    }

-- {COLUMN} 1.3.6.1.4.1.2356.11.1.88.9.1.1.1
lcsStatusWirelessEpaperCoordPeerTableEntryId OBJECT-TYPE
    SYNTAX     Unsigned32 (0..4294967295)
    MAX-ACCESS read-only
    STATUS     current
    DESCRIPTION
            "-- empty --"
    ::= { lcsStatusWirelessEpaperCoordPeerTableEntry 1 }

-- {COLUMN} 1.3.6.1.4.1.2356.11.1.88.9.1.1.2
lcsStatusWirelessEpaperCoordPeerTableEntryState OBJECT-TYPE
    SYNTAX     INTEGER {
                  ePassive (0),
                  eSlave (1),
                  eMaster (2),
                  eInactive (255)
            }
    MAX-ACCESS read-only
    STATUS     current
    DESCRIPTION
            "-- empty --"
    ::= { lcsStatusWirelessEpaperCoordPeerTableEntry 2 }

-- {COLUMN} 1.3.6.1.4.1.2356.11.1.88.9.1.1.3
lcsStatusWirelessEpaperCoordPeerTableEntryIpAddress OBJECT-TYPE
    SYNTAX     OCTET STRING (SIZE(0..40))
    MAX-ACCESS read-only
    STATUS     current
    DESCRIPTION
            "-- empty --"
    ::= { lcsStatusWirelessEpaperCoordPeerTableEntry 3 }

-- {COLUMN} 1.3.6.1.4.1.2356.11.1.88.9.1.1.4
lcsStatusWirelessEpaperCoordPeerTableEntryRtgTag OBJECT-TYPE
    SYNTAX     Unsigned32 (0..65535)
    MAX-ACCESS read-only
    STATUS     current
    DESCRIPTION
            "-- empty --"
    ::= { lcsStatusWirelessEpaperCoordPeerTableEntry 4 }

-- {COLUMN} 1.3.6.1.4.1.2356.11.1.88.9.1.1.5
lcsStatusWirelessEpaperCoordPeerTableEntryConnected OBJECT-TYPE
    SYNTAX     INTEGER {
                  eNo (0),
                  eYes (1)
            }
    MAX-ACCESS read-only
    STATUS     current
    DESCRIPTION
            "-- empty --"
    ::= { lcsStatusWirelessEpaperCoordPeerTableEntry 5 }

-- {COLUMN} 1.3.6.1.4.1.2356.11.1.88.9.1.1.6
lcsStatusWirelessEpaperCoordPeerTableEntryAssessment OBJECT-TYPE
    SYNTAX     OCTET STRING (SIZE(0..67))
    MAX-ACCESS read-only
    STATUS     current
    DESCRIPTION
            "-- empty --"
    ::= { lcsStatusWirelessEpaperCoordPeerTableEntry 6 }

-- {COLUMN} 1.3.6.1.4.1.2356.11.1.88.9.1.1.7
lcsStatusWirelessEpaperCoordPeerTableEntryAssignment OBJECT-TYPE
    SYNTAX     Unsigned32 (0..255)
    MAX-ACCESS read-only
    STATUS     current
    DESCRIPTION
            "-- empty --"
    ::= { lcsStatusWirelessEpaperCoordPeerTableEntry 7 }

-- {SCALAR} 1.3.6.1.4.1.2356.11.1.88.10
lcsStatusWirelessEpaperControllerProtocolVersion OBJECT-TYPE
    SYNTAX     INTEGER {
                  eNone (0),
                  eThinap10Udp (1),
                  eThinap20Tcp (2)
            }
    MAX-ACCESS read-only
    STATUS     current
    DESCRIPTION
            "-- empty --"
    ::= { lcsStatusWirelessEpaper 10 }

-- {NODE} 1.3.6.1.4.1.2356.11.1.90
lcsStatusBluetooth OBJECT IDENTIFIER ::= { lcsStatus 90 }

-- {NODE} 1.3.6.1.4.1.2356.11.1.90.1
lcsStatusBluetoothIbeacon OBJECT IDENTIFIER ::= { lcsStatusBluetooth 1 }

-- {SCALAR} 1.3.6.1.4.1.2356.11.1.90.1.1
lcsStatusBluetoothIbeaconOperating OBJECT-TYPE
    SYNTAX     INTEGER {
                  eNo (0),
                  eYes (1)
            }
    MAX-ACCESS read-only
    STATUS     current
    DESCRIPTION
            "-- empty --"
    ::= { lcsStatusBluetoothIbeacon 1 }

-- {SCALAR} 1.3.6.1.4.1.2356.11.1.90.1.2
lcsStatusBluetoothIbeaconUuid OBJECT-TYPE
    SYNTAX     DisplayString (SIZE(0..36))
    MAX-ACCESS read-only
    STATUS     current
    DESCRIPTION
            "-- empty --"
    ::= { lcsStatusBluetoothIbeacon 2 }

-- {SCALAR} 1.3.6.1.4.1.2356.11.1.90.1.3
lcsStatusBluetoothIbeaconMajor OBJECT-TYPE
    SYNTAX     Integer32 (0..65535)
    MAX-ACCESS read-only
    STATUS     current
    DESCRIPTION
            "-- empty --"
    ::= { lcsStatusBluetoothIbeacon 3 }

-- {SCALAR} 1.3.6.1.4.1.2356.11.1.90.1.4
lcsStatusBluetoothIbeaconMinor OBJECT-TYPE
    SYNTAX     Integer32 (0..65535)
    MAX-ACCESS read-only
    STATUS     current
    DESCRIPTION
            "-- empty --"
    ::= { lcsStatusBluetoothIbeacon 4 }

-- {SCALAR} 1.3.6.1.4.1.2356.11.1.90.1.5
lcsStatusBluetoothIbeaconMeasuredPower OBJECT-TYPE
    SYNTAX     Integer32 (-128..127)
    MAX-ACCESS read-only
    STATUS     current
    DESCRIPTION
            "-- empty --"
    ::= { lcsStatusBluetoothIbeacon 5 }

-- {SCALAR} 1.3.6.1.4.1.2356.11.1.90.1.6
lcsStatusBluetoothIbeaconTransmitPower OBJECT-TYPE
    SYNTAX     INTEGER {
                  eLow (0),
                  eMedium (1),
                  eHigh (2),
                  eNotSet (254)
            }
    MAX-ACCESS read-only
    STATUS     current
    DESCRIPTION
            "-- empty --"
    ::= { lcsStatusBluetoothIbeacon 6 }

-- {SCALAR} 1.3.6.1.4.1.2356.11.1.90.1.7
lcsStatusBluetoothIbeaconChannelS OBJECT-TYPE
    SYNTAX     BITS {
                  e2480mhz (5),
                  e2426mhz (6),
                  e2402mhz (7)
            }
    MAX-ACCESS read-only
    STATUS     current
    DESCRIPTION
            "-- empty --"
    ::= { lcsStatusBluetoothIbeacon 7 }

-- {SCALAR} 1.3.6.1.4.1.2356.11.1.90.1.8
lcsStatusBluetoothIbeaconCoexistence OBJECT-TYPE
    SYNTAX     INTEGER {
                  eNo (0),
                  eYes (1)
            }
    MAX-ACCESS read-only
    STATUS     current
    DESCRIPTION
            "-- empty --"
    ::= { lcsStatusBluetoothIbeacon 8 }

-- {SCALAR} 1.3.6.1.4.1.2356.11.1.90.1.9
lcsStatusBluetoothIbeaconSoftwareVersion OBJECT-TYPE
    SYNTAX     Integer32 (0..65535)
    MAX-ACCESS read-only
    STATUS     current
    DESCRIPTION
            "-- empty --"
    ::= { lcsStatusBluetoothIbeacon 9 }

-- {SCALAR} 1.3.6.1.4.1.2356.11.1.90.1.10
lcsStatusBluetoothIbeaconRestartCause OBJECT-TYPE
    SYNTAX     INTEGER {
                  ePowerOn (0),
                  eResetSignal (1),
                  eResetMessage (6),
                  eNotStarted (256)
            }
    MAX-ACCESS read-only
    STATUS     current
    DESCRIPTION
            "-- empty --"
    ::= { lcsStatusBluetoothIbeacon 10 }

-- {SCALAR} 1.3.6.1.4.1.2356.11.1.90.1.11
lcsStatusBluetoothIbeaconLastKnownError OBJECT-TYPE
    SYNTAX     INTEGER {
                  eStartupSuccessful (0),
                  eFirmwareUploadSuccessful (1),
                  eFirmwareUploadFailure (2),
                  eUnrecoverableMessageError (3),
                  eFinalMessageFailure (4),
                  eSerialInterfaceFailure (5),
                  eFirmwareChecksumVerification (6),
                  eFirmwareChecksumMismatch (7),
                  eFirmwareChecksumFileReadError (8),
                  eUnrecoverableFirmwareChecksumError (9),
                  eNotStarted (256)
            }
    MAX-ACCESS read-only
    STATUS     current
    DESCRIPTION
            "-- empty --"
    ::= { lcsStatusBluetoothIbeacon 11 }

-- {NODE} 1.3.6.1.4.1.2356.11.1.91
lcsStatusRolloutAgent OBJECT IDENTIFIER ::= { lcsStatus 91 }

-- {SCALAR} 1.3.6.1.4.1.2356.11.1.91.1
lcsStatusRolloutAgentOperating OBJECT-TYPE
    SYNTAX     INTEGER {
                  eNo (0),
                  eYes (1),
                  eDhcpInitiated (2)
            }
    MAX-ACCESS read-only
    STATUS     current
    DESCRIPTION
            "-- empty --"
    ::= { lcsStatusRolloutAgent 1 }

-- {SCALAR} 1.3.6.1.4.1.2356.11.1.91.2
lcsStatusRolloutAgentConfigServer OBJECT-TYPE
    SYNTAX     DisplayString (SIZE(0..255))
    MAX-ACCESS read-only
    STATUS     current
    DESCRIPTION
            "-- empty --"
    ::= { lcsStatusRolloutAgent 2 }

-- {SCALAR} 1.3.6.1.4.1.2356.11.1.91.3
lcsStatusRolloutAgentFirmwareServer OBJECT-TYPE
    SYNTAX     DisplayString (SIZE(0..255))
    MAX-ACCESS read-only
    STATUS     current
    DESCRIPTION
            "-- empty --"
    ::= { lcsStatusRolloutAgent 3 }

-- {SCALAR} 1.3.6.1.4.1.2356.11.1.91.4
lcsStatusRolloutAgentUsername OBJECT-TYPE
    SYNTAX     DisplayString (SIZE(0..255))
    MAX-ACCESS read-only
    STATUS     current
    DESCRIPTION
            "-- empty --"
    ::= { lcsStatusRolloutAgent 4 }

-- {SCALAR} 1.3.6.1.4.1.2356.11.1.91.5
lcsStatusRolloutAgentPassword OBJECT-TYPE
    SYNTAX     DisplayString (SIZE(0..255))
    MAX-ACCESS read-only
    STATUS     current
    DESCRIPTION
            "-- empty --"
    ::= { lcsStatusRolloutAgent 5 }

-- {SCALAR} 1.3.6.1.4.1.2356.11.1.91.6
lcsStatusRolloutAgentProjectNumber OBJECT-TYPE
    SYNTAX     DisplayString (SIZE(0..255))
    MAX-ACCESS read-only
    STATUS     current
    DESCRIPTION
            "-- empty --"
    ::= { lcsStatusRolloutAgent 6 }

-- {SCALAR} 1.3.6.1.4.1.2356.11.1.91.7
lcsStatusRolloutAgentAdditionalParameter OBJECT-TYPE
    SYNTAX     DisplayString (SIZE(0..255))
    MAX-ACCESS read-only
    STATUS     current
    DESCRIPTION
            "-- empty --"
    ::= { lcsStatusRolloutAgent 7 }

-- {SCALAR} 1.3.6.1.4.1.2356.11.1.91.8
lcsStatusRolloutAgentRebootTime OBJECT-TYPE
    SYNTAX     Integer32 (0..2147483647)
    MAX-ACCESS read-only
    STATUS     current
    DESCRIPTION
            "-- empty --"
    ::= { lcsStatusRolloutAgent 8 }

-- {SCALAR} 1.3.6.1.4.1.2356.11.1.91.9
lcsStatusRolloutAgentRequestInterval OBJECT-TYPE
    SYNTAX     Integer32 (0..2147483647)
    MAX-ACCESS read-only
    STATUS     current
    DESCRIPTION
            "-- empty --"
    ::= { lcsStatusRolloutAgent 9 }

-- {SCALAR} 1.3.6.1.4.1.2356.11.1.91.10
lcsStatusRolloutAgentTan OBJECT-TYPE
    SYNTAX     DisplayString (SIZE(0..255))
    MAX-ACCESS read-only
    STATUS     current
    DESCRIPTION
            "-- empty --"
    ::= { lcsStatusRolloutAgent 10 }

-- {SCALAR} 1.3.6.1.4.1.2356.11.1.91.11
lcsStatusRolloutAgentDeviceId OBJECT-TYPE
    SYNTAX     DisplayString (SIZE(0..255))
    MAX-ACCESS read-only
    STATUS     current
    DESCRIPTION
            "-- empty --"
    ::= { lcsStatusRolloutAgent 11 }

-- {SCALAR} 1.3.6.1.4.1.2356.11.1.91.12
lcsStatusRolloutAgentRequestDelay OBJECT-TYPE
    SYNTAX     Integer32 (0..2147483647)
    MAX-ACCESS read-only
    STATUS     current
    DESCRIPTION
            "-- empty --"
    ::= { lcsStatusRolloutAgent 12 }

-- {SCALAR} 1.3.6.1.4.1.2356.11.1.91.13
lcsStatusRolloutAgentRequestTimeRandom OBJECT-TYPE
    SYNTAX     DisplayString
    MAX-ACCESS read-only
    STATUS     current
    DESCRIPTION
            "-- empty --"
    ::= { lcsStatusRolloutAgent 13 }

-- {SCALAR} 1.3.6.1.4.1.2356.11.1.91.14
lcsStatusRolloutAgentOmitCertificateCheck OBJECT-TYPE
    SYNTAX     DisplayString
    MAX-ACCESS read-only
    STATUS     current
    DESCRIPTION
            "-- empty --"
    ::= { lcsStatusRolloutAgent 14 }

-- {SCALAR} 1.3.6.1.4.1.2356.11.1.91.15
lcsStatusRolloutAgentStartupRequestUrl OBJECT-TYPE
    SYNTAX     DisplayString (SIZE(0..255))
    MAX-ACCESS read-only
    STATUS     current
    DESCRIPTION
            "-- empty --"
    ::= { lcsStatusRolloutAgent 15 }

-- {SCALAR} 1.3.6.1.4.1.2356.11.1.91.16
lcsStatusRolloutAgentConfigRequestUrl OBJECT-TYPE
    SYNTAX     DisplayString (SIZE(0..255))
    MAX-ACCESS read-only
    STATUS     current
    DESCRIPTION
            "-- empty --"
    ::= { lcsStatusRolloutAgent 16 }

-- {NODE} 1.3.6.1.4.1.2356.11.1.93
lcsStatusRoutProt OBJECT IDENTIFIER ::= { lcsStatus 93 }

-- {NODE} 1.3.6.1.4.1.2356.11.1.93.1
lcsStatusRoutProtBgp OBJECT IDENTIFIER ::= { lcsStatusRoutProt 1 }

-- {TABLE} 1.3.6.1.4.1.2356.11.1.93.1.1
lcsStatusRoutProtBgpNeighborsTable OBJECT-TYPE
    SYNTAX     SEQUENCE OF LcsStatusRoutProtBgpNeighborsEntry
    MAX-ACCESS not-accessible
    STATUS     current
    DESCRIPTION
            "-- empty --"
    ::= { lcsStatusRoutProtBgp 1 }

-- {ROW} 1.3.6.1.4.1.2356.11.1.93.1.1.1
lcsStatusRoutProtBgpNeighborsEntry OBJECT-TYPE
    SYNTAX     LcsStatusRoutProtBgpNeighborsEntry
    MAX-ACCESS not-accessible
    STATUS     current
    DESCRIPTION
            ""
    INDEX {
            lcsStatusRoutProtBgpNeighborsEntryIpAddress,
            lcsStatusRoutProtBgpNeighborsEntryPort,
            lcsStatusRoutProtBgpNeighborsEntryLoopbackAddress,
            lcsStatusRoutProtBgpNeighborsEntryRtgTag,
            lcsStatusRoutProtBgpNeighborsEntryRemoteAs
          }
    ::= { lcsStatusRoutProtBgpNeighborsTable 1 }

LcsStatusRoutProtBgpNeighborsEntry ::= SEQUENCE {
            lcsStatusRoutProtBgpNeighborsEntryIpAddress DisplayString,
            lcsStatusRoutProtBgpNeighborsEntryPort Integer32,
            lcsStatusRoutProtBgpNeighborsEntryLoopbackAddress DisplayString,
            lcsStatusRoutProtBgpNeighborsEntryRtgTag Integer32,
            lcsStatusRoutProtBgpNeighborsEntryRemoteAs Integer32,
            lcsStatusRoutProtBgpNeighborsEntryRouterId DisplayString,
            lcsStatusRoutProtBgpNeighborsEntryState INTEGER,
            lcsStatusRoutProtBgpNeighborsEntryPreviousState INTEGER,
            lcsStatusRoutProtBgpNeighborsEntryLastError DisplayString,
            lcsStatusRoutProtBgpNeighborsEntryEstabTransit Integer32,
            lcsStatusRoutProtBgpNeighborsEntryConnTime DisplayString,
            lcsStatusRoutProtBgpNeighborsEntryKeepalive Integer32,
            lcsStatusRoutProtBgpNeighborsEntryHoldtime Integer32,
            lcsStatusRoutProtBgpNeighborsEntryConnTimeSnmp Counter64
    }

-- {COLUMN} 1.3.6.1.4.1.2356.11.1.93.1.1.1.1
lcsStatusRoutProtBgpNeighborsEntryIpAddress OBJECT-TYPE
    SYNTAX     DisplayString (SIZE(0..56))
    MAX-ACCESS read-only
    STATUS     current
    DESCRIPTION
            "-- empty --"
    ::= { lcsStatusRoutProtBgpNeighborsEntry 1 }

-- {COLUMN} 1.3.6.1.4.1.2356.11.1.93.1.1.1.2
lcsStatusRoutProtBgpNeighborsEntryPort OBJECT-TYPE
    SYNTAX     Integer32 (0..65535)
    MAX-ACCESS read-only
    STATUS     current
    DESCRIPTION
            "-- empty --"
    ::= { lcsStatusRoutProtBgpNeighborsEntry 2 }

-- {COLUMN} 1.3.6.1.4.1.2356.11.1.93.1.1.1.3
lcsStatusRoutProtBgpNeighborsEntryLoopbackAddress OBJECT-TYPE
    SYNTAX     DisplayString (SIZE(0..56))
    MAX-ACCESS read-only
    STATUS     current
    DESCRIPTION
            "-- empty --"
    ::= { lcsStatusRoutProtBgpNeighborsEntry 3 }

-- {COLUMN} 1.3.6.1.4.1.2356.11.1.93.1.1.1.4
lcsStatusRoutProtBgpNeighborsEntryRtgTag OBJECT-TYPE
    SYNTAX     Integer32 (0..65535)
    MAX-ACCESS read-only
    STATUS     current
    DESCRIPTION
            "-- empty --"
    ::= { lcsStatusRoutProtBgpNeighborsEntry 4 }

-- {COLUMN} 1.3.6.1.4.1.2356.11.1.93.1.1.1.5
lcsStatusRoutProtBgpNeighborsEntryRemoteAs OBJECT-TYPE
    SYNTAX     Integer32 (0..2147483647)
    MAX-ACCESS read-only
    STATUS     current
    DESCRIPTION
            "-- empty --"
    ::= { lcsStatusRoutProtBgpNeighborsEntry 5 }

-- {COLUMN} 1.3.6.1.4.1.2356.11.1.93.1.1.1.6
lcsStatusRoutProtBgpNeighborsEntryRouterId OBJECT-TYPE
    SYNTAX     DisplayString (SIZE(0..15))
    MAX-ACCESS read-only
    STATUS     current
    DESCRIPTION
            "-- empty --"
    ::= { lcsStatusRoutProtBgpNeighborsEntry 6 }

-- {COLUMN} 1.3.6.1.4.1.2356.11.1.93.1.1.1.7
lcsStatusRoutProtBgpNeighborsEntryState OBJECT-TYPE
    SYNTAX     INTEGER {
                  eIdle (0),
                  eConnect (1),
                  eActive (2),
                  eOpenSent (3),
                  eOpenConfirm (4),
                  eEstablished (5)
            }
    MAX-ACCESS read-only
    STATUS     current
    DESCRIPTION
            "-- empty --"
    ::= { lcsStatusRoutProtBgpNeighborsEntry 7 }

-- {COLUMN} 1.3.6.1.4.1.2356.11.1.93.1.1.1.8
lcsStatusRoutProtBgpNeighborsEntryPreviousState OBJECT-TYPE
    SYNTAX     INTEGER {
                  eIdle (0),
                  eConnect (1),
                  eActive (2),
                  eOpenSent (3),
                  eOpenConfirm (4),
                  eEstablished (5)
            }
    MAX-ACCESS read-only
    STATUS     current
    DESCRIPTION
            "-- empty --"
    ::= { lcsStatusRoutProtBgpNeighborsEntry 8 }

-- {COLUMN} 1.3.6.1.4.1.2356.11.1.93.1.1.1.9
lcsStatusRoutProtBgpNeighborsEntryLastError OBJECT-TYPE
    SYNTAX     DisplayString (SIZE(0..75))
    MAX-ACCESS read-only
    STATUS     current
    DESCRIPTION
            "-- empty --"
    ::= { lcsStatusRoutProtBgpNeighborsEntry 9 }

-- {COLUMN} 1.3.6.1.4.1.2356.11.1.93.1.1.1.10
lcsStatusRoutProtBgpNeighborsEntryEstabTransit OBJECT-TYPE
    SYNTAX     Integer32 (0..2147483647)
    MAX-ACCESS read-only
    STATUS     current
    DESCRIPTION
            "-- empty --"
    ::= { lcsStatusRoutProtBgpNeighborsEntry 10 }

-- {COLUMN} 1.3.6.1.4.1.2356.11.1.93.1.1.1.11
lcsStatusRoutProtBgpNeighborsEntryConnTime OBJECT-TYPE
    SYNTAX     DisplayString (SIZE(0..255))
    MAX-ACCESS read-only
    STATUS     current
    DESCRIPTION
            "-- empty --"
    ::= { lcsStatusRoutProtBgpNeighborsEntry 11 }

-- {COLUMN} 1.3.6.1.4.1.2356.11.1.93.1.1.1.12
lcsStatusRoutProtBgpNeighborsEntryKeepalive OBJECT-TYPE
    SYNTAX     Integer32 (0..65535)
    MAX-ACCESS read-only
    STATUS     current
    DESCRIPTION
            "-- empty --"
    ::= { lcsStatusRoutProtBgpNeighborsEntry 12 }

-- {COLUMN} 1.3.6.1.4.1.2356.11.1.93.1.1.1.13
lcsStatusRoutProtBgpNeighborsEntryHoldtime OBJECT-TYPE
    SYNTAX     Integer32 (0..65535)
    MAX-ACCESS read-only
    STATUS     current
    DESCRIPTION
            "-- empty --"
    ::= { lcsStatusRoutProtBgpNeighborsEntry 13 }

-- {COLUMN} 1.3.6.1.4.1.2356.11.1.93.1.1.1.15
lcsStatusRoutProtBgpNeighborsEntryConnTimeSnmp OBJECT-TYPE
    SYNTAX     Counter64
    MAX-ACCESS read-only
    STATUS     current
    DESCRIPTION
            "-- empty --"
    ::= { lcsStatusRoutProtBgpNeighborsEntry 15 }

-- {TABLE} 1.3.6.1.4.1.2356.11.1.93.1.2
lcsStatusRoutProtBgpMessagesTable OBJECT-TYPE
    SYNTAX     SEQUENCE OF LcsStatusRoutProtBgpMessagesEntry
    MAX-ACCESS not-accessible
    STATUS     current
    DESCRIPTION
            "-- empty --"
    ::= { lcsStatusRoutProtBgp 2 }

-- {ROW} 1.3.6.1.4.1.2356.11.1.93.1.2.1
lcsStatusRoutProtBgpMessagesEntry OBJECT-TYPE
    SYNTAX     LcsStatusRoutProtBgpMessagesEntry
    MAX-ACCESS not-accessible
    STATUS     current
    DESCRIPTION
            ""
    INDEX {
            lcsStatusRoutProtBgpMessagesEntryIpAddress,
            lcsStatusRoutProtBgpMessagesEntryPort,
            lcsStatusRoutProtBgpMessagesEntryLoopbackAddress,
            lcsStatusRoutProtBgpMessagesEntryRtgTag,
            lcsStatusRoutProtBgpMessagesEntryRemoteAs
          }
    ::= { lcsStatusRoutProtBgpMessagesTable 1 }

LcsStatusRoutProtBgpMessagesEntry ::= SEQUENCE {
            lcsStatusRoutProtBgpMessagesEntryIpAddress DisplayString,
            lcsStatusRoutProtBgpMessagesEntryPort Integer32,
            lcsStatusRoutProtBgpMessagesEntryLoopbackAddress DisplayString,
            lcsStatusRoutProtBgpMessagesEntryRtgTag Integer32,
            lcsStatusRoutProtBgpMessagesEntryRemoteAs Integer32,
            lcsStatusRoutProtBgpMessagesEntryTotalTx Integer32,
            lcsStatusRoutProtBgpMessagesEntryTotalRx Integer32,
            lcsStatusRoutProtBgpMessagesEntryOpenTx Integer32,
            lcsStatusRoutProtBgpMessagesEntryOpenRx Integer32,
            lcsStatusRoutProtBgpMessagesEntryUpdateTx Integer32,
            lcsStatusRoutProtBgpMessagesEntryUpdateRx Integer32,
            lcsStatusRoutProtBgpMessagesEntryKeepaliveTx Integer32,
            lcsStatusRoutProtBgpMessagesEntryKeepaliveRx Integer32,
            lcsStatusRoutProtBgpMessagesEntryNotifTx Integer32,
            lcsStatusRoutProtBgpMessagesEntryNotifRx Integer32,
            lcsStatusRoutProtBgpMessagesEntryRRefreshTx Integer32,
            lcsStatusRoutProtBgpMessagesEntryRRefreshRx Integer32
    }

-- {COLUMN} 1.3.6.1.4.1.2356.11.1.93.1.2.1.1
lcsStatusRoutProtBgpMessagesEntryIpAddress OBJECT-TYPE
    SYNTAX     DisplayString (SIZE(0..56))
    MAX-ACCESS read-only
    STATUS     current
    DESCRIPTION
            "-- empty --"
    ::= { lcsStatusRoutProtBgpMessagesEntry 1 }

-- {COLUMN} 1.3.6.1.4.1.2356.11.1.93.1.2.1.2
lcsStatusRoutProtBgpMessagesEntryPort OBJECT-TYPE
    SYNTAX     Integer32 (0..65535)
    MAX-ACCESS read-only
    STATUS     current
    DESCRIPTION
            "-- empty --"
    ::= { lcsStatusRoutProtBgpMessagesEntry 2 }

-- {COLUMN} 1.3.6.1.4.1.2356.11.1.93.1.2.1.3
lcsStatusRoutProtBgpMessagesEntryLoopbackAddress OBJECT-TYPE
    SYNTAX     DisplayString (SIZE(0..56))
    MAX-ACCESS read-only
    STATUS     current
    DESCRIPTION
            "-- empty --"
    ::= { lcsStatusRoutProtBgpMessagesEntry 3 }

-- {COLUMN} 1.3.6.1.4.1.2356.11.1.93.1.2.1.4
lcsStatusRoutProtBgpMessagesEntryRtgTag OBJECT-TYPE
    SYNTAX     Integer32 (0..65535)
    MAX-ACCESS read-only
    STATUS     current
    DESCRIPTION
            "-- empty --"
    ::= { lcsStatusRoutProtBgpMessagesEntry 4 }

-- {COLUMN} 1.3.6.1.4.1.2356.11.1.93.1.2.1.5
lcsStatusRoutProtBgpMessagesEntryRemoteAs OBJECT-TYPE
    SYNTAX     Integer32 (0..2147483647)
    MAX-ACCESS read-only
    STATUS     current
    DESCRIPTION
            "-- empty --"
    ::= { lcsStatusRoutProtBgpMessagesEntry 5 }

-- {COLUMN} 1.3.6.1.4.1.2356.11.1.93.1.2.1.6
lcsStatusRoutProtBgpMessagesEntryTotalTx OBJECT-TYPE
    SYNTAX     Integer32 (0..2147483647)
    MAX-ACCESS read-only
    STATUS     current
    DESCRIPTION
            "-- empty --"
    ::= { lcsStatusRoutProtBgpMessagesEntry 6 }

-- {COLUMN} 1.3.6.1.4.1.2356.11.1.93.1.2.1.7
lcsStatusRoutProtBgpMessagesEntryTotalRx OBJECT-TYPE
    SYNTAX     Integer32 (0..2147483647)
    MAX-ACCESS read-only
    STATUS     current
    DESCRIPTION
            "-- empty --"
    ::= { lcsStatusRoutProtBgpMessagesEntry 7 }

-- {COLUMN} 1.3.6.1.4.1.2356.11.1.93.1.2.1.8
lcsStatusRoutProtBgpMessagesEntryOpenTx OBJECT-TYPE
    SYNTAX     Integer32 (0..2147483647)
    MAX-ACCESS read-only
    STATUS     current
    DESCRIPTION
            "-- empty --"
    ::= { lcsStatusRoutProtBgpMessagesEntry 8 }

-- {COLUMN} 1.3.6.1.4.1.2356.11.1.93.1.2.1.9
lcsStatusRoutProtBgpMessagesEntryOpenRx OBJECT-TYPE
    SYNTAX     Integer32 (0..2147483647)
    MAX-ACCESS read-only
    STATUS     current
    DESCRIPTION
            "-- empty --"
    ::= { lcsStatusRoutProtBgpMessagesEntry 9 }

-- {COLUMN} 1.3.6.1.4.1.2356.11.1.93.1.2.1.10
lcsStatusRoutProtBgpMessagesEntryUpdateTx OBJECT-TYPE
    SYNTAX     Integer32 (0..2147483647)
    MAX-ACCESS read-only
    STATUS     current
    DESCRIPTION
            "-- empty --"
    ::= { lcsStatusRoutProtBgpMessagesEntry 10 }

-- {COLUMN} 1.3.6.1.4.1.2356.11.1.93.1.2.1.11
lcsStatusRoutProtBgpMessagesEntryUpdateRx OBJECT-TYPE
    SYNTAX     Integer32 (0..2147483647)
    MAX-ACCESS read-only
    STATUS     current
    DESCRIPTION
            "-- empty --"
    ::= { lcsStatusRoutProtBgpMessagesEntry 11 }

-- {COLUMN} 1.3.6.1.4.1.2356.11.1.93.1.2.1.12
lcsStatusRoutProtBgpMessagesEntryKeepaliveTx OBJECT-TYPE
    SYNTAX     Integer32 (0..2147483647)
    MAX-ACCESS read-only
    STATUS     current
    DESCRIPTION
            "-- empty --"
    ::= { lcsStatusRoutProtBgpMessagesEntry 12 }

-- {COLUMN} 1.3.6.1.4.1.2356.11.1.93.1.2.1.13
lcsStatusRoutProtBgpMessagesEntryKeepaliveRx OBJECT-TYPE
    SYNTAX     Integer32 (0..2147483647)
    MAX-ACCESS read-only
    STATUS     current
    DESCRIPTION
            "-- empty --"
    ::= { lcsStatusRoutProtBgpMessagesEntry 13 }

-- {COLUMN} 1.3.6.1.4.1.2356.11.1.93.1.2.1.14
lcsStatusRoutProtBgpMessagesEntryNotifTx OBJECT-TYPE
    SYNTAX     Integer32 (0..2147483647)
    MAX-ACCESS read-only
    STATUS     current
    DESCRIPTION
            "-- empty --"
    ::= { lcsStatusRoutProtBgpMessagesEntry 14 }

-- {COLUMN} 1.3.6.1.4.1.2356.11.1.93.1.2.1.15
lcsStatusRoutProtBgpMessagesEntryNotifRx OBJECT-TYPE
    SYNTAX     Integer32 (0..2147483647)
    MAX-ACCESS read-only
    STATUS     current
    DESCRIPTION
            "-- empty --"
    ::= { lcsStatusRoutProtBgpMessagesEntry 15 }

-- {COLUMN} 1.3.6.1.4.1.2356.11.1.93.1.2.1.16
lcsStatusRoutProtBgpMessagesEntryRRefreshTx OBJECT-TYPE
    SYNTAX     Integer32 (0..2147483647)
    MAX-ACCESS read-only
    STATUS     current
    DESCRIPTION
            "-- empty --"
    ::= { lcsStatusRoutProtBgpMessagesEntry 16 }

-- {COLUMN} 1.3.6.1.4.1.2356.11.1.93.1.2.1.17
lcsStatusRoutProtBgpMessagesEntryRRefreshRx OBJECT-TYPE
    SYNTAX     Integer32 (0..2147483647)
    MAX-ACCESS read-only
    STATUS     current
    DESCRIPTION
            "-- empty --"
    ::= { lcsStatusRoutProtBgpMessagesEntry 17 }

-- {TABLE} 1.3.6.1.4.1.2356.11.1.93.1.3
lcsStatusRoutProtBgpPrefixesTable OBJECT-TYPE
    SYNTAX     SEQUENCE OF LcsStatusRoutProtBgpPrefixesEntry
    MAX-ACCESS not-accessible
    STATUS     current
    DESCRIPTION
            "-- empty --"
    ::= { lcsStatusRoutProtBgp 3 }

-- {ROW} 1.3.6.1.4.1.2356.11.1.93.1.3.1
lcsStatusRoutProtBgpPrefixesEntry OBJECT-TYPE
    SYNTAX     LcsStatusRoutProtBgpPrefixesEntry
    MAX-ACCESS not-accessible
    STATUS     current
    DESCRIPTION
            ""
    INDEX {
            lcsStatusRoutProtBgpPrefixesEntryIpAddress,
            lcsStatusRoutProtBgpPrefixesEntryPort,
            lcsStatusRoutProtBgpPrefixesEntryLoopbackAddress,
            lcsStatusRoutProtBgpPrefixesEntryRtgTag,
            lcsStatusRoutProtBgpPrefixesEntryRemoteAs
          }
    ::= { lcsStatusRoutProtBgpPrefixesTable 1 }

LcsStatusRoutProtBgpPrefixesEntry ::= SEQUENCE {
            lcsStatusRoutProtBgpPrefixesEntryIpAddress DisplayString,
            lcsStatusRoutProtBgpPrefixesEntryPort Integer32,
            lcsStatusRoutProtBgpPrefixesEntryLoopbackAddress DisplayString,
            lcsStatusRoutProtBgpPrefixesEntryRtgTag Integer32,
            lcsStatusRoutProtBgpPrefixesEntryRemoteAs Integer32,
            lcsStatusRoutProtBgpPrefixesEntryCurrentTx Integer32,
            lcsStatusRoutProtBgpPrefixesEntryCurrentRx Integer32,
            lcsStatusRoutProtBgpPrefixesEntryTotalTx Integer32,
            lcsStatusRoutProtBgpPrefixesEntryTotalRx Integer32,
            lcsStatusRoutProtBgpPrefixesEntryImplWithdrTx Integer32,
            lcsStatusRoutProtBgpPrefixesEntryImplWithdrRx Integer32,
            lcsStatusRoutProtBgpPrefixesEntryExplWithdrTx Integer32,
            lcsStatusRoutProtBgpPrefixesEntryExplWithdrRx Integer32
    }

-- {COLUMN} 1.3.6.1.4.1.2356.11.1.93.1.3.1.1
lcsStatusRoutProtBgpPrefixesEntryIpAddress OBJECT-TYPE
    SYNTAX     DisplayString (SIZE(0..56))
    MAX-ACCESS read-only
    STATUS     current
    DESCRIPTION
            "-- empty --"
    ::= { lcsStatusRoutProtBgpPrefixesEntry 1 }

-- {COLUMN} 1.3.6.1.4.1.2356.11.1.93.1.3.1.2
lcsStatusRoutProtBgpPrefixesEntryPort OBJECT-TYPE
    SYNTAX     Integer32 (0..65535)
    MAX-ACCESS read-only
    STATUS     current
    DESCRIPTION
            "-- empty --"
    ::= { lcsStatusRoutProtBgpPrefixesEntry 2 }

-- {COLUMN} 1.3.6.1.4.1.2356.11.1.93.1.3.1.3
lcsStatusRoutProtBgpPrefixesEntryLoopbackAddress OBJECT-TYPE
    SYNTAX     DisplayString (SIZE(0..56))
    MAX-ACCESS read-only
    STATUS     current
    DESCRIPTION
            "-- empty --"
    ::= { lcsStatusRoutProtBgpPrefixesEntry 3 }

-- {COLUMN} 1.3.6.1.4.1.2356.11.1.93.1.3.1.4
lcsStatusRoutProtBgpPrefixesEntryRtgTag OBJECT-TYPE
    SYNTAX     Integer32 (0..65535)
    MAX-ACCESS read-only
    STATUS     current
    DESCRIPTION
            "-- empty --"
    ::= { lcsStatusRoutProtBgpPrefixesEntry 4 }

-- {COLUMN} 1.3.6.1.4.1.2356.11.1.93.1.3.1.5
lcsStatusRoutProtBgpPrefixesEntryRemoteAs OBJECT-TYPE
    SYNTAX     Integer32 (0..2147483647)
    MAX-ACCESS read-only
    STATUS     current
    DESCRIPTION
            "-- empty --"
    ::= { lcsStatusRoutProtBgpPrefixesEntry 5 }

-- {COLUMN} 1.3.6.1.4.1.2356.11.1.93.1.3.1.6
lcsStatusRoutProtBgpPrefixesEntryCurrentTx OBJECT-TYPE
    SYNTAX     Integer32 (0..2147483647)
    MAX-ACCESS read-only
    STATUS     current
    DESCRIPTION
            "-- empty --"
    ::= { lcsStatusRoutProtBgpPrefixesEntry 6 }

-- {COLUMN} 1.3.6.1.4.1.2356.11.1.93.1.3.1.7
lcsStatusRoutProtBgpPrefixesEntryCurrentRx OBJECT-TYPE
    SYNTAX     Integer32 (0..2147483647)
    MAX-ACCESS read-only
    STATUS     current
    DESCRIPTION
            "-- empty --"
    ::= { lcsStatusRoutProtBgpPrefixesEntry 7 }

-- {COLUMN} 1.3.6.1.4.1.2356.11.1.93.1.3.1.8
lcsStatusRoutProtBgpPrefixesEntryTotalTx OBJECT-TYPE
    SYNTAX     Integer32 (0..2147483647)
    MAX-ACCESS read-only
    STATUS     current
    DESCRIPTION
            "-- empty --"
    ::= { lcsStatusRoutProtBgpPrefixesEntry 8 }

-- {COLUMN} 1.3.6.1.4.1.2356.11.1.93.1.3.1.9
lcsStatusRoutProtBgpPrefixesEntryTotalRx OBJECT-TYPE
    SYNTAX     Integer32 (0..2147483647)
    MAX-ACCESS read-only
    STATUS     current
    DESCRIPTION
            "-- empty --"
    ::= { lcsStatusRoutProtBgpPrefixesEntry 9 }

-- {COLUMN} 1.3.6.1.4.1.2356.11.1.93.1.3.1.10
lcsStatusRoutProtBgpPrefixesEntryImplWithdrTx OBJECT-TYPE
    SYNTAX     Integer32 (0..2147483647)
    MAX-ACCESS read-only
    STATUS     current
    DESCRIPTION
            "-- empty --"
    ::= { lcsStatusRoutProtBgpPrefixesEntry 10 }

-- {COLUMN} 1.3.6.1.4.1.2356.11.1.93.1.3.1.11
lcsStatusRoutProtBgpPrefixesEntryImplWithdrRx OBJECT-TYPE
    SYNTAX     Integer32 (0..2147483647)
    MAX-ACCESS read-only
    STATUS     current
    DESCRIPTION
            "-- empty --"
    ::= { lcsStatusRoutProtBgpPrefixesEntry 11 }

-- {COLUMN} 1.3.6.1.4.1.2356.11.1.93.1.3.1.12
lcsStatusRoutProtBgpPrefixesEntryExplWithdrTx OBJECT-TYPE
    SYNTAX     Integer32 (0..2147483647)
    MAX-ACCESS read-only
    STATUS     current
    DESCRIPTION
            "-- empty --"
    ::= { lcsStatusRoutProtBgpPrefixesEntry 12 }

-- {COLUMN} 1.3.6.1.4.1.2356.11.1.93.1.3.1.13
lcsStatusRoutProtBgpPrefixesEntryExplWithdrRx OBJECT-TYPE
    SYNTAX     Integer32 (0..2147483647)
    MAX-ACCESS read-only
    STATUS     current
    DESCRIPTION
            "-- empty --"
    ::= { lcsStatusRoutProtBgpPrefixesEntry 13 }

-- {TABLE} 1.3.6.1.4.1.2356.11.1.93.1.4
lcsStatusRoutProtBgpPoliciesTable OBJECT-TYPE
    SYNTAX     SEQUENCE OF LcsStatusRoutProtBgpPoliciesEntry
    MAX-ACCESS not-accessible
    STATUS     current
    DESCRIPTION
            "-- empty --"
    ::= { lcsStatusRoutProtBgp 4 }

-- {ROW} 1.3.6.1.4.1.2356.11.1.93.1.4.1
lcsStatusRoutProtBgpPoliciesEntry OBJECT-TYPE
    SYNTAX     LcsStatusRoutProtBgpPoliciesEntry
    MAX-ACCESS not-accessible
    STATUS     current
    DESCRIPTION
            ""
    INDEX {
            lcsStatusRoutProtBgpPoliciesEntryIpAddress,
            lcsStatusRoutProtBgpPoliciesEntryPort,
            lcsStatusRoutProtBgpPoliciesEntryLoopbackAddress,
            lcsStatusRoutProtBgpPoliciesEntryRtgTag,
            lcsStatusRoutProtBgpPoliciesEntryRemoteAs
          }
    ::= { lcsStatusRoutProtBgpPoliciesTable 1 }

LcsStatusRoutProtBgpPoliciesEntry ::= SEQUENCE {
            lcsStatusRoutProtBgpPoliciesEntryIpAddress DisplayString,
            lcsStatusRoutProtBgpPoliciesEntryPort Integer32,
            lcsStatusRoutProtBgpPoliciesEntryLoopbackAddress DisplayString,
            lcsStatusRoutProtBgpPoliciesEntryRtgTag Integer32,
            lcsStatusRoutProtBgpPoliciesEntryRemoteAs Integer32,
            lcsStatusRoutProtBgpPoliciesEntryAcceptedPrfxTx Integer32,
            lcsStatusRoutProtBgpPoliciesEntryAcceptedPrfxRx Integer32,
            lcsStatusRoutProtBgpPoliciesEntryRejectedPrfxTx Integer32,
            lcsStatusRoutProtBgpPoliciesEntryRejectedPrfxRx Integer32
    }

-- {COLUMN} 1.3.6.1.4.1.2356.11.1.93.1.4.1.1
lcsStatusRoutProtBgpPoliciesEntryIpAddress OBJECT-TYPE
    SYNTAX     DisplayString (SIZE(0..56))
    MAX-ACCESS read-only
    STATUS     current
    DESCRIPTION
            "-- empty --"
    ::= { lcsStatusRoutProtBgpPoliciesEntry 1 }

-- {COLUMN} 1.3.6.1.4.1.2356.11.1.93.1.4.1.2
lcsStatusRoutProtBgpPoliciesEntryPort OBJECT-TYPE
    SYNTAX     Integer32 (0..65535)
    MAX-ACCESS read-only
    STATUS     current
    DESCRIPTION
            "-- empty --"
    ::= { lcsStatusRoutProtBgpPoliciesEntry 2 }

-- {COLUMN} 1.3.6.1.4.1.2356.11.1.93.1.4.1.3
lcsStatusRoutProtBgpPoliciesEntryLoopbackAddress OBJECT-TYPE
    SYNTAX     DisplayString (SIZE(0..56))
    MAX-ACCESS read-only
    STATUS     current
    DESCRIPTION
            "-- empty --"
    ::= { lcsStatusRoutProtBgpPoliciesEntry 3 }

-- {COLUMN} 1.3.6.1.4.1.2356.11.1.93.1.4.1.4
lcsStatusRoutProtBgpPoliciesEntryRtgTag OBJECT-TYPE
    SYNTAX     Integer32 (0..65535)
    MAX-ACCESS read-only
    STATUS     current
    DESCRIPTION
            "-- empty --"
    ::= { lcsStatusRoutProtBgpPoliciesEntry 4 }

-- {COLUMN} 1.3.6.1.4.1.2356.11.1.93.1.4.1.5
lcsStatusRoutProtBgpPoliciesEntryRemoteAs OBJECT-TYPE
    SYNTAX     Integer32 (0..2147483647)
    MAX-ACCESS read-only
    STATUS     current
    DESCRIPTION
            "-- empty --"
    ::= { lcsStatusRoutProtBgpPoliciesEntry 5 }

-- {COLUMN} 1.3.6.1.4.1.2356.11.1.93.1.4.1.6
lcsStatusRoutProtBgpPoliciesEntryAcceptedPrfxTx OBJECT-TYPE
    SYNTAX     Integer32 (0..2147483647)
    MAX-ACCESS read-only
    STATUS     current
    DESCRIPTION
            "-- empty --"
    ::= { lcsStatusRoutProtBgpPoliciesEntry 6 }

-- {COLUMN} 1.3.6.1.4.1.2356.11.1.93.1.4.1.7
lcsStatusRoutProtBgpPoliciesEntryAcceptedPrfxRx OBJECT-TYPE
    SYNTAX     Integer32 (0..2147483647)
    MAX-ACCESS read-only
    STATUS     current
    DESCRIPTION
            "-- empty --"
    ::= { lcsStatusRoutProtBgpPoliciesEntry 7 }

-- {COLUMN} 1.3.6.1.4.1.2356.11.1.93.1.4.1.8
lcsStatusRoutProtBgpPoliciesEntryRejectedPrfxTx OBJECT-TYPE
    SYNTAX     Integer32 (0..2147483647)
    MAX-ACCESS read-only
    STATUS     current
    DESCRIPTION
            "-- empty --"
    ::= { lcsStatusRoutProtBgpPoliciesEntry 8 }

-- {COLUMN} 1.3.6.1.4.1.2356.11.1.93.1.4.1.9
lcsStatusRoutProtBgpPoliciesEntryRejectedPrfxRx OBJECT-TYPE
    SYNTAX     Integer32 (0..2147483647)
    MAX-ACCESS read-only
    STATUS     current
    DESCRIPTION
            "-- empty --"
    ::= { lcsStatusRoutProtBgpPoliciesEntry 9 }

-- {SCALAR} 1.3.6.1.4.1.2356.11.1.93.1.5
lcsStatusRoutProtBgpNumConnections OBJECT-TYPE
    SYNTAX     Integer32 (0..2147483647)
    MAX-ACCESS read-only
    STATUS     current
    DESCRIPTION
            "-- empty --"
    ::= { lcsStatusRoutProtBgp 5 }

-- {NODE} 1.3.6.1.4.1.2356.11.1.93.2
lcsStatusRoutProtRouteMonitor OBJECT IDENTIFIER ::= { lcsStatusRoutProt 2 }

-- {TABLE} 1.3.6.1.4.1.2356.11.1.93.2.1
lcsStatusRoutProtRouteMonitorMonitorTableTable OBJECT-TYPE
    SYNTAX     SEQUENCE OF LcsStatusRoutProtRouteMonitorMonitorTableEntry
    MAX-ACCESS not-accessible
    STATUS     current
    DESCRIPTION
            "-- empty --"
    ::= { lcsStatusRoutProtRouteMonitor 1 }

-- {ROW} 1.3.6.1.4.1.2356.11.1.93.2.1.1
lcsStatusRoutProtRouteMonitorMonitorTableEntry OBJECT-TYPE
    SYNTAX     LcsStatusRoutProtRouteMonitorMonitorTableEntry
    MAX-ACCESS not-accessible
    STATUS     current
    DESCRIPTION
            ""
    INDEX {
            lcsStatusRoutProtRouteMonitorMonitorTableEntryBackupPeer,
            lcsStatusRoutProtRouteMonitorMonitorTableEntryPrefix,
            lcsStatusRoutProtRouteMonitorMonitorTableEntryRtgTag
          }
    ::= { lcsStatusRoutProtRouteMonitorMonitorTableTable 1 }

LcsStatusRoutProtRouteMonitorMonitorTableEntry ::= SEQUENCE {
            lcsStatusRoutProtRouteMonitorMonitorTableEntryBackupPeer DisplayString,
            lcsStatusRoutProtRouteMonitorMonitorTableEntryPrefix DisplayString,
            lcsStatusRoutProtRouteMonitorMonitorTableEntryRtgTag Integer32,
            lcsStatusRoutProtRouteMonitorMonitorTableEntryPrefixState INTEGER,
            lcsStatusRoutProtRouteMonitorMonitorTableEntryBackupState INTEGER,
            lcsStatusRoutProtRouteMonitorMonitorTableEntryPeerState INTEGER
    }

-- {COLUMN} 1.3.6.1.4.1.2356.11.1.93.2.1.1.1
lcsStatusRoutProtRouteMonitorMonitorTableEntryBackupPeer OBJECT-TYPE
    SYNTAX     DisplayString (SIZE(0..255))
    MAX-ACCESS read-only
    STATUS     current
    DESCRIPTION
            "-- empty --"
    ::= { lcsStatusRoutProtRouteMonitorMonitorTableEntry 1 }

-- {COLUMN} 1.3.6.1.4.1.2356.11.1.93.2.1.1.2
lcsStatusRoutProtRouteMonitorMonitorTableEntryPrefix OBJECT-TYPE
    SYNTAX     DisplayString (SIZE(0..255))
    MAX-ACCESS read-only
    STATUS     current
    DESCRIPTION
            "-- empty --"
    ::= { lcsStatusRoutProtRouteMonitorMonitorTableEntry 2 }

-- {COLUMN} 1.3.6.1.4.1.2356.11.1.93.2.1.1.3
lcsStatusRoutProtRouteMonitorMonitorTableEntryRtgTag OBJECT-TYPE
    SYNTAX     Integer32 (0..65535)
    MAX-ACCESS read-only
    STATUS     current
    DESCRIPTION
            "-- empty --"
    ::= { lcsStatusRoutProtRouteMonitorMonitorTableEntry 3 }

-- {COLUMN} 1.3.6.1.4.1.2356.11.1.93.2.1.1.4
lcsStatusRoutProtRouteMonitorMonitorTableEntryPrefixState OBJECT-TYPE
    SYNTAX     INTEGER {
                  eUnavailable (0),
                  eAvailable (1),
                  eUnknown (2)
            }
    MAX-ACCESS read-only
    STATUS     current
    DESCRIPTION
            "-- empty --"
    ::= { lcsStatusRoutProtRouteMonitorMonitorTableEntry 4 }

-- {COLUMN} 1.3.6.1.4.1.2356.11.1.93.2.1.1.5
lcsStatusRoutProtRouteMonitorMonitorTableEntryBackupState OBJECT-TYPE
    SYNTAX     INTEGER {
                  eUnknown (0),
                  eDown (1),
                  eUp (2),
                  eWaitUp (3),
                  eWaitDown (4),
                  eInitialized (5)
            }
    MAX-ACCESS read-only
    STATUS     current
    DESCRIPTION
            "-- empty --"
    ::= { lcsStatusRoutProtRouteMonitorMonitorTableEntry 5 }

-- {COLUMN} 1.3.6.1.4.1.2356.11.1.93.2.1.1.6
lcsStatusRoutProtRouteMonitorMonitorTableEntryPeerState OBJECT-TYPE
    SYNTAX     INTEGER {
                  eDisconnectedUnknown (0),
                  eConnected (1)
            }
    MAX-ACCESS read-only
    STATUS     current
    DESCRIPTION
            "-- empty --"
    ::= { lcsStatusRoutProtRouteMonitorMonitorTableEntry 6 }

-- {NODE} 1.3.6.1.4.1.2356.11.1.93.3
lcsStatusRoutProtOspf OBJECT IDENTIFIER ::= { lcsStatusRoutProt 3 }

-- {TABLE} 1.3.6.1.4.1.2356.11.1.93.3.1
lcsStatusRoutProtOspfGeneralTable OBJECT-TYPE
    SYNTAX     SEQUENCE OF LcsStatusRoutProtOspfGeneralEntry
    MAX-ACCESS not-accessible
    STATUS     current
    DESCRIPTION
            "-- empty --"
    ::= { lcsStatusRoutProtOspf 1 }

-- {ROW} 1.3.6.1.4.1.2356.11.1.93.3.1.1
lcsStatusRoutProtOspfGeneralEntry OBJECT-TYPE
    SYNTAX     LcsStatusRoutProtOspfGeneralEntry
    MAX-ACCESS not-accessible
    STATUS     current
    DESCRIPTION
            ""
    INDEX {
            lcsStatusRoutProtOspfGeneralEntryOspfInstance
          }
    ::= { lcsStatusRoutProtOspfGeneralTable 1 }

LcsStatusRoutProtOspfGeneralEntry ::= SEQUENCE {
            lcsStatusRoutProtOspfGeneralEntryRouterId IpAddress,
            lcsStatusRoutProtOspfGeneralEntryOperating INTEGER,
            lcsStatusRoutProtOspfGeneralEntryVersion INTEGER,
            lcsStatusRoutProtOspfGeneralEntryAreaBorderRouter INTEGER,
            lcsStatusRoutProtOspfGeneralEntryAsBorderRouter INTEGER,
            lcsStatusRoutProtOspfGeneralEntryExtLsaCount Integer32,
            lcsStatusRoutProtOspfGeneralEntryExtLsaChecksum Integer32,
            lcsStatusRoutProtOspfGeneralEntryTosSupport Integer32,
            lcsStatusRoutProtOspfGeneralEntryLsasOriginated Integer32,
            lcsStatusRoutProtOspfGeneralEntryLsasReceived Integer32,
            lcsStatusRoutProtOspfGeneralEntryExtLsdbLimit Integer32,
            lcsStatusRoutProtOspfGeneralEntryMulticastExtensions Integer32,
            lcsStatusRoutProtOspfGeneralEntryExitOverflowInterval Integer32,
            lcsStatusRoutProtOspfGeneralEntryDemandRoutingExtensions Integer32,
            lcsStatusRoutProtOspfGeneralEntryOspfInstance DisplayString,
            lcsStatusRoutProtOspfGeneralEntryRtgTag Integer32
    }

-- {COLUMN} 1.3.6.1.4.1.2356.11.1.93.3.1.1.1
lcsStatusRoutProtOspfGeneralEntryRouterId OBJECT-TYPE
    SYNTAX     IpAddress
    MAX-ACCESS read-only
    STATUS     current
    DESCRIPTION
            "-- empty --"
    ::= { lcsStatusRoutProtOspfGeneralEntry 1 }

-- {COLUMN} 1.3.6.1.4.1.2356.11.1.93.3.1.1.2
lcsStatusRoutProtOspfGeneralEntryOperating OBJECT-TYPE
    SYNTAX     INTEGER {
                  eNo (0),
                  eYes (1)
            }
    MAX-ACCESS read-only
    STATUS     current
    DESCRIPTION
            "-- empty --"
    ::= { lcsStatusRoutProtOspfGeneralEntry 2 }

-- {COLUMN} 1.3.6.1.4.1.2356.11.1.93.3.1.1.3
lcsStatusRoutProtOspfGeneralEntryVersion OBJECT-TYPE
    SYNTAX     INTEGER {
                  e2 (2),
                  e3 (3)
            }
    MAX-ACCESS read-only
    STATUS     current
    DESCRIPTION
            "-- empty --"
    ::= { lcsStatusRoutProtOspfGeneralEntry 3 }

-- {COLUMN} 1.3.6.1.4.1.2356.11.1.93.3.1.1.4
lcsStatusRoutProtOspfGeneralEntryAreaBorderRouter OBJECT-TYPE
    SYNTAX     INTEGER {
                  eNo (0),
                  eYes (1)
            }
    MAX-ACCESS read-only
    STATUS     current
    DESCRIPTION
            "-- empty --"
    ::= { lcsStatusRoutProtOspfGeneralEntry 4 }

-- {COLUMN} 1.3.6.1.4.1.2356.11.1.93.3.1.1.5
lcsStatusRoutProtOspfGeneralEntryAsBorderRouter OBJECT-TYPE
    SYNTAX     INTEGER {
                  eNo (0),
                  eYes (1)
            }
    MAX-ACCESS read-only
    STATUS     current
    DESCRIPTION
            "-- empty --"
    ::= { lcsStatusRoutProtOspfGeneralEntry 5 }

-- {COLUMN} 1.3.6.1.4.1.2356.11.1.93.3.1.1.6
lcsStatusRoutProtOspfGeneralEntryExtLsaCount OBJECT-TYPE
    SYNTAX     Integer32 (0..2147483647)
    MAX-ACCESS read-only
    STATUS     current
    DESCRIPTION
            "-- empty --"
    ::= { lcsStatusRoutProtOspfGeneralEntry 6 }

-- {COLUMN} 1.3.6.1.4.1.2356.11.1.93.3.1.1.7
lcsStatusRoutProtOspfGeneralEntryExtLsaChecksum OBJECT-TYPE
    SYNTAX     Integer32 (0..2147483647)
    MAX-ACCESS read-only
    STATUS     current
    DESCRIPTION
            "-- empty --"
    ::= { lcsStatusRoutProtOspfGeneralEntry 7 }

-- {COLUMN} 1.3.6.1.4.1.2356.11.1.93.3.1.1.8
lcsStatusRoutProtOspfGeneralEntryTosSupport OBJECT-TYPE
    SYNTAX     Integer32 (0..255)
    MAX-ACCESS read-only
    STATUS     current
    DESCRIPTION
            "-- empty --"
    ::= { lcsStatusRoutProtOspfGeneralEntry 8 }

-- {COLUMN} 1.3.6.1.4.1.2356.11.1.93.3.1.1.9
lcsStatusRoutProtOspfGeneralEntryLsasOriginated OBJECT-TYPE
    SYNTAX     Integer32 (0..2147483647)
    MAX-ACCESS read-only
    STATUS     current
    DESCRIPTION
            "-- empty --"
    ::= { lcsStatusRoutProtOspfGeneralEntry 9 }

-- {COLUMN} 1.3.6.1.4.1.2356.11.1.93.3.1.1.10
lcsStatusRoutProtOspfGeneralEntryLsasReceived OBJECT-TYPE
    SYNTAX     Integer32 (0..2147483647)
    MAX-ACCESS read-only
    STATUS     current
    DESCRIPTION
            "-- empty --"
    ::= { lcsStatusRoutProtOspfGeneralEntry 10 }

-- {COLUMN} 1.3.6.1.4.1.2356.11.1.93.3.1.1.11
lcsStatusRoutProtOspfGeneralEntryExtLsdbLimit OBJECT-TYPE
    SYNTAX     Integer32 (-2147483648..2147483647)
    MAX-ACCESS read-only
    STATUS     current
    DESCRIPTION
            "-- empty --"
    ::= { lcsStatusRoutProtOspfGeneralEntry 11 }

-- {COLUMN} 1.3.6.1.4.1.2356.11.1.93.3.1.1.12
lcsStatusRoutProtOspfGeneralEntryMulticastExtensions OBJECT-TYPE
    SYNTAX     Integer32 (0..2147483647)
    MAX-ACCESS read-only
    STATUS     current
    DESCRIPTION
            "-- empty --"
    ::= { lcsStatusRoutProtOspfGeneralEntry 12 }

-- {COLUMN} 1.3.6.1.4.1.2356.11.1.93.3.1.1.13
lcsStatusRoutProtOspfGeneralEntryExitOverflowInterval OBJECT-TYPE
    SYNTAX     Integer32 (0..2147483647)
    MAX-ACCESS read-only
    STATUS     current
    DESCRIPTION
            "-- empty --"
    ::= { lcsStatusRoutProtOspfGeneralEntry 13 }

-- {COLUMN} 1.3.6.1.4.1.2356.11.1.93.3.1.1.14
lcsStatusRoutProtOspfGeneralEntryDemandRoutingExtensions OBJECT-TYPE
    SYNTAX     Integer32 (0..2147483647)
    MAX-ACCESS read-only
    STATUS     current
    DESCRIPTION
            "-- empty --"
    ::= { lcsStatusRoutProtOspfGeneralEntry 14 }

-- {COLUMN} 1.3.6.1.4.1.2356.11.1.93.3.1.1.200
lcsStatusRoutProtOspfGeneralEntryOspfInstance OBJECT-TYPE
    SYNTAX     DisplayString (SIZE(0..16))
    MAX-ACCESS read-only
    STATUS     current
    DESCRIPTION
            "-- empty --"
    ::= { lcsStatusRoutProtOspfGeneralEntry 200 }

-- {COLUMN} 1.3.6.1.4.1.2356.11.1.93.3.1.1.201
lcsStatusRoutProtOspfGeneralEntryRtgTag OBJECT-TYPE
    SYNTAX     Integer32 (0..65535)
    MAX-ACCESS read-only
    STATUS     current
    DESCRIPTION
            "-- empty --"
    ::= { lcsStatusRoutProtOspfGeneralEntry 201 }

-- {TABLE} 1.3.6.1.4.1.2356.11.1.93.3.2
lcsStatusRoutProtOspfAreaTableTable OBJECT-TYPE
    SYNTAX     SEQUENCE OF LcsStatusRoutProtOspfAreaTableEntry
    MAX-ACCESS not-accessible
    STATUS     current
    DESCRIPTION
            "-- empty --"
    ::= { lcsStatusRoutProtOspf 2 }

-- {ROW} 1.3.6.1.4.1.2356.11.1.93.3.2.1
lcsStatusRoutProtOspfAreaTableEntry OBJECT-TYPE
    SYNTAX     LcsStatusRoutProtOspfAreaTableEntry
    MAX-ACCESS not-accessible
    STATUS     current
    DESCRIPTION
            ""
    INDEX {
            lcsStatusRoutProtOspfAreaTableEntryOspfInstance,
            lcsStatusRoutProtOspfAreaTableEntryAreaId
          }
    ::= { lcsStatusRoutProtOspfAreaTableTable 1 }

LcsStatusRoutProtOspfAreaTableEntry ::= SEQUENCE {
            lcsStatusRoutProtOspfAreaTableEntryAreaId IpAddress,
            lcsStatusRoutProtOspfAreaTableEntryImportAsExternal INTEGER,
            lcsStatusRoutProtOspfAreaTableEntrySpfRuns Integer32,
            lcsStatusRoutProtOspfAreaTableEntryAbrCount Integer32,
            lcsStatusRoutProtOspfAreaTableEntryAsbrCount Integer32,
            lcsStatusRoutProtOspfAreaTableEntryLsaCount Integer32,
            lcsStatusRoutProtOspfAreaTableEntryLsaChecksum Integer32,
            lcsStatusRoutProtOspfAreaTableEntrySendSummaryLsa INTEGER,
            lcsStatusRoutProtOspfAreaTableEntryOspfInstance DisplayString
    }

-- {COLUMN} 1.3.6.1.4.1.2356.11.1.93.3.2.1.1
lcsStatusRoutProtOspfAreaTableEntryAreaId OBJECT-TYPE
    SYNTAX     IpAddress
    MAX-ACCESS read-only
    STATUS     current
    DESCRIPTION
            "-- empty --"
    ::= { lcsStatusRoutProtOspfAreaTableEntry 1 }

-- {COLUMN} 1.3.6.1.4.1.2356.11.1.93.3.2.1.3
lcsStatusRoutProtOspfAreaTableEntryImportAsExternal OBJECT-TYPE
    SYNTAX     INTEGER {
                  eExternal (1),
                  eNoExternal (2),
                  eNssa (3)
            }
    MAX-ACCESS read-only
    STATUS     current
    DESCRIPTION
            "-- empty --"
    ::= { lcsStatusRoutProtOspfAreaTableEntry 3 }

-- {COLUMN} 1.3.6.1.4.1.2356.11.1.93.3.2.1.4
lcsStatusRoutProtOspfAreaTableEntrySpfRuns OBJECT-TYPE
    SYNTAX     Integer32 (0..2147483647)
    MAX-ACCESS read-only
    STATUS     current
    DESCRIPTION
            "-- empty --"
    ::= { lcsStatusRoutProtOspfAreaTableEntry 4 }

-- {COLUMN} 1.3.6.1.4.1.2356.11.1.93.3.2.1.5
lcsStatusRoutProtOspfAreaTableEntryAbrCount OBJECT-TYPE
    SYNTAX     Integer32 (0..2147483647)
    MAX-ACCESS read-only
    STATUS     current
    DESCRIPTION
            "-- empty --"
    ::= { lcsStatusRoutProtOspfAreaTableEntry 5 }

-- {COLUMN} 1.3.6.1.4.1.2356.11.1.93.3.2.1.6
lcsStatusRoutProtOspfAreaTableEntryAsbrCount OBJECT-TYPE
    SYNTAX     Integer32 (0..2147483647)
    MAX-ACCESS read-only
    STATUS     current
    DESCRIPTION
            "-- empty --"
    ::= { lcsStatusRoutProtOspfAreaTableEntry 6 }

-- {COLUMN} 1.3.6.1.4.1.2356.11.1.93.3.2.1.7
lcsStatusRoutProtOspfAreaTableEntryLsaCount OBJECT-TYPE
    SYNTAX     Integer32 (0..2147483647)
    MAX-ACCESS read-only
    STATUS     current
    DESCRIPTION
            "-- empty --"
    ::= { lcsStatusRoutProtOspfAreaTableEntry 7 }

-- {COLUMN} 1.3.6.1.4.1.2356.11.1.93.3.2.1.8
lcsStatusRoutProtOspfAreaTableEntryLsaChecksum OBJECT-TYPE
    SYNTAX     Integer32 (0..2147483647)
    MAX-ACCESS read-only
    STATUS     current
    DESCRIPTION
            "-- empty --"
    ::= { lcsStatusRoutProtOspfAreaTableEntry 8 }

-- {COLUMN} 1.3.6.1.4.1.2356.11.1.93.3.2.1.9
lcsStatusRoutProtOspfAreaTableEntrySendSummaryLsa OBJECT-TYPE
    SYNTAX     INTEGER {
                  eNo (0),
                  eYes (1)
            }
    MAX-ACCESS read-only
    STATUS     current
    DESCRIPTION
            "-- empty --"
    ::= { lcsStatusRoutProtOspfAreaTableEntry 9 }

-- {COLUMN} 1.3.6.1.4.1.2356.11.1.93.3.2.1.200
lcsStatusRoutProtOspfAreaTableEntryOspfInstance OBJECT-TYPE
    SYNTAX     DisplayString (SIZE(0..16))
    MAX-ACCESS read-only
    STATUS     current
    DESCRIPTION
            "-- empty --"
    ::= { lcsStatusRoutProtOspfAreaTableEntry 200 }

-- {TABLE} 1.3.6.1.4.1.2356.11.1.93.3.4
lcsStatusRoutProtOspfLinkStateDbTableTable OBJECT-TYPE
    SYNTAX     SEQUENCE OF LcsStatusRoutProtOspfLinkStateDbTableEntry
    MAX-ACCESS not-accessible
    STATUS     current
    DESCRIPTION
            "-- empty --"
    ::= { lcsStatusRoutProtOspf 4 }

-- {ROW} 1.3.6.1.4.1.2356.11.1.93.3.4.1
lcsStatusRoutProtOspfLinkStateDbTableEntry OBJECT-TYPE
    SYNTAX     LcsStatusRoutProtOspfLinkStateDbTableEntry
    MAX-ACCESS not-accessible
    STATUS     current
    DESCRIPTION
            ""
    INDEX {
            lcsStatusRoutProtOspfLinkStateDbTableEntryOspfInstance,
            lcsStatusRoutProtOspfLinkStateDbTableEntryAreaId,
            lcsStatusRoutProtOspfLinkStateDbTableEntryLsaType,
            lcsStatusRoutProtOspfLinkStateDbTableEntryLsId,
            lcsStatusRoutProtOspfLinkStateDbTableEntryRouterId
          }
    ::= { lcsStatusRoutProtOspfLinkStateDbTableTable 1 }

LcsStatusRoutProtOspfLinkStateDbTableEntry ::= SEQUENCE {
            lcsStatusRoutProtOspfLinkStateDbTableEntryAreaId IpAddress,
            lcsStatusRoutProtOspfLinkStateDbTableEntryLsaType INTEGER,
            lcsStatusRoutProtOspfLinkStateDbTableEntryLsId IpAddress,
            lcsStatusRoutProtOspfLinkStateDbTableEntryRouterId IpAddress,
            lcsStatusRoutProtOspfLinkStateDbTableEntrySequenceNumber Integer32,
            lcsStatusRoutProtOspfLinkStateDbTableEntryLsaAge Integer32,
            lcsStatusRoutProtOspfLinkStateDbTableEntryLsaChecksum Integer32,
            lcsStatusRoutProtOspfLinkStateDbTableEntryOspfInstance DisplayString
    }

-- {COLUMN} 1.3.6.1.4.1.2356.11.1.93.3.4.1.1
lcsStatusRoutProtOspfLinkStateDbTableEntryAreaId OBJECT-TYPE
    SYNTAX     IpAddress
    MAX-ACCESS read-only
    STATUS     current
    DESCRIPTION
            "-- empty --"
    ::= { lcsStatusRoutProtOspfLinkStateDbTableEntry 1 }

-- {COLUMN} 1.3.6.1.4.1.2356.11.1.93.3.4.1.2
lcsStatusRoutProtOspfLinkStateDbTableEntryLsaType OBJECT-TYPE
    SYNTAX     INTEGER {
                  eRouterLink (1),
                  eNetworkLink (2),
                  eSummaryLink (3),
                  eAsSummaryLink (4),
                  eAsExtenalLink (5)
            }
    MAX-ACCESS read-only
    STATUS     current
    DESCRIPTION
            "-- empty --"
    ::= { lcsStatusRoutProtOspfLinkStateDbTableEntry 2 }

-- {COLUMN} 1.3.6.1.4.1.2356.11.1.93.3.4.1.3
lcsStatusRoutProtOspfLinkStateDbTableEntryLsId OBJECT-TYPE
    SYNTAX     IpAddress
    MAX-ACCESS read-only
    STATUS     current
    DESCRIPTION
            "-- empty --"
    ::= { lcsStatusRoutProtOspfLinkStateDbTableEntry 3 }

-- {COLUMN} 1.3.6.1.4.1.2356.11.1.93.3.4.1.4
lcsStatusRoutProtOspfLinkStateDbTableEntryRouterId OBJECT-TYPE
    SYNTAX     IpAddress
    MAX-ACCESS read-only
    STATUS     current
    DESCRIPTION
            "-- empty --"
    ::= { lcsStatusRoutProtOspfLinkStateDbTableEntry 4 }

-- {COLUMN} 1.3.6.1.4.1.2356.11.1.93.3.4.1.5
lcsStatusRoutProtOspfLinkStateDbTableEntrySequenceNumber OBJECT-TYPE
    SYNTAX     Integer32 (0..2147483647)
    MAX-ACCESS read-only
    STATUS     current
    DESCRIPTION
            "-- empty --"
    ::= { lcsStatusRoutProtOspfLinkStateDbTableEntry 5 }

-- {COLUMN} 1.3.6.1.4.1.2356.11.1.93.3.4.1.6
lcsStatusRoutProtOspfLinkStateDbTableEntryLsaAge OBJECT-TYPE
    SYNTAX     Integer32 (0..2147483647)
    MAX-ACCESS read-only
    STATUS     current
    DESCRIPTION
            "-- empty --"
    ::= { lcsStatusRoutProtOspfLinkStateDbTableEntry 6 }

-- {COLUMN} 1.3.6.1.4.1.2356.11.1.93.3.4.1.7
lcsStatusRoutProtOspfLinkStateDbTableEntryLsaChecksum OBJECT-TYPE
    SYNTAX     Integer32 (0..2147483647)
    MAX-ACCESS read-only
    STATUS     current
    DESCRIPTION
            "-- empty --"
    ::= { lcsStatusRoutProtOspfLinkStateDbTableEntry 7 }

-- {COLUMN} 1.3.6.1.4.1.2356.11.1.93.3.4.1.200
lcsStatusRoutProtOspfLinkStateDbTableEntryOspfInstance OBJECT-TYPE
    SYNTAX     DisplayString (SIZE(0..16))
    MAX-ACCESS read-only
    STATUS     current
    DESCRIPTION
            "-- empty --"
    ::= { lcsStatusRoutProtOspfLinkStateDbTableEntry 200 }

-- {TABLE} 1.3.6.1.4.1.2356.11.1.93.3.7
lcsStatusRoutProtOspfInterfaceTableTable OBJECT-TYPE
    SYNTAX     SEQUENCE OF LcsStatusRoutProtOspfInterfaceTableEntry
    MAX-ACCESS not-accessible
    STATUS     current
    DESCRIPTION
            "-- empty --"
    ::= { lcsStatusRoutProtOspf 7 }

-- {ROW} 1.3.6.1.4.1.2356.11.1.93.3.7.1
lcsStatusRoutProtOspfInterfaceTableEntry OBJECT-TYPE
    SYNTAX     LcsStatusRoutProtOspfInterfaceTableEntry
    MAX-ACCESS not-accessible
    STATUS     current
    DESCRIPTION
            ""
    INDEX {
            lcsStatusRoutProtOspfInterfaceTableEntryOspfInstance,
            lcsStatusRoutProtOspfInterfaceTableEntryInterface
          }
    ::= { lcsStatusRoutProtOspfInterfaceTableTable 1 }

LcsStatusRoutProtOspfInterfaceTableEntry ::= SEQUENCE {
            lcsStatusRoutProtOspfInterfaceTableEntryIpAddress IpAddress,
            lcsStatusRoutProtOspfInterfaceTableEntryIndex Integer32,
            lcsStatusRoutProtOspfInterfaceTableEntryAreaId IpAddress,
            lcsStatusRoutProtOspfInterfaceTableEntryType INTEGER,
            lcsStatusRoutProtOspfInterfaceTableEntryOperating INTEGER,
            lcsStatusRoutProtOspfInterfaceTableEntryRouterPriority Integer32,
            lcsStatusRoutProtOspfInterfaceTableEntryInfTransDelay Integer32,
            lcsStatusRoutProtOspfInterfaceTableEntryRxmtInterval Integer32,
            lcsStatusRoutProtOspfInterfaceTableEntryHelloInterval Integer32,
            lcsStatusRoutProtOspfInterfaceTableEntryRouterDeadInterval Integer32,
            lcsStatusRoutProtOspfInterfaceTableEntryPollInterval Integer32,
            lcsStatusRoutProtOspfInterfaceTableEntryState INTEGER,
            lcsStatusRoutProtOspfInterfaceTableEntryDrIp IpAddress,
            lcsStatusRoutProtOspfInterfaceTableEntryBdrIp IpAddress,
            lcsStatusRoutProtOspfInterfaceTableEntryEvents Integer32,
            lcsStatusRoutProtOspfInterfaceTableEntryAuthenticationKey DisplayString,
            lcsStatusRoutProtOspfInterfaceTableEntryMulticastForwarding Integer32,
            lcsStatusRoutProtOspfInterfaceTableEntryDemandProc Integer32,
            lcsStatusRoutProtOspfInterfaceTableEntryAuthenticationType INTEGER,
            lcsStatusRoutProtOspfInterfaceTableEntryOspfInstance DisplayString,
            lcsStatusRoutProtOspfInterfaceTableEntryInterface DisplayString
    }

-- {COLUMN} 1.3.6.1.4.1.2356.11.1.93.3.7.1.1
lcsStatusRoutProtOspfInterfaceTableEntryIpAddress OBJECT-TYPE
    SYNTAX     IpAddress
    MAX-ACCESS read-only
    STATUS     current
    DESCRIPTION
            "-- empty --"
    ::= { lcsStatusRoutProtOspfInterfaceTableEntry 1 }

-- {COLUMN} 1.3.6.1.4.1.2356.11.1.93.3.7.1.2
lcsStatusRoutProtOspfInterfaceTableEntryIndex OBJECT-TYPE
    SYNTAX     Integer32 (0..2147483647)
    MAX-ACCESS read-only
    STATUS     current
    DESCRIPTION
            "-- empty --"
    ::= { lcsStatusRoutProtOspfInterfaceTableEntry 2 }

-- {COLUMN} 1.3.6.1.4.1.2356.11.1.93.3.7.1.3
lcsStatusRoutProtOspfInterfaceTableEntryAreaId OBJECT-TYPE
    SYNTAX     IpAddress
    MAX-ACCESS read-only
    STATUS     current
    DESCRIPTION
            "-- empty --"
    ::= { lcsStatusRoutProtOspfInterfaceTableEntry 3 }

-- {COLUMN} 1.3.6.1.4.1.2356.11.1.93.3.7.1.4
lcsStatusRoutProtOspfInterfaceTableEntryType OBJECT-TYPE
    SYNTAX     INTEGER {
                  eBroadcast (0),
                  ePointToPoint (1),
                  eNbma (2),
                  ePointToMultipoint (3)
            }
    MAX-ACCESS read-only
    STATUS     current
    DESCRIPTION
            "-- empty --"
    ::= { lcsStatusRoutProtOspfInterfaceTableEntry 4 }

-- {COLUMN} 1.3.6.1.4.1.2356.11.1.93.3.7.1.5
lcsStatusRoutProtOspfInterfaceTableEntryOperating OBJECT-TYPE
    SYNTAX     INTEGER {
                  eNo (0),
                  eYes (1)
            }
    MAX-ACCESS read-only
    STATUS     current
    DESCRIPTION
            "-- empty --"
    ::= { lcsStatusRoutProtOspfInterfaceTableEntry 5 }

-- {COLUMN} 1.3.6.1.4.1.2356.11.1.93.3.7.1.6
lcsStatusRoutProtOspfInterfaceTableEntryRouterPriority OBJECT-TYPE
    SYNTAX     Integer32 (0..2147483647)
    MAX-ACCESS read-only
    STATUS     current
    DESCRIPTION
            "-- empty --"
    ::= { lcsStatusRoutProtOspfInterfaceTableEntry 6 }

-- {COLUMN} 1.3.6.1.4.1.2356.11.1.93.3.7.1.7
lcsStatusRoutProtOspfInterfaceTableEntryInfTransDelay OBJECT-TYPE
    SYNTAX     Integer32 (0..2147483647)
    MAX-ACCESS read-only
    STATUS     current
    DESCRIPTION
            "-- empty --"
    ::= { lcsStatusRoutProtOspfInterfaceTableEntry 7 }

-- {COLUMN} 1.3.6.1.4.1.2356.11.1.93.3.7.1.8
lcsStatusRoutProtOspfInterfaceTableEntryRxmtInterval OBJECT-TYPE
    SYNTAX     Integer32 (0..2147483647)
    MAX-ACCESS read-only
    STATUS     current
    DESCRIPTION
            "-- empty --"
    ::= { lcsStatusRoutProtOspfInterfaceTableEntry 8 }

-- {COLUMN} 1.3.6.1.4.1.2356.11.1.93.3.7.1.9
lcsStatusRoutProtOspfInterfaceTableEntryHelloInterval OBJECT-TYPE
    SYNTAX     Integer32 (0..2147483647)
    MAX-ACCESS read-only
    STATUS     current
    DESCRIPTION
            "-- empty --"
    ::= { lcsStatusRoutProtOspfInterfaceTableEntry 9 }

-- {COLUMN} 1.3.6.1.4.1.2356.11.1.93.3.7.1.10
lcsStatusRoutProtOspfInterfaceTableEntryRouterDeadInterval OBJECT-TYPE
    SYNTAX     Integer32 (0..2147483647)
    MAX-ACCESS read-only
    STATUS     current
    DESCRIPTION
            "-- empty --"
    ::= { lcsStatusRoutProtOspfInterfaceTableEntry 10 }

-- {COLUMN} 1.3.6.1.4.1.2356.11.1.93.3.7.1.11
lcsStatusRoutProtOspfInterfaceTableEntryPollInterval OBJECT-TYPE
    SYNTAX     Integer32 (0..2147483647)
    MAX-ACCESS read-only
    STATUS     current
    DESCRIPTION
            "-- empty --"
    ::= { lcsStatusRoutProtOspfInterfaceTableEntry 11 }

-- {COLUMN} 1.3.6.1.4.1.2356.11.1.93.3.7.1.12
lcsStatusRoutProtOspfInterfaceTableEntryState OBJECT-TYPE
    SYNTAX     INTEGER {
                  eDown (0),
                  eLoopback (1),
                  eWaiting (2),
                  ePointToPoint (3),
                  eDrOther (4),
                  eDrBackup (5),
                  eDr (6)
            }
    MAX-ACCESS read-only
    STATUS     current
    DESCRIPTION
            "-- empty --"
    ::= { lcsStatusRoutProtOspfInterfaceTableEntry 12 }

-- {COLUMN} 1.3.6.1.4.1.2356.11.1.93.3.7.1.13
lcsStatusRoutProtOspfInterfaceTableEntryDrIp OBJECT-TYPE
    SYNTAX     IpAddress
    MAX-ACCESS read-only
    STATUS     current
    DESCRIPTION
            "-- empty --"
    ::= { lcsStatusRoutProtOspfInterfaceTableEntry 13 }

-- {COLUMN} 1.3.6.1.4.1.2356.11.1.93.3.7.1.14
lcsStatusRoutProtOspfInterfaceTableEntryBdrIp OBJECT-TYPE
    SYNTAX     IpAddress
    MAX-ACCESS read-only
    STATUS     current
    DESCRIPTION
            "-- empty --"
    ::= { lcsStatusRoutProtOspfInterfaceTableEntry 14 }

-- {COLUMN} 1.3.6.1.4.1.2356.11.1.93.3.7.1.15
lcsStatusRoutProtOspfInterfaceTableEntryEvents OBJECT-TYPE
    SYNTAX     Integer32 (0..2147483647)
    MAX-ACCESS read-only
    STATUS     current
    DESCRIPTION
            "-- empty --"
    ::= { lcsStatusRoutProtOspfInterfaceTableEntry 15 }

-- {COLUMN} 1.3.6.1.4.1.2356.11.1.93.3.7.1.16
lcsStatusRoutProtOspfInterfaceTableEntryAuthenticationKey OBJECT-TYPE
    SYNTAX     DisplayString (SIZE(0..16))
    MAX-ACCESS read-only
    STATUS     current
    DESCRIPTION
            "-- empty --"
    ::= { lcsStatusRoutProtOspfInterfaceTableEntry 16 }

-- {COLUMN} 1.3.6.1.4.1.2356.11.1.93.3.7.1.18
lcsStatusRoutProtOspfInterfaceTableEntryMulticastForwarding OBJECT-TYPE
    SYNTAX     Integer32 (0..2147483647)
    MAX-ACCESS read-only
    STATUS     current
    DESCRIPTION
            "-- empty --"
    ::= { lcsStatusRoutProtOspfInterfaceTableEntry 18 }

-- {COLUMN} 1.3.6.1.4.1.2356.11.1.93.3.7.1.19
lcsStatusRoutProtOspfInterfaceTableEntryDemandProc OBJECT-TYPE
    SYNTAX     Integer32 (0..2147483647)
    MAX-ACCESS read-only
    STATUS     current
    DESCRIPTION
            "-- empty --"
    ::= { lcsStatusRoutProtOspfInterfaceTableEntry 19 }

-- {COLUMN} 1.3.6.1.4.1.2356.11.1.93.3.7.1.20
lcsStatusRoutProtOspfInterfaceTableEntryAuthenticationType OBJECT-TYPE
    SYNTAX     INTEGER {
                  eNull (0),
                  eSimplePassword (1),
                  eCryptographicMd5 (2)
            }
    MAX-ACCESS read-only
    STATUS     current
    DESCRIPTION
            "-- empty --"
    ::= { lcsStatusRoutProtOspfInterfaceTableEntry 20 }

-- {COLUMN} 1.3.6.1.4.1.2356.11.1.93.3.7.1.200
lcsStatusRoutProtOspfInterfaceTableEntryOspfInstance OBJECT-TYPE
    SYNTAX     DisplayString (SIZE(0..16))
    MAX-ACCESS read-only
    STATUS     current
    DESCRIPTION
            "-- empty --"
    ::= { lcsStatusRoutProtOspfInterfaceTableEntry 200 }

-- {COLUMN} 1.3.6.1.4.1.2356.11.1.93.3.7.1.201
lcsStatusRoutProtOspfInterfaceTableEntryInterface OBJECT-TYPE
    SYNTAX     DisplayString (SIZE(0..16))
    MAX-ACCESS read-only
    STATUS     current
    DESCRIPTION
            "-- empty --"
    ::= { lcsStatusRoutProtOspfInterfaceTableEntry 201 }

-- {TABLE} 1.3.6.1.4.1.2356.11.1.93.3.9
lcsStatusRoutProtOspfVirtIfcTable OBJECT-TYPE
    SYNTAX     SEQUENCE OF LcsStatusRoutProtOspfVirtIfcEntry
    MAX-ACCESS not-accessible
    STATUS     current
    DESCRIPTION
            ""
    ::= { lcsStatusRoutProtOspf 9 }

-- {ROW} 1.3.6.1.4.1.2356.11.1.93.3.9.1
lcsStatusRoutProtOspfVirtIfcEntry OBJECT-TYPE
    SYNTAX     LcsStatusRoutProtOspfVirtIfcEntry
    MAX-ACCESS not-accessible
    STATUS     current
    DESCRIPTION
            ""
    INDEX {
            lcsStatusRoutProtOspfVirtIfcEntryOspfInstance,
            lcsStatusRoutProtOspfVirtIfcEntryAreaId,
            lcsStatusRoutProtOspfVirtIfcEntryRouterId
          }
    ::= { lcsStatusRoutProtOspfVirtIfcTable 1 }

LcsStatusRoutProtOspfVirtIfcEntry ::= SEQUENCE {
            lcsStatusRoutProtOspfVirtIfcEntryAreaId IpAddress,
            lcsStatusRoutProtOspfVirtIfcEntryRouterId IpAddress,
            lcsStatusRoutProtOspfVirtIfcEntryInfTransDelay Integer32,
            lcsStatusRoutProtOspfVirtIfcEntryRxmtInterval Integer32,
            lcsStatusRoutProtOspfVirtIfcEntryHelloInterval Integer32,
            lcsStatusRoutProtOspfVirtIfcEntryRouterDeadInterval Integer32,
            lcsStatusRoutProtOspfVirtIfcEntryState INTEGER,
            lcsStatusRoutProtOspfVirtIfcEntryEvents Integer32,
            lcsStatusRoutProtOspfVirtIfcEntryAuthenticationKey DisplayString,
            lcsStatusRoutProtOspfVirtIfcEntryAuthenticationType INTEGER,
            lcsStatusRoutProtOspfVirtIfcEntryOspfInstance DisplayString
    }

-- {COLUMN} 1.3.6.1.4.1.2356.11.1.93.3.9.1.1
lcsStatusRoutProtOspfVirtIfcEntryAreaId OBJECT-TYPE
    SYNTAX     IpAddress
    MAX-ACCESS read-only
    STATUS     current
    DESCRIPTION
            "-- empty --"
    ::= { lcsStatusRoutProtOspfVirtIfcEntry 1 }

-- {COLUMN} 1.3.6.1.4.1.2356.11.1.93.3.9.1.2
lcsStatusRoutProtOspfVirtIfcEntryRouterId OBJECT-TYPE
    SYNTAX     IpAddress
    MAX-ACCESS read-only
    STATUS     current
    DESCRIPTION
            "-- empty --"
    ::= { lcsStatusRoutProtOspfVirtIfcEntry 2 }

-- {COLUMN} 1.3.6.1.4.1.2356.11.1.93.3.9.1.3
lcsStatusRoutProtOspfVirtIfcEntryInfTransDelay OBJECT-TYPE
    SYNTAX     Integer32 (0..2147483647)
    MAX-ACCESS read-only
    STATUS     current
    DESCRIPTION
            "-- empty --"
    ::= { lcsStatusRoutProtOspfVirtIfcEntry 3 }

-- {COLUMN} 1.3.6.1.4.1.2356.11.1.93.3.9.1.4
lcsStatusRoutProtOspfVirtIfcEntryRxmtInterval OBJECT-TYPE
    SYNTAX     Integer32 (0..2147483647)
    MAX-ACCESS read-only
    STATUS     current
    DESCRIPTION
            "-- empty --"
    ::= { lcsStatusRoutProtOspfVirtIfcEntry 4 }

-- {COLUMN} 1.3.6.1.4.1.2356.11.1.93.3.9.1.5
lcsStatusRoutProtOspfVirtIfcEntryHelloInterval OBJECT-TYPE
    SYNTAX     Integer32 (0..2147483647)
    MAX-ACCESS read-only
    STATUS     current
    DESCRIPTION
            "-- empty --"
    ::= { lcsStatusRoutProtOspfVirtIfcEntry 5 }

-- {COLUMN} 1.3.6.1.4.1.2356.11.1.93.3.9.1.6
lcsStatusRoutProtOspfVirtIfcEntryRouterDeadInterval OBJECT-TYPE
    SYNTAX     Integer32 (0..2147483647)
    MAX-ACCESS read-only
    STATUS     current
    DESCRIPTION
            "-- empty --"
    ::= { lcsStatusRoutProtOspfVirtIfcEntry 6 }

-- {COLUMN} 1.3.6.1.4.1.2356.11.1.93.3.9.1.7
lcsStatusRoutProtOspfVirtIfcEntryState OBJECT-TYPE
    SYNTAX     INTEGER {
                  eDown (0),
                  eLoopback (1),
                  eWaiting (2),
                  ePointToPoint (3),
                  eDrOther (4),
                  eDrBackup (5),
                  eDr (6)
            }
    MAX-ACCESS read-only
    STATUS     current
    DESCRIPTION
            "-- empty --"
    ::= { lcsStatusRoutProtOspfVirtIfcEntry 7 }

-- {COLUMN} 1.3.6.1.4.1.2356.11.1.93.3.9.1.8
lcsStatusRoutProtOspfVirtIfcEntryEvents OBJECT-TYPE
    SYNTAX     Integer32 (0..2147483647)
    MAX-ACCESS read-only
    STATUS     current
    DESCRIPTION
            "-- empty --"
    ::= { lcsStatusRoutProtOspfVirtIfcEntry 8 }

-- {COLUMN} 1.3.6.1.4.1.2356.11.1.93.3.9.1.9
lcsStatusRoutProtOspfVirtIfcEntryAuthenticationKey OBJECT-TYPE
    SYNTAX     DisplayString (SIZE(0..16))
    MAX-ACCESS read-only
    STATUS     current
    DESCRIPTION
            "-- empty --"
    ::= { lcsStatusRoutProtOspfVirtIfcEntry 9 }

-- {COLUMN} 1.3.6.1.4.1.2356.11.1.93.3.9.1.11
lcsStatusRoutProtOspfVirtIfcEntryAuthenticationType OBJECT-TYPE
    SYNTAX     INTEGER {
                  eNull (0),
                  eSimplePassword (1),
                  eCryptographicMd5 (2)
            }
    MAX-ACCESS read-only
    STATUS     current
    DESCRIPTION
            "-- empty --"
    ::= { lcsStatusRoutProtOspfVirtIfcEntry 11 }

-- {COLUMN} 1.3.6.1.4.1.2356.11.1.93.3.9.1.200
lcsStatusRoutProtOspfVirtIfcEntryOspfInstance OBJECT-TYPE
    SYNTAX     DisplayString (SIZE(0..16))
    MAX-ACCESS read-only
    STATUS     current
    DESCRIPTION
            "-- empty --"
    ::= { lcsStatusRoutProtOspfVirtIfcEntry 200 }

-- {TABLE} 1.3.6.1.4.1.2356.11.1.93.3.10
lcsStatusRoutProtOspfNeighborTableTable OBJECT-TYPE
    SYNTAX     SEQUENCE OF LcsStatusRoutProtOspfNeighborTableEntry
    MAX-ACCESS not-accessible
    STATUS     current
    DESCRIPTION
            "-- empty --"
    ::= { lcsStatusRoutProtOspf 10 }

-- {ROW} 1.3.6.1.4.1.2356.11.1.93.3.10.1
lcsStatusRoutProtOspfNeighborTableEntry OBJECT-TYPE
    SYNTAX     LcsStatusRoutProtOspfNeighborTableEntry
    MAX-ACCESS not-accessible
    STATUS     current
    DESCRIPTION
            ""
    INDEX {
            lcsStatusRoutProtOspfNeighborTableEntryOspfInstance,
            lcsStatusRoutProtOspfNeighborTableEntryInterface,
            lcsStatusRoutProtOspfNeighborTableEntryIpAddress
          }
    ::= { lcsStatusRoutProtOspfNeighborTableTable 1 }

LcsStatusRoutProtOspfNeighborTableEntry ::= SEQUENCE {
            lcsStatusRoutProtOspfNeighborTableEntryIpAddress IpAddress,
            lcsStatusRoutProtOspfNeighborTableEntryIndex Integer32,
            lcsStatusRoutProtOspfNeighborTableEntryRouterId IpAddress,
            lcsStatusRoutProtOspfNeighborTableEntryOptions Integer32,
            lcsStatusRoutProtOspfNeighborTableEntryRouterPriority Integer32,
            lcsStatusRoutProtOspfNeighborTableEntryState INTEGER,
            lcsStatusRoutProtOspfNeighborTableEntryEvents Integer32,
            lcsStatusRoutProtOspfNeighborTableEntryRetransmissionQueueLength Integer32,
            lcsStatusRoutProtOspfNeighborTableEntryPermanence INTEGER,
            lcsStatusRoutProtOspfNeighborTableEntryHelloSuppressed INTEGER,
            lcsStatusRoutProtOspfNeighborTableEntryOspfInstance DisplayString,
            lcsStatusRoutProtOspfNeighborTableEntryInterface DisplayString
    }

-- {COLUMN} 1.3.6.1.4.1.2356.11.1.93.3.10.1.1
lcsStatusRoutProtOspfNeighborTableEntryIpAddress OBJECT-TYPE
    SYNTAX     IpAddress
    MAX-ACCESS read-only
    STATUS     current
    DESCRIPTION
            "-- empty --"
    ::= { lcsStatusRoutProtOspfNeighborTableEntry 1 }

-- {COLUMN} 1.3.6.1.4.1.2356.11.1.93.3.10.1.2
lcsStatusRoutProtOspfNeighborTableEntryIndex OBJECT-TYPE
    SYNTAX     Integer32 (0..2147483647)
    MAX-ACCESS read-only
    STATUS     current
    DESCRIPTION
            "-- empty --"
    ::= { lcsStatusRoutProtOspfNeighborTableEntry 2 }

-- {COLUMN} 1.3.6.1.4.1.2356.11.1.93.3.10.1.3
lcsStatusRoutProtOspfNeighborTableEntryRouterId OBJECT-TYPE
    SYNTAX     IpAddress
    MAX-ACCESS read-only
    STATUS     current
    DESCRIPTION
            "-- empty --"
    ::= { lcsStatusRoutProtOspfNeighborTableEntry 3 }

-- {COLUMN} 1.3.6.1.4.1.2356.11.1.93.3.10.1.4
lcsStatusRoutProtOspfNeighborTableEntryOptions OBJECT-TYPE
    SYNTAX     Integer32 (0..2147483647)
    MAX-ACCESS read-only
    STATUS     current
    DESCRIPTION
            "-- empty --"
    ::= { lcsStatusRoutProtOspfNeighborTableEntry 4 }

-- {COLUMN} 1.3.6.1.4.1.2356.11.1.93.3.10.1.5
lcsStatusRoutProtOspfNeighborTableEntryRouterPriority OBJECT-TYPE
    SYNTAX     Integer32 (0..2147483647)
    MAX-ACCESS read-only
    STATUS     current
    DESCRIPTION
            "-- empty --"
    ::= { lcsStatusRoutProtOspfNeighborTableEntry 5 }

-- {COLUMN} 1.3.6.1.4.1.2356.11.1.93.3.10.1.6
lcsStatusRoutProtOspfNeighborTableEntryState OBJECT-TYPE
    SYNTAX     INTEGER {
                  eDown (1),
                  eAttempt (2),
                  eInit (3),
                  eTwoWay (4),
                  eExStart (5),
                  eExchange (6),
                  eLoading (7),
                  eFull (8)
            }
    MAX-ACCESS read-only
    STATUS     current
    DESCRIPTION
            "-- empty --"
    ::= { lcsStatusRoutProtOspfNeighborTableEntry 6 }

-- {COLUMN} 1.3.6.1.4.1.2356.11.1.93.3.10.1.7
lcsStatusRoutProtOspfNeighborTableEntryEvents OBJECT-TYPE
    SYNTAX     Integer32 (0..2147483647)
    MAX-ACCESS read-only
    STATUS     current
    DESCRIPTION
            "-- empty --"
    ::= { lcsStatusRoutProtOspfNeighborTableEntry 7 }

-- {COLUMN} 1.3.6.1.4.1.2356.11.1.93.3.10.1.8
lcsStatusRoutProtOspfNeighborTableEntryRetransmissionQueueLength OBJECT-TYPE
    SYNTAX     Integer32 (0..2147483647)
    MAX-ACCESS read-only
    STATUS     current
    DESCRIPTION
            "-- empty --"
    ::= { lcsStatusRoutProtOspfNeighborTableEntry 8 }

-- {COLUMN} 1.3.6.1.4.1.2356.11.1.93.3.10.1.10
lcsStatusRoutProtOspfNeighborTableEntryPermanence OBJECT-TYPE
    SYNTAX     INTEGER {
                  eDynamic (1),
                  ePermanent (2)
            }
    MAX-ACCESS read-only
    STATUS     current
    DESCRIPTION
            "-- empty --"
    ::= { lcsStatusRoutProtOspfNeighborTableEntry 10 }

-- {COLUMN} 1.3.6.1.4.1.2356.11.1.93.3.10.1.11
lcsStatusRoutProtOspfNeighborTableEntryHelloSuppressed OBJECT-TYPE
    SYNTAX     INTEGER {
                  eNo (0),
                  eYes (1)
            }
    MAX-ACCESS read-only
    STATUS     current
    DESCRIPTION
            "-- empty --"
    ::= { lcsStatusRoutProtOspfNeighborTableEntry 11 }

-- {COLUMN} 1.3.6.1.4.1.2356.11.1.93.3.10.1.200
lcsStatusRoutProtOspfNeighborTableEntryOspfInstance OBJECT-TYPE
    SYNTAX     DisplayString (SIZE(0..16))
    MAX-ACCESS read-only
    STATUS     current
    DESCRIPTION
            "-- empty --"
    ::= { lcsStatusRoutProtOspfNeighborTableEntry 200 }

-- {COLUMN} 1.3.6.1.4.1.2356.11.1.93.3.10.1.201
lcsStatusRoutProtOspfNeighborTableEntryInterface OBJECT-TYPE
    SYNTAX     DisplayString (SIZE(0..16))
    MAX-ACCESS read-only
    STATUS     current
    DESCRIPTION
            "-- empty --"
    ::= { lcsStatusRoutProtOspfNeighborTableEntry 201 }

-- {TABLE} 1.3.6.1.4.1.2356.11.1.93.3.11
lcsStatusRoutProtOspfVirtNeighTable OBJECT-TYPE
    SYNTAX     SEQUENCE OF LcsStatusRoutProtOspfVirtNeighEntry
    MAX-ACCESS not-accessible
    STATUS     current
    DESCRIPTION
            ""
    ::= { lcsStatusRoutProtOspf 11 }

-- {ROW} 1.3.6.1.4.1.2356.11.1.93.3.11.1
lcsStatusRoutProtOspfVirtNeighEntry OBJECT-TYPE
    SYNTAX     LcsStatusRoutProtOspfVirtNeighEntry
    MAX-ACCESS not-accessible
    STATUS     current
    DESCRIPTION
            ""
    INDEX {
            lcsStatusRoutProtOspfVirtNeighEntryOspfInstance,
            lcsStatusRoutProtOspfVirtNeighEntryAreaId,
            lcsStatusRoutProtOspfVirtNeighEntryRouterId
          }
    ::= { lcsStatusRoutProtOspfVirtNeighTable 1 }

LcsStatusRoutProtOspfVirtNeighEntry ::= SEQUENCE {
            lcsStatusRoutProtOspfVirtNeighEntryAreaId IpAddress,
            lcsStatusRoutProtOspfVirtNeighEntryRouterId IpAddress,
            lcsStatusRoutProtOspfVirtNeighEntryIpAddress IpAddress,
            lcsStatusRoutProtOspfVirtNeighEntryOptions Integer32,
            lcsStatusRoutProtOspfVirtNeighEntryState INTEGER,
            lcsStatusRoutProtOspfVirtNeighEntryEvents Integer32,
            lcsStatusRoutProtOspfVirtNeighEntryRetransmissionQueueLength Integer32,
            lcsStatusRoutProtOspfVirtNeighEntryHelloSuppressed Integer32,
            lcsStatusRoutProtOspfVirtNeighEntryOspfInstance DisplayString
    }

-- {COLUMN} 1.3.6.1.4.1.2356.11.1.93.3.11.1.1
lcsStatusRoutProtOspfVirtNeighEntryAreaId OBJECT-TYPE
    SYNTAX     IpAddress
    MAX-ACCESS read-only
    STATUS     current
    DESCRIPTION
            "-- empty --"
    ::= { lcsStatusRoutProtOspfVirtNeighEntry 1 }

-- {COLUMN} 1.3.6.1.4.1.2356.11.1.93.3.11.1.2
lcsStatusRoutProtOspfVirtNeighEntryRouterId OBJECT-TYPE
    SYNTAX     IpAddress
    MAX-ACCESS read-only
    STATUS     current
    DESCRIPTION
            "-- empty --"
    ::= { lcsStatusRoutProtOspfVirtNeighEntry 2 }

-- {COLUMN} 1.3.6.1.4.1.2356.11.1.93.3.11.1.3
lcsStatusRoutProtOspfVirtNeighEntryIpAddress OBJECT-TYPE
    SYNTAX     IpAddress
    MAX-ACCESS read-only
    STATUS     current
    DESCRIPTION
            "-- empty --"
    ::= { lcsStatusRoutProtOspfVirtNeighEntry 3 }

-- {COLUMN} 1.3.6.1.4.1.2356.11.1.93.3.11.1.4
lcsStatusRoutProtOspfVirtNeighEntryOptions OBJECT-TYPE
    SYNTAX     Integer32 (0..2147483647)
    MAX-ACCESS read-only
    STATUS     current
    DESCRIPTION
            "-- empty --"
    ::= { lcsStatusRoutProtOspfVirtNeighEntry 4 }

-- {COLUMN} 1.3.6.1.4.1.2356.11.1.93.3.11.1.5
lcsStatusRoutProtOspfVirtNeighEntryState OBJECT-TYPE
    SYNTAX     INTEGER {
                  eDown (1),
                  eAttempt (2),
                  eInit (3),
                  eTwoWay (4),
                  eExStart (5),
                  eExchange (6),
                  eLoading (7),
                  eFull (8)
            }
    MAX-ACCESS read-only
    STATUS     current
    DESCRIPTION
            "-- empty --"
    ::= { lcsStatusRoutProtOspfVirtNeighEntry 5 }

-- {COLUMN} 1.3.6.1.4.1.2356.11.1.93.3.11.1.6
lcsStatusRoutProtOspfVirtNeighEntryEvents OBJECT-TYPE
    SYNTAX     Integer32 (0..2147483647)
    MAX-ACCESS read-only
    STATUS     current
    DESCRIPTION
            "-- empty --"
    ::= { lcsStatusRoutProtOspfVirtNeighEntry 6 }

-- {COLUMN} 1.3.6.1.4.1.2356.11.1.93.3.11.1.7
lcsStatusRoutProtOspfVirtNeighEntryRetransmissionQueueLength OBJECT-TYPE
    SYNTAX     Integer32 (0..2147483647)
    MAX-ACCESS read-only
    STATUS     current
    DESCRIPTION
            "-- empty --"
    ::= { lcsStatusRoutProtOspfVirtNeighEntry 7 }

-- {COLUMN} 1.3.6.1.4.1.2356.11.1.93.3.11.1.8
lcsStatusRoutProtOspfVirtNeighEntryHelloSuppressed OBJECT-TYPE
    SYNTAX     Integer32 (0..255)
    MAX-ACCESS read-only
    STATUS     current
    DESCRIPTION
            "-- empty --"
    ::= { lcsStatusRoutProtOspfVirtNeighEntry 8 }

-- {COLUMN} 1.3.6.1.4.1.2356.11.1.93.3.11.1.200
lcsStatusRoutProtOspfVirtNeighEntryOspfInstance OBJECT-TYPE
    SYNTAX     DisplayString (SIZE(0..16))
    MAX-ACCESS read-only
    STATUS     current
    DESCRIPTION
            "-- empty --"
    ::= { lcsStatusRoutProtOspfVirtNeighEntry 200 }

-- {TABLE} 1.3.6.1.4.1.2356.11.1.93.3.12
lcsStatusRoutProtOspfLinkStateDbExternalTableTable OBJECT-TYPE
    SYNTAX     SEQUENCE OF LcsStatusRoutProtOspfLinkStateDbExternalTableEntry
    MAX-ACCESS not-accessible
    STATUS     current
    DESCRIPTION
            "-- empty --"
    ::= { lcsStatusRoutProtOspf 12 }

-- {ROW} 1.3.6.1.4.1.2356.11.1.93.3.12.1
lcsStatusRoutProtOspfLinkStateDbExternalTableEntry OBJECT-TYPE
    SYNTAX     LcsStatusRoutProtOspfLinkStateDbExternalTableEntry
    MAX-ACCESS not-accessible
    STATUS     current
    DESCRIPTION
            ""
    INDEX {
            lcsStatusRoutProtOspfLinkStateDbExternalTableEntryOspfInstance,
            lcsStatusRoutProtOspfLinkStateDbExternalTableEntryLsaType,
            lcsStatusRoutProtOspfLinkStateDbExternalTableEntryLsId,
            lcsStatusRoutProtOspfLinkStateDbExternalTableEntryRouterId
          }
    ::= { lcsStatusRoutProtOspfLinkStateDbExternalTableTable 1 }

LcsStatusRoutProtOspfLinkStateDbExternalTableEntry ::= SEQUENCE {
            lcsStatusRoutProtOspfLinkStateDbExternalTableEntryLsaType INTEGER,
            lcsStatusRoutProtOspfLinkStateDbExternalTableEntryLsId IpAddress,
            lcsStatusRoutProtOspfLinkStateDbExternalTableEntryRouterId IpAddress,
            lcsStatusRoutProtOspfLinkStateDbExternalTableEntrySequenceNumber Integer32,
            lcsStatusRoutProtOspfLinkStateDbExternalTableEntryLsaAge Integer32,
            lcsStatusRoutProtOspfLinkStateDbExternalTableEntryLsaChecksum Integer32,
            lcsStatusRoutProtOspfLinkStateDbExternalTableEntryOspfInstance DisplayString
    }

-- {COLUMN} 1.3.6.1.4.1.2356.11.1.93.3.12.1.1
lcsStatusRoutProtOspfLinkStateDbExternalTableEntryLsaType OBJECT-TYPE
    SYNTAX     INTEGER {
                  eRouterLink (1),
                  eNetworkLink (2),
                  eSummaryLink (3),
                  eAsSummaryLink (4),
                  eAsExtenalLink (5)
            }
    MAX-ACCESS read-only
    STATUS     current
    DESCRIPTION
            "-- empty --"
    ::= { lcsStatusRoutProtOspfLinkStateDbExternalTableEntry 1 }

-- {COLUMN} 1.3.6.1.4.1.2356.11.1.93.3.12.1.2
lcsStatusRoutProtOspfLinkStateDbExternalTableEntryLsId OBJECT-TYPE
    SYNTAX     IpAddress
    MAX-ACCESS read-only
    STATUS     current
    DESCRIPTION
            "-- empty --"
    ::= { lcsStatusRoutProtOspfLinkStateDbExternalTableEntry 2 }

-- {COLUMN} 1.3.6.1.4.1.2356.11.1.93.3.12.1.3
lcsStatusRoutProtOspfLinkStateDbExternalTableEntryRouterId OBJECT-TYPE
    SYNTAX     IpAddress
    MAX-ACCESS read-only
    STATUS     current
    DESCRIPTION
            "-- empty --"
    ::= { lcsStatusRoutProtOspfLinkStateDbExternalTableEntry 3 }

-- {COLUMN} 1.3.6.1.4.1.2356.11.1.93.3.12.1.4
lcsStatusRoutProtOspfLinkStateDbExternalTableEntrySequenceNumber OBJECT-TYPE
    SYNTAX     Integer32 (0..2147483647)
    MAX-ACCESS read-only
    STATUS     current
    DESCRIPTION
            "-- empty --"
    ::= { lcsStatusRoutProtOspfLinkStateDbExternalTableEntry 4 }

-- {COLUMN} 1.3.6.1.4.1.2356.11.1.93.3.12.1.5
lcsStatusRoutProtOspfLinkStateDbExternalTableEntryLsaAge OBJECT-TYPE
    SYNTAX     Integer32 (0..2147483647)
    MAX-ACCESS read-only
    STATUS     current
    DESCRIPTION
            "-- empty --"
    ::= { lcsStatusRoutProtOspfLinkStateDbExternalTableEntry 5 }

-- {COLUMN} 1.3.6.1.4.1.2356.11.1.93.3.12.1.6
lcsStatusRoutProtOspfLinkStateDbExternalTableEntryLsaChecksum OBJECT-TYPE
    SYNTAX     Integer32 (0..2147483647)
    MAX-ACCESS read-only
    STATUS     current
    DESCRIPTION
            "-- empty --"
    ::= { lcsStatusRoutProtOspfLinkStateDbExternalTableEntry 6 }

-- {COLUMN} 1.3.6.1.4.1.2356.11.1.93.3.12.1.200
lcsStatusRoutProtOspfLinkStateDbExternalTableEntryOspfInstance OBJECT-TYPE
    SYNTAX     DisplayString (SIZE(0..16))
    MAX-ACCESS read-only
    STATUS     current
    DESCRIPTION
            "-- empty --"
    ::= { lcsStatusRoutProtOspfLinkStateDbExternalTableEntry 200 }

-- {NODE} 1.3.6.1.4.1.2356.11.1.93.4
lcsStatusRoutProtLisp OBJECT IDENTIFIER ::= { lcsStatusRoutProt 4 }

-- {TABLE} 1.3.6.1.4.1.2356.11.1.93.4.1
lcsStatusRoutProtLispInstancesTable OBJECT-TYPE
    SYNTAX     SEQUENCE OF LcsStatusRoutProtLispInstancesEntry
    MAX-ACCESS not-accessible
    STATUS     current
    DESCRIPTION
            "-- empty --"
    ::= { lcsStatusRoutProtLisp 1 }

-- {ROW} 1.3.6.1.4.1.2356.11.1.93.4.1.1
lcsStatusRoutProtLispInstancesEntry OBJECT-TYPE
    SYNTAX     LcsStatusRoutProtLispInstancesEntry
    MAX-ACCESS not-accessible
    STATUS     current
    DESCRIPTION
            ""
    INDEX {
            lcsStatusRoutProtLispInstancesEntryName
          }
    ::= { lcsStatusRoutProtLispInstancesTable 1 }

LcsStatusRoutProtLispInstancesEntry ::= SEQUENCE {
            lcsStatusRoutProtLispInstancesEntryName OCTET STRING,
            lcsStatusRoutProtLispInstancesEntryEidRtgTag Unsigned32,
            lcsStatusRoutProtLispInstancesEntryRlocRtgTag Unsigned32,
            lcsStatusRoutProtLispInstancesEntryInstanceId Unsigned32,
            lcsStatusRoutProtLispInstancesEntryMapCacheSize Unsigned32,
            lcsStatusRoutProtLispInstancesEntryProbingMethod INTEGER,
            lcsStatusRoutProtLispInstancesEntryAdminDistance Unsigned32,
            lcsStatusRoutProtLispInstancesEntryItrEnabled INTEGER,
            lcsStatusRoutProtLispInstancesEntryEtrEnabled INTEGER,
            lcsStatusRoutProtLispInstancesEntryForwardEnabled INTEGER,
            lcsStatusRoutProtLispInstancesEntryRedistributionEnabled INTEGER
    }

-- {COLUMN} 1.3.6.1.4.1.2356.11.1.93.4.1.1.1
lcsStatusRoutProtLispInstancesEntryName OBJECT-TYPE
    SYNTAX     OCTET STRING (SIZE(0..24))
    MAX-ACCESS read-only
    STATUS     current
    DESCRIPTION
            "-- empty --"
    ::= { lcsStatusRoutProtLispInstancesEntry 1 }

-- {COLUMN} 1.3.6.1.4.1.2356.11.1.93.4.1.1.2
lcsStatusRoutProtLispInstancesEntryEidRtgTag OBJECT-TYPE
    SYNTAX     Unsigned32 (0..4294967295)
    MAX-ACCESS read-only
    STATUS     current
    DESCRIPTION
            "-- empty --"
    ::= { lcsStatusRoutProtLispInstancesEntry 2 }

-- {COLUMN} 1.3.6.1.4.1.2356.11.1.93.4.1.1.3
lcsStatusRoutProtLispInstancesEntryRlocRtgTag OBJECT-TYPE
    SYNTAX     Unsigned32 (0..4294967295)
    MAX-ACCESS read-only
    STATUS     current
    DESCRIPTION
            "-- empty --"
    ::= { lcsStatusRoutProtLispInstancesEntry 3 }

-- {COLUMN} 1.3.6.1.4.1.2356.11.1.93.4.1.1.4
lcsStatusRoutProtLispInstancesEntryInstanceId OBJECT-TYPE
    SYNTAX     Unsigned32 (0..4294967295)
    MAX-ACCESS read-only
    STATUS     current
    DESCRIPTION
            "-- empty --"
    ::= { lcsStatusRoutProtLispInstancesEntry 4 }

-- {COLUMN} 1.3.6.1.4.1.2356.11.1.93.4.1.1.6
lcsStatusRoutProtLispInstancesEntryMapCacheSize OBJECT-TYPE
    SYNTAX     Unsigned32 (0..4294967295)
    MAX-ACCESS read-only
    STATUS     current
    DESCRIPTION
            "-- empty --"
    ::= { lcsStatusRoutProtLispInstancesEntry 6 }

-- {COLUMN} 1.3.6.1.4.1.2356.11.1.93.4.1.1.7
lcsStatusRoutProtLispInstancesEntryProbingMethod OBJECT-TYPE
    SYNTAX     INTEGER {
                  eOff (0),
                  eRlocProbing (1)
            }
    MAX-ACCESS read-only
    STATUS     current
    DESCRIPTION
            "-- empty --"
    ::= { lcsStatusRoutProtLispInstancesEntry 7 }

-- {COLUMN} 1.3.6.1.4.1.2356.11.1.93.4.1.1.8
lcsStatusRoutProtLispInstancesEntryAdminDistance OBJECT-TYPE
    SYNTAX     Unsigned32 (0..255)
    MAX-ACCESS read-only
    STATUS     current
    DESCRIPTION
            "-- empty --"
    ::= { lcsStatusRoutProtLispInstancesEntry 8 }

-- {COLUMN} 1.3.6.1.4.1.2356.11.1.93.4.1.1.9
lcsStatusRoutProtLispInstancesEntryItrEnabled OBJECT-TYPE
    SYNTAX     INTEGER {
                  eNo (0),
                  eYes (1)
            }
    MAX-ACCESS read-only
    STATUS     current
    DESCRIPTION
            "-- empty --"
    ::= { lcsStatusRoutProtLispInstancesEntry 9 }

-- {COLUMN} 1.3.6.1.4.1.2356.11.1.93.4.1.1.10
lcsStatusRoutProtLispInstancesEntryEtrEnabled OBJECT-TYPE
    SYNTAX     INTEGER {
                  eNo (0),
                  eYes (1)
            }
    MAX-ACCESS read-only
    STATUS     current
    DESCRIPTION
            "-- empty --"
    ::= { lcsStatusRoutProtLispInstancesEntry 10 }

-- {COLUMN} 1.3.6.1.4.1.2356.11.1.93.4.1.1.11
lcsStatusRoutProtLispInstancesEntryForwardEnabled OBJECT-TYPE
    SYNTAX     INTEGER {
                  eNo (0),
                  eYes (1)
            }
    MAX-ACCESS read-only
    STATUS     current
    DESCRIPTION
            "-- empty --"
    ::= { lcsStatusRoutProtLispInstancesEntry 11 }

-- {COLUMN} 1.3.6.1.4.1.2356.11.1.93.4.1.1.12
lcsStatusRoutProtLispInstancesEntryRedistributionEnabled OBJECT-TYPE
    SYNTAX     INTEGER {
                  eNo (0),
                  eYes (1)
            }
    MAX-ACCESS read-only
    STATUS     current
    DESCRIPTION
            "-- empty --"
    ::= { lcsStatusRoutProtLispInstancesEntry 12 }

-- {TABLE} 1.3.6.1.4.1.2356.11.1.93.4.2
lcsStatusRoutProtLispGlobalCounterTable OBJECT-TYPE
    SYNTAX     SEQUENCE OF LcsStatusRoutProtLispGlobalCounterEntry
    MAX-ACCESS not-accessible
    STATUS     current
    DESCRIPTION
            "-- empty --"
    ::= { lcsStatusRoutProtLisp 2 }

-- {ROW} 1.3.6.1.4.1.2356.11.1.93.4.2.1
lcsStatusRoutProtLispGlobalCounterEntry OBJECT-TYPE
    SYNTAX     LcsStatusRoutProtLispGlobalCounterEntry
    MAX-ACCESS not-accessible
    STATUS     current
    DESCRIPTION
            ""
    INDEX {
            lcsStatusRoutProtLispGlobalCounterEntryName
          }
    ::= { lcsStatusRoutProtLispGlobalCounterTable 1 }

LcsStatusRoutProtLispGlobalCounterEntry ::= SEQUENCE {
            lcsStatusRoutProtLispGlobalCounterEntryName OCTET STRING,
            lcsStatusRoutProtLispGlobalCounterEntryMapRequestIn Counter64,
            lcsStatusRoutProtLispGlobalCounterEntryMapRequestOut Counter64,
            lcsStatusRoutProtLispGlobalCounterEntryMapRepliesIn Counter64,
            lcsStatusRoutProtLispGlobalCounterEntryMapRepliesOut Counter64,
            lcsStatusRoutProtLispGlobalCounterEntryMapRegisterIn Counter64,
            lcsStatusRoutProtLispGlobalCounterEntryMapRegisterOut Counter64
    }

-- {COLUMN} 1.3.6.1.4.1.2356.11.1.93.4.2.1.1
lcsStatusRoutProtLispGlobalCounterEntryName OBJECT-TYPE
    SYNTAX     OCTET STRING (SIZE(0..24))
    MAX-ACCESS read-only
    STATUS     current
    DESCRIPTION
            "-- empty --"
    ::= { lcsStatusRoutProtLispGlobalCounterEntry 1 }

-- {COLUMN} 1.3.6.1.4.1.2356.11.1.93.4.2.1.2
lcsStatusRoutProtLispGlobalCounterEntryMapRequestIn OBJECT-TYPE
    SYNTAX     Counter64
    MAX-ACCESS read-only
    STATUS     current
    DESCRIPTION
            "-- empty --"
    ::= { lcsStatusRoutProtLispGlobalCounterEntry 2 }

-- {COLUMN} 1.3.6.1.4.1.2356.11.1.93.4.2.1.3
lcsStatusRoutProtLispGlobalCounterEntryMapRequestOut OBJECT-TYPE
    SYNTAX     Counter64
    MAX-ACCESS read-only
    STATUS     current
    DESCRIPTION
            "-- empty --"
    ::= { lcsStatusRoutProtLispGlobalCounterEntry 3 }

-- {COLUMN} 1.3.6.1.4.1.2356.11.1.93.4.2.1.4
lcsStatusRoutProtLispGlobalCounterEntryMapRepliesIn OBJECT-TYPE
    SYNTAX     Counter64
    MAX-ACCESS read-only
    STATUS     current
    DESCRIPTION
            "-- empty --"
    ::= { lcsStatusRoutProtLispGlobalCounterEntry 4 }

-- {COLUMN} 1.3.6.1.4.1.2356.11.1.93.4.2.1.5
lcsStatusRoutProtLispGlobalCounterEntryMapRepliesOut OBJECT-TYPE
    SYNTAX     Counter64
    MAX-ACCESS read-only
    STATUS     current
    DESCRIPTION
            "-- empty --"
    ::= { lcsStatusRoutProtLispGlobalCounterEntry 5 }

-- {COLUMN} 1.3.6.1.4.1.2356.11.1.93.4.2.1.6
lcsStatusRoutProtLispGlobalCounterEntryMapRegisterIn OBJECT-TYPE
    SYNTAX     Counter64
    MAX-ACCESS read-only
    STATUS     current
    DESCRIPTION
            "-- empty --"
    ::= { lcsStatusRoutProtLispGlobalCounterEntry 6 }

-- {COLUMN} 1.3.6.1.4.1.2356.11.1.93.4.2.1.7
lcsStatusRoutProtLispGlobalCounterEntryMapRegisterOut OBJECT-TYPE
    SYNTAX     Counter64
    MAX-ACCESS read-only
    STATUS     current
    DESCRIPTION
            "-- empty --"
    ::= { lcsStatusRoutProtLispGlobalCounterEntry 7 }

-- {TABLE} 1.3.6.1.4.1.2356.11.1.93.4.3
lcsStatusRoutProtLispPacketCounterTable OBJECT-TYPE
    SYNTAX     SEQUENCE OF LcsStatusRoutProtLispPacketCounterEntry
    MAX-ACCESS not-accessible
    STATUS     current
    DESCRIPTION
            "-- empty --"
    ::= { lcsStatusRoutProtLisp 3 }

-- {ROW} 1.3.6.1.4.1.2356.11.1.93.4.3.1
lcsStatusRoutProtLispPacketCounterEntry OBJECT-TYPE
    SYNTAX     LcsStatusRoutProtLispPacketCounterEntry
    MAX-ACCESS not-accessible
    STATUS     current
    DESCRIPTION
            ""
    INDEX {
            lcsStatusRoutProtLispPacketCounterEntryName,
            lcsStatusRoutProtLispPacketCounterEntryLocator
          }
    ::= { lcsStatusRoutProtLispPacketCounterTable 1 }

LcsStatusRoutProtLispPacketCounterEntry ::= SEQUENCE {
            lcsStatusRoutProtLispPacketCounterEntryName OCTET STRING,
            lcsStatusRoutProtLispPacketCounterEntryLocator OCTET STRING,
            lcsStatusRoutProtLispPacketCounterEntryPacketsIn Counter64,
            lcsStatusRoutProtLispPacketCounterEntryBytesIn Counter64,
            lcsStatusRoutProtLispPacketCounterEntryPacketsOut Counter64,
            lcsStatusRoutProtLispPacketCounterEntryBytesOut Counter64
    }

-- {COLUMN} 1.3.6.1.4.1.2356.11.1.93.4.3.1.1
lcsStatusRoutProtLispPacketCounterEntryName OBJECT-TYPE
    SYNTAX     OCTET STRING (SIZE(0..24))
    MAX-ACCESS read-only
    STATUS     current
    DESCRIPTION
            "-- empty --"
    ::= { lcsStatusRoutProtLispPacketCounterEntry 1 }

-- {COLUMN} 1.3.6.1.4.1.2356.11.1.93.4.3.1.2
lcsStatusRoutProtLispPacketCounterEntryLocator OBJECT-TYPE
    SYNTAX     OCTET STRING (SIZE(0..39))
    MAX-ACCESS read-only
    STATUS     current
    DESCRIPTION
            "-- empty --"
    ::= { lcsStatusRoutProtLispPacketCounterEntry 2 }

-- {COLUMN} 1.3.6.1.4.1.2356.11.1.93.4.3.1.3
lcsStatusRoutProtLispPacketCounterEntryPacketsIn OBJECT-TYPE
    SYNTAX     Counter64
    MAX-ACCESS read-only
    STATUS     current
    DESCRIPTION
            "-- empty --"
    ::= { lcsStatusRoutProtLispPacketCounterEntry 3 }

-- {COLUMN} 1.3.6.1.4.1.2356.11.1.93.4.3.1.4
lcsStatusRoutProtLispPacketCounterEntryBytesIn OBJECT-TYPE
    SYNTAX     Counter64
    MAX-ACCESS read-only
    STATUS     current
    DESCRIPTION
            "-- empty --"
    ::= { lcsStatusRoutProtLispPacketCounterEntry 4 }

-- {COLUMN} 1.3.6.1.4.1.2356.11.1.93.4.3.1.5
lcsStatusRoutProtLispPacketCounterEntryPacketsOut OBJECT-TYPE
    SYNTAX     Counter64
    MAX-ACCESS read-only
    STATUS     current
    DESCRIPTION
            "-- empty --"
    ::= { lcsStatusRoutProtLispPacketCounterEntry 5 }

-- {COLUMN} 1.3.6.1.4.1.2356.11.1.93.4.3.1.6
lcsStatusRoutProtLispPacketCounterEntryBytesOut OBJECT-TYPE
    SYNTAX     Counter64
    MAX-ACCESS read-only
    STATUS     current
    DESCRIPTION
            "-- empty --"
    ::= { lcsStatusRoutProtLispPacketCounterEntry 6 }

-- {SCALAR} 1.3.6.1.4.1.2356.11.1.93.4.4
lcsStatusRoutProtLispFlushMapCache OBJECT-TYPE
    SYNTAX     DisplayString
    MAX-ACCESS read-write
    STATUS     current
    DESCRIPTION
            "-- empty --"
    ::= { lcsStatusRoutProtLisp 4 }

-- {SCALAR} 1.3.6.1.4.1.2356.11.1.93.4.5
lcsStatusRoutProtLispTunnels OBJECT-TYPE
    SYNTAX     Integer32 (0..2147483647)
    MAX-ACCESS read-only
    STATUS     current
    DESCRIPTION
            "-- empty --"
    ::= { lcsStatusRoutProtLisp 5 }

-- {NODE} 1.3.6.1.4.1.2356.11.1.94
lcsStatusPacketCapture OBJECT IDENTIFIER ::= { lcsStatus 94 }

-- {SCALAR} 1.3.6.1.4.1.2356.11.1.94.1
lcsStatusPacketCapturePacketsCaptured OBJECT-TYPE
    SYNTAX     Counter32
    MAX-ACCESS read-only
    STATUS     current
    DESCRIPTION
            "-- empty --"
    ::= { lcsStatusPacketCapture 1 }

-- {SCALAR} 1.3.6.1.4.1.2356.11.1.94.2
lcsStatusPacketCapturePacketsFiltered OBJECT-TYPE
    SYNTAX     Counter32
    MAX-ACCESS read-only
    STATUS     current
    DESCRIPTION
            "-- empty --"
    ::= { lcsStatusPacketCapture 2 }

-- {SCALAR} 1.3.6.1.4.1.2356.11.1.94.3
lcsStatusPacketCapturePacketsDropped OBJECT-TYPE
    SYNTAX     Counter32
    MAX-ACCESS read-only
    STATUS     current
    DESCRIPTION
            "-- empty --"
    ::= { lcsStatusPacketCapture 3 }

-- {SCALAR} 1.3.6.1.4.1.2356.11.1.94.100
lcsStatusPacketCaptureDeleteValues OBJECT-TYPE
    SYNTAX     DisplayString
    MAX-ACCESS read-write
    STATUS     current
    DESCRIPTION
            "-- empty --"
    ::= { lcsStatusPacketCapture 100 }

-- {NODE} 1.3.6.1.4.1.2356.11.1.95
lcsStatusLay7AppDet OBJECT IDENTIFIER ::= { lcsStatus 95 }

-- {TABLE} 1.3.6.1.4.1.2356.11.1.95.1
lcsStatusLay7AppDetApplicationsTable OBJECT-TYPE
    SYNTAX     SEQUENCE OF LcsStatusLay7AppDetApplicationsEntry
    MAX-ACCESS not-accessible
    STATUS     current
    DESCRIPTION
            "-- empty --"
    ::= { lcsStatusLay7AppDet 1 }

-- {ROW} 1.3.6.1.4.1.2356.11.1.95.1.1
lcsStatusLay7AppDetApplicationsEntry OBJECT-TYPE
    SYNTAX     LcsStatusLay7AppDetApplicationsEntry
    MAX-ACCESS not-accessible
    STATUS     current
    DESCRIPTION
            ""
    INDEX {
            lcsStatusLay7AppDetApplicationsEntryAppname,
            lcsStatusLay7AppDetApplicationsEntryUserName,
            lcsStatusLay7AppDetApplicationsEntryUserMac
          }
    ::= { lcsStatusLay7AppDetApplicationsTable 1 }

LcsStatusLay7AppDetApplicationsEntry ::= SEQUENCE {
            lcsStatusLay7AppDetApplicationsEntryAppname DisplayString,
            lcsStatusLay7AppDetApplicationsEntryUserName DisplayString,
            lcsStatusLay7AppDetApplicationsEntryUserMac DisplayString,
            lcsStatusLay7AppDetApplicationsEntryPspotUserName DisplayString,
            lcsStatusLay7AppDetApplicationsEntryTxKbytes Counter64,
            lcsStatusLay7AppDetApplicationsEntryRxKbytes Counter64,
            lcsStatusLay7AppDetApplicationsEntryVlanId Integer32,
            lcsStatusLay7AppDetApplicationsEntryInterface DisplayString
    }

-- {COLUMN} 1.3.6.1.4.1.2356.11.1.95.1.1.1
lcsStatusLay7AppDetApplicationsEntryAppname OBJECT-TYPE
    SYNTAX     DisplayString (SIZE(0..64))
    MAX-ACCESS read-only
    STATUS     current
    DESCRIPTION
            "Application name"
    ::= { lcsStatusLay7AppDetApplicationsEntry 1 }

-- {COLUMN} 1.3.6.1.4.1.2356.11.1.95.1.1.2
lcsStatusLay7AppDetApplicationsEntryUserName OBJECT-TYPE
    SYNTAX     DisplayString (SIZE(0..64))
    MAX-ACCESS read-only
    STATUS     current
    DESCRIPTION
            "-- empty --"
    ::= { lcsStatusLay7AppDetApplicationsEntry 2 }

-- {COLUMN} 1.3.6.1.4.1.2356.11.1.95.1.1.3
lcsStatusLay7AppDetApplicationsEntryUserMac OBJECT-TYPE
    SYNTAX     DisplayString (SIZE(0..12))
    MAX-ACCESS read-only
    STATUS     current
    DESCRIPTION
            "-- empty --"
    ::= { lcsStatusLay7AppDetApplicationsEntry 3 }

-- {COLUMN} 1.3.6.1.4.1.2356.11.1.95.1.1.4
lcsStatusLay7AppDetApplicationsEntryPspotUserName OBJECT-TYPE
    SYNTAX     DisplayString (SIZE(0..64))
    MAX-ACCESS read-only
    STATUS     current
    DESCRIPTION
            "-- empty --"
    ::= { lcsStatusLay7AppDetApplicationsEntry 4 }

-- {COLUMN} 1.3.6.1.4.1.2356.11.1.95.1.1.5
lcsStatusLay7AppDetApplicationsEntryTxKbytes OBJECT-TYPE
    SYNTAX     Counter64
    MAX-ACCESS read-only
    STATUS     current
    DESCRIPTION
            "-- empty --"
    ::= { lcsStatusLay7AppDetApplicationsEntry 5 }

-- {COLUMN} 1.3.6.1.4.1.2356.11.1.95.1.1.6
lcsStatusLay7AppDetApplicationsEntryRxKbytes OBJECT-TYPE
    SYNTAX     Counter64
    MAX-ACCESS read-only
    STATUS     current
    DESCRIPTION
            "-- empty --"
    ::= { lcsStatusLay7AppDetApplicationsEntry 6 }

-- {COLUMN} 1.3.6.1.4.1.2356.11.1.95.1.1.7
lcsStatusLay7AppDetApplicationsEntryVlanId OBJECT-TYPE
    SYNTAX     Integer32 (0..65535)
    MAX-ACCESS read-only
    STATUS     current
    DESCRIPTION
            "-- empty --"
    ::= { lcsStatusLay7AppDetApplicationsEntry 7 }

-- {COLUMN} 1.3.6.1.4.1.2356.11.1.95.1.1.8
lcsStatusLay7AppDetApplicationsEntryInterface OBJECT-TYPE
    SYNTAX     DisplayString (SIZE(0..64))
    MAX-ACCESS read-only
    STATUS     current
    DESCRIPTION
            "-- empty --"
    ::= { lcsStatusLay7AppDetApplicationsEntry 8 }

-- {TABLE} 1.3.6.1.4.1.2356.11.1.95.2
lcsStatusLay7AppDetTotTrafperAppTable OBJECT-TYPE
    SYNTAX     SEQUENCE OF LcsStatusLay7AppDetTotTrafperAppEntry
    MAX-ACCESS not-accessible
    STATUS     current
    DESCRIPTION
            "Total Traffic per Application"
    ::= { lcsStatusLay7AppDet 2 }

-- {ROW} 1.3.6.1.4.1.2356.11.1.95.2.1
lcsStatusLay7AppDetTotTrafperAppEntry OBJECT-TYPE
    SYNTAX     LcsStatusLay7AppDetTotTrafperAppEntry
    MAX-ACCESS not-accessible
    STATUS     current
    DESCRIPTION
            ""
    INDEX {
            lcsStatusLay7AppDetTotTrafperAppEntryAppname
          }
    ::= { lcsStatusLay7AppDetTotTrafperAppTable 1 }

LcsStatusLay7AppDetTotTrafperAppEntry ::= SEQUENCE {
            lcsStatusLay7AppDetTotTrafperAppEntryAppname DisplayString,
            lcsStatusLay7AppDetTotTrafperAppEntryTxKbytes Counter64,
            lcsStatusLay7AppDetTotTrafperAppEntryRxKbytes Counter64,
            lcsStatusLay7AppDetTotTrafperAppEntryTxKbytesDay2 Counter64,
            lcsStatusLay7AppDetTotTrafperAppEntryRxKbytesDay2 Counter64,
            lcsStatusLay7AppDetTotTrafperAppEntryTxKbytesDay3 Counter64,
            lcsStatusLay7AppDetTotTrafperAppEntryRxKbytesDay3 Counter64,
            lcsStatusLay7AppDetTotTrafperAppEntryTxKbytesDay4 Counter64,
            lcsStatusLay7AppDetTotTrafperAppEntryRxKbytesDay4 Counter64,
            lcsStatusLay7AppDetTotTrafperAppEntryTxKbytesDay5 Counter64,
            lcsStatusLay7AppDetTotTrafperAppEntryRxKbytesDay5 Counter64,
            lcsStatusLay7AppDetTotTrafperAppEntryTxKbytesDay6 Counter64,
            lcsStatusLay7AppDetTotTrafperAppEntryRxKbytesDay6 Counter64,
            lcsStatusLay7AppDetTotTrafperAppEntryTxKbytesCurrDay Counter64,
            lcsStatusLay7AppDetTotTrafperAppEntryRxKbytesCurrDay Counter64
    }

-- {COLUMN} 1.3.6.1.4.1.2356.11.1.95.2.1.1
lcsStatusLay7AppDetTotTrafperAppEntryAppname OBJECT-TYPE
    SYNTAX     DisplayString (SIZE(0..64))
    MAX-ACCESS read-only
    STATUS     current
    DESCRIPTION
            "Application name"
    ::= { lcsStatusLay7AppDetTotTrafperAppEntry 1 }

-- {COLUMN} 1.3.6.1.4.1.2356.11.1.95.2.1.2
lcsStatusLay7AppDetTotTrafperAppEntryTxKbytes OBJECT-TYPE
    SYNTAX     Counter64
    MAX-ACCESS read-only
    STATUS     current
    DESCRIPTION
            "-- empty --"
    ::= { lcsStatusLay7AppDetTotTrafperAppEntry 2 }

-- {COLUMN} 1.3.6.1.4.1.2356.11.1.95.2.1.3
lcsStatusLay7AppDetTotTrafperAppEntryRxKbytes OBJECT-TYPE
    SYNTAX     Counter64
    MAX-ACCESS read-only
    STATUS     current
    DESCRIPTION
            "-- empty --"
    ::= { lcsStatusLay7AppDetTotTrafperAppEntry 3 }

-- {COLUMN} 1.3.6.1.4.1.2356.11.1.95.2.1.4
lcsStatusLay7AppDetTotTrafperAppEntryTxKbytesDay2 OBJECT-TYPE
    SYNTAX     Counter64
    MAX-ACCESS read-only
    STATUS     current
    DESCRIPTION
            "-- empty --"
    ::= { lcsStatusLay7AppDetTotTrafperAppEntry 4 }

-- {COLUMN} 1.3.6.1.4.1.2356.11.1.95.2.1.5
lcsStatusLay7AppDetTotTrafperAppEntryRxKbytesDay2 OBJECT-TYPE
    SYNTAX     Counter64
    MAX-ACCESS read-only
    STATUS     current
    DESCRIPTION
            "-- empty --"
    ::= { lcsStatusLay7AppDetTotTrafperAppEntry 5 }

-- {COLUMN} 1.3.6.1.4.1.2356.11.1.95.2.1.6
lcsStatusLay7AppDetTotTrafperAppEntryTxKbytesDay3 OBJECT-TYPE
    SYNTAX     Counter64
    MAX-ACCESS read-only
    STATUS     current
    DESCRIPTION
            "-- empty --"
    ::= { lcsStatusLay7AppDetTotTrafperAppEntry 6 }

-- {COLUMN} 1.3.6.1.4.1.2356.11.1.95.2.1.7
lcsStatusLay7AppDetTotTrafperAppEntryRxKbytesDay3 OBJECT-TYPE
    SYNTAX     Counter64
    MAX-ACCESS read-only
    STATUS     current
    DESCRIPTION
            "-- empty --"
    ::= { lcsStatusLay7AppDetTotTrafperAppEntry 7 }

-- {COLUMN} 1.3.6.1.4.1.2356.11.1.95.2.1.8
lcsStatusLay7AppDetTotTrafperAppEntryTxKbytesDay4 OBJECT-TYPE
    SYNTAX     Counter64
    MAX-ACCESS read-only
    STATUS     current
    DESCRIPTION
            "-- empty --"
    ::= { lcsStatusLay7AppDetTotTrafperAppEntry 8 }

-- {COLUMN} 1.3.6.1.4.1.2356.11.1.95.2.1.9
lcsStatusLay7AppDetTotTrafperAppEntryRxKbytesDay4 OBJECT-TYPE
    SYNTAX     Counter64
    MAX-ACCESS read-only
    STATUS     current
    DESCRIPTION
            "-- empty --"
    ::= { lcsStatusLay7AppDetTotTrafperAppEntry 9 }

-- {COLUMN} 1.3.6.1.4.1.2356.11.1.95.2.1.10
lcsStatusLay7AppDetTotTrafperAppEntryTxKbytesDay5 OBJECT-TYPE
    SYNTAX     Counter64
    MAX-ACCESS read-only
    STATUS     current
    DESCRIPTION
            "-- empty --"
    ::= { lcsStatusLay7AppDetTotTrafperAppEntry 10 }

-- {COLUMN} 1.3.6.1.4.1.2356.11.1.95.2.1.11
lcsStatusLay7AppDetTotTrafperAppEntryRxKbytesDay5 OBJECT-TYPE
    SYNTAX     Counter64
    MAX-ACCESS read-only
    STATUS     current
    DESCRIPTION
            "-- empty --"
    ::= { lcsStatusLay7AppDetTotTrafperAppEntry 11 }

-- {COLUMN} 1.3.6.1.4.1.2356.11.1.95.2.1.12
lcsStatusLay7AppDetTotTrafperAppEntryTxKbytesDay6 OBJECT-TYPE
    SYNTAX     Counter64
    MAX-ACCESS read-only
    STATUS     current
    DESCRIPTION
            "-- empty --"
    ::= { lcsStatusLay7AppDetTotTrafperAppEntry 12 }

-- {COLUMN} 1.3.6.1.4.1.2356.11.1.95.2.1.13
lcsStatusLay7AppDetTotTrafperAppEntryRxKbytesDay6 OBJECT-TYPE
    SYNTAX     Counter64
    MAX-ACCESS read-only
    STATUS     current
    DESCRIPTION
            "-- empty --"
    ::= { lcsStatusLay7AppDetTotTrafperAppEntry 13 }

-- {COLUMN} 1.3.6.1.4.1.2356.11.1.95.2.1.14
lcsStatusLay7AppDetTotTrafperAppEntryTxKbytesCurrDay OBJECT-TYPE
    SYNTAX     Counter64
    MAX-ACCESS read-only
    STATUS     current
    DESCRIPTION
            "-- empty --"
    ::= { lcsStatusLay7AppDetTotTrafperAppEntry 14 }

-- {COLUMN} 1.3.6.1.4.1.2356.11.1.95.2.1.15
lcsStatusLay7AppDetTotTrafperAppEntryRxKbytesCurrDay OBJECT-TYPE
    SYNTAX     Counter64
    MAX-ACCESS read-only
    STATUS     current
    DESCRIPTION
            "-- empty --"
    ::= { lcsStatusLay7AppDetTotTrafperAppEntry 15 }

-- {TABLE} 1.3.6.1.4.1.2356.11.1.95.3
lcsStatusLay7AppDetTotTrafperUserTable OBJECT-TYPE
    SYNTAX     SEQUENCE OF LcsStatusLay7AppDetTotTrafperUserEntry
    MAX-ACCESS not-accessible
    STATUS     current
    DESCRIPTION
            "Total Traffic per User"
    ::= { lcsStatusLay7AppDet 3 }

-- {ROW} 1.3.6.1.4.1.2356.11.1.95.3.1
lcsStatusLay7AppDetTotTrafperUserEntry OBJECT-TYPE
    SYNTAX     LcsStatusLay7AppDetTotTrafperUserEntry
    MAX-ACCESS not-accessible
    STATUS     current
    DESCRIPTION
            ""
    INDEX {
            lcsStatusLay7AppDetTotTrafperUserEntryUserMac
          }
    ::= { lcsStatusLay7AppDetTotTrafperUserTable 1 }

LcsStatusLay7AppDetTotTrafperUserEntry ::= SEQUENCE {
            lcsStatusLay7AppDetTotTrafperUserEntryUserMac DisplayString,
            lcsStatusLay7AppDetTotTrafperUserEntryUserName DisplayString,
            lcsStatusLay7AppDetTotTrafperUserEntryPspotUserName DisplayString,
            lcsStatusLay7AppDetTotTrafperUserEntryTxKbytes Counter64,
            lcsStatusLay7AppDetTotTrafperUserEntryRxKbytes Counter64,
            lcsStatusLay7AppDetTotTrafperUserEntryTxKbytesDay2 Counter64,
            lcsStatusLay7AppDetTotTrafperUserEntryRxKbytesDay2 Counter64,
            lcsStatusLay7AppDetTotTrafperUserEntryTxKbytesDay3 Counter64,
            lcsStatusLay7AppDetTotTrafperUserEntryRxKbytesDay3 Counter64,
            lcsStatusLay7AppDetTotTrafperUserEntryTxKbytesDay4 Counter64,
            lcsStatusLay7AppDetTotTrafperUserEntryRxKbytesDay4 Counter64,
            lcsStatusLay7AppDetTotTrafperUserEntryTxKbytesDay5 Counter64,
            lcsStatusLay7AppDetTotTrafperUserEntryRxKbytesDay5 Counter64,
            lcsStatusLay7AppDetTotTrafperUserEntryTxKbytesDay6 Counter64,
            lcsStatusLay7AppDetTotTrafperUserEntryRxKbytesDay6 Counter64,
            lcsStatusLay7AppDetTotTrafperUserEntryTxKbytesCurrDay Counter64,
            lcsStatusLay7AppDetTotTrafperUserEntryRxKbytesCurrDay Counter64,
            lcsStatusLay7AppDetTotTrafperUserEntryVlanId Integer32,
            lcsStatusLay7AppDetTotTrafperUserEntryInterface DisplayString
    }

-- {COLUMN} 1.3.6.1.4.1.2356.11.1.95.3.1.1
lcsStatusLay7AppDetTotTrafperUserEntryUserMac OBJECT-TYPE
    SYNTAX     DisplayString (SIZE(0..12))
    MAX-ACCESS read-only
    STATUS     current
    DESCRIPTION
            "-- empty --"
    ::= { lcsStatusLay7AppDetTotTrafperUserEntry 1 }

-- {COLUMN} 1.3.6.1.4.1.2356.11.1.95.3.1.2
lcsStatusLay7AppDetTotTrafperUserEntryUserName OBJECT-TYPE
    SYNTAX     DisplayString (SIZE(0..64))
    MAX-ACCESS read-only
    STATUS     current
    DESCRIPTION
            "-- empty --"
    ::= { lcsStatusLay7AppDetTotTrafperUserEntry 2 }

-- {COLUMN} 1.3.6.1.4.1.2356.11.1.95.3.1.3
lcsStatusLay7AppDetTotTrafperUserEntryPspotUserName OBJECT-TYPE
    SYNTAX     DisplayString (SIZE(0..64))
    MAX-ACCESS read-only
    STATUS     current
    DESCRIPTION
            "-- empty --"
    ::= { lcsStatusLay7AppDetTotTrafperUserEntry 3 }

-- {COLUMN} 1.3.6.1.4.1.2356.11.1.95.3.1.4
lcsStatusLay7AppDetTotTrafperUserEntryTxKbytes OBJECT-TYPE
    SYNTAX     Counter64
    MAX-ACCESS read-only
    STATUS     current
    DESCRIPTION
            "-- empty --"
    ::= { lcsStatusLay7AppDetTotTrafperUserEntry 4 }

-- {COLUMN} 1.3.6.1.4.1.2356.11.1.95.3.1.5
lcsStatusLay7AppDetTotTrafperUserEntryRxKbytes OBJECT-TYPE
    SYNTAX     Counter64
    MAX-ACCESS read-only
    STATUS     current
    DESCRIPTION
            "-- empty --"
    ::= { lcsStatusLay7AppDetTotTrafperUserEntry 5 }

-- {COLUMN} 1.3.6.1.4.1.2356.11.1.95.3.1.6
lcsStatusLay7AppDetTotTrafperUserEntryTxKbytesDay2 OBJECT-TYPE
    SYNTAX     Counter64
    MAX-ACCESS read-only
    STATUS     current
    DESCRIPTION
            "-- empty --"
    ::= { lcsStatusLay7AppDetTotTrafperUserEntry 6 }

-- {COLUMN} 1.3.6.1.4.1.2356.11.1.95.3.1.7
lcsStatusLay7AppDetTotTrafperUserEntryRxKbytesDay2 OBJECT-TYPE
    SYNTAX     Counter64
    MAX-ACCESS read-only
    STATUS     current
    DESCRIPTION
            "-- empty --"
    ::= { lcsStatusLay7AppDetTotTrafperUserEntry 7 }

-- {COLUMN} 1.3.6.1.4.1.2356.11.1.95.3.1.8
lcsStatusLay7AppDetTotTrafperUserEntryTxKbytesDay3 OBJECT-TYPE
    SYNTAX     Counter64
    MAX-ACCESS read-only
    STATUS     current
    DESCRIPTION
            "-- empty --"
    ::= { lcsStatusLay7AppDetTotTrafperUserEntry 8 }

-- {COLUMN} 1.3.6.1.4.1.2356.11.1.95.3.1.9
lcsStatusLay7AppDetTotTrafperUserEntryRxKbytesDay3 OBJECT-TYPE
    SYNTAX     Counter64
    MAX-ACCESS read-only
    STATUS     current
    DESCRIPTION
            "-- empty --"
    ::= { lcsStatusLay7AppDetTotTrafperUserEntry 9 }

-- {COLUMN} 1.3.6.1.4.1.2356.11.1.95.3.1.10
lcsStatusLay7AppDetTotTrafperUserEntryTxKbytesDay4 OBJECT-TYPE
    SYNTAX     Counter64
    MAX-ACCESS read-only
    STATUS     current
    DESCRIPTION
            "-- empty --"
    ::= { lcsStatusLay7AppDetTotTrafperUserEntry 10 }

-- {COLUMN} 1.3.6.1.4.1.2356.11.1.95.3.1.11
lcsStatusLay7AppDetTotTrafperUserEntryRxKbytesDay4 OBJECT-TYPE
    SYNTAX     Counter64
    MAX-ACCESS read-only
    STATUS     current
    DESCRIPTION
            "-- empty --"
    ::= { lcsStatusLay7AppDetTotTrafperUserEntry 11 }

-- {COLUMN} 1.3.6.1.4.1.2356.11.1.95.3.1.12
lcsStatusLay7AppDetTotTrafperUserEntryTxKbytesDay5 OBJECT-TYPE
    SYNTAX     Counter64
    MAX-ACCESS read-only
    STATUS     current
    DESCRIPTION
            "-- empty --"
    ::= { lcsStatusLay7AppDetTotTrafperUserEntry 12 }

-- {COLUMN} 1.3.6.1.4.1.2356.11.1.95.3.1.13
lcsStatusLay7AppDetTotTrafperUserEntryRxKbytesDay5 OBJECT-TYPE
    SYNTAX     Counter64
    MAX-ACCESS read-only
    STATUS     current
    DESCRIPTION
            "-- empty --"
    ::= { lcsStatusLay7AppDetTotTrafperUserEntry 13 }

-- {COLUMN} 1.3.6.1.4.1.2356.11.1.95.3.1.14
lcsStatusLay7AppDetTotTrafperUserEntryTxKbytesDay6 OBJECT-TYPE
    SYNTAX     Counter64
    MAX-ACCESS read-only
    STATUS     current
    DESCRIPTION
            "-- empty --"
    ::= { lcsStatusLay7AppDetTotTrafperUserEntry 14 }

-- {COLUMN} 1.3.6.1.4.1.2356.11.1.95.3.1.15
lcsStatusLay7AppDetTotTrafperUserEntryRxKbytesDay6 OBJECT-TYPE
    SYNTAX     Counter64
    MAX-ACCESS read-only
    STATUS     current
    DESCRIPTION
            "-- empty --"
    ::= { lcsStatusLay7AppDetTotTrafperUserEntry 15 }

-- {COLUMN} 1.3.6.1.4.1.2356.11.1.95.3.1.16
lcsStatusLay7AppDetTotTrafperUserEntryTxKbytesCurrDay OBJECT-TYPE
    SYNTAX     Counter64
    MAX-ACCESS read-only
    STATUS     current
    DESCRIPTION
            "-- empty --"
    ::= { lcsStatusLay7AppDetTotTrafperUserEntry 16 }

-- {COLUMN} 1.3.6.1.4.1.2356.11.1.95.3.1.17
lcsStatusLay7AppDetTotTrafperUserEntryRxKbytesCurrDay OBJECT-TYPE
    SYNTAX     Counter64
    MAX-ACCESS read-only
    STATUS     current
    DESCRIPTION
            "-- empty --"
    ::= { lcsStatusLay7AppDetTotTrafperUserEntry 17 }

-- {COLUMN} 1.3.6.1.4.1.2356.11.1.95.3.1.18
lcsStatusLay7AppDetTotTrafperUserEntryVlanId OBJECT-TYPE
    SYNTAX     Integer32 (0..65535)
    MAX-ACCESS read-only
    STATUS     current
    DESCRIPTION
            "-- empty --"
    ::= { lcsStatusLay7AppDetTotTrafperUserEntry 18 }

-- {COLUMN} 1.3.6.1.4.1.2356.11.1.95.3.1.19
lcsStatusLay7AppDetTotTrafperUserEntryInterface OBJECT-TYPE
    SYNTAX     DisplayString (SIZE(0..64))
    MAX-ACCESS read-only
    STATUS     current
    DESCRIPTION
            "-- empty --"
    ::= { lcsStatusLay7AppDetTotTrafperUserEntry 19 }

-- {TABLE} 1.3.6.1.4.1.2356.11.1.95.4
lcsStatusLay7AppDetHttpHttpsHitListTable OBJECT-TYPE
    SYNTAX     SEQUENCE OF LcsStatusLay7AppDetHttpHttpsHitListEntry
    MAX-ACCESS not-accessible
    STATUS     current
    DESCRIPTION
            "-- empty --"
    ::= { lcsStatusLay7AppDet 4 }

-- {ROW} 1.3.6.1.4.1.2356.11.1.95.4.1
lcsStatusLay7AppDetHttpHttpsHitListEntry OBJECT-TYPE
    SYNTAX     LcsStatusLay7AppDetHttpHttpsHitListEntry
    MAX-ACCESS not-accessible
    STATUS     current
    DESCRIPTION
            ""
    INDEX {
            lcsStatusLay7AppDetHttpHttpsHitListEntryHostName
          }
    ::= { lcsStatusLay7AppDetHttpHttpsHitListTable 1 }

LcsStatusLay7AppDetHttpHttpsHitListEntry ::= SEQUENCE {
            lcsStatusLay7AppDetHttpHttpsHitListEntryHostName DisplayString,
            lcsStatusLay7AppDetHttpHttpsHitListEntryHits Integer32
    }

-- {COLUMN} 1.3.6.1.4.1.2356.11.1.95.4.1.1
lcsStatusLay7AppDetHttpHttpsHitListEntryHostName OBJECT-TYPE
    SYNTAX     DisplayString (SIZE(0..254))
    MAX-ACCESS read-only
    STATUS     current
    DESCRIPTION
            "-- empty --"
    ::= { lcsStatusLay7AppDetHttpHttpsHitListEntry 1 }

-- {COLUMN} 1.3.6.1.4.1.2356.11.1.95.4.1.2
lcsStatusLay7AppDetHttpHttpsHitListEntryHits OBJECT-TYPE
    SYNTAX     Integer32 (0..2147483647)
    MAX-ACCESS read-only
    STATUS     current
    DESCRIPTION
            "-- empty --"
    ::= { lcsStatusLay7AppDetHttpHttpsHitListEntry 2 }

-- {SCALAR} 1.3.6.1.4.1.2356.11.1.95.5
lcsStatusLay7AppDetOperating OBJECT-TYPE
    SYNTAX     INTEGER {
                  eNo (0),
                  eYes (1)
            }
    MAX-ACCESS read-only
    STATUS     current
    DESCRIPTION
            "-- empty --"
    ::= { lcsStatusLay7AppDet 5 }

-- {SCALAR} 1.3.6.1.4.1.2356.11.1.95.6
lcsStatusLay7AppDetDeleteValues OBJECT-TYPE
    SYNTAX     DisplayString
    MAX-ACCESS read-write
    STATUS     current
    DESCRIPTION
            "-- empty --"
    ::= { lcsStatusLay7AppDet 6 }

-- {TABLE} 1.3.6.1.4.1.2356.11.1.95.8
lcsStatusLay7AppDetTotalTrafficPerProtocolTable OBJECT-TYPE
    SYNTAX     SEQUENCE OF LcsStatusLay7AppDetTotalTrafficPerProtocolEntry
    MAX-ACCESS not-accessible
    STATUS     current
    DESCRIPTION
            "-- empty --"
    ::= { lcsStatusLay7AppDet 8 }

-- {ROW} 1.3.6.1.4.1.2356.11.1.95.8.1
lcsStatusLay7AppDetTotalTrafficPerProtocolEntry OBJECT-TYPE
    SYNTAX     LcsStatusLay7AppDetTotalTrafficPerProtocolEntry
    MAX-ACCESS not-accessible
    STATUS     current
    DESCRIPTION
            ""
    INDEX {
            lcsStatusLay7AppDetTotalTrafficPerProtocolEntryProtocolName
          }
    ::= { lcsStatusLay7AppDetTotalTrafficPerProtocolTable 1 }

LcsStatusLay7AppDetTotalTrafficPerProtocolEntry ::= SEQUENCE {
            lcsStatusLay7AppDetTotalTrafficPerProtocolEntryProtocolName DisplayString,
            lcsStatusLay7AppDetTotalTrafficPerProtocolEntryTxKbytes Counter64,
            lcsStatusLay7AppDetTotalTrafficPerProtocolEntryRxKbytes Counter64,
            lcsStatusLay7AppDetTotalTrafficPerProtocolEntryTxKbytesCurrDay Counter64,
            lcsStatusLay7AppDetTotalTrafficPerProtocolEntryRxKbytesCurrDay Counter64,
            lcsStatusLay7AppDetTotalTrafficPerProtocolEntryTxKbytesDay2 Counter64,
            lcsStatusLay7AppDetTotalTrafficPerProtocolEntryRxKbytesDay2 Counter64,
            lcsStatusLay7AppDetTotalTrafficPerProtocolEntryTxKbytesDay3 Counter64,
            lcsStatusLay7AppDetTotalTrafficPerProtocolEntryRxKbytesDay3 Counter64,
            lcsStatusLay7AppDetTotalTrafficPerProtocolEntryTxKbytesDay4 Counter64,
            lcsStatusLay7AppDetTotalTrafficPerProtocolEntryRxKbytesDay4 Counter64,
            lcsStatusLay7AppDetTotalTrafficPerProtocolEntryTxKbytesDay5 Counter64,
            lcsStatusLay7AppDetTotalTrafficPerProtocolEntryRxKbytesDay5 Counter64,
            lcsStatusLay7AppDetTotalTrafficPerProtocolEntryTxKbytesDay6 Counter64,
            lcsStatusLay7AppDetTotalTrafficPerProtocolEntryRxKbytesDay6 Counter64
    }

-- {COLUMN} 1.3.6.1.4.1.2356.11.1.95.8.1.1
lcsStatusLay7AppDetTotalTrafficPerProtocolEntryProtocolName OBJECT-TYPE
    SYNTAX     DisplayString (SIZE(0..5))
    MAX-ACCESS read-only
    STATUS     current
    DESCRIPTION
            "-- empty --"
    ::= { lcsStatusLay7AppDetTotalTrafficPerProtocolEntry 1 }

-- {COLUMN} 1.3.6.1.4.1.2356.11.1.95.8.1.2
lcsStatusLay7AppDetTotalTrafficPerProtocolEntryTxKbytes OBJECT-TYPE
    SYNTAX     Counter64
    MAX-ACCESS read-only
    STATUS     current
    DESCRIPTION
            "-- empty --"
    ::= { lcsStatusLay7AppDetTotalTrafficPerProtocolEntry 2 }

-- {COLUMN} 1.3.6.1.4.1.2356.11.1.95.8.1.3
lcsStatusLay7AppDetTotalTrafficPerProtocolEntryRxKbytes OBJECT-TYPE
    SYNTAX     Counter64
    MAX-ACCESS read-only
    STATUS     current
    DESCRIPTION
            "-- empty --"
    ::= { lcsStatusLay7AppDetTotalTrafficPerProtocolEntry 3 }

-- {COLUMN} 1.3.6.1.4.1.2356.11.1.95.8.1.4
lcsStatusLay7AppDetTotalTrafficPerProtocolEntryTxKbytesCurrDay OBJECT-TYPE
    SYNTAX     Counter64
    MAX-ACCESS read-only
    STATUS     current
    DESCRIPTION
            "-- empty --"
    ::= { lcsStatusLay7AppDetTotalTrafficPerProtocolEntry 4 }

-- {COLUMN} 1.3.6.1.4.1.2356.11.1.95.8.1.5
lcsStatusLay7AppDetTotalTrafficPerProtocolEntryRxKbytesCurrDay OBJECT-TYPE
    SYNTAX     Counter64
    MAX-ACCESS read-only
    STATUS     current
    DESCRIPTION
            "-- empty --"
    ::= { lcsStatusLay7AppDetTotalTrafficPerProtocolEntry 5 }

-- {COLUMN} 1.3.6.1.4.1.2356.11.1.95.8.1.6
lcsStatusLay7AppDetTotalTrafficPerProtocolEntryTxKbytesDay2 OBJECT-TYPE
    SYNTAX     Counter64
    MAX-ACCESS read-only
    STATUS     current
    DESCRIPTION
            "-- empty --"
    ::= { lcsStatusLay7AppDetTotalTrafficPerProtocolEntry 6 }

-- {COLUMN} 1.3.6.1.4.1.2356.11.1.95.8.1.7
lcsStatusLay7AppDetTotalTrafficPerProtocolEntryRxKbytesDay2 OBJECT-TYPE
    SYNTAX     Counter64
    MAX-ACCESS read-only
    STATUS     current
    DESCRIPTION
            "-- empty --"
    ::= { lcsStatusLay7AppDetTotalTrafficPerProtocolEntry 7 }

-- {COLUMN} 1.3.6.1.4.1.2356.11.1.95.8.1.8
lcsStatusLay7AppDetTotalTrafficPerProtocolEntryTxKbytesDay3 OBJECT-TYPE
    SYNTAX     Counter64
    MAX-ACCESS read-only
    STATUS     current
    DESCRIPTION
            "-- empty --"
    ::= { lcsStatusLay7AppDetTotalTrafficPerProtocolEntry 8 }

-- {COLUMN} 1.3.6.1.4.1.2356.11.1.95.8.1.9
lcsStatusLay7AppDetTotalTrafficPerProtocolEntryRxKbytesDay3 OBJECT-TYPE
    SYNTAX     Counter64
    MAX-ACCESS read-only
    STATUS     current
    DESCRIPTION
            "-- empty --"
    ::= { lcsStatusLay7AppDetTotalTrafficPerProtocolEntry 9 }

-- {COLUMN} 1.3.6.1.4.1.2356.11.1.95.8.1.10
lcsStatusLay7AppDetTotalTrafficPerProtocolEntryTxKbytesDay4 OBJECT-TYPE
    SYNTAX     Counter64
    MAX-ACCESS read-only
    STATUS     current
    DESCRIPTION
            "-- empty --"
    ::= { lcsStatusLay7AppDetTotalTrafficPerProtocolEntry 10 }

-- {COLUMN} 1.3.6.1.4.1.2356.11.1.95.8.1.11
lcsStatusLay7AppDetTotalTrafficPerProtocolEntryRxKbytesDay4 OBJECT-TYPE
    SYNTAX     Counter64
    MAX-ACCESS read-only
    STATUS     current
    DESCRIPTION
            "-- empty --"
    ::= { lcsStatusLay7AppDetTotalTrafficPerProtocolEntry 11 }

-- {COLUMN} 1.3.6.1.4.1.2356.11.1.95.8.1.12
lcsStatusLay7AppDetTotalTrafficPerProtocolEntryTxKbytesDay5 OBJECT-TYPE
    SYNTAX     Counter64
    MAX-ACCESS read-only
    STATUS     current
    DESCRIPTION
            "-- empty --"
    ::= { lcsStatusLay7AppDetTotalTrafficPerProtocolEntry 12 }

-- {COLUMN} 1.3.6.1.4.1.2356.11.1.95.8.1.13
lcsStatusLay7AppDetTotalTrafficPerProtocolEntryRxKbytesDay5 OBJECT-TYPE
    SYNTAX     Counter64
    MAX-ACCESS read-only
    STATUS     current
    DESCRIPTION
            "-- empty --"
    ::= { lcsStatusLay7AppDetTotalTrafficPerProtocolEntry 13 }

-- {COLUMN} 1.3.6.1.4.1.2356.11.1.95.8.1.14
lcsStatusLay7AppDetTotalTrafficPerProtocolEntryTxKbytesDay6 OBJECT-TYPE
    SYNTAX     Counter64
    MAX-ACCESS read-only
    STATUS     current
    DESCRIPTION
            "-- empty --"
    ::= { lcsStatusLay7AppDetTotalTrafficPerProtocolEntry 14 }

-- {COLUMN} 1.3.6.1.4.1.2356.11.1.95.8.1.15
lcsStatusLay7AppDetTotalTrafficPerProtocolEntryRxKbytesDay6 OBJECT-TYPE
    SYNTAX     Counter64
    MAX-ACCESS read-only
    STATUS     current
    DESCRIPTION
            "-- empty --"
    ::= { lcsStatusLay7AppDetTotalTrafficPerProtocolEntry 15 }

-- {SCALAR} 1.3.6.1.4.1.2356.11.1.95.9
lcsStatusLay7AppDetSkippedPacketsTx OBJECT-TYPE
    SYNTAX     Integer32 (0..2147483647)
    MAX-ACCESS read-only
    STATUS     current
    DESCRIPTION
            "-- empty --"
    ::= { lcsStatusLay7AppDet 9 }

-- {SCALAR} 1.3.6.1.4.1.2356.11.1.95.10
lcsStatusLay7AppDetSkippedPacketsRx OBJECT-TYPE
    SYNTAX     Integer32 (0..2147483647)
    MAX-ACCESS read-only
    STATUS     current
    DESCRIPTION
            "-- empty --"
    ::= { lcsStatusLay7AppDet 10 }

-- {SCALAR} 1.3.6.1.4.1.2356.11.1.95.11
lcsStatusLay7AppDetAllTxFramesBytes OBJECT-TYPE
    SYNTAX     Integer32 (0..2147483647)
    MAX-ACCESS read-only
    STATUS     current
    DESCRIPTION
            "-- empty --"
    ::= { lcsStatusLay7AppDet 11 }

-- {SCALAR} 1.3.6.1.4.1.2356.11.1.95.12
lcsStatusLay7AppDetAllRxFramesBytes OBJECT-TYPE
    SYNTAX     Integer32 (0..2147483647)
    MAX-ACCESS read-only
    STATUS     current
    DESCRIPTION
            "-- empty --"
    ::= { lcsStatusLay7AppDet 12 }

-- {SCALAR} 1.3.6.1.4.1.2356.11.1.95.13
lcsStatusLay7AppDetSkippedTxFramesBytes OBJECT-TYPE
    SYNTAX     Integer32 (0..2147483647)
    MAX-ACCESS read-only
    STATUS     current
    DESCRIPTION
            "-- empty --"
    ::= { lcsStatusLay7AppDet 13 }

-- {SCALAR} 1.3.6.1.4.1.2356.11.1.95.14
lcsStatusLay7AppDetSkippedRxFramesBytes OBJECT-TYPE
    SYNTAX     Integer32 (0..2147483647)
    MAX-ACCESS read-only
    STATUS     current
    DESCRIPTION
            "-- empty --"
    ::= { lcsStatusLay7AppDet 14 }

-- {SCALAR} 1.3.6.1.4.1.2356.11.1.95.15
lcsStatusLay7AppDetSkippedPacketsTx64 OBJECT-TYPE
    SYNTAX     Counter64
    MAX-ACCESS read-only
    STATUS     current
    DESCRIPTION
            ""
    ::= { lcsStatusLay7AppDet 15 }

-- {SCALAR} 1.3.6.1.4.1.2356.11.1.95.16
lcsStatusLay7AppDetSkippedPacketsRx64 OBJECT-TYPE
    SYNTAX     Counter64
    MAX-ACCESS read-only
    STATUS     current
    DESCRIPTION
            ""
    ::= { lcsStatusLay7AppDet 16 }

-- {SCALAR} 1.3.6.1.4.1.2356.11.1.95.17
lcsStatusLay7AppDetAllTxFramesBytes64 OBJECT-TYPE
    SYNTAX     Counter64
    MAX-ACCESS read-only
    STATUS     current
    DESCRIPTION
            ""
    ::= { lcsStatusLay7AppDet 17 }

-- {SCALAR} 1.3.6.1.4.1.2356.11.1.95.18
lcsStatusLay7AppDetAllRxFramesBytes64 OBJECT-TYPE
    SYNTAX     Counter64
    MAX-ACCESS read-only
    STATUS     current
    DESCRIPTION
            ""
    ::= { lcsStatusLay7AppDet 18 }

-- {SCALAR} 1.3.6.1.4.1.2356.11.1.95.19
lcsStatusLay7AppDetSkippedTxFramesBytes64 OBJECT-TYPE
    SYNTAX     Counter64
    MAX-ACCESS read-only
    STATUS     current
    DESCRIPTION
            ""
    ::= { lcsStatusLay7AppDet 19 }

-- {SCALAR} 1.3.6.1.4.1.2356.11.1.95.20
lcsStatusLay7AppDetSkippedRxFramesBytes64 OBJECT-TYPE
    SYNTAX     Counter64
    MAX-ACCESS read-only
    STATUS     current
    DESCRIPTION
            ""
    ::= { lcsStatusLay7AppDet 20 }

-- {NODE} 1.3.6.1.4.1.2356.11.1.96
lcsStatusIperf OBJECT IDENTIFIER ::= { lcsStatus 96 }

-- {NODE} 1.3.6.1.4.1.2356.11.1.96.1
lcsStatusIperfLastResults OBJECT IDENTIFIER ::= { lcsStatusIperf 1 }

-- {TABLE} 1.3.6.1.4.1.2356.11.1.96.1.1
lcsStatusIperfLastResultsUdpTable OBJECT-TYPE
    SYNTAX     SEQUENCE OF LcsStatusIperfLastResultsUdpEntry
    MAX-ACCESS not-accessible
    STATUS     current
    DESCRIPTION
            "-- empty --"
    ::= { lcsStatusIperfLastResults 1 }

-- {ROW} 1.3.6.1.4.1.2356.11.1.96.1.1.1
lcsStatusIperfLastResultsUdpEntry OBJECT-TYPE
    SYNTAX     LcsStatusIperfLastResultsUdpEntry
    MAX-ACCESS not-accessible
    STATUS     current
    DESCRIPTION
            ""
    INDEX {
            lcsStatusIperfLastResultsUdpEntryIndex
          }
    ::= { lcsStatusIperfLastResultsUdpTable 1 }

LcsStatusIperfLastResultsUdpEntry ::= SEQUENCE {
            lcsStatusIperfLastResultsUdpEntryIndex Gauge32,
            lcsStatusIperfLastResultsUdpEntryLocalIp DisplayString,
            lcsStatusIperfLastResultsUdpEntryRemoteIp DisplayString,
            lcsStatusIperfLastResultsUdpEntryMode INTEGER,
            lcsStatusIperfLastResultsUdpEntryConnections Integer32,
            lcsStatusIperfLastResultsUdpEntryServerStart DisplayString,
            lcsStatusIperfLastResultsUdpEntryServerStartNum Counter32,
            lcsStatusIperfLastResultsUdpEntryServerStop DisplayString,
            lcsStatusIperfLastResultsUdpEntryServerStopNum Counter32,
            lcsStatusIperfLastResultsUdpEntryServerDurationMs Counter32,
            lcsStatusIperfLastResultsUdpEntryServerBytes Counter64,
            lcsStatusIperfLastResultsUdpEntryServerBandwidthKbps Gauge32,
            lcsStatusIperfLastResultsUdpEntryServerPackets Counter32,
            lcsStatusIperfLastResultsUdpEntryServerLostPackets Counter32,
            lcsStatusIperfLastResultsUdpEntryServerOutOrderPackets Counter32,
            lcsStatusIperfLastResultsUdpEntryServerJitterUs Gauge32,
            lcsStatusIperfLastResultsUdpEntryServerError DisplayString,
            lcsStatusIperfLastResultsUdpEntryClientStart DisplayString,
            lcsStatusIperfLastResultsUdpEntryClientStartNum Counter32,
            lcsStatusIperfLastResultsUdpEntryClientStop DisplayString,
            lcsStatusIperfLastResultsUdpEntryClientStopNum Counter32,
            lcsStatusIperfLastResultsUdpEntryClientDurationMs Counter32,
            lcsStatusIperfLastResultsUdpEntryClientBytes Counter64,
            lcsStatusIperfLastResultsUdpEntryClientBandwidthKbps Gauge32,
            lcsStatusIperfLastResultsUdpEntryClientPackets Counter32,
            lcsStatusIperfLastResultsUdpEntryClientError DisplayString,
            lcsStatusIperfLastResultsUdpEntryRemoteServerDurationMs Counter32,
            lcsStatusIperfLastResultsUdpEntryRemoteServerBytes Counter64,
            lcsStatusIperfLastResultsUdpEntryRemoteServerBandwidthKbps Gauge32,
            lcsStatusIperfLastResultsUdpEntryRemoteServerPackets Counter32,
            lcsStatusIperfLastResultsUdpEntryRemoteServerLostPackets Counter32,
            lcsStatusIperfLastResultsUdpEntryRemoteServerOutOrderPackets Counter32,
            lcsStatusIperfLastResultsUdpEntryRemoteServerJitterUs Gauge32
    }

-- {COLUMN} 1.3.6.1.4.1.2356.11.1.96.1.1.1.1
lcsStatusIperfLastResultsUdpEntryIndex OBJECT-TYPE
    SYNTAX     Gauge32
    MAX-ACCESS read-only
    STATUS     current
    DESCRIPTION
            "-- empty --"
    ::= { lcsStatusIperfLastResultsUdpEntry 1 }

-- {COLUMN} 1.3.6.1.4.1.2356.11.1.96.1.1.1.2
lcsStatusIperfLastResultsUdpEntryLocalIp OBJECT-TYPE
    SYNTAX     DisplayString (SIZE(0..255))
    MAX-ACCESS read-only
    STATUS     current
    DESCRIPTION
            "-- empty --"
    ::= { lcsStatusIperfLastResultsUdpEntry 2 }

-- {COLUMN} 1.3.6.1.4.1.2356.11.1.96.1.1.1.3
lcsStatusIperfLastResultsUdpEntryRemoteIp OBJECT-TYPE
    SYNTAX     DisplayString (SIZE(0..255))
    MAX-ACCESS read-only
    STATUS     current
    DESCRIPTION
            "-- empty --"
    ::= { lcsStatusIperfLastResultsUdpEntry 3 }

-- {COLUMN} 1.3.6.1.4.1.2356.11.1.96.1.1.1.4
lcsStatusIperfLastResultsUdpEntryMode OBJECT-TYPE
    SYNTAX     INTEGER {
                  eUndefined (0),
                  eUnidirectionalServer (1),
                  eDualServer (2),
                  eTradeoffServer (3),
                  eUnidirectionalClient (4),
                  eDualClient (5),
                  eTradeoffClient (6)
            }
    MAX-ACCESS read-only
    STATUS     current
    DESCRIPTION
            "-- empty --"
    ::= { lcsStatusIperfLastResultsUdpEntry 4 }

-- {COLUMN} 1.3.6.1.4.1.2356.11.1.96.1.1.1.5
lcsStatusIperfLastResultsUdpEntryConnections OBJECT-TYPE
    SYNTAX     Integer32 (0..65535)
    MAX-ACCESS read-only
    STATUS     current
    DESCRIPTION
            "-- empty --"
    ::= { lcsStatusIperfLastResultsUdpEntry 5 }

-- {COLUMN} 1.3.6.1.4.1.2356.11.1.96.1.1.1.6
lcsStatusIperfLastResultsUdpEntryServerStart OBJECT-TYPE
    SYNTAX     DisplayString (SIZE(0..255))
    MAX-ACCESS read-only
    STATUS     current
    DESCRIPTION
            "-- empty --"
    ::= { lcsStatusIperfLastResultsUdpEntry 6 }

-- {COLUMN} 1.3.6.1.4.1.2356.11.1.96.1.1.1.7
lcsStatusIperfLastResultsUdpEntryServerStartNum OBJECT-TYPE
    SYNTAX     Counter32
    MAX-ACCESS read-only
    STATUS     current
    DESCRIPTION
            "-- empty --"
    ::= { lcsStatusIperfLastResultsUdpEntry 7 }

-- {COLUMN} 1.3.6.1.4.1.2356.11.1.96.1.1.1.8
lcsStatusIperfLastResultsUdpEntryServerStop OBJECT-TYPE
    SYNTAX     DisplayString (SIZE(0..255))
    MAX-ACCESS read-only
    STATUS     current
    DESCRIPTION
            "-- empty --"
    ::= { lcsStatusIperfLastResultsUdpEntry 8 }

-- {COLUMN} 1.3.6.1.4.1.2356.11.1.96.1.1.1.9
lcsStatusIperfLastResultsUdpEntryServerStopNum OBJECT-TYPE
    SYNTAX     Counter32
    MAX-ACCESS read-only
    STATUS     current
    DESCRIPTION
            "-- empty --"
    ::= { lcsStatusIperfLastResultsUdpEntry 9 }

-- {COLUMN} 1.3.6.1.4.1.2356.11.1.96.1.1.1.10
lcsStatusIperfLastResultsUdpEntryServerDurationMs OBJECT-TYPE
    SYNTAX     Counter32
    MAX-ACCESS read-only
    STATUS     current
    DESCRIPTION
            "-- empty --"
    ::= { lcsStatusIperfLastResultsUdpEntry 10 }

-- {COLUMN} 1.3.6.1.4.1.2356.11.1.96.1.1.1.11
lcsStatusIperfLastResultsUdpEntryServerBytes OBJECT-TYPE
    SYNTAX     Counter64
    MAX-ACCESS read-only
    STATUS     current
    DESCRIPTION
            "-- empty --"
    ::= { lcsStatusIperfLastResultsUdpEntry 11 }

-- {COLUMN} 1.3.6.1.4.1.2356.11.1.96.1.1.1.12
lcsStatusIperfLastResultsUdpEntryServerBandwidthKbps OBJECT-TYPE
    SYNTAX     Gauge32
    MAX-ACCESS read-only
    STATUS     current
    DESCRIPTION
            "-- empty --"
    ::= { lcsStatusIperfLastResultsUdpEntry 12 }

-- {COLUMN} 1.3.6.1.4.1.2356.11.1.96.1.1.1.13
lcsStatusIperfLastResultsUdpEntryServerPackets OBJECT-TYPE
    SYNTAX     Counter32
    MAX-ACCESS read-only
    STATUS     current
    DESCRIPTION
            "-- empty --"
    ::= { lcsStatusIperfLastResultsUdpEntry 13 }

-- {COLUMN} 1.3.6.1.4.1.2356.11.1.96.1.1.1.14
lcsStatusIperfLastResultsUdpEntryServerLostPackets OBJECT-TYPE
    SYNTAX     Counter32
    MAX-ACCESS read-only
    STATUS     current
    DESCRIPTION
            "-- empty --"
    ::= { lcsStatusIperfLastResultsUdpEntry 14 }

-- {COLUMN} 1.3.6.1.4.1.2356.11.1.96.1.1.1.15
lcsStatusIperfLastResultsUdpEntryServerOutOrderPackets OBJECT-TYPE
    SYNTAX     Counter32
    MAX-ACCESS read-only
    STATUS     current
    DESCRIPTION
            "-- empty --"
    ::= { lcsStatusIperfLastResultsUdpEntry 15 }

-- {COLUMN} 1.3.6.1.4.1.2356.11.1.96.1.1.1.16
lcsStatusIperfLastResultsUdpEntryServerJitterUs OBJECT-TYPE
    SYNTAX     Gauge32
    MAX-ACCESS read-only
    STATUS     current
    DESCRIPTION
            "-- empty --"
    ::= { lcsStatusIperfLastResultsUdpEntry 16 }

-- {COLUMN} 1.3.6.1.4.1.2356.11.1.96.1.1.1.17
lcsStatusIperfLastResultsUdpEntryServerError OBJECT-TYPE
    SYNTAX     DisplayString (SIZE(0..255))
    MAX-ACCESS read-only
    STATUS     current
    DESCRIPTION
            "-- empty --"
    ::= { lcsStatusIperfLastResultsUdpEntry 17 }

-- {COLUMN} 1.3.6.1.4.1.2356.11.1.96.1.1.1.18
lcsStatusIperfLastResultsUdpEntryClientStart OBJECT-TYPE
    SYNTAX     DisplayString (SIZE(0..255))
    MAX-ACCESS read-only
    STATUS     current
    DESCRIPTION
            "-- empty --"
    ::= { lcsStatusIperfLastResultsUdpEntry 18 }

-- {COLUMN} 1.3.6.1.4.1.2356.11.1.96.1.1.1.19
lcsStatusIperfLastResultsUdpEntryClientStartNum OBJECT-TYPE
    SYNTAX     Counter32
    MAX-ACCESS read-only
    STATUS     current
    DESCRIPTION
            "-- empty --"
    ::= { lcsStatusIperfLastResultsUdpEntry 19 }

-- {COLUMN} 1.3.6.1.4.1.2356.11.1.96.1.1.1.20
lcsStatusIperfLastResultsUdpEntryClientStop OBJECT-TYPE
    SYNTAX     DisplayString (SIZE(0..255))
    MAX-ACCESS read-only
    STATUS     current
    DESCRIPTION
            "-- empty --"
    ::= { lcsStatusIperfLastResultsUdpEntry 20 }

-- {COLUMN} 1.3.6.1.4.1.2356.11.1.96.1.1.1.21
lcsStatusIperfLastResultsUdpEntryClientStopNum OBJECT-TYPE
    SYNTAX     Counter32
    MAX-ACCESS read-only
    STATUS     current
    DESCRIPTION
            "-- empty --"
    ::= { lcsStatusIperfLastResultsUdpEntry 21 }

-- {COLUMN} 1.3.6.1.4.1.2356.11.1.96.1.1.1.22
lcsStatusIperfLastResultsUdpEntryClientDurationMs OBJECT-TYPE
    SYNTAX     Counter32
    MAX-ACCESS read-only
    STATUS     current
    DESCRIPTION
            "-- empty --"
    ::= { lcsStatusIperfLastResultsUdpEntry 22 }

-- {COLUMN} 1.3.6.1.4.1.2356.11.1.96.1.1.1.23
lcsStatusIperfLastResultsUdpEntryClientBytes OBJECT-TYPE
    SYNTAX     Counter64
    MAX-ACCESS read-only
    STATUS     current
    DESCRIPTION
            "-- empty --"
    ::= { lcsStatusIperfLastResultsUdpEntry 23 }

-- {COLUMN} 1.3.6.1.4.1.2356.11.1.96.1.1.1.24
lcsStatusIperfLastResultsUdpEntryClientBandwidthKbps OBJECT-TYPE
    SYNTAX     Gauge32
    MAX-ACCESS read-only
    STATUS     current
    DESCRIPTION
            "-- empty --"
    ::= { lcsStatusIperfLastResultsUdpEntry 24 }

-- {COLUMN} 1.3.6.1.4.1.2356.11.1.96.1.1.1.25
lcsStatusIperfLastResultsUdpEntryClientPackets OBJECT-TYPE
    SYNTAX     Counter32
    MAX-ACCESS read-only
    STATUS     current
    DESCRIPTION
            "-- empty --"
    ::= { lcsStatusIperfLastResultsUdpEntry 25 }

-- {COLUMN} 1.3.6.1.4.1.2356.11.1.96.1.1.1.26
lcsStatusIperfLastResultsUdpEntryClientError OBJECT-TYPE
    SYNTAX     DisplayString (SIZE(0..255))
    MAX-ACCESS read-only
    STATUS     current
    DESCRIPTION
            "-- empty --"
    ::= { lcsStatusIperfLastResultsUdpEntry 26 }

-- {COLUMN} 1.3.6.1.4.1.2356.11.1.96.1.1.1.27
lcsStatusIperfLastResultsUdpEntryRemoteServerDurationMs OBJECT-TYPE
    SYNTAX     Counter32
    MAX-ACCESS read-only
    STATUS     current
    DESCRIPTION
            "-- empty --"
    ::= { lcsStatusIperfLastResultsUdpEntry 27 }

-- {COLUMN} 1.3.6.1.4.1.2356.11.1.96.1.1.1.28
lcsStatusIperfLastResultsUdpEntryRemoteServerBytes OBJECT-TYPE
    SYNTAX     Counter64
    MAX-ACCESS read-only
    STATUS     current
    DESCRIPTION
            "-- empty --"
    ::= { lcsStatusIperfLastResultsUdpEntry 28 }

-- {COLUMN} 1.3.6.1.4.1.2356.11.1.96.1.1.1.29
lcsStatusIperfLastResultsUdpEntryRemoteServerBandwidthKbps OBJECT-TYPE
    SYNTAX     Gauge32
    MAX-ACCESS read-only
    STATUS     current
    DESCRIPTION
            "-- empty --"
    ::= { lcsStatusIperfLastResultsUdpEntry 29 }

-- {COLUMN} 1.3.6.1.4.1.2356.11.1.96.1.1.1.30
lcsStatusIperfLastResultsUdpEntryRemoteServerPackets OBJECT-TYPE
    SYNTAX     Counter32
    MAX-ACCESS read-only
    STATUS     current
    DESCRIPTION
            "-- empty --"
    ::= { lcsStatusIperfLastResultsUdpEntry 30 }

-- {COLUMN} 1.3.6.1.4.1.2356.11.1.96.1.1.1.31
lcsStatusIperfLastResultsUdpEntryRemoteServerLostPackets OBJECT-TYPE
    SYNTAX     Counter32
    MAX-ACCESS read-only
    STATUS     current
    DESCRIPTION
            "-- empty --"
    ::= { lcsStatusIperfLastResultsUdpEntry 31 }

-- {COLUMN} 1.3.6.1.4.1.2356.11.1.96.1.1.1.32
lcsStatusIperfLastResultsUdpEntryRemoteServerOutOrderPackets OBJECT-TYPE
    SYNTAX     Counter32
    MAX-ACCESS read-only
    STATUS     current
    DESCRIPTION
            "-- empty --"
    ::= { lcsStatusIperfLastResultsUdpEntry 32 }

-- {COLUMN} 1.3.6.1.4.1.2356.11.1.96.1.1.1.33
lcsStatusIperfLastResultsUdpEntryRemoteServerJitterUs OBJECT-TYPE
    SYNTAX     Gauge32
    MAX-ACCESS read-only
    STATUS     current
    DESCRIPTION
            "-- empty --"
    ::= { lcsStatusIperfLastResultsUdpEntry 33 }

-- {TABLE} 1.3.6.1.4.1.2356.11.1.96.1.2
lcsStatusIperfLastResultsTcpTable OBJECT-TYPE
    SYNTAX     SEQUENCE OF LcsStatusIperfLastResultsTcpEntry
    MAX-ACCESS not-accessible
    STATUS     current
    DESCRIPTION
            "-- empty --"
    ::= { lcsStatusIperfLastResults 2 }

-- {ROW} 1.3.6.1.4.1.2356.11.1.96.1.2.1
lcsStatusIperfLastResultsTcpEntry OBJECT-TYPE
    SYNTAX     LcsStatusIperfLastResultsTcpEntry
    MAX-ACCESS not-accessible
    STATUS     current
    DESCRIPTION
            ""
    INDEX {
            lcsStatusIperfLastResultsTcpEntryIndex
          }
    ::= { lcsStatusIperfLastResultsTcpTable 1 }

LcsStatusIperfLastResultsTcpEntry ::= SEQUENCE {
            lcsStatusIperfLastResultsTcpEntryIndex Gauge32,
            lcsStatusIperfLastResultsTcpEntryLocalIp DisplayString,
            lcsStatusIperfLastResultsTcpEntryRemoteIp DisplayString,
            lcsStatusIperfLastResultsTcpEntryMode INTEGER,
            lcsStatusIperfLastResultsTcpEntryConnections Integer32,
            lcsStatusIperfLastResultsTcpEntryServerStart DisplayString,
            lcsStatusIperfLastResultsTcpEntryServerStartNum Counter32,
            lcsStatusIperfLastResultsTcpEntryServerStop DisplayString,
            lcsStatusIperfLastResultsTcpEntryServerStopNum Counter32,
            lcsStatusIperfLastResultsTcpEntryServerDurationMs Counter32,
            lcsStatusIperfLastResultsTcpEntryServerBytes Counter64,
            lcsStatusIperfLastResultsTcpEntryServerBandwidthKbps Gauge32,
            lcsStatusIperfLastResultsTcpEntryServerError DisplayString,
            lcsStatusIperfLastResultsTcpEntryClientStart DisplayString,
            lcsStatusIperfLastResultsTcpEntryClientStartNum Counter32,
            lcsStatusIperfLastResultsTcpEntryClientStop DisplayString,
            lcsStatusIperfLastResultsTcpEntryClientStopNum Counter32,
            lcsStatusIperfLastResultsTcpEntryClientDurationMs Counter32,
            lcsStatusIperfLastResultsTcpEntryClientBytes Counter64,
            lcsStatusIperfLastResultsTcpEntryClientBandwidthKbps Gauge32,
            lcsStatusIperfLastResultsTcpEntryClientError DisplayString
    }

-- {COLUMN} 1.3.6.1.4.1.2356.11.1.96.1.2.1.1
lcsStatusIperfLastResultsTcpEntryIndex OBJECT-TYPE
    SYNTAX     Gauge32
    MAX-ACCESS read-only
    STATUS     current
    DESCRIPTION
            "-- empty --"
    ::= { lcsStatusIperfLastResultsTcpEntry 1 }

-- {COLUMN} 1.3.6.1.4.1.2356.11.1.96.1.2.1.2
lcsStatusIperfLastResultsTcpEntryLocalIp OBJECT-TYPE
    SYNTAX     DisplayString (SIZE(0..255))
    MAX-ACCESS read-only
    STATUS     current
    DESCRIPTION
            "-- empty --"
    ::= { lcsStatusIperfLastResultsTcpEntry 2 }

-- {COLUMN} 1.3.6.1.4.1.2356.11.1.96.1.2.1.3
lcsStatusIperfLastResultsTcpEntryRemoteIp OBJECT-TYPE
    SYNTAX     DisplayString (SIZE(0..255))
    MAX-ACCESS read-only
    STATUS     current
    DESCRIPTION
            "-- empty --"
    ::= { lcsStatusIperfLastResultsTcpEntry 3 }

-- {COLUMN} 1.3.6.1.4.1.2356.11.1.96.1.2.1.4
lcsStatusIperfLastResultsTcpEntryMode OBJECT-TYPE
    SYNTAX     INTEGER {
                  eUndefined (0),
                  eUnidirectionalServer (1),
                  eDualServer (2),
                  eTradeoffServer (3),
                  eUnidirectionalClient (4),
                  eDualClient (5),
                  eTradeoffClient (6)
            }
    MAX-ACCESS read-only
    STATUS     current
    DESCRIPTION
            "-- empty --"
    ::= { lcsStatusIperfLastResultsTcpEntry 4 }

-- {COLUMN} 1.3.6.1.4.1.2356.11.1.96.1.2.1.5
lcsStatusIperfLastResultsTcpEntryConnections OBJECT-TYPE
    SYNTAX     Integer32 (0..65535)
    MAX-ACCESS read-only
    STATUS     current
    DESCRIPTION
            "-- empty --"
    ::= { lcsStatusIperfLastResultsTcpEntry 5 }

-- {COLUMN} 1.3.6.1.4.1.2356.11.1.96.1.2.1.6
lcsStatusIperfLastResultsTcpEntryServerStart OBJECT-TYPE
    SYNTAX     DisplayString (SIZE(0..255))
    MAX-ACCESS read-only
    STATUS     current
    DESCRIPTION
            "-- empty --"
    ::= { lcsStatusIperfLastResultsTcpEntry 6 }

-- {COLUMN} 1.3.6.1.4.1.2356.11.1.96.1.2.1.7
lcsStatusIperfLastResultsTcpEntryServerStartNum OBJECT-TYPE
    SYNTAX     Counter32
    MAX-ACCESS read-only
    STATUS     current
    DESCRIPTION
            "-- empty --"
    ::= { lcsStatusIperfLastResultsTcpEntry 7 }

-- {COLUMN} 1.3.6.1.4.1.2356.11.1.96.1.2.1.8
lcsStatusIperfLastResultsTcpEntryServerStop OBJECT-TYPE
    SYNTAX     DisplayString (SIZE(0..255))
    MAX-ACCESS read-only
    STATUS     current
    DESCRIPTION
            "-- empty --"
    ::= { lcsStatusIperfLastResultsTcpEntry 8 }

-- {COLUMN} 1.3.6.1.4.1.2356.11.1.96.1.2.1.9
lcsStatusIperfLastResultsTcpEntryServerStopNum OBJECT-TYPE
    SYNTAX     Counter32
    MAX-ACCESS read-only
    STATUS     current
    DESCRIPTION
            "-- empty --"
    ::= { lcsStatusIperfLastResultsTcpEntry 9 }

-- {COLUMN} 1.3.6.1.4.1.2356.11.1.96.1.2.1.10
lcsStatusIperfLastResultsTcpEntryServerDurationMs OBJECT-TYPE
    SYNTAX     Counter32
    MAX-ACCESS read-only
    STATUS     current
    DESCRIPTION
            "-- empty --"
    ::= { lcsStatusIperfLastResultsTcpEntry 10 }

-- {COLUMN} 1.3.6.1.4.1.2356.11.1.96.1.2.1.11
lcsStatusIperfLastResultsTcpEntryServerBytes OBJECT-TYPE
    SYNTAX     Counter64
    MAX-ACCESS read-only
    STATUS     current
    DESCRIPTION
            "-- empty --"
    ::= { lcsStatusIperfLastResultsTcpEntry 11 }

-- {COLUMN} 1.3.6.1.4.1.2356.11.1.96.1.2.1.12
lcsStatusIperfLastResultsTcpEntryServerBandwidthKbps OBJECT-TYPE
    SYNTAX     Gauge32
    MAX-ACCESS read-only
    STATUS     current
    DESCRIPTION
            "-- empty --"
    ::= { lcsStatusIperfLastResultsTcpEntry 12 }

-- {COLUMN} 1.3.6.1.4.1.2356.11.1.96.1.2.1.13
lcsStatusIperfLastResultsTcpEntryServerError OBJECT-TYPE
    SYNTAX     DisplayString (SIZE(0..255))
    MAX-ACCESS read-only
    STATUS     current
    DESCRIPTION
            "-- empty --"
    ::= { lcsStatusIperfLastResultsTcpEntry 13 }

-- {COLUMN} 1.3.6.1.4.1.2356.11.1.96.1.2.1.14
lcsStatusIperfLastResultsTcpEntryClientStart OBJECT-TYPE
    SYNTAX     DisplayString (SIZE(0..255))
    MAX-ACCESS read-only
    STATUS     current
    DESCRIPTION
            "-- empty --"
    ::= { lcsStatusIperfLastResultsTcpEntry 14 }

-- {COLUMN} 1.3.6.1.4.1.2356.11.1.96.1.2.1.15
lcsStatusIperfLastResultsTcpEntryClientStartNum OBJECT-TYPE
    SYNTAX     Counter32
    MAX-ACCESS read-only
    STATUS     current
    DESCRIPTION
            "-- empty --"
    ::= { lcsStatusIperfLastResultsTcpEntry 15 }

-- {COLUMN} 1.3.6.1.4.1.2356.11.1.96.1.2.1.16
lcsStatusIperfLastResultsTcpEntryClientStop OBJECT-TYPE
    SYNTAX     DisplayString (SIZE(0..255))
    MAX-ACCESS read-only
    STATUS     current
    DESCRIPTION
            "-- empty --"
    ::= { lcsStatusIperfLastResultsTcpEntry 16 }

-- {COLUMN} 1.3.6.1.4.1.2356.11.1.96.1.2.1.17
lcsStatusIperfLastResultsTcpEntryClientStopNum OBJECT-TYPE
    SYNTAX     Counter32
    MAX-ACCESS read-only
    STATUS     current
    DESCRIPTION
            "-- empty --"
    ::= { lcsStatusIperfLastResultsTcpEntry 17 }

-- {COLUMN} 1.3.6.1.4.1.2356.11.1.96.1.2.1.18
lcsStatusIperfLastResultsTcpEntryClientDurationMs OBJECT-TYPE
    SYNTAX     Counter32
    MAX-ACCESS read-only
    STATUS     current
    DESCRIPTION
            "-- empty --"
    ::= { lcsStatusIperfLastResultsTcpEntry 18 }

-- {COLUMN} 1.3.6.1.4.1.2356.11.1.96.1.2.1.19
lcsStatusIperfLastResultsTcpEntryClientBytes OBJECT-TYPE
    SYNTAX     Counter64
    MAX-ACCESS read-only
    STATUS     current
    DESCRIPTION
            "-- empty --"
    ::= { lcsStatusIperfLastResultsTcpEntry 19 }

-- {COLUMN} 1.3.6.1.4.1.2356.11.1.96.1.2.1.20
lcsStatusIperfLastResultsTcpEntryClientBandwidthKbps OBJECT-TYPE
    SYNTAX     Gauge32
    MAX-ACCESS read-only
    STATUS     current
    DESCRIPTION
            "-- empty --"
    ::= { lcsStatusIperfLastResultsTcpEntry 20 }

-- {COLUMN} 1.3.6.1.4.1.2356.11.1.96.1.2.1.21
lcsStatusIperfLastResultsTcpEntryClientError OBJECT-TYPE
    SYNTAX     DisplayString (SIZE(0..255))
    MAX-ACCESS read-only
    STATUS     current
    DESCRIPTION
            "-- empty --"
    ::= { lcsStatusIperfLastResultsTcpEntry 21 }

-- {NODE} 1.3.6.1.4.1.2356.11.1.96.2
lcsStatusIperfResultHistory OBJECT IDENTIFIER ::= { lcsStatusIperf 2 }

-- {TABLE} 1.3.6.1.4.1.2356.11.1.96.2.1
lcsStatusIperfResultHistoryUdpTable OBJECT-TYPE
    SYNTAX     SEQUENCE OF LcsStatusIperfResultHistoryUdpEntry
    MAX-ACCESS not-accessible
    STATUS     current
    DESCRIPTION
            "-- empty --"
    ::= { lcsStatusIperfResultHistory 1 }

-- {ROW} 1.3.6.1.4.1.2356.11.1.96.2.1.1
lcsStatusIperfResultHistoryUdpEntry OBJECT-TYPE
    SYNTAX     LcsStatusIperfResultHistoryUdpEntry
    MAX-ACCESS not-accessible
    STATUS     current
    DESCRIPTION
            ""
    INDEX {
            lcsStatusIperfResultHistoryUdpEntryIndex
          }
    ::= { lcsStatusIperfResultHistoryUdpTable 1 }

LcsStatusIperfResultHistoryUdpEntry ::= SEQUENCE {
            lcsStatusIperfResultHistoryUdpEntryIndex Gauge32,
            lcsStatusIperfResultHistoryUdpEntryLocalIp DisplayString,
            lcsStatusIperfResultHistoryUdpEntryRemoteIp DisplayString,
            lcsStatusIperfResultHistoryUdpEntryMode INTEGER,
            lcsStatusIperfResultHistoryUdpEntryConnections Integer32,
            lcsStatusIperfResultHistoryUdpEntryServerStart DisplayString,
            lcsStatusIperfResultHistoryUdpEntryServerStartNum Counter32,
            lcsStatusIperfResultHistoryUdpEntryServerStop DisplayString,
            lcsStatusIperfResultHistoryUdpEntryServerStopNum Counter32,
            lcsStatusIperfResultHistoryUdpEntryServerDurationMs Counter32,
            lcsStatusIperfResultHistoryUdpEntryServerBytes Counter64,
            lcsStatusIperfResultHistoryUdpEntryServerBandwidthKbps Gauge32,
            lcsStatusIperfResultHistoryUdpEntryServerPackets Counter32,
            lcsStatusIperfResultHistoryUdpEntryServerLostPackets Counter32,
            lcsStatusIperfResultHistoryUdpEntryServerOutOrderPackets Counter32,
            lcsStatusIperfResultHistoryUdpEntryServerJitterUs Gauge32,
            lcsStatusIperfResultHistoryUdpEntryServerError DisplayString,
            lcsStatusIperfResultHistoryUdpEntryClientStart DisplayString,
            lcsStatusIperfResultHistoryUdpEntryClientStartNum Counter32,
            lcsStatusIperfResultHistoryUdpEntryClientStop DisplayString,
            lcsStatusIperfResultHistoryUdpEntryClientStopNum Counter32,
            lcsStatusIperfResultHistoryUdpEntryClientDurationMs Counter32,
            lcsStatusIperfResultHistoryUdpEntryClientBytes Counter64,
            lcsStatusIperfResultHistoryUdpEntryClientBandwidthKbps Gauge32,
            lcsStatusIperfResultHistoryUdpEntryClientPackets Counter32,
            lcsStatusIperfResultHistoryUdpEntryClientError DisplayString,
            lcsStatusIperfResultHistoryUdpEntryRemoteServerDurationMs Counter32,
            lcsStatusIperfResultHistoryUdpEntryRemoteServerBytes Counter64,
            lcsStatusIperfResultHistoryUdpEntryRemoteServerBandwidthKbps Gauge32,
            lcsStatusIperfResultHistoryUdpEntryRemoteServerPackets Counter32,
            lcsStatusIperfResultHistoryUdpEntryRemoteServerLostPackets Counter32,
            lcsStatusIperfResultHistoryUdpEntryRemoteServerOutOrderPackets Counter32,
            lcsStatusIperfResultHistoryUdpEntryRemoteServerJitterUs Gauge32
    }

-- {COLUMN} 1.3.6.1.4.1.2356.11.1.96.2.1.1.1
lcsStatusIperfResultHistoryUdpEntryIndex OBJECT-TYPE
    SYNTAX     Gauge32
    MAX-ACCESS read-only
    STATUS     current
    DESCRIPTION
            "-- empty --"
    ::= { lcsStatusIperfResultHistoryUdpEntry 1 }

-- {COLUMN} 1.3.6.1.4.1.2356.11.1.96.2.1.1.2
lcsStatusIperfResultHistoryUdpEntryLocalIp OBJECT-TYPE
    SYNTAX     DisplayString (SIZE(0..255))
    MAX-ACCESS read-only
    STATUS     current
    DESCRIPTION
            "-- empty --"
    ::= { lcsStatusIperfResultHistoryUdpEntry 2 }

-- {COLUMN} 1.3.6.1.4.1.2356.11.1.96.2.1.1.3
lcsStatusIperfResultHistoryUdpEntryRemoteIp OBJECT-TYPE
    SYNTAX     DisplayString (SIZE(0..255))
    MAX-ACCESS read-only
    STATUS     current
    DESCRIPTION
            "-- empty --"
    ::= { lcsStatusIperfResultHistoryUdpEntry 3 }

-- {COLUMN} 1.3.6.1.4.1.2356.11.1.96.2.1.1.4
lcsStatusIperfResultHistoryUdpEntryMode OBJECT-TYPE
    SYNTAX     INTEGER {
                  eUndefined (0),
                  eUnidirectionalServer (1),
                  eDualServer (2),
                  eTradeoffServer (3),
                  eUnidirectionalClient (4),
                  eDualClient (5),
                  eTradeoffClient (6)
            }
    MAX-ACCESS read-only
    STATUS     current
    DESCRIPTION
            "-- empty --"
    ::= { lcsStatusIperfResultHistoryUdpEntry 4 }

-- {COLUMN} 1.3.6.1.4.1.2356.11.1.96.2.1.1.5
lcsStatusIperfResultHistoryUdpEntryConnections OBJECT-TYPE
    SYNTAX     Integer32 (0..65535)
    MAX-ACCESS read-only
    STATUS     current
    DESCRIPTION
            "-- empty --"
    ::= { lcsStatusIperfResultHistoryUdpEntry 5 }

-- {COLUMN} 1.3.6.1.4.1.2356.11.1.96.2.1.1.6
lcsStatusIperfResultHistoryUdpEntryServerStart OBJECT-TYPE
    SYNTAX     DisplayString (SIZE(0..255))
    MAX-ACCESS read-only
    STATUS     current
    DESCRIPTION
            "-- empty --"
    ::= { lcsStatusIperfResultHistoryUdpEntry 6 }

-- {COLUMN} 1.3.6.1.4.1.2356.11.1.96.2.1.1.7
lcsStatusIperfResultHistoryUdpEntryServerStartNum OBJECT-TYPE
    SYNTAX     Counter32
    MAX-ACCESS read-only
    STATUS     current
    DESCRIPTION
            "-- empty --"
    ::= { lcsStatusIperfResultHistoryUdpEntry 7 }

-- {COLUMN} 1.3.6.1.4.1.2356.11.1.96.2.1.1.8
lcsStatusIperfResultHistoryUdpEntryServerStop OBJECT-TYPE
    SYNTAX     DisplayString (SIZE(0..255))
    MAX-ACCESS read-only
    STATUS     current
    DESCRIPTION
            "-- empty --"
    ::= { lcsStatusIperfResultHistoryUdpEntry 8 }

-- {COLUMN} 1.3.6.1.4.1.2356.11.1.96.2.1.1.9
lcsStatusIperfResultHistoryUdpEntryServerStopNum OBJECT-TYPE
    SYNTAX     Counter32
    MAX-ACCESS read-only
    STATUS     current
    DESCRIPTION
            "-- empty --"
    ::= { lcsStatusIperfResultHistoryUdpEntry 9 }

-- {COLUMN} 1.3.6.1.4.1.2356.11.1.96.2.1.1.10
lcsStatusIperfResultHistoryUdpEntryServerDurationMs OBJECT-TYPE
    SYNTAX     Counter32
    MAX-ACCESS read-only
    STATUS     current
    DESCRIPTION
            "-- empty --"
    ::= { lcsStatusIperfResultHistoryUdpEntry 10 }

-- {COLUMN} 1.3.6.1.4.1.2356.11.1.96.2.1.1.11
lcsStatusIperfResultHistoryUdpEntryServerBytes OBJECT-TYPE
    SYNTAX     Counter64
    MAX-ACCESS read-only
    STATUS     current
    DESCRIPTION
            "-- empty --"
    ::= { lcsStatusIperfResultHistoryUdpEntry 11 }

-- {COLUMN} 1.3.6.1.4.1.2356.11.1.96.2.1.1.12
lcsStatusIperfResultHistoryUdpEntryServerBandwidthKbps OBJECT-TYPE
    SYNTAX     Gauge32
    MAX-ACCESS read-only
    STATUS     current
    DESCRIPTION
            "-- empty --"
    ::= { lcsStatusIperfResultHistoryUdpEntry 12 }

-- {COLUMN} 1.3.6.1.4.1.2356.11.1.96.2.1.1.13
lcsStatusIperfResultHistoryUdpEntryServerPackets OBJECT-TYPE
    SYNTAX     Counter32
    MAX-ACCESS read-only
    STATUS     current
    DESCRIPTION
            "-- empty --"
    ::= { lcsStatusIperfResultHistoryUdpEntry 13 }

-- {COLUMN} 1.3.6.1.4.1.2356.11.1.96.2.1.1.14
lcsStatusIperfResultHistoryUdpEntryServerLostPackets OBJECT-TYPE
    SYNTAX     Counter32
    MAX-ACCESS read-only
    STATUS     current
    DESCRIPTION
            "-- empty --"
    ::= { lcsStatusIperfResultHistoryUdpEntry 14 }

-- {COLUMN} 1.3.6.1.4.1.2356.11.1.96.2.1.1.15
lcsStatusIperfResultHistoryUdpEntryServerOutOrderPackets OBJECT-TYPE
    SYNTAX     Counter32
    MAX-ACCESS read-only
    STATUS     current
    DESCRIPTION
            "-- empty --"
    ::= { lcsStatusIperfResultHistoryUdpEntry 15 }

-- {COLUMN} 1.3.6.1.4.1.2356.11.1.96.2.1.1.16
lcsStatusIperfResultHistoryUdpEntryServerJitterUs OBJECT-TYPE
    SYNTAX     Gauge32
    MAX-ACCESS read-only
    STATUS     current
    DESCRIPTION
            "-- empty --"
    ::= { lcsStatusIperfResultHistoryUdpEntry 16 }

-- {COLUMN} 1.3.6.1.4.1.2356.11.1.96.2.1.1.17
lcsStatusIperfResultHistoryUdpEntryServerError OBJECT-TYPE
    SYNTAX     DisplayString (SIZE(0..255))
    MAX-ACCESS read-only
    STATUS     current
    DESCRIPTION
            "-- empty --"
    ::= { lcsStatusIperfResultHistoryUdpEntry 17 }

-- {COLUMN} 1.3.6.1.4.1.2356.11.1.96.2.1.1.18
lcsStatusIperfResultHistoryUdpEntryClientStart OBJECT-TYPE
    SYNTAX     DisplayString (SIZE(0..255))
    MAX-ACCESS read-only
    STATUS     current
    DESCRIPTION
            "-- empty --"
    ::= { lcsStatusIperfResultHistoryUdpEntry 18 }

-- {COLUMN} 1.3.6.1.4.1.2356.11.1.96.2.1.1.19
lcsStatusIperfResultHistoryUdpEntryClientStartNum OBJECT-TYPE
    SYNTAX     Counter32
    MAX-ACCESS read-only
    STATUS     current
    DESCRIPTION
            "-- empty --"
    ::= { lcsStatusIperfResultHistoryUdpEntry 19 }

-- {COLUMN} 1.3.6.1.4.1.2356.11.1.96.2.1.1.20
lcsStatusIperfResultHistoryUdpEntryClientStop OBJECT-TYPE
    SYNTAX     DisplayString (SIZE(0..255))
    MAX-ACCESS read-only
    STATUS     current
    DESCRIPTION
            "-- empty --"
    ::= { lcsStatusIperfResultHistoryUdpEntry 20 }

-- {COLUMN} 1.3.6.1.4.1.2356.11.1.96.2.1.1.21
lcsStatusIperfResultHistoryUdpEntryClientStopNum OBJECT-TYPE
    SYNTAX     Counter32
    MAX-ACCESS read-only
    STATUS     current
    DESCRIPTION
            "-- empty --"
    ::= { lcsStatusIperfResultHistoryUdpEntry 21 }

-- {COLUMN} 1.3.6.1.4.1.2356.11.1.96.2.1.1.22
lcsStatusIperfResultHistoryUdpEntryClientDurationMs OBJECT-TYPE
    SYNTAX     Counter32
    MAX-ACCESS read-only
    STATUS     current
    DESCRIPTION
            "-- empty --"
    ::= { lcsStatusIperfResultHistoryUdpEntry 22 }

-- {COLUMN} 1.3.6.1.4.1.2356.11.1.96.2.1.1.23
lcsStatusIperfResultHistoryUdpEntryClientBytes OBJECT-TYPE
    SYNTAX     Counter64
    MAX-ACCESS read-only
    STATUS     current
    DESCRIPTION
            "-- empty --"
    ::= { lcsStatusIperfResultHistoryUdpEntry 23 }

-- {COLUMN} 1.3.6.1.4.1.2356.11.1.96.2.1.1.24
lcsStatusIperfResultHistoryUdpEntryClientBandwidthKbps OBJECT-TYPE
    SYNTAX     Gauge32
    MAX-ACCESS read-only
    STATUS     current
    DESCRIPTION
            "-- empty --"
    ::= { lcsStatusIperfResultHistoryUdpEntry 24 }

-- {COLUMN} 1.3.6.1.4.1.2356.11.1.96.2.1.1.25
lcsStatusIperfResultHistoryUdpEntryClientPackets OBJECT-TYPE
    SYNTAX     Counter32
    MAX-ACCESS read-only
    STATUS     current
    DESCRIPTION
            "-- empty --"
    ::= { lcsStatusIperfResultHistoryUdpEntry 25 }

-- {COLUMN} 1.3.6.1.4.1.2356.11.1.96.2.1.1.26
lcsStatusIperfResultHistoryUdpEntryClientError OBJECT-TYPE
    SYNTAX     DisplayString (SIZE(0..255))
    MAX-ACCESS read-only
    STATUS     current
    DESCRIPTION
            "-- empty --"
    ::= { lcsStatusIperfResultHistoryUdpEntry 26 }

-- {COLUMN} 1.3.6.1.4.1.2356.11.1.96.2.1.1.27
lcsStatusIperfResultHistoryUdpEntryRemoteServerDurationMs OBJECT-TYPE
    SYNTAX     Counter32
    MAX-ACCESS read-only
    STATUS     current
    DESCRIPTION
            "-- empty --"
    ::= { lcsStatusIperfResultHistoryUdpEntry 27 }

-- {COLUMN} 1.3.6.1.4.1.2356.11.1.96.2.1.1.28
lcsStatusIperfResultHistoryUdpEntryRemoteServerBytes OBJECT-TYPE
    SYNTAX     Counter64
    MAX-ACCESS read-only
    STATUS     current
    DESCRIPTION
            "-- empty --"
    ::= { lcsStatusIperfResultHistoryUdpEntry 28 }

-- {COLUMN} 1.3.6.1.4.1.2356.11.1.96.2.1.1.29
lcsStatusIperfResultHistoryUdpEntryRemoteServerBandwidthKbps OBJECT-TYPE
    SYNTAX     Gauge32
    MAX-ACCESS read-only
    STATUS     current
    DESCRIPTION
            "-- empty --"
    ::= { lcsStatusIperfResultHistoryUdpEntry 29 }

-- {COLUMN} 1.3.6.1.4.1.2356.11.1.96.2.1.1.30
lcsStatusIperfResultHistoryUdpEntryRemoteServerPackets OBJECT-TYPE
    SYNTAX     Counter32
    MAX-ACCESS read-only
    STATUS     current
    DESCRIPTION
            "-- empty --"
    ::= { lcsStatusIperfResultHistoryUdpEntry 30 }

-- {COLUMN} 1.3.6.1.4.1.2356.11.1.96.2.1.1.31
lcsStatusIperfResultHistoryUdpEntryRemoteServerLostPackets OBJECT-TYPE
    SYNTAX     Counter32
    MAX-ACCESS read-only
    STATUS     current
    DESCRIPTION
            "-- empty --"
    ::= { lcsStatusIperfResultHistoryUdpEntry 31 }

-- {COLUMN} 1.3.6.1.4.1.2356.11.1.96.2.1.1.32
lcsStatusIperfResultHistoryUdpEntryRemoteServerOutOrderPackets OBJECT-TYPE
    SYNTAX     Counter32
    MAX-ACCESS read-only
    STATUS     current
    DESCRIPTION
            "-- empty --"
    ::= { lcsStatusIperfResultHistoryUdpEntry 32 }

-- {COLUMN} 1.3.6.1.4.1.2356.11.1.96.2.1.1.33
lcsStatusIperfResultHistoryUdpEntryRemoteServerJitterUs OBJECT-TYPE
    SYNTAX     Gauge32
    MAX-ACCESS read-only
    STATUS     current
    DESCRIPTION
            "-- empty --"
    ::= { lcsStatusIperfResultHistoryUdpEntry 33 }

-- {TABLE} 1.3.6.1.4.1.2356.11.1.96.2.2
lcsStatusIperfResultHistoryTcpTable OBJECT-TYPE
    SYNTAX     SEQUENCE OF LcsStatusIperfResultHistoryTcpEntry
    MAX-ACCESS not-accessible
    STATUS     current
    DESCRIPTION
            "-- empty --"
    ::= { lcsStatusIperfResultHistory 2 }

-- {ROW} 1.3.6.1.4.1.2356.11.1.96.2.2.1
lcsStatusIperfResultHistoryTcpEntry OBJECT-TYPE
    SYNTAX     LcsStatusIperfResultHistoryTcpEntry
    MAX-ACCESS not-accessible
    STATUS     current
    DESCRIPTION
            ""
    INDEX {
            lcsStatusIperfResultHistoryTcpEntryIndex
          }
    ::= { lcsStatusIperfResultHistoryTcpTable 1 }

LcsStatusIperfResultHistoryTcpEntry ::= SEQUENCE {
            lcsStatusIperfResultHistoryTcpEntryIndex Gauge32,
            lcsStatusIperfResultHistoryTcpEntryLocalIp DisplayString,
            lcsStatusIperfResultHistoryTcpEntryRemoteIp DisplayString,
            lcsStatusIperfResultHistoryTcpEntryMode INTEGER,
            lcsStatusIperfResultHistoryTcpEntryConnections Integer32,
            lcsStatusIperfResultHistoryTcpEntryServerStart DisplayString,
            lcsStatusIperfResultHistoryTcpEntryServerStartNum Counter32,
            lcsStatusIperfResultHistoryTcpEntryServerStop DisplayString,
            lcsStatusIperfResultHistoryTcpEntryServerStopNum Counter32,
            lcsStatusIperfResultHistoryTcpEntryServerDurationMs Counter32,
            lcsStatusIperfResultHistoryTcpEntryServerBytes Counter64,
            lcsStatusIperfResultHistoryTcpEntryServerBandwidthKbps Gauge32,
            lcsStatusIperfResultHistoryTcpEntryServerError DisplayString,
            lcsStatusIperfResultHistoryTcpEntryClientStart DisplayString,
            lcsStatusIperfResultHistoryTcpEntryClientStartNum Counter32,
            lcsStatusIperfResultHistoryTcpEntryClientStop DisplayString,
            lcsStatusIperfResultHistoryTcpEntryClientStopNum Counter32,
            lcsStatusIperfResultHistoryTcpEntryClientDurationMs Counter32,
            lcsStatusIperfResultHistoryTcpEntryClientBytes Counter64,
            lcsStatusIperfResultHistoryTcpEntryClientBandwidthKbps Gauge32,
            lcsStatusIperfResultHistoryTcpEntryClientError DisplayString
    }

-- {COLUMN} 1.3.6.1.4.1.2356.11.1.96.2.2.1.1
lcsStatusIperfResultHistoryTcpEntryIndex OBJECT-TYPE
    SYNTAX     Gauge32
    MAX-ACCESS read-only
    STATUS     current
    DESCRIPTION
            "-- empty --"
    ::= { lcsStatusIperfResultHistoryTcpEntry 1 }

-- {COLUMN} 1.3.6.1.4.1.2356.11.1.96.2.2.1.2
lcsStatusIperfResultHistoryTcpEntryLocalIp OBJECT-TYPE
    SYNTAX     DisplayString (SIZE(0..255))
    MAX-ACCESS read-only
    STATUS     current
    DESCRIPTION
            "-- empty --"
    ::= { lcsStatusIperfResultHistoryTcpEntry 2 }

-- {COLUMN} 1.3.6.1.4.1.2356.11.1.96.2.2.1.3
lcsStatusIperfResultHistoryTcpEntryRemoteIp OBJECT-TYPE
    SYNTAX     DisplayString (SIZE(0..255))
    MAX-ACCESS read-only
    STATUS     current
    DESCRIPTION
            "-- empty --"
    ::= { lcsStatusIperfResultHistoryTcpEntry 3 }

-- {COLUMN} 1.3.6.1.4.1.2356.11.1.96.2.2.1.4
lcsStatusIperfResultHistoryTcpEntryMode OBJECT-TYPE
    SYNTAX     INTEGER {
                  eUndefined (0),
                  eUnidirectionalServer (1),
                  eDualServer (2),
                  eTradeoffServer (3),
                  eUnidirectionalClient (4),
                  eDualClient (5),
                  eTradeoffClient (6)
            }
    MAX-ACCESS read-only
    STATUS     current
    DESCRIPTION
            "-- empty --"
    ::= { lcsStatusIperfResultHistoryTcpEntry 4 }

-- {COLUMN} 1.3.6.1.4.1.2356.11.1.96.2.2.1.5
lcsStatusIperfResultHistoryTcpEntryConnections OBJECT-TYPE
    SYNTAX     Integer32 (0..65535)
    MAX-ACCESS read-only
    STATUS     current
    DESCRIPTION
            "-- empty --"
    ::= { lcsStatusIperfResultHistoryTcpEntry 5 }

-- {COLUMN} 1.3.6.1.4.1.2356.11.1.96.2.2.1.6
lcsStatusIperfResultHistoryTcpEntryServerStart OBJECT-TYPE
    SYNTAX     DisplayString (SIZE(0..255))
    MAX-ACCESS read-only
    STATUS     current
    DESCRIPTION
            "-- empty --"
    ::= { lcsStatusIperfResultHistoryTcpEntry 6 }

-- {COLUMN} 1.3.6.1.4.1.2356.11.1.96.2.2.1.7
lcsStatusIperfResultHistoryTcpEntryServerStartNum OBJECT-TYPE
    SYNTAX     Counter32
    MAX-ACCESS read-only
    STATUS     current
    DESCRIPTION
            "-- empty --"
    ::= { lcsStatusIperfResultHistoryTcpEntry 7 }

-- {COLUMN} 1.3.6.1.4.1.2356.11.1.96.2.2.1.8
lcsStatusIperfResultHistoryTcpEntryServerStop OBJECT-TYPE
    SYNTAX     DisplayString (SIZE(0..255))
    MAX-ACCESS read-only
    STATUS     current
    DESCRIPTION
            "-- empty --"
    ::= { lcsStatusIperfResultHistoryTcpEntry 8 }

-- {COLUMN} 1.3.6.1.4.1.2356.11.1.96.2.2.1.9
lcsStatusIperfResultHistoryTcpEntryServerStopNum OBJECT-TYPE
    SYNTAX     Counter32
    MAX-ACCESS read-only
    STATUS     current
    DESCRIPTION
            "-- empty --"
    ::= { lcsStatusIperfResultHistoryTcpEntry 9 }

-- {COLUMN} 1.3.6.1.4.1.2356.11.1.96.2.2.1.10
lcsStatusIperfResultHistoryTcpEntryServerDurationMs OBJECT-TYPE
    SYNTAX     Counter32
    MAX-ACCESS read-only
    STATUS     current
    DESCRIPTION
            "-- empty --"
    ::= { lcsStatusIperfResultHistoryTcpEntry 10 }

-- {COLUMN} 1.3.6.1.4.1.2356.11.1.96.2.2.1.11
lcsStatusIperfResultHistoryTcpEntryServerBytes OBJECT-TYPE
    SYNTAX     Counter64
    MAX-ACCESS read-only
    STATUS     current
    DESCRIPTION
            "-- empty --"
    ::= { lcsStatusIperfResultHistoryTcpEntry 11 }

-- {COLUMN} 1.3.6.1.4.1.2356.11.1.96.2.2.1.12
lcsStatusIperfResultHistoryTcpEntryServerBandwidthKbps OBJECT-TYPE
    SYNTAX     Gauge32
    MAX-ACCESS read-only
    STATUS     current
    DESCRIPTION
            "-- empty --"
    ::= { lcsStatusIperfResultHistoryTcpEntry 12 }

-- {COLUMN} 1.3.6.1.4.1.2356.11.1.96.2.2.1.13
lcsStatusIperfResultHistoryTcpEntryServerError OBJECT-TYPE
    SYNTAX     DisplayString (SIZE(0..255))
    MAX-ACCESS read-only
    STATUS     current
    DESCRIPTION
            "-- empty --"
    ::= { lcsStatusIperfResultHistoryTcpEntry 13 }

-- {COLUMN} 1.3.6.1.4.1.2356.11.1.96.2.2.1.14
lcsStatusIperfResultHistoryTcpEntryClientStart OBJECT-TYPE
    SYNTAX     DisplayString (SIZE(0..255))
    MAX-ACCESS read-only
    STATUS     current
    DESCRIPTION
            "-- empty --"
    ::= { lcsStatusIperfResultHistoryTcpEntry 14 }

-- {COLUMN} 1.3.6.1.4.1.2356.11.1.96.2.2.1.15
lcsStatusIperfResultHistoryTcpEntryClientStartNum OBJECT-TYPE
    SYNTAX     Counter32
    MAX-ACCESS read-only
    STATUS     current
    DESCRIPTION
            "-- empty --"
    ::= { lcsStatusIperfResultHistoryTcpEntry 15 }

-- {COLUMN} 1.3.6.1.4.1.2356.11.1.96.2.2.1.16
lcsStatusIperfResultHistoryTcpEntryClientStop OBJECT-TYPE
    SYNTAX     DisplayString (SIZE(0..255))
    MAX-ACCESS read-only
    STATUS     current
    DESCRIPTION
            "-- empty --"
    ::= { lcsStatusIperfResultHistoryTcpEntry 16 }

-- {COLUMN} 1.3.6.1.4.1.2356.11.1.96.2.2.1.17
lcsStatusIperfResultHistoryTcpEntryClientStopNum OBJECT-TYPE
    SYNTAX     Counter32
    MAX-ACCESS read-only
    STATUS     current
    DESCRIPTION
            "-- empty --"
    ::= { lcsStatusIperfResultHistoryTcpEntry 17 }

-- {COLUMN} 1.3.6.1.4.1.2356.11.1.96.2.2.1.18
lcsStatusIperfResultHistoryTcpEntryClientDurationMs OBJECT-TYPE
    SYNTAX     Counter32
    MAX-ACCESS read-only
    STATUS     current
    DESCRIPTION
            "-- empty --"
    ::= { lcsStatusIperfResultHistoryTcpEntry 18 }

-- {COLUMN} 1.3.6.1.4.1.2356.11.1.96.2.2.1.19
lcsStatusIperfResultHistoryTcpEntryClientBytes OBJECT-TYPE
    SYNTAX     Counter64
    MAX-ACCESS read-only
    STATUS     current
    DESCRIPTION
            "-- empty --"
    ::= { lcsStatusIperfResultHistoryTcpEntry 19 }

-- {COLUMN} 1.3.6.1.4.1.2356.11.1.96.2.2.1.20
lcsStatusIperfResultHistoryTcpEntryClientBandwidthKbps OBJECT-TYPE
    SYNTAX     Gauge32
    MAX-ACCESS read-only
    STATUS     current
    DESCRIPTION
            "-- empty --"
    ::= { lcsStatusIperfResultHistoryTcpEntry 20 }

-- {COLUMN} 1.3.6.1.4.1.2356.11.1.96.2.2.1.21
lcsStatusIperfResultHistoryTcpEntryClientError OBJECT-TYPE
    SYNTAX     DisplayString (SIZE(0..255))
    MAX-ACCESS read-only
    STATUS     current
    DESCRIPTION
            "-- empty --"
    ::= { lcsStatusIperfResultHistoryTcpEntry 21 }

-- {SCALAR} 1.3.6.1.4.1.2356.11.1.96.3
lcsStatusIperfDeleteResults OBJECT-TYPE
    SYNTAX     DisplayString
    MAX-ACCESS read-write
    STATUS     current
    DESCRIPTION
            "-- empty --"
    ::= { lcsStatusIperf 3 }

-- {SCALAR} 1.3.6.1.4.1.2356.11.1.96.4
lcsStatusIperfUdpDaemonState OBJECT-TYPE
    SYNTAX     INTEGER {
                  eInactive (0),
                  eRunning (1),
                  eErrorInvalidSettings (2),
                  eErrorPortNotAvailable (3)
            }
    MAX-ACCESS read-only
    STATUS     current
    DESCRIPTION
            "-- empty --"
    ::= { lcsStatusIperf 4 }

-- {SCALAR} 1.3.6.1.4.1.2356.11.1.96.5
lcsStatusIperfTcpDaemonState OBJECT-TYPE
    SYNTAX     INTEGER {
                  eInactive (0),
                  eRunning (1),
                  eErrorInvalidSettings (2),
                  eErrorPortNotAvailable (3)
            }
    MAX-ACCESS read-only
    STATUS     current
    DESCRIPTION
            "-- empty --"
    ::= { lcsStatusIperf 5 }

-- {NODE} 1.3.6.1.4.1.2356.11.1.97
lcsStatusBatteryPack OBJECT IDENTIFIER ::= { lcsStatus 97 }

-- {SCALAR} 1.3.6.1.4.1.2356.11.1.97.1
lcsStatusBatteryPackConnected OBJECT-TYPE
    SYNTAX     INTEGER {
                  eNo (0),
                  eYes (1),
                  eNever (128)
            }
    MAX-ACCESS read-only
    STATUS     current
    DESCRIPTION
            "-- empty --"
    ::= { lcsStatusBatteryPack 1 }

-- {SCALAR} 1.3.6.1.4.1.2356.11.1.97.2
lcsStatusBatteryPackMainsAvailable OBJECT-TYPE
    SYNTAX     INTEGER {
                  eNo (0),
                  eYes (1)
            }
    MAX-ACCESS read-only
    STATUS     current
    DESCRIPTION
            "-- empty --"
    ::= { lcsStatusBatteryPack 2 }

-- {SCALAR} 1.3.6.1.4.1.2356.11.1.97.3
lcsStatusBatteryPackChargerState OBJECT-TYPE
    SYNTAX     INTEGER {
                  eStandby (1),
                  eBadBattery (2),
                  eCharging (3),
                  ePause (4),
                  eBackup (5),
                  eDischarging (6)
            }
    MAX-ACCESS read-only
    STATUS     current
    DESCRIPTION
            "-- empty --"
    ::= { lcsStatusBatteryPack 3 }

-- {SCALAR} 1.3.6.1.4.1.2356.11.1.97.4
lcsStatusBatteryPackChargeCycles OBJECT-TYPE
    SYNTAX     Integer32 (0..2147483647)
    MAX-ACCESS read-only
    STATUS     current
    DESCRIPTION
            "-- empty --"
    ::= { lcsStatusBatteryPack 4 }

-- {SCALAR} 1.3.6.1.4.1.2356.11.1.97.5
lcsStatusBatteryPackTemperatureDegrees OBJECT-TYPE
    SYNTAX     Integer32 (-128..127)
    MAX-ACCESS read-only
    STATUS     current
    DESCRIPTION
            "-- empty --"
    ::= { lcsStatusBatteryPack 5 }

-- {SCALAR} 1.3.6.1.4.1.2356.11.1.97.6
lcsStatusBatteryPackOperatingTime OBJECT-TYPE
    SYNTAX     Gauge32
    MAX-ACCESS read-only
    STATUS     current
    DESCRIPTION
            "-- empty --"
    ::= { lcsStatusBatteryPack 6 }

-- {SCALAR} 1.3.6.1.4.1.2356.11.1.97.7
lcsStatusBatteryPackChargeConditionPercent OBJECT-TYPE
    SYNTAX     Integer32 (0..255)
    MAX-ACCESS read-only
    STATUS     current
    DESCRIPTION
            "-- empty --"
    ::= { lcsStatusBatteryPack 7 }

-- {SCALAR} 1.3.6.1.4.1.2356.11.1.97.8
lcsStatusBatteryPackSerialNumber OBJECT-TYPE
    SYNTAX     DisplayString (SIZE(0..16))
    MAX-ACCESS read-only
    STATUS     current
    DESCRIPTION
            "-- empty --"
    ::= { lcsStatusBatteryPack 8 }

-- {SCALAR} 1.3.6.1.4.1.2356.11.1.97.11
lcsStatusBatteryPackFirmwareVersion OBJECT-TYPE
    SYNTAX     DisplayString (SIZE(0..10))
    MAX-ACCESS read-only
    STATUS     current
    DESCRIPTION
            "-- empty --"
    ::= { lcsStatusBatteryPack 11 }

-- {TABLE} 1.3.6.1.4.1.2356.11.1.97.12
lcsStatusBatteryPackPowerOutageTable OBJECT-TYPE
    SYNTAX     SEQUENCE OF LcsStatusBatteryPackPowerOutageEntry
    MAX-ACCESS not-accessible
    STATUS     current
    DESCRIPTION
            "-- empty --"
    ::= { lcsStatusBatteryPack 12 }

-- {ROW} 1.3.6.1.4.1.2356.11.1.97.12.1
lcsStatusBatteryPackPowerOutageEntry OBJECT-TYPE
    SYNTAX     LcsStatusBatteryPackPowerOutageEntry
    MAX-ACCESS not-accessible
    STATUS     current
    DESCRIPTION
            ""
    INDEX {
            lcsStatusBatteryPackPowerOutageEntryIndex
          }
    ::= { lcsStatusBatteryPackPowerOutageTable 1 }

LcsStatusBatteryPackPowerOutageEntry ::= SEQUENCE {
            lcsStatusBatteryPackPowerOutageEntryIndex Integer32,
            lcsStatusBatteryPackPowerOutageEntryFailureTime Gauge32,
            lcsStatusBatteryPackPowerOutageEntryRestoreTime Gauge32,
            lcsStatusBatteryPackPowerOutageEntryDuration Gauge32,
            lcsStatusBatteryPackPowerOutageEntryEnergyWs Integer32
    }

-- {COLUMN} 1.3.6.1.4.1.2356.11.1.97.12.1.1
lcsStatusBatteryPackPowerOutageEntryIndex OBJECT-TYPE
    SYNTAX     Integer32 (0..2147483647)
    MAX-ACCESS read-only
    STATUS     current
    DESCRIPTION
            "-- empty --"
    ::= { lcsStatusBatteryPackPowerOutageEntry 1 }

-- {COLUMN} 1.3.6.1.4.1.2356.11.1.97.12.1.2
lcsStatusBatteryPackPowerOutageEntryFailureTime OBJECT-TYPE
    SYNTAX     Gauge32
    MAX-ACCESS read-only
    STATUS     current
    DESCRIPTION
            "-- empty --"
    ::= { lcsStatusBatteryPackPowerOutageEntry 2 }

-- {COLUMN} 1.3.6.1.4.1.2356.11.1.97.12.1.3
lcsStatusBatteryPackPowerOutageEntryRestoreTime OBJECT-TYPE
    SYNTAX     Gauge32
    MAX-ACCESS read-only
    STATUS     current
    DESCRIPTION
            "-- empty --"
    ::= { lcsStatusBatteryPackPowerOutageEntry 3 }

-- {COLUMN} 1.3.6.1.4.1.2356.11.1.97.12.1.4
lcsStatusBatteryPackPowerOutageEntryDuration OBJECT-TYPE
    SYNTAX     Gauge32
    MAX-ACCESS read-only
    STATUS     current
    DESCRIPTION
            "-- empty --"
    ::= { lcsStatusBatteryPackPowerOutageEntry 4 }

-- {COLUMN} 1.3.6.1.4.1.2356.11.1.97.12.1.5
lcsStatusBatteryPackPowerOutageEntryEnergyWs OBJECT-TYPE
    SYNTAX     Integer32 (-2147483648..2147483647)
    MAX-ACCESS read-only
    STATUS     current
    DESCRIPTION
            "-- empty --"
    ::= { lcsStatusBatteryPackPowerOutageEntry 5 }

-- {TABLE} 1.3.6.1.4.1.2356.11.1.97.13
lcsStatusBatteryPackLoadConditionTable OBJECT-TYPE
    SYNTAX     SEQUENCE OF LcsStatusBatteryPackLoadConditionEntry
    MAX-ACCESS not-accessible
    STATUS     current
    DESCRIPTION
            "-- empty --"
    ::= { lcsStatusBatteryPack 13 }

-- {ROW} 1.3.6.1.4.1.2356.11.1.97.13.1
lcsStatusBatteryPackLoadConditionEntry OBJECT-TYPE
    SYNTAX     LcsStatusBatteryPackLoadConditionEntry
    MAX-ACCESS not-accessible
    STATUS     current
    DESCRIPTION
            ""
    INDEX {
            lcsStatusBatteryPackLoadConditionEntryOutput
          }
    ::= { lcsStatusBatteryPackLoadConditionTable 1 }

LcsStatusBatteryPackLoadConditionEntry ::= SEQUENCE {
            lcsStatusBatteryPackLoadConditionEntryOutput DisplayString,
            lcsStatusBatteryPackLoadConditionEntryVoltageMv Integer32,
            lcsStatusBatteryPackLoadConditionEntryCurrentMa Integer32,
            lcsStatusBatteryPackLoadConditionEntryPowerMw Integer32
    }

-- {COLUMN} 1.3.6.1.4.1.2356.11.1.97.13.1.1
lcsStatusBatteryPackLoadConditionEntryOutput OBJECT-TYPE
    SYNTAX     DisplayString (SIZE(0..4))
    MAX-ACCESS read-only
    STATUS     current
    DESCRIPTION
            "-- empty --"
    ::= { lcsStatusBatteryPackLoadConditionEntry 1 }

-- {COLUMN} 1.3.6.1.4.1.2356.11.1.97.13.1.2
lcsStatusBatteryPackLoadConditionEntryVoltageMv OBJECT-TYPE
    SYNTAX     Integer32 (-32768..32767)
    MAX-ACCESS read-only
    STATUS     current
    DESCRIPTION
            "-- empty --"
    ::= { lcsStatusBatteryPackLoadConditionEntry 2 }

-- {COLUMN} 1.3.6.1.4.1.2356.11.1.97.13.1.3
lcsStatusBatteryPackLoadConditionEntryCurrentMa OBJECT-TYPE
    SYNTAX     Integer32 (-32768..32767)
    MAX-ACCESS read-only
    STATUS     current
    DESCRIPTION
            "-- empty --"
    ::= { lcsStatusBatteryPackLoadConditionEntry 3 }

-- {COLUMN} 1.3.6.1.4.1.2356.11.1.97.13.1.4
lcsStatusBatteryPackLoadConditionEntryPowerMw OBJECT-TYPE
    SYNTAX     Integer32 (-32768..32767)
    MAX-ACCESS read-only
    STATUS     current
    DESCRIPTION
            "-- empty --"
    ::= { lcsStatusBatteryPackLoadConditionEntry 4 }

-- {SCALAR} 1.3.6.1.4.1.2356.11.1.97.14
lcsStatusBatteryPackBoardRevision OBJECT-TYPE
    SYNTAX     DisplayString (SIZE(0..1))
    MAX-ACCESS read-only
    STATUS     current
    DESCRIPTION
            "-- empty --"
    ::= { lcsStatusBatteryPack 14 }

-- {SCALAR} 1.3.6.1.4.1.2356.11.1.97.15
lcsStatusBatteryPackModLevel OBJECT-TYPE
    SYNTAX     DisplayString (SIZE(0..2))
    MAX-ACCESS read-only
    STATUS     current
    DESCRIPTION
            "-- empty --"
    ::= { lcsStatusBatteryPack 15 }

-- {SCALAR} 1.3.6.1.4.1.2356.11.1.97.16
lcsStatusBatteryPackRemainingEnergyWs OBJECT-TYPE
    SYNTAX     Integer32 (0..2147483647)
    MAX-ACCESS read-only
    STATUS     current
    DESCRIPTION
            "-- empty --"
    ::= { lcsStatusBatteryPack 16 }

-- {SCALAR} 1.3.6.1.4.1.2356.11.1.97.17
lcsStatusBatteryPackRemainingTime OBJECT-TYPE
    SYNTAX     Gauge32
    MAX-ACCESS read-only
    STATUS     current
    DESCRIPTION
            "-- empty --"
    ::= { lcsStatusBatteryPack 17 }

-- {SCALAR} 1.3.6.1.4.1.2356.11.1.97.18
lcsStatusBatteryPackDeleteValues OBJECT-TYPE
    SYNTAX     DisplayString
    MAX-ACCESS read-write
    STATUS     current
    DESCRIPTION
            "-- empty --"
    ::= { lcsStatusBatteryPack 18 }

-- {SCALAR} 1.3.6.1.4.1.2356.11.1.97.19
lcsStatusBatteryPackProductionDate OBJECT-TYPE
    SYNTAX     Gauge32
    MAX-ACCESS read-only
    STATUS     current
    DESCRIPTION
            "-- empty --"
    ::= { lcsStatusBatteryPack 19 }

-- {SCALAR} 1.3.6.1.4.1.2356.11.1.97.20
lcsStatusBatteryPackBatteryChangeDate OBJECT-TYPE
    SYNTAX     Gauge32
    MAX-ACCESS read-only
    STATUS     current
    DESCRIPTION
            "-- empty --"
    ::= { lcsStatusBatteryPack 20 }

-- {SCALAR} 1.3.6.1.4.1.2356.11.1.97.21
lcsStatusBatteryPackDischargeEnergyWs OBJECT-TYPE
    SYNTAX     Integer32 (0..2147483647)
    MAX-ACCESS read-only
    STATUS     current
    DESCRIPTION
            "-- empty --"
    ::= { lcsStatusBatteryPack 21 }

-- {SCALAR} 1.3.6.1.4.1.2356.11.1.97.22
lcsStatusBatteryPackNominalEnergyWs OBJECT-TYPE
    SYNTAX     Integer32 (0..2147483647)
    MAX-ACCESS read-only
    STATUS     current
    DESCRIPTION
            "-- empty --"
    ::= { lcsStatusBatteryPack 22 }

-- {SCALAR} 1.3.6.1.4.1.2356.11.1.97.23
lcsStatusBatteryPackServiceRequest OBJECT-TYPE
    SYNTAX     INTEGER {
                  eNo (0),
                  eYes (1)
            }
    MAX-ACCESS read-only
    STATUS     current
    DESCRIPTION
            "-- empty --"
    ::= { lcsStatusBatteryPack 23 }

-- {SCALAR} 1.3.6.1.4.1.2356.11.1.97.24
lcsStatusBatteryPackServiceDate OBJECT-TYPE
    SYNTAX     Gauge32
    MAX-ACCESS read-only
    STATUS     current
    DESCRIPTION
            "-- empty --"
    ::= { lcsStatusBatteryPack 24 }

-- {SCALAR} 1.3.6.1.4.1.2356.11.1.97.25
lcsStatusBatteryPackServiceOperatingTime OBJECT-TYPE
    SYNTAX     Gauge32
    MAX-ACCESS read-only
    STATUS     current
    DESCRIPTION
            "-- empty --"
    ::= { lcsStatusBatteryPack 25 }

-- {SCALAR} 1.3.6.1.4.1.2356.11.1.97.26
lcsStatusBatteryPackServiceChargeCycles OBJECT-TYPE
    SYNTAX     Integer32 (0..2147483647)
    MAX-ACCESS read-only
    STATUS     current
    DESCRIPTION
            "-- empty --"
    ::= { lcsStatusBatteryPack 26 }

-- {NODE} 1.3.6.1.4.1.2356.11.1.98
lcsStatusLmc OBJECT IDENTIFIER ::= { lcsStatus 98 }

-- {TABLE} 1.3.6.1.4.1.2356.11.1.98.1
lcsStatusLmcTransportStatusTable OBJECT-TYPE
    SYNTAX     SEQUENCE OF LcsStatusLmcTransportStatusEntry
    MAX-ACCESS not-accessible
    STATUS     current
    DESCRIPTION
            "-- empty --"
    ::= { lcsStatusLmc 1 }

-- {ROW} 1.3.6.1.4.1.2356.11.1.98.1.1
lcsStatusLmcTransportStatusEntry OBJECT-TYPE
    SYNTAX     LcsStatusLmcTransportStatusEntry
    MAX-ACCESS not-accessible
    STATUS     current
    DESCRIPTION
            ""
    INDEX {
            lcsStatusLmcTransportStatusEntryServiceName
          }
    ::= { lcsStatusLmcTransportStatusTable 1 }

LcsStatusLmcTransportStatusEntry ::= SEQUENCE {
            lcsStatusLmcTransportStatusEntryServiceName INTEGER,
            lcsStatusLmcTransportStatusEntryHttpRequests Integer32,
            lcsStatusLmcTransportStatusEntryHttpRequestErrors Integer32,
            lcsStatusLmcTransportStatusEntryTxBytes Integer32,
            lcsStatusLmcTransportStatusEntryTxBytesPerSecond DisplayString,
            lcsStatusLmcTransportStatusEntryRxBytes Integer32,
            lcsStatusLmcTransportStatusEntryRxBytesPerSecond DisplayString
    }

-- {COLUMN} 1.3.6.1.4.1.2356.11.1.98.1.1.1
lcsStatusLmcTransportStatusEntryServiceName OBJECT-TYPE
    SYNTAX     INTEGER {
                  eControlService (1),
                  eMonitorService (2),
                  ePairingService (3),
                  eTunnelService (4)
            }
    MAX-ACCESS read-only
    STATUS     current
    DESCRIPTION
            "-- empty --"
    ::= { lcsStatusLmcTransportStatusEntry 1 }

-- {COLUMN} 1.3.6.1.4.1.2356.11.1.98.1.1.2
lcsStatusLmcTransportStatusEntryHttpRequests OBJECT-TYPE
    SYNTAX     Integer32 (0..2147483647)
    MAX-ACCESS read-only
    STATUS     current
    DESCRIPTION
            "-- empty --"
    ::= { lcsStatusLmcTransportStatusEntry 2 }

-- {COLUMN} 1.3.6.1.4.1.2356.11.1.98.1.1.3
lcsStatusLmcTransportStatusEntryHttpRequestErrors OBJECT-TYPE
    SYNTAX     Integer32 (0..2147483647)
    MAX-ACCESS read-only
    STATUS     current
    DESCRIPTION
            "-- empty --"
    ::= { lcsStatusLmcTransportStatusEntry 3 }

-- {COLUMN} 1.3.6.1.4.1.2356.11.1.98.1.1.4
lcsStatusLmcTransportStatusEntryTxBytes OBJECT-TYPE
    SYNTAX     Integer32 (0..2147483647)
    MAX-ACCESS read-only
    STATUS     current
    DESCRIPTION
            "-- empty --"
    ::= { lcsStatusLmcTransportStatusEntry 4 }

-- {COLUMN} 1.3.6.1.4.1.2356.11.1.98.1.1.5
lcsStatusLmcTransportStatusEntryTxBytesPerSecond OBJECT-TYPE
    SYNTAX     DisplayString (SIZE(0..255))
    MAX-ACCESS read-only
    STATUS     current
    DESCRIPTION
            "-- empty --"
    ::= { lcsStatusLmcTransportStatusEntry 5 }

-- {COLUMN} 1.3.6.1.4.1.2356.11.1.98.1.1.6
lcsStatusLmcTransportStatusEntryRxBytes OBJECT-TYPE
    SYNTAX     Integer32 (0..2147483647)
    MAX-ACCESS read-only
    STATUS     current
    DESCRIPTION
            "-- empty --"
    ::= { lcsStatusLmcTransportStatusEntry 6 }

-- {COLUMN} 1.3.6.1.4.1.2356.11.1.98.1.1.7
lcsStatusLmcTransportStatusEntryRxBytesPerSecond OBJECT-TYPE
    SYNTAX     DisplayString (SIZE(0..255))
    MAX-ACCESS read-only
    STATUS     current
    DESCRIPTION
            "-- empty --"
    ::= { lcsStatusLmcTransportStatusEntry 7 }

-- {SCALAR} 1.3.6.1.4.1.2356.11.1.98.2
lcsStatusLmcClearTransportStatus OBJECT-TYPE
    SYNTAX     DisplayString
    MAX-ACCESS read-write
    STATUS     current
    DESCRIPTION
            "-- empty --"
    ::= { lcsStatusLmc 2 }

-- {TABLE} 1.3.6.1.4.1.2356.11.1.98.3
lcsStatusLmcLogTableTable OBJECT-TYPE
    SYNTAX     SEQUENCE OF LcsStatusLmcLogTableEntry
    MAX-ACCESS not-accessible
    STATUS     current
    DESCRIPTION
            "-- empty --"
    ::= { lcsStatusLmc 3 }

-- {ROW} 1.3.6.1.4.1.2356.11.1.98.3.1
lcsStatusLmcLogTableEntry OBJECT-TYPE
    SYNTAX     LcsStatusLmcLogTableEntry
    MAX-ACCESS not-accessible
    STATUS     current
    DESCRIPTION
            ""
    INDEX {
            lcsStatusLmcLogTableEntryIndex
          }
    ::= { lcsStatusLmcLogTableTable 1 }

LcsStatusLmcLogTableEntry ::= SEQUENCE {
            lcsStatusLmcLogTableEntryIndex Integer32,
            lcsStatusLmcLogTableEntryTime DisplayString,
            lcsStatusLmcLogTableEntryService INTEGER,
            lcsStatusLmcLogTableEntryEvent DisplayString
    }

-- {COLUMN} 1.3.6.1.4.1.2356.11.1.98.3.1.1
lcsStatusLmcLogTableEntryIndex OBJECT-TYPE
    SYNTAX     Integer32 (0..2147483647)
    MAX-ACCESS read-only
    STATUS     current
    DESCRIPTION
            "-- empty --"
    ::= { lcsStatusLmcLogTableEntry 1 }

-- {COLUMN} 1.3.6.1.4.1.2356.11.1.98.3.1.2
lcsStatusLmcLogTableEntryTime OBJECT-TYPE
    SYNTAX     DisplayString (SIZE(0..19))
    MAX-ACCESS read-only
    STATUS     current
    DESCRIPTION
            "-- empty --"
    ::= { lcsStatusLmcLogTableEntry 2 }

-- {COLUMN} 1.3.6.1.4.1.2356.11.1.98.3.1.3
lcsStatusLmcLogTableEntryService OBJECT-TYPE
    SYNTAX     INTEGER {
                  eControlService (1),
                  eMonitorService (2),
                  ePairingService (3),
                  eTunnelService (4)
            }
    MAX-ACCESS read-only
    STATUS     current
    DESCRIPTION
            "-- empty --"
    ::= { lcsStatusLmcLogTableEntry 3 }

-- {COLUMN} 1.3.6.1.4.1.2356.11.1.98.3.1.4
lcsStatusLmcLogTableEntryEvent OBJECT-TYPE
    SYNTAX     DisplayString (SIZE(0..210))
    MAX-ACCESS read-only
    STATUS     current
    DESCRIPTION
            "-- empty --"
    ::= { lcsStatusLmcLogTableEntry 4 }

-- {SCALAR} 1.3.6.1.4.1.2356.11.1.98.4
lcsStatusLmcClearLogTable OBJECT-TYPE
    SYNTAX     DisplayString
    MAX-ACCESS read-write
    STATUS     current
    DESCRIPTION
            "-- empty --"
    ::= { lcsStatusLmc 4 }

-- {SCALAR} 1.3.6.1.4.1.2356.11.1.98.5
lcsStatusLmcCustomerDeviceId OBJECT-TYPE
    SYNTAX     DisplayString (SIZE(0..99))
    MAX-ACCESS read-only
    STATUS     current
    DESCRIPTION
            "-- empty --"
    ::= { lcsStatusLmc 5 }

-- {SCALAR} 1.3.6.1.4.1.2356.11.1.98.6
lcsStatusLmcRoundTripTime OBJECT-TYPE
    SYNTAX     Integer32 (0..2147483647)
    MAX-ACCESS read-only
    STATUS     current
    DESCRIPTION
            "-- empty --"
    ::= { lcsStatusLmc 6 }

-- {SCALAR} 1.3.6.1.4.1.2356.11.1.98.7
lcsStatusLmcManagementStatus OBJECT-TYPE
    SYNTAX     INTEGER {
                  eNotAuthenticatedWithLmcNoCloudManagement (0),
                  eAuthenticatedWithLmcCloudManagementInactive (1),
                  eDisabled (2),
                  eDisabledByWlc (3),
                  eOperating (4),
                  eHttpProtocolError (5),
                  eHttpConnectionError (6),
                  eDnsError (7),
                  eMemoryError (8),
                  eWaitingNotYet (9),
                  eRedirect (10),
                  eAuthenticationError (11),
                  eGenericError (12),
                  eCertificateStorageFailed (13),
                  eAuthenticatedWithLmcCloudManagementActive (14),
                  eCertificateGenerationAborted (15),
                  eNoActivationCode (16)
            }
    MAX-ACCESS read-only
    STATUS     current
    DESCRIPTION
            "-- empty --"
    ::= { lcsStatusLmc 7 }

-- {SCALAR} 1.3.6.1.4.1.2356.11.1.98.8
lcsStatusLmcShowCertificate OBJECT-TYPE
    SYNTAX     DisplayString
    MAX-ACCESS read-write
    STATUS     current
    DESCRIPTION
            "-- empty --"
    ::= { lcsStatusLmc 8 }

-- {SCALAR} 1.3.6.1.4.1.2356.11.1.98.9
lcsStatusLmcControlStatus OBJECT-TYPE
    SYNTAX     INTEGER {
                  eNotAuthenticatedWithLmcNoCloudManagement (0),
                  eAuthenticatedWithLmcCloudManagementInactive (1),
                  eDisabled (2),
                  eDisabledByWlc (3),
                  eOperating (4),
                  eHttpProtocolError (5),
                  eHttpConnectionError (6),
                  eDnsError (7),
                  eMemoryError (8),
                  eWaitingNotYet (9),
                  eRedirect (10),
                  eAuthenticationError (11),
                  eGenericError (12),
                  eCertificateStorageFailed (13),
                  eAuthenticatedWithLmcCloudManagementActive (14),
                  eCertificateGenerationAborted (15),
                  eNoActivationCode (16)
            }
    MAX-ACCESS read-only
    STATUS     current
    DESCRIPTION
            "-- empty --"
    ::= { lcsStatusLmc 9 }

-- {SCALAR} 1.3.6.1.4.1.2356.11.1.98.10
lcsStatusLmcMonitorStatus OBJECT-TYPE
    SYNTAX     INTEGER {
                  eNotAuthenticatedWithLmcNoCloudManagement (0),
                  eAuthenticatedWithLmcCloudManagementInactive (1),
                  eDisabled (2),
                  eDisabledByWlc (3),
                  eOperating (4),
                  eHttpProtocolError (5),
                  eHttpConnectionError (6),
                  eDnsError (7),
                  eMemoryError (8),
                  eWaitingNotYet (9),
                  eRedirect (10),
                  eAuthenticationError (11),
                  eGenericError (12),
                  eCertificateStorageFailed (13),
                  eAuthenticatedWithLmcCloudManagementActive (14),
                  eCertificateGenerationAborted (15),
                  eNoActivationCode (16)
            }
    MAX-ACCESS read-only
    STATUS     current
    DESCRIPTION
            "-- empty --"
    ::= { lcsStatusLmc 10 }

-- {TABLE} 1.3.6.1.4.1.2356.11.1.98.11
lcsStatusLmcConfigLogTable OBJECT-TYPE
    SYNTAX     SEQUENCE OF LcsStatusLmcConfigLogEntry
    MAX-ACCESS not-accessible
    STATUS     current
    DESCRIPTION
            "-- empty --"
    ::= { lcsStatusLmc 11 }

-- {ROW} 1.3.6.1.4.1.2356.11.1.98.11.1
lcsStatusLmcConfigLogEntry OBJECT-TYPE
    SYNTAX     LcsStatusLmcConfigLogEntry
    MAX-ACCESS not-accessible
    STATUS     current
    DESCRIPTION
            ""
    INDEX {
            lcsStatusLmcConfigLogEntryIndex
          }
    ::= { lcsStatusLmcConfigLogTable 1 }

LcsStatusLmcConfigLogEntry ::= SEQUENCE {
            lcsStatusLmcConfigLogEntryIndex Integer32,
            lcsStatusLmcConfigLogEntryTime DisplayString,
            lcsStatusLmcConfigLogEntrySuccessful INTEGER,
            lcsStatusLmcConfigLogEntryErrorType DisplayString,
            lcsStatusLmcConfigLogEntryComment DisplayString
    }

-- {COLUMN} 1.3.6.1.4.1.2356.11.1.98.11.1.1
lcsStatusLmcConfigLogEntryIndex OBJECT-TYPE
    SYNTAX     Integer32 (0..2147483647)
    MAX-ACCESS read-only
    STATUS     current
    DESCRIPTION
            "-- empty --"
    ::= { lcsStatusLmcConfigLogEntry 1 }

-- {COLUMN} 1.3.6.1.4.1.2356.11.1.98.11.1.2
lcsStatusLmcConfigLogEntryTime OBJECT-TYPE
    SYNTAX     DisplayString (SIZE(0..19))
    MAX-ACCESS read-only
    STATUS     current
    DESCRIPTION
            "-- empty --"
    ::= { lcsStatusLmcConfigLogEntry 2 }

-- {COLUMN} 1.3.6.1.4.1.2356.11.1.98.11.1.3
lcsStatusLmcConfigLogEntrySuccessful OBJECT-TYPE
    SYNTAX     INTEGER {
                  eNo (0),
                  eYes (1)
            }
    MAX-ACCESS read-only
    STATUS     current
    DESCRIPTION
            "-- empty --"
    ::= { lcsStatusLmcConfigLogEntry 3 }

-- {COLUMN} 1.3.6.1.4.1.2356.11.1.98.11.1.4
lcsStatusLmcConfigLogEntryErrorType OBJECT-TYPE
    SYNTAX     DisplayString (SIZE(0..20))
    MAX-ACCESS read-only
    STATUS     current
    DESCRIPTION
            "-- empty --"
    ::= { lcsStatusLmcConfigLogEntry 4 }

-- {COLUMN} 1.3.6.1.4.1.2356.11.1.98.11.1.5
lcsStatusLmcConfigLogEntryComment OBJECT-TYPE
    SYNTAX     DisplayString (SIZE(0..140))
    MAX-ACCESS read-only
    STATUS     current
    DESCRIPTION
            "-- empty --"
    ::= { lcsStatusLmcConfigLogEntry 5 }

-- {SCALAR} 1.3.6.1.4.1.2356.11.1.98.12
lcsStatusLmcZeroTouchSupport OBJECT-TYPE
    SYNTAX     INTEGER {
                  eNo (0),
                  eYes (1)
            }
    MAX-ACCESS read-only
    STATUS     current
    DESCRIPTION
            "-- empty --"
    ::= { lcsStatusLmc 12 }

-- {SCALAR} 1.3.6.1.4.1.2356.11.1.98.13
lcsStatusLmcPairingTokenPresent OBJECT-TYPE
    SYNTAX     INTEGER {
                  eNo (0),
                  eYes (1)
            }
    MAX-ACCESS read-only
    STATUS     current
    DESCRIPTION
            "-- empty --"
    ::= { lcsStatusLmc 13 }

-- {SCALAR} 1.3.6.1.4.1.2356.11.1.98.14
lcsStatusLmcLmcDomain OBJECT-TYPE
    SYNTAX     DisplayString (SIZE(0..254))
    MAX-ACCESS read-only
    STATUS     current
    DESCRIPTION
            "-- empty --"
    ::= { lcsStatusLmc 14 }

-- {SCALAR} 1.3.6.1.4.1.2356.11.1.98.15
lcsStatusLmcConfigModified OBJECT-TYPE
    SYNTAX     INTEGER {
                  eNo (0),
                  eYes (1)
            }
    MAX-ACCESS read-only
    STATUS     current
    DESCRIPTION
            "-- empty --"
    ::= { lcsStatusLmc 15 }

-- {SCALAR} 1.3.6.1.4.1.2356.11.1.98.16
lcsStatusLmcClearConfigLog OBJECT-TYPE
    SYNTAX     DisplayString
    MAX-ACCESS read-write
    STATUS     current
    DESCRIPTION
            "-- empty --"
    ::= { lcsStatusLmc 16 }

-- {SCALAR} 1.3.6.1.4.1.2356.11.1.98.17
lcsStatusLmcConfigNotifierActive OBJECT-TYPE
    SYNTAX     INTEGER {
                  eNo (0),
                  eYes (1)
            }
    MAX-ACCESS read-only
    STATUS     current
    DESCRIPTION
            "-- empty --"
    ::= { lcsStatusLmc 17 }

-- {TABLE} 1.3.6.1.4.1.2356.11.1.98.18
lcsStatusLmcDetectedModificationsTable OBJECT-TYPE
    SYNTAX     SEQUENCE OF LcsStatusLmcDetectedModificationsEntry
    MAX-ACCESS not-accessible
    STATUS     current
    DESCRIPTION
            "-- empty --"
    ::= { lcsStatusLmc 18 }

-- {ROW} 1.3.6.1.4.1.2356.11.1.98.18.1
lcsStatusLmcDetectedModificationsEntry OBJECT-TYPE
    SYNTAX     LcsStatusLmcDetectedModificationsEntry
    MAX-ACCESS not-accessible
    STATUS     current
    DESCRIPTION
            ""
    INDEX {
            lcsStatusLmcDetectedModificationsEntryIndex
          }
    ::= { lcsStatusLmcDetectedModificationsTable 1 }

LcsStatusLmcDetectedModificationsEntry ::= SEQUENCE {
            lcsStatusLmcDetectedModificationsEntryIndex Integer32,
            lcsStatusLmcDetectedModificationsEntryTime DisplayString,
            lcsStatusLmcDetectedModificationsEntryPath DisplayString,
            lcsStatusLmcDetectedModificationsEntryType INTEGER,
            lcsStatusLmcDetectedModificationsEntryKeys DisplayString,
            lcsStatusLmcDetectedModificationsEntryValue DisplayString
    }

-- {COLUMN} 1.3.6.1.4.1.2356.11.1.98.18.1.1
lcsStatusLmcDetectedModificationsEntryIndex OBJECT-TYPE
    SYNTAX     Integer32 (0..2147483647)
    MAX-ACCESS read-only
    STATUS     current
    DESCRIPTION
            "-- empty --"
    ::= { lcsStatusLmcDetectedModificationsEntry 1 }

-- {COLUMN} 1.3.6.1.4.1.2356.11.1.98.18.1.2
lcsStatusLmcDetectedModificationsEntryTime OBJECT-TYPE
    SYNTAX     DisplayString (SIZE(0..19))
    MAX-ACCESS read-only
    STATUS     current
    DESCRIPTION
            "-- empty --"
    ::= { lcsStatusLmcDetectedModificationsEntry 2 }

-- {COLUMN} 1.3.6.1.4.1.2356.11.1.98.18.1.3
lcsStatusLmcDetectedModificationsEntryPath OBJECT-TYPE
    SYNTAX     DisplayString (SIZE(0..100))
    MAX-ACCESS read-only
    STATUS     current
    DESCRIPTION
            "-- empty --"
    ::= { lcsStatusLmcDetectedModificationsEntry 3 }

-- {COLUMN} 1.3.6.1.4.1.2356.11.1.98.18.1.4
lcsStatusLmcDetectedModificationsEntryType OBJECT-TYPE
    SYNTAX     INTEGER {
                  eUpdateScalar (0),
                  eUpdateRow (1),
                  eDeleteRow (2)
            }
    MAX-ACCESS read-only
    STATUS     current
    DESCRIPTION
            "-- empty --"
    ::= { lcsStatusLmcDetectedModificationsEntry 4 }

-- {COLUMN} 1.3.6.1.4.1.2356.11.1.98.18.1.5
lcsStatusLmcDetectedModificationsEntryKeys OBJECT-TYPE
    SYNTAX     DisplayString (SIZE(0..254))
    MAX-ACCESS read-only
    STATUS     current
    DESCRIPTION
            "-- empty --"
    ::= { lcsStatusLmcDetectedModificationsEntry 5 }

-- {COLUMN} 1.3.6.1.4.1.2356.11.1.98.18.1.6
lcsStatusLmcDetectedModificationsEntryValue OBJECT-TYPE
    SYNTAX     DisplayString (SIZE(0..254))
    MAX-ACCESS read-only
    STATUS     current
    DESCRIPTION
            "-- empty --"
    ::= { lcsStatusLmcDetectedModificationsEntry 6 }

-- {SCALAR} 1.3.6.1.4.1.2356.11.1.98.19
lcsStatusLmcClearDetectedModifications OBJECT-TYPE
    SYNTAX     DisplayString
    MAX-ACCESS read-write
    STATUS     current
    DESCRIPTION
            "-- empty --"
    ::= { lcsStatusLmc 19 }

-- {SCALAR} 1.3.6.1.4.1.2356.11.1.98.20
lcsStatusLmcRolloutProjectId OBJECT-TYPE
    SYNTAX     DisplayString (SIZE(0..36))
    MAX-ACCESS read-only
    STATUS     current
    DESCRIPTION
            "-- empty --"
    ::= { lcsStatusLmc 20 }

-- {SCALAR} 1.3.6.1.4.1.2356.11.1.98.21
lcsStatusLmcRolloutLocationId OBJECT-TYPE
    SYNTAX     DisplayString (SIZE(0..36))
    MAX-ACCESS read-only
    STATUS     current
    DESCRIPTION
            "-- empty --"
    ::= { lcsStatusLmc 21 }

-- {SCALAR} 1.3.6.1.4.1.2356.11.1.98.22
lcsStatusLmcRolloutDeviceRole OBJECT-TYPE
    SYNTAX     DisplayString (SIZE(0..36))
    MAX-ACCESS read-only
    STATUS     current
    DESCRIPTION
            "-- empty --"
    ::= { lcsStatusLmc 22 }

-- {SCALAR} 1.3.6.1.4.1.2356.11.1.98.23
lcsStatusLmcActiveTerminalSessions OBJECT-TYPE
    SYNTAX     Integer32 (0..255)
    MAX-ACCESS read-only
    STATUS     current
    DESCRIPTION
            "-- empty --"
    ::= { lcsStatusLmc 23 }

-- {NODE} 1.3.6.1.4.1.2356.11.1.99
lcsStatusXdsl OBJECT IDENTIFIER ::= { lcsStatus 99 }

-- {NODE} 1.3.6.1.4.1.2356.11.1.99.1
lcsStatusXdslAdsl OBJECT IDENTIFIER ::= { lcsStatusXdsl 1 }

-- {SCALAR} 1.3.6.1.4.1.2356.11.1.99.1.1
lcsStatusXdslAdslLineState OBJECT-TYPE
    SYNTAX     INTEGER {
                  eUnknown (0),
                  eDown (1),
                  eIdle (2),
                  eHandshake (3),
                  eTraining (4),
                  eShowtime (5),
                  eShutdown (6)
            }
    MAX-ACCESS read-only
    STATUS     current
    DESCRIPTION
            "-- empty --"
    ::= { lcsStatusXdslAdsl 1 }

-- {SCALAR} 1.3.6.1.4.1.2356.11.1.99.1.2
lcsStatusXdslAdslLineType OBJECT-TYPE
    SYNTAX     DisplayString
    MAX-ACCESS read-only
    STATUS     current
    DESCRIPTION
            "-- empty --"
    ::= { lcsStatusXdslAdsl 2 }

-- {SCALAR} 1.3.6.1.4.1.2356.11.1.99.1.3
lcsStatusXdslAdslStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGVector (254),
                  eUnknown (255)
            }
    MAX-ACCESS read-only
    STATUS     current
    DESCRIPTION
            "-- empty --"
    ::= { lcsStatusXdslAdsl 3 }

-- {SCALAR} 1.3.6.1.4.1.2356.11.1.99.1.4
lcsStatusXdslAdslDataRateUpstreamKbps OBJECT-TYPE
    SYNTAX     Integer32 (0..2147483647)
    MAX-ACCESS read-only
    STATUS     current
    DESCRIPTION
            "-- empty --"
    ::= { lcsStatusXdslAdsl 4 }

-- {SCALAR} 1.3.6.1.4.1.2356.11.1.99.1.5
lcsStatusXdslAdslDataRateDownstreamKbps OBJECT-TYPE
    SYNTAX     Integer32 (0..2147483647)
    MAX-ACCESS read-only
    STATUS     current
    DESCRIPTION
            "-- empty --"
    ::= { lcsStatusXdslAdsl 5 }

-- {SCALAR} 1.3.6.1.4.1.2356.11.1.99.1.6
lcsStatusXdslAdslSnrDownstreamDb OBJECT-TYPE
    SYNTAX     DisplayString (SIZE(0..3))
    MAX-ACCESS read-only
    STATUS     current
    DESCRIPTION
            "-- empty --"
    ::= { lcsStatusXdslAdsl 6 }

-- {SCALAR} 1.3.6.1.4.1.2356.11.1.99.1.7
lcsStatusXdslAdslSnrUpstreamDb OBJECT-TYPE
    SYNTAX     DisplayString (SIZE(0..3))
    MAX-ACCESS read-only
    STATUS     current
    DESCRIPTION
            "-- empty --"
    ::= { lcsStatusXdslAdsl 7 }

-- {SCALAR} 1.3.6.1.4.1.2356.11.1.99.1.8
lcsStatusXdslAdslAttenuationDownstreamDb OBJECT-TYPE
    SYNTAX     DisplayString (SIZE(0..3))
    MAX-ACCESS read-only
    STATUS     current
    DESCRIPTION
            "-- empty --"
    ::= { lcsStatusXdslAdsl 8 }

-- {SCALAR} 1.3.6.1.4.1.2356.11.1.99.1.9
lcsStatusXdslAdslAttenuationUpstreamDb OBJECT-TYPE
    SYNTAX     DisplayString (SIZE(0..3))
    MAX-ACCESS read-only
    STATUS     current
    DESCRIPTION
            "-- empty --"
    ::= { lcsStatusXdslAdsl 9 }

-- {SCALAR} 1.3.6.1.4.1.2356.11.1.99.1.10
lcsStatusXdslAdslInterleaveUpstreamMs OBJECT-TYPE
    SYNTAX     DisplayString
    MAX-ACCESS read-only
    STATUS     current
    DESCRIPTION
            "-- empty --"
    ::= { lcsStatusXdslAdsl 10 }

-- {SCALAR} 1.3.6.1.4.1.2356.11.1.99.1.11
lcsStatusXdslAdslInterleaveDownstreamMs OBJECT-TYPE
    SYNTAX     DisplayString
    MAX-ACCESS read-only
    STATUS     current
    DESCRIPTION
            "-- empty --"
    ::= { lcsStatusXdslAdsl 11 }

-- {TABLE} 1.3.6.1.4.1.2356.11.1.99.1.12
lcsStatusXdslAdslConnectionHistoryTable OBJECT-TYPE
    SYNTAX     SEQUENCE OF LcsStatusXdslAdslConnectionHistoryEntry
    MAX-ACCESS not-accessible
    STATUS     current
    DESCRIPTION
            "-- empty --"
    ::= { lcsStatusXdslAdsl 12 }

-- {ROW} 1.3.6.1.4.1.2356.11.1.99.1.12.1
lcsStatusXdslAdslConnectionHistoryEntry OBJECT-TYPE
    SYNTAX     LcsStatusXdslAdslConnectionHistoryEntry
    MAX-ACCESS not-accessible
    STATUS     current
    DESCRIPTION
            ""
    INDEX {
            lcsStatusXdslAdslConnectionHistoryEntryIndex
          }
    ::= { lcsStatusXdslAdslConnectionHistoryTable 1 }

LcsStatusXdslAdslConnectionHistoryEntry ::= SEQUENCE {
            lcsStatusXdslAdslConnectionHistoryEntrySyncTime Gauge32,
            lcsStatusXdslAdslConnectionHistoryEntryStandard INTEGER,
            lcsStatusXdslAdslConnectionHistoryEntryDsDatarate Integer32,
            lcsStatusXdslAdslConnectionHistoryEntryUsDatarate Integer32,
            lcsStatusXdslAdslConnectionHistoryEntryDsAttenuation DisplayString,
            lcsStatusXdslAdslConnectionHistoryEntryDsSnr DisplayString,
            lcsStatusXdslAdslConnectionHistoryEntryDisconnectTime Gauge32,
            lcsStatusXdslAdslConnectionHistoryEntryIndex Integer32,
            lcsStatusXdslAdslConnectionHistoryEntryReason INTEGER,
            lcsStatusXdslAdslConnectionHistoryEntryUsAttenuation DisplayString,
            lcsStatusXdslAdslConnectionHistoryEntryUsSnr DisplayString,
            lcsStatusXdslAdslConnectionHistoryEntryLinecode DisplayString
    }

-- {COLUMN} 1.3.6.1.4.1.2356.11.1.99.1.12.1.1
lcsStatusXdslAdslConnectionHistoryEntrySyncTime OBJECT-TYPE
    SYNTAX     Gauge32
    MAX-ACCESS read-only
    STATUS     current
    DESCRIPTION
            "-- empty --"
    ::= { lcsStatusXdslAdslConnectionHistoryEntry 1 }

-- {COLUMN} 1.3.6.1.4.1.2356.11.1.99.1.12.1.2
lcsStatusXdslAdslConnectionHistoryEntryStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGVector (254),
                  eUnknown (255)
            }
    MAX-ACCESS read-only
    STATUS     current
    DESCRIPTION
            "-- empty --"
    ::= { lcsStatusXdslAdslConnectionHistoryEntry 2 }

-- {COLUMN} 1.3.6.1.4.1.2356.11.1.99.1.12.1.3
lcsStatusXdslAdslConnectionHistoryEntryDsDatarate OBJECT-TYPE
    SYNTAX     Integer32 (0..2147483647)
    MAX-ACCESS read-only
    STATUS     current
    DESCRIPTION
            "-- empty --"
    ::= { lcsStatusXdslAdslConnectionHistoryEntry 3 }

-- {COLUMN} 1.3.6.1.4.1.2356.11.1.99.1.12.1.4
lcsStatusXdslAdslConnectionHistoryEntryUsDatarate OBJECT-TYPE
    SYNTAX     Integer32 (0..2147483647)
    MAX-ACCESS read-only
    STATUS     current
    DESCRIPTION
            "-- empty --"
    ::= { lcsStatusXdslAdslConnectionHistoryEntry 4 }

-- {COLUMN} 1.3.6.1.4.1.2356.11.1.99.1.12.1.5
lcsStatusXdslAdslConnectionHistoryEntryDsAttenuation OBJECT-TYPE
    SYNTAX     DisplayString (SIZE(0..1))
    MAX-ACCESS read-only
    STATUS     current
    DESCRIPTION
            "-- empty --"
    ::= { lcsStatusXdslAdslConnectionHistoryEntry 5 }

-- {COLUMN} 1.3.6.1.4.1.2356.11.1.99.1.12.1.6
lcsStatusXdslAdslConnectionHistoryEntryDsSnr OBJECT-TYPE
    SYNTAX     DisplayString (SIZE(0..1))
    MAX-ACCESS read-only
    STATUS     current
    DESCRIPTION
            "-- empty --"
    ::= { lcsStatusXdslAdslConnectionHistoryEntry 6 }

-- {COLUMN} 1.3.6.1.4.1.2356.11.1.99.1.12.1.7
lcsStatusXdslAdslConnectionHistoryEntryDisconnectTime OBJECT-TYPE
    SYNTAX     Gauge32
    MAX-ACCESS read-only
    STATUS     current
    DESCRIPTION
            "-- empty --"
    ::= { lcsStatusXdslAdslConnectionHistoryEntry 7 }

-- {COLUMN} 1.3.6.1.4.1.2356.11.1.99.1.12.1.8
lcsStatusXdslAdslConnectionHistoryEntryIndex OBJECT-TYPE
    SYNTAX     Integer32 (0..2147483647)
    MAX-ACCESS read-only
    STATUS     current
    DESCRIPTION
            "-- empty --"
    ::= { lcsStatusXdslAdslConnectionHistoryEntry 8 }

-- {COLUMN} 1.3.6.1.4.1.2356.11.1.99.1.12.1.9
lcsStatusXdslAdslConnectionHistoryEntryReason OBJECT-TYPE
    SYNTAX     INTEGER {
                  eModemReboot (1),
                  eRetrain (2),
                  eSilence (3),
                  eLineError (4),
                  eProtocol (5),
                  eLineType (6),
                  eAutomode (7),
                  eTimeout (8),
                  eVcParameters (13)
            }
    MAX-ACCESS read-only
    STATUS     current
    DESCRIPTION
            "-- empty --"
    ::= { lcsStatusXdslAdslConnectionHistoryEntry 9 }

-- {COLUMN} 1.3.6.1.4.1.2356.11.1.99.1.12.1.10
lcsStatusXdslAdslConnectionHistoryEntryUsAttenuation OBJECT-TYPE
    SYNTAX     DisplayString (SIZE(0..1))
    MAX-ACCESS read-only
    STATUS     current
    DESCRIPTION
            "-- empty --"
    ::= { lcsStatusXdslAdslConnectionHistoryEntry 10 }

-- {COLUMN} 1.3.6.1.4.1.2356.11.1.99.1.12.1.11
lcsStatusXdslAdslConnectionHistoryEntryUsSnr OBJECT-TYPE
    SYNTAX     DisplayString (SIZE(0..1))
    MAX-ACCESS read-only
    STATUS     current
    DESCRIPTION
            "-- empty --"
    ::= { lcsStatusXdslAdslConnectionHistoryEntry 11 }

-- {COLUMN} 1.3.6.1.4.1.2356.11.1.99.1.12.1.12
lcsStatusXdslAdslConnectionHistoryEntryLinecode OBJECT-TYPE
    SYNTAX     DisplayString (SIZE(0..1))
    MAX-ACCESS read-only
    STATUS     current
    DESCRIPTION
            "-- empty --"
    ::= { lcsStatusXdslAdslConnectionHistoryEntry 12 }

-- {SCALAR} 1.3.6.1.4.1.2356.11.1.99.1.13
lcsStatusXdslAdslRetrain OBJECT-TYPE
    SYNTAX     DisplayString
    MAX-ACCESS read-write
    STATUS     current
    DESCRIPTION
            "-- empty --"
    ::= { lcsStatusXdslAdsl 13 }

-- {SCALAR} 1.3.6.1.4.1.2356.11.1.99.1.14
lcsStatusXdslAdslDslamChipsetManufacturer OBJECT-TYPE
    SYNTAX     DisplayString (SIZE(0..63))
    MAX-ACCESS read-only
    STATUS     current
    DESCRIPTION
            "-- empty --"
    ::= { lcsStatusXdslAdsl 14 }

-- {SCALAR} 1.3.6.1.4.1.2356.11.1.99.1.23
lcsStatusXdslAdslModemType OBJECT-TYPE
    SYNTAX     DisplayString
    MAX-ACCESS read-only
    STATUS     current
    DESCRIPTION
            "-- empty --"
    ::= { lcsStatusXdslAdsl 23 }

-- {NODE} 1.3.6.1.4.1.2356.11.1.99.1.25
lcsStatusXdslAdslAdvanced OBJECT IDENTIFIER ::= { lcsStatusXdslAdsl 25 }

-- {SCALAR} 1.3.6.1.4.1.2356.11.1.99.1.25.1
lcsStatusXdslAdslAdvancedLineState OBJECT-TYPE
    SYNTAX     INTEGER {
                  eUnknown (0),
                  eDown (1),
                  eIdle (2),
                  eHandshake (3),
                  eTraining (4),
                  eShowtime (5),
                  eShutdown (6)
            }
    MAX-ACCESS read-only
    STATUS     current
    DESCRIPTION
            "-- empty --"
    ::= { lcsStatusXdslAdslAdvanced 1 }

-- {SCALAR} 1.3.6.1.4.1.2356.11.1.99.1.25.2
lcsStatusXdslAdslAdvancedStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGVector (254),
                  eUnknown (255)
            }
    MAX-ACCESS read-only
    STATUS     current
    DESCRIPTION
            "-- empty --"
    ::= { lcsStatusXdslAdslAdvanced 2 }

-- {SCALAR} 1.3.6.1.4.1.2356.11.1.99.1.25.3
lcsStatusXdslAdslAdvancedDsDataRateKbps OBJECT-TYPE
    SYNTAX     Integer32 (0..2147483647)
    MAX-ACCESS read-only
    STATUS     current
    DESCRIPTION
            "-- empty --"
    ::= { lcsStatusXdslAdslAdvanced 3 }

-- {SCALAR} 1.3.6.1.4.1.2356.11.1.99.1.25.4
lcsStatusXdslAdslAdvancedDsSnrMarginDb OBJECT-TYPE
    SYNTAX     DisplayString (SIZE(0..3))
    MAX-ACCESS read-only
    STATUS     current
    DESCRIPTION
            "-- empty --"
    ::= { lcsStatusXdslAdslAdvanced 4 }

-- {SCALAR} 1.3.6.1.4.1.2356.11.1.99.1.25.5
lcsStatusXdslAdslAdvancedDsLineAttenuationDb OBJECT-TYPE
    SYNTAX     DisplayString (SIZE(0..3))
    MAX-ACCESS read-only
    STATUS     current
    DESCRIPTION
            "-- empty --"
    ::= { lcsStatusXdslAdslAdvanced 5 }

-- {SCALAR} 1.3.6.1.4.1.2356.11.1.99.1.25.6
lcsStatusXdslAdslAdvancedDsInterleaveMs OBJECT-TYPE
    SYNTAX     DisplayString
    MAX-ACCESS read-only
    STATUS     current
    DESCRIPTION
            "-- empty --"
    ::= { lcsStatusXdslAdslAdvanced 6 }

-- {TABLE} 1.3.6.1.4.1.2356.11.1.99.1.25.13
lcsStatusXdslAdslAdvancedDsBitLoadingTable OBJECT-TYPE
    SYNTAX     SEQUENCE OF LcsStatusXdslAdslAdvancedDsBitLoadingEntry
    MAX-ACCESS not-accessible
    STATUS     current
    DESCRIPTION
            "-- empty --"
    ::= { lcsStatusXdslAdslAdvanced 13 }

-- {ROW} 1.3.6.1.4.1.2356.11.1.99.1.25.13.1
lcsStatusXdslAdslAdvancedDsBitLoadingEntry OBJECT-TYPE
    SYNTAX     LcsStatusXdslAdslAdvancedDsBitLoadingEntry
    MAX-ACCESS not-accessible
    STATUS     current
    DESCRIPTION
            ""
    INDEX {
            lcsStatusXdslAdslAdvancedDsBitLoadingEntryBinNumber
          }
    ::= { lcsStatusXdslAdslAdvancedDsBitLoadingTable 1 }

LcsStatusXdslAdslAdvancedDsBitLoadingEntry ::= SEQUENCE {
            lcsStatusXdslAdslAdvancedDsBitLoadingEntryBinNumber DisplayString,
            lcsStatusXdslAdslAdvancedDsBitLoadingEntryX0 Integer32,
            lcsStatusXdslAdslAdvancedDsBitLoadingEntryX1 Integer32,
            lcsStatusXdslAdslAdvancedDsBitLoadingEntryX2 Integer32,
            lcsStatusXdslAdslAdvancedDsBitLoadingEntryX3 Integer32,
            lcsStatusXdslAdslAdvancedDsBitLoadingEntryX4 Integer32,
            lcsStatusXdslAdslAdvancedDsBitLoadingEntryX5 Integer32,
            lcsStatusXdslAdslAdvancedDsBitLoadingEntryX6 Integer32,
            lcsStatusXdslAdslAdvancedDsBitLoadingEntryX7 Integer32,
            lcsStatusXdslAdslAdvancedDsBitLoadingEntryX8 Integer32,
            lcsStatusXdslAdslAdvancedDsBitLoadingEntryX9 Integer32,
            lcsStatusXdslAdslAdvancedDsBitLoadingEntryGraph DisplayString
    }

-- {COLUMN} 1.3.6.1.4.1.2356.11.1.99.1.25.13.1.1
lcsStatusXdslAdslAdvancedDsBitLoadingEntryBinNumber OBJECT-TYPE
    SYNTAX     DisplayString (SIZE(0..255))
    MAX-ACCESS read-only
    STATUS     current
    DESCRIPTION
            "-- empty --"
    ::= { lcsStatusXdslAdslAdvancedDsBitLoadingEntry 1 }

-- {COLUMN} 1.3.6.1.4.1.2356.11.1.99.1.25.13.1.2
lcsStatusXdslAdslAdvancedDsBitLoadingEntryX0 OBJECT-TYPE
    SYNTAX     Integer32 (0..2147483647)
    MAX-ACCESS read-only
    STATUS     current
    DESCRIPTION
            "-- empty --"
    ::= { lcsStatusXdslAdslAdvancedDsBitLoadingEntry 2 }

-- {COLUMN} 1.3.6.1.4.1.2356.11.1.99.1.25.13.1.3
lcsStatusXdslAdslAdvancedDsBitLoadingEntryX1 OBJECT-TYPE
    SYNTAX     Integer32 (0..2147483647)
    MAX-ACCESS read-only
    STATUS     current
    DESCRIPTION
            "-- empty --"
    ::= { lcsStatusXdslAdslAdvancedDsBitLoadingEntry 3 }

-- {COLUMN} 1.3.6.1.4.1.2356.11.1.99.1.25.13.1.4
lcsStatusXdslAdslAdvancedDsBitLoadingEntryX2 OBJECT-TYPE
    SYNTAX     Integer32 (0..2147483647)
    MAX-ACCESS read-only
    STATUS     current
    DESCRIPTION
            "-- empty --"
    ::= { lcsStatusXdslAdslAdvancedDsBitLoadingEntry 4 }

-- {COLUMN} 1.3.6.1.4.1.2356.11.1.99.1.25.13.1.5
lcsStatusXdslAdslAdvancedDsBitLoadingEntryX3 OBJECT-TYPE
    SYNTAX     Integer32 (0..2147483647)
    MAX-ACCESS read-only
    STATUS     current
    DESCRIPTION
            "-- empty --"
    ::= { lcsStatusXdslAdslAdvancedDsBitLoadingEntry 5 }

-- {COLUMN} 1.3.6.1.4.1.2356.11.1.99.1.25.13.1.6
lcsStatusXdslAdslAdvancedDsBitLoadingEntryX4 OBJECT-TYPE
    SYNTAX     Integer32 (0..2147483647)
    MAX-ACCESS read-only
    STATUS     current
    DESCRIPTION
            "-- empty --"
    ::= { lcsStatusXdslAdslAdvancedDsBitLoadingEntry 6 }

-- {COLUMN} 1.3.6.1.4.1.2356.11.1.99.1.25.13.1.7
lcsStatusXdslAdslAdvancedDsBitLoadingEntryX5 OBJECT-TYPE
    SYNTAX     Integer32 (0..2147483647)
    MAX-ACCESS read-only
    STATUS     current
    DESCRIPTION
            "-- empty --"
    ::= { lcsStatusXdslAdslAdvancedDsBitLoadingEntry 7 }

-- {COLUMN} 1.3.6.1.4.1.2356.11.1.99.1.25.13.1.8
lcsStatusXdslAdslAdvancedDsBitLoadingEntryX6 OBJECT-TYPE
    SYNTAX     Integer32 (0..2147483647)
    MAX-ACCESS read-only
    STATUS     current
    DESCRIPTION
            "-- empty --"
    ::= { lcsStatusXdslAdslAdvancedDsBitLoadingEntry 8 }

-- {COLUMN} 1.3.6.1.4.1.2356.11.1.99.1.25.13.1.9
lcsStatusXdslAdslAdvancedDsBitLoadingEntryX7 OBJECT-TYPE
    SYNTAX     Integer32 (0..2147483647)
    MAX-ACCESS read-only
    STATUS     current
    DESCRIPTION
            "-- empty --"
    ::= { lcsStatusXdslAdslAdvancedDsBitLoadingEntry 9 }

-- {COLUMN} 1.3.6.1.4.1.2356.11.1.99.1.25.13.1.10
lcsStatusXdslAdslAdvancedDsBitLoadingEntryX8 OBJECT-TYPE
    SYNTAX     Integer32 (0..2147483647)
    MAX-ACCESS read-only
    STATUS     current
    DESCRIPTION
            "-- empty --"
    ::= { lcsStatusXdslAdslAdvancedDsBitLoadingEntry 10 }

-- {COLUMN} 1.3.6.1.4.1.2356.11.1.99.1.25.13.1.11
lcsStatusXdslAdslAdvancedDsBitLoadingEntryX9 OBJECT-TYPE
    SYNTAX     Integer32 (0..2147483647)
    MAX-ACCESS read-only
    STATUS     current
    DESCRIPTION
            "-- empty --"
    ::= { lcsStatusXdslAdslAdvancedDsBitLoadingEntry 11 }

-- {COLUMN} 1.3.6.1.4.1.2356.11.1.99.1.25.13.1.12
lcsStatusXdslAdslAdvancedDsBitLoadingEntryGraph OBJECT-TYPE
    SYNTAX     DisplayString (SIZE(0..255))
    MAX-ACCESS read-only
    STATUS     current
    DESCRIPTION
            "-- empty --"
    ::= { lcsStatusXdslAdslAdvancedDsBitLoadingEntry 12 }

-- {SCALAR} 1.3.6.1.4.1.2356.11.1.99.1.25.15
lcsStatusXdslAdslAdvancedUsDataRateKbps OBJECT-TYPE
    SYNTAX     Integer32 (0..2147483647)
    MAX-ACCESS read-only
    STATUS     current
    DESCRIPTION
            "-- empty --"
    ::= { lcsStatusXdslAdslAdvanced 15 }

-- {SCALAR} 1.3.6.1.4.1.2356.11.1.99.1.25.16
lcsStatusXdslAdslAdvancedUsSnrMarginDb OBJECT-TYPE
    SYNTAX     DisplayString (SIZE(0..3))
    MAX-ACCESS read-only
    STATUS     current
    DESCRIPTION
            "-- empty --"
    ::= { lcsStatusXdslAdslAdvanced 16 }

-- {SCALAR} 1.3.6.1.4.1.2356.11.1.99.1.25.17
lcsStatusXdslAdslAdvancedUsLineAttenuationDb OBJECT-TYPE
    SYNTAX     DisplayString (SIZE(0..3))
    MAX-ACCESS read-only
    STATUS     current
    DESCRIPTION
            "-- empty --"
    ::= { lcsStatusXdslAdslAdvanced 17 }

-- {SCALAR} 1.3.6.1.4.1.2356.11.1.99.1.25.18
lcsStatusXdslAdslAdvancedUsInterleaveMs OBJECT-TYPE
    SYNTAX     DisplayString
    MAX-ACCESS read-only
    STATUS     current
    DESCRIPTION
            "-- empty --"
    ::= { lcsStatusXdslAdslAdvanced 18 }

-- {TABLE} 1.3.6.1.4.1.2356.11.1.99.1.25.25
lcsStatusXdslAdslAdvancedUsBitLoadingTable OBJECT-TYPE
    SYNTAX     SEQUENCE OF LcsStatusXdslAdslAdvancedUsBitLoadingEntry
    MAX-ACCESS not-accessible
    STATUS     current
    DESCRIPTION
            "-- empty --"
    ::= { lcsStatusXdslAdslAdvanced 25 }

-- {ROW} 1.3.6.1.4.1.2356.11.1.99.1.25.25.1
lcsStatusXdslAdslAdvancedUsBitLoadingEntry OBJECT-TYPE
    SYNTAX     LcsStatusXdslAdslAdvancedUsBitLoadingEntry
    MAX-ACCESS not-accessible
    STATUS     current
    DESCRIPTION
            ""
    INDEX {
            lcsStatusXdslAdslAdvancedUsBitLoadingEntryBinNumber
          }
    ::= { lcsStatusXdslAdslAdvancedUsBitLoadingTable 1 }

LcsStatusXdslAdslAdvancedUsBitLoadingEntry ::= SEQUENCE {
            lcsStatusXdslAdslAdvancedUsBitLoadingEntryBinNumber DisplayString,
            lcsStatusXdslAdslAdvancedUsBitLoadingEntryX0 Integer32,
            lcsStatusXdslAdslAdvancedUsBitLoadingEntryX1 Integer32,
            lcsStatusXdslAdslAdvancedUsBitLoadingEntryX2 Integer32,
            lcsStatusXdslAdslAdvancedUsBitLoadingEntryX3 Integer32,
            lcsStatusXdslAdslAdvancedUsBitLoadingEntryX4 Integer32,
            lcsStatusXdslAdslAdvancedUsBitLoadingEntryX5 Integer32,
            lcsStatusXdslAdslAdvancedUsBitLoadingEntryX6 Integer32,
            lcsStatusXdslAdslAdvancedUsBitLoadingEntryX7 Integer32,
            lcsStatusXdslAdslAdvancedUsBitLoadingEntryX8 Integer32,
            lcsStatusXdslAdslAdvancedUsBitLoadingEntryX9 Integer32,
            lcsStatusXdslAdslAdvancedUsBitLoadingEntryGraph DisplayString
    }

-- {COLUMN} 1.3.6.1.4.1.2356.11.1.99.1.25.25.1.1
lcsStatusXdslAdslAdvancedUsBitLoadingEntryBinNumber OBJECT-TYPE
    SYNTAX     DisplayString (SIZE(0..255))
    MAX-ACCESS read-only
    STATUS     current
    DESCRIPTION
            "-- empty --"
    ::= { lcsStatusXdslAdslAdvancedUsBitLoadingEntry 1 }

-- {COLUMN} 1.3.6.1.4.1.2356.11.1.99.1.25.25.1.2
lcsStatusXdslAdslAdvancedUsBitLoadingEntryX0 OBJECT-TYPE
    SYNTAX     Integer32 (0..2147483647)
    MAX-ACCESS read-only
    STATUS     current
    DESCRIPTION
            "-- empty --"
    ::= { lcsStatusXdslAdslAdvancedUsBitLoadingEntry 2 }

-- {COLUMN} 1.3.6.1.4.1.2356.11.1.99.1.25.25.1.3
lcsStatusXdslAdslAdvancedUsBitLoadingEntryX1 OBJECT-TYPE
    SYNTAX     Integer32 (0..2147483647)
    MAX-ACCESS read-only
    STATUS     current
    DESCRIPTION
            "-- empty --"
    ::= { lcsStatusXdslAdslAdvancedUsBitLoadingEntry 3 }

-- {COLUMN} 1.3.6.1.4.1.2356.11.1.99.1.25.25.1.4
lcsStatusXdslAdslAdvancedUsBitLoadingEntryX2 OBJECT-TYPE
    SYNTAX     Integer32 (0..2147483647)
    MAX-ACCESS read-only
    STATUS     current
    DESCRIPTION
            "-- empty --"
    ::= { lcsStatusXdslAdslAdvancedUsBitLoadingEntry 4 }

-- {COLUMN} 1.3.6.1.4.1.2356.11.1.99.1.25.25.1.5
lcsStatusXdslAdslAdvancedUsBitLoadingEntryX3 OBJECT-TYPE
    SYNTAX     Integer32 (0..2147483647)
    MAX-ACCESS read-only
    STATUS     current
    DESCRIPTION
            "-- empty --"
    ::= { lcsStatusXdslAdslAdvancedUsBitLoadingEntry 5 }

-- {COLUMN} 1.3.6.1.4.1.2356.11.1.99.1.25.25.1.6
lcsStatusXdslAdslAdvancedUsBitLoadingEntryX4 OBJECT-TYPE
    SYNTAX     Integer32 (0..2147483647)
    MAX-ACCESS read-only
    STATUS     current
    DESCRIPTION
            "-- empty --"
    ::= { lcsStatusXdslAdslAdvancedUsBitLoadingEntry 6 }

-- {COLUMN} 1.3.6.1.4.1.2356.11.1.99.1.25.25.1.7
lcsStatusXdslAdslAdvancedUsBitLoadingEntryX5 OBJECT-TYPE
    SYNTAX     Integer32 (0..2147483647)
    MAX-ACCESS read-only
    STATUS     current
    DESCRIPTION
            "-- empty --"
    ::= { lcsStatusXdslAdslAdvancedUsBitLoadingEntry 7 }

-- {COLUMN} 1.3.6.1.4.1.2356.11.1.99.1.25.25.1.8
lcsStatusXdslAdslAdvancedUsBitLoadingEntryX6 OBJECT-TYPE
    SYNTAX     Integer32 (0..2147483647)
    MAX-ACCESS read-only
    STATUS     current
    DESCRIPTION
            "-- empty --"
    ::= { lcsStatusXdslAdslAdvancedUsBitLoadingEntry 8 }

-- {COLUMN} 1.3.6.1.4.1.2356.11.1.99.1.25.25.1.9
lcsStatusXdslAdslAdvancedUsBitLoadingEntryX7 OBJECT-TYPE
    SYNTAX     Integer32 (0..2147483647)
    MAX-ACCESS read-only
    STATUS     current
    DESCRIPTION
            "-- empty --"
    ::= { lcsStatusXdslAdslAdvancedUsBitLoadingEntry 9 }

-- {COLUMN} 1.3.6.1.4.1.2356.11.1.99.1.25.25.1.10
lcsStatusXdslAdslAdvancedUsBitLoadingEntryX8 OBJECT-TYPE
    SYNTAX     Integer32 (0..2147483647)
    MAX-ACCESS read-only
    STATUS     current
    DESCRIPTION
            "-- empty --"
    ::= { lcsStatusXdslAdslAdvancedUsBitLoadingEntry 10 }

-- {COLUMN} 1.3.6.1.4.1.2356.11.1.99.1.25.25.1.11
lcsStatusXdslAdslAdvancedUsBitLoadingEntryX9 OBJECT-TYPE
    SYNTAX     Integer32 (0..2147483647)
    MAX-ACCESS read-only
    STATUS     current
    DESCRIPTION
            "-- empty --"
    ::= { lcsStatusXdslAdslAdvancedUsBitLoadingEntry 11 }

-- {COLUMN} 1.3.6.1.4.1.2356.11.1.99.1.25.25.1.12
lcsStatusXdslAdslAdvancedUsBitLoadingEntryGraph OBJECT-TYPE
    SYNTAX     DisplayString (SIZE(0..255))
    MAX-ACCESS read-only
    STATUS     current
    DESCRIPTION
            "-- empty --"
    ::= { lcsStatusXdslAdslAdvancedUsBitLoadingEntry 12 }

-- {SCALAR} 1.3.6.1.4.1.2356.11.1.99.1.25.26
lcsStatusXdslAdslAdvancedRetrain OBJECT-TYPE
    SYNTAX     DisplayString
    MAX-ACCESS read-write
    STATUS     current
    DESCRIPTION
            "-- empty --"
    ::= { lcsStatusXdslAdslAdvanced 26 }

-- {SCALAR} 1.3.6.1.4.1.2356.11.1.99.1.25.41
lcsStatusXdslAdslAdvancedDslamManufacturer OBJECT-TYPE
    SYNTAX     DisplayString (SIZE(0..63))
    MAX-ACCESS read-only
    STATUS     current
    DESCRIPTION
            "-- empty --"
    ::= { lcsStatusXdslAdslAdvanced 41 }

-- {SCALAR} 1.3.6.1.4.1.2356.11.1.99.1.25.42
lcsStatusXdslAdslAdvancedDslamVersion OBJECT-TYPE
    SYNTAX     DisplayString (SIZE(0..34))
    MAX-ACCESS read-only
    STATUS     current
    DESCRIPTION
            "-- empty --"
    ::= { lcsStatusXdslAdslAdvanced 42 }

-- {SCALAR} 1.3.6.1.4.1.2356.11.1.99.1.25.43
lcsStatusXdslAdslAdvancedDslamSerialNumber OBJECT-TYPE
    SYNTAX     DisplayString (SIZE(0..66))
    MAX-ACCESS read-only
    STATUS     current
    DESCRIPTION
            "-- empty --"
    ::= { lcsStatusXdslAdslAdvanced 43 }

-- {SCALAR} 1.3.6.1.4.1.2356.11.1.99.1.25.44
lcsStatusXdslAdslAdvancedDslamChipsetManufacturer OBJECT-TYPE
    SYNTAX     DisplayString (SIZE(0..63))
    MAX-ACCESS read-only
    STATUS     current
    DESCRIPTION
            "-- empty --"
    ::= { lcsStatusXdslAdslAdvanced 44 }

-- {SCALAR} 1.3.6.1.4.1.2356.11.1.99.1.25.47
lcsStatusXdslAdslAdvancedDslamChipsetManufacturerDump OBJECT-TYPE
    SYNTAX     OCTET STRING
    MAX-ACCESS read-only
    STATUS     current
    DESCRIPTION
            "-- empty --"
    ::= { lcsStatusXdslAdslAdvanced 47 }

-- {SCALAR} 1.3.6.1.4.1.2356.11.1.99.1.25.48
lcsStatusXdslAdslAdvancedDslamManufacturerDump OBJECT-TYPE
    SYNTAX     OCTET STRING
    MAX-ACCESS read-only
    STATUS     current
    DESCRIPTION
            "-- empty --"
    ::= { lcsStatusXdslAdslAdvanced 48 }

-- {SCALAR} 1.3.6.1.4.1.2356.11.1.99.1.25.53
lcsStatusXdslAdslAdvancedConnectionCount OBJECT-TYPE
    SYNTAX     Integer32 (0..2147483647)
    MAX-ACCESS read-only
    STATUS     current
    DESCRIPTION
            "-- empty --"
    ::= { lcsStatusXdslAdslAdvanced 53 }

-- {SCALAR} 1.3.6.1.4.1.2356.11.1.99.1.25.54
lcsStatusXdslAdslAdvancedConnectionDuration OBJECT-TYPE
    SYNTAX     Gauge32
    MAX-ACCESS read-only
    STATUS     current
    DESCRIPTION
            "-- empty --"
    ::= { lcsStatusXdslAdslAdvanced 54 }

-- {SCALAR} 1.3.6.1.4.1.2356.11.1.99.1.25.100
lcsStatusXdslAdslAdvancedDsAttainableDataRateKbps OBJECT-TYPE
    SYNTAX     Integer32 (0..2147483647)
    MAX-ACCESS read-only
    STATUS     current
    DESCRIPTION
            "-- empty --"
    ::= { lcsStatusXdslAdslAdvanced 100 }

-- {SCALAR} 1.3.6.1.4.1.2356.11.1.99.1.25.101
lcsStatusXdslAdslAdvancedDsInpSymbols OBJECT-TYPE
    SYNTAX     DisplayString (SIZE(0..3))
    MAX-ACCESS read-only
    STATUS     current
    DESCRIPTION
            "-- empty --"
    ::= { lcsStatusXdslAdslAdvanced 101 }

-- {SCALAR} 1.3.6.1.4.1.2356.11.1.99.1.25.102
lcsStatusXdslAdslAdvancedDsCrcErrors OBJECT-TYPE
    SYNTAX     Integer32 (0..2147483647)
    MAX-ACCESS read-only
    STATUS     current
    DESCRIPTION
            "-- empty --"
    ::= { lcsStatusXdslAdslAdvanced 102 }

-- {SCALAR} 1.3.6.1.4.1.2356.11.1.99.1.25.103
lcsStatusXdslAdslAdvancedDsFecErrors OBJECT-TYPE
    SYNTAX     Integer32 (0..2147483647)
    MAX-ACCESS read-only
    STATUS     current
    DESCRIPTION
            "-- empty --"
    ::= { lcsStatusXdslAdslAdvanced 103 }

-- {SCALAR} 1.3.6.1.4.1.2356.11.1.99.1.25.104
lcsStatusXdslAdslAdvancedDsAtmHecErrors OBJECT-TYPE
    SYNTAX     Integer32 (0..2147483647)
    MAX-ACCESS read-only
    STATUS     current
    DESCRIPTION
            "-- empty --"
    ::= { lcsStatusXdslAdslAdvanced 104 }

-- {SCALAR} 1.3.6.1.4.1.2356.11.1.99.1.25.105
lcsStatusXdslAdslAdvancedDsDataPathCrcpErrors OBJECT-TYPE
    SYNTAX     Integer32 (0..2147483647)
    MAX-ACCESS read-only
    STATUS     current
    DESCRIPTION
            "-- empty --"
    ::= { lcsStatusXdslAdslAdvanced 105 }

-- {SCALAR} 1.3.6.1.4.1.2356.11.1.99.1.25.106
lcsStatusXdslAdslAdvancedDsDataPathCrcnpErrors OBJECT-TYPE
    SYNTAX     Integer32 (0..2147483647)
    MAX-ACCESS read-only
    STATUS     current
    DESCRIPTION
            "-- empty --"
    ::= { lcsStatusXdslAdslAdvanced 106 }

-- {SCALAR} 1.3.6.1.4.1.2356.11.1.99.1.25.107
lcsStatusXdslAdslAdvancedDsDataPathCvpErrors OBJECT-TYPE
    SYNTAX     Integer32 (0..2147483647)
    MAX-ACCESS read-only
    STATUS     current
    DESCRIPTION
            "-- empty --"
    ::= { lcsStatusXdslAdslAdvanced 107 }

-- {SCALAR} 1.3.6.1.4.1.2356.11.1.99.1.25.108
lcsStatusXdslAdslAdvancedDsDataPathCvnpErrors OBJECT-TYPE
    SYNTAX     Integer32 (0..2147483647)
    MAX-ACCESS read-only
    STATUS     current
    DESCRIPTION
            "-- empty --"
    ::= { lcsStatusXdslAdslAdvanced 108 }

-- {SCALAR} 1.3.6.1.4.1.2356.11.1.99.1.25.109
lcsStatusXdslAdslAdvancedDsAtmIdleBitErrors OBJECT-TYPE
    SYNTAX     Integer32 (0..2147483647)
    MAX-ACCESS read-only
    STATUS     current
    DESCRIPTION
            "-- empty --"
    ::= { lcsStatusXdslAdslAdvanced 109 }

-- {SCALAR} 1.3.6.1.4.1.2356.11.1.99.1.25.110
lcsStatusXdslAdslAdvancedDsAtmCells OBJECT-TYPE
    SYNTAX     Integer32 (0..2147483647)
    MAX-ACCESS read-only
    STATUS     current
    DESCRIPTION
            "-- empty --"
    ::= { lcsStatusXdslAdslAdvanced 110 }

-- {SCALAR} 1.3.6.1.4.1.2356.11.1.99.1.25.120
lcsStatusXdslAdslAdvancedUsAttainableDataRateKbps OBJECT-TYPE
    SYNTAX     Integer32 (0..2147483647)
    MAX-ACCESS read-only
    STATUS     current
    DESCRIPTION
            "-- empty --"
    ::= { lcsStatusXdslAdslAdvanced 120 }

-- {SCALAR} 1.3.6.1.4.1.2356.11.1.99.1.25.121
lcsStatusXdslAdslAdvancedUsInpSymbols OBJECT-TYPE
    SYNTAX     DisplayString (SIZE(0..3))
    MAX-ACCESS read-only
    STATUS     current
    DESCRIPTION
            "-- empty --"
    ::= { lcsStatusXdslAdslAdvanced 121 }

-- {SCALAR} 1.3.6.1.4.1.2356.11.1.99.1.25.122
lcsStatusXdslAdslAdvancedUsCrcErrors OBJECT-TYPE
    SYNTAX     Integer32 (0..2147483647)
    MAX-ACCESS read-only
    STATUS     current
    DESCRIPTION
            "-- empty --"
    ::= { lcsStatusXdslAdslAdvanced 122 }

-- {SCALAR} 1.3.6.1.4.1.2356.11.1.99.1.25.123
lcsStatusXdslAdslAdvancedUsFecErrors OBJECT-TYPE
    SYNTAX     Integer32 (0..2147483647)
    MAX-ACCESS read-only
    STATUS     current
    DESCRIPTION
            "-- empty --"
    ::= { lcsStatusXdslAdslAdvanced 123 }

-- {SCALAR} 1.3.6.1.4.1.2356.11.1.99.1.25.124
lcsStatusXdslAdslAdvancedUsAtmHecErrors OBJECT-TYPE
    SYNTAX     Integer32 (0..2147483647)
    MAX-ACCESS read-only
    STATUS     current
    DESCRIPTION
            "-- empty --"
    ::= { lcsStatusXdslAdslAdvanced 124 }

-- {SCALAR} 1.3.6.1.4.1.2356.11.1.99.1.25.125
lcsStatusXdslAdslAdvancedUsDataPathCrcpErrors OBJECT-TYPE
    SYNTAX     Integer32 (0..2147483647)
    MAX-ACCESS read-only
    STATUS     current
    DESCRIPTION
            "-- empty --"
    ::= { lcsStatusXdslAdslAdvanced 125 }

-- {SCALAR} 1.3.6.1.4.1.2356.11.1.99.1.25.126
lcsStatusXdslAdslAdvancedUsDataPathCrcnpErrors OBJECT-TYPE
    SYNTAX     Integer32 (0..2147483647)
    MAX-ACCESS read-only
    STATUS     current
    DESCRIPTION
            "-- empty --"
    ::= { lcsStatusXdslAdslAdvanced 126 }

-- {SCALAR} 1.3.6.1.4.1.2356.11.1.99.1.25.127
lcsStatusXdslAdslAdvancedUsDataPathCvpErrors OBJECT-TYPE
    SYNTAX     Integer32 (0..2147483647)
    MAX-ACCESS read-only
    STATUS     current
    DESCRIPTION
            "-- empty --"
    ::= { lcsStatusXdslAdslAdvanced 127 }

-- {SCALAR} 1.3.6.1.4.1.2356.11.1.99.1.25.128
lcsStatusXdslAdslAdvancedUsDataPathCvnpErrors OBJECT-TYPE
    SYNTAX     Integer32 (0..2147483647)
    MAX-ACCESS read-only
    STATUS     current
    DESCRIPTION
            "-- empty --"
    ::= { lcsStatusXdslAdslAdvanced 128 }

-- {SCALAR} 1.3.6.1.4.1.2356.11.1.99.1.25.129
lcsStatusXdslAdslAdvancedUsAtmIdleBitErrors OBJECT-TYPE
    SYNTAX     Integer32 (0..2147483647)
    MAX-ACCESS read-only
    STATUS     current
    DESCRIPTION
            "-- empty --"
    ::= { lcsStatusXdslAdslAdvanced 129 }

-- {SCALAR} 1.3.6.1.4.1.2356.11.1.99.1.25.130
lcsStatusXdslAdslAdvancedUsAtmCells OBJECT-TYPE
    SYNTAX     Integer32 (0..2147483647)
    MAX-ACCESS read-only
    STATUS     current
    DESCRIPTION
            "-- empty --"
    ::= { lcsStatusXdslAdslAdvanced 130 }

-- {SCALAR} 1.3.6.1.4.1.2356.11.1.99.1.25.140
lcsStatusXdslAdslAdvancedWanTxPacketCount OBJECT-TYPE
    SYNTAX     Integer32 (0..2147483647)
    MAX-ACCESS read-only
    STATUS     current
    DESCRIPTION
            "-- empty --"
    ::= { lcsStatusXdslAdslAdvanced 140 }

-- {SCALAR} 1.3.6.1.4.1.2356.11.1.99.1.25.141
lcsStatusXdslAdslAdvancedWanTxPacketBytes OBJECT-TYPE
    SYNTAX     Integer32 (0..2147483647)
    MAX-ACCESS read-only
    STATUS     current
    DESCRIPTION
            "-- empty --"
    ::= { lcsStatusXdslAdslAdvanced 141 }

-- {SCALAR} 1.3.6.1.4.1.2356.11.1.99.1.25.142
lcsStatusXdslAdslAdvancedWanTxPacketErrors OBJECT-TYPE
    SYNTAX     Integer32 (0..2147483647)
    MAX-ACCESS read-only
    STATUS     current
    DESCRIPTION
            "-- empty --"
    ::= { lcsStatusXdslAdslAdvanced 142 }

-- {SCALAR} 1.3.6.1.4.1.2356.11.1.99.1.25.143
lcsStatusXdslAdslAdvancedWanTxPacketDrops OBJECT-TYPE
    SYNTAX     Integer32 (0..2147483647)
    MAX-ACCESS read-only
    STATUS     current
    DESCRIPTION
            "-- empty --"
    ::= { lcsStatusXdslAdslAdvanced 143 }

-- {SCALAR} 1.3.6.1.4.1.2356.11.1.99.1.25.144
lcsStatusXdslAdslAdvancedWanTxOverruns OBJECT-TYPE
    SYNTAX     Integer32 (0..2147483647)
    MAX-ACCESS read-only
    STATUS     current
    DESCRIPTION
            "-- empty --"
    ::= { lcsStatusXdslAdslAdvanced 144 }

-- {SCALAR} 1.3.6.1.4.1.2356.11.1.99.1.25.146
lcsStatusXdslAdslAdvancedTxPacketCount OBJECT-TYPE
    SYNTAX     Integer32 (0..2147483647)
    MAX-ACCESS read-only
    STATUS     current
    DESCRIPTION
            "-- empty --"
    ::= { lcsStatusXdslAdslAdvanced 146 }

-- {SCALAR} 1.3.6.1.4.1.2356.11.1.99.1.25.150
lcsStatusXdslAdslAdvancedWanRxPacketCount OBJECT-TYPE
    SYNTAX     Integer32 (0..2147483647)
    MAX-ACCESS read-only
    STATUS     current
    DESCRIPTION
            "-- empty --"
    ::= { lcsStatusXdslAdslAdvanced 150 }

-- {SCALAR} 1.3.6.1.4.1.2356.11.1.99.1.25.151
lcsStatusXdslAdslAdvancedWanRxPacketBytes OBJECT-TYPE
    SYNTAX     Integer32 (0..2147483647)
    MAX-ACCESS read-only
    STATUS     current
    DESCRIPTION
            "-- empty --"
    ::= { lcsStatusXdslAdslAdvanced 151 }

-- {SCALAR} 1.3.6.1.4.1.2356.11.1.99.1.25.152
lcsStatusXdslAdslAdvancedWanRxPacketErrors OBJECT-TYPE
    SYNTAX     Integer32 (0..2147483647)
    MAX-ACCESS read-only
    STATUS     current
    DESCRIPTION
            "-- empty --"
    ::= { lcsStatusXdslAdslAdvanced 152 }

-- {SCALAR} 1.3.6.1.4.1.2356.11.1.99.1.25.153
lcsStatusXdslAdslAdvancedWanRxPacketDrops OBJECT-TYPE
    SYNTAX     Integer32 (0..2147483647)
    MAX-ACCESS read-only
    STATUS     current
    DESCRIPTION
            "-- empty --"
    ::= { lcsStatusXdslAdslAdvanced 153 }

-- {SCALAR} 1.3.6.1.4.1.2356.11.1.99.1.25.154
lcsStatusXdslAdslAdvancedWanRxOverruns OBJECT-TYPE
    SYNTAX     Integer32 (0..2147483647)
    MAX-ACCESS read-only
    STATUS     current
    DESCRIPTION
            "-- empty --"
    ::= { lcsStatusXdslAdslAdvanced 154 }

-- {SCALAR} 1.3.6.1.4.1.2356.11.1.99.1.25.156
lcsStatusXdslAdslAdvancedRxPacketCount OBJECT-TYPE
    SYNTAX     Integer32 (0..2147483647)
    MAX-ACCESS read-only
    STATUS     current
    DESCRIPTION
            "-- empty --"
    ::= { lcsStatusXdslAdslAdvanced 156 }

-- {SCALAR} 1.3.6.1.4.1.2356.11.1.99.1.34
lcsStatusXdslAdslInpDownstreamSymbols OBJECT-TYPE
    SYNTAX     DisplayString (SIZE(0..3))
    MAX-ACCESS read-only
    STATUS     current
    DESCRIPTION
            "-- empty --"
    ::= { lcsStatusXdslAdsl 34 }

-- {SCALAR} 1.3.6.1.4.1.2356.11.1.99.1.35
lcsStatusXdslAdslInpUpstreamSymbols OBJECT-TYPE
    SYNTAX     DisplayString (SIZE(0..3))
    MAX-ACCESS read-only
    STATUS     current
    DESCRIPTION
            "-- empty --"
    ::= { lcsStatusXdslAdsl 35 }

-- {SCALAR} 1.3.6.1.4.1.2356.11.1.99.1.36
lcsStatusXdslAdslAttainableDataRateDownstreamKbps OBJECT-TYPE
    SYNTAX     Integer32 (0..2147483647)
    MAX-ACCESS read-only
    STATUS     current
    DESCRIPTION
            "-- empty --"
    ::= { lcsStatusXdslAdsl 36 }

-- {SCALAR} 1.3.6.1.4.1.2356.11.1.99.1.37
lcsStatusXdslAdslAttainableDataRateUpstreamKbps OBJECT-TYPE
    SYNTAX     Integer32 (0..2147483647)
    MAX-ACCESS read-only
    STATUS     current
    DESCRIPTION
            "-- empty --"
    ::= { lcsStatusXdslAdsl 37 }

-- {SCALAR} 1.3.6.1.4.1.2356.11.1.99.1.41
lcsStatusXdslAdslDslamManufacturer OBJECT-TYPE
    SYNTAX     DisplayString (SIZE(0..63))
    MAX-ACCESS read-only
    STATUS     current
    DESCRIPTION
            "-- empty --"
    ::= { lcsStatusXdslAdsl 41 }

-- {SCALAR} 1.3.6.1.4.1.2356.11.1.99.1.42
lcsStatusXdslAdslDslamVersion OBJECT-TYPE
    SYNTAX     DisplayString (SIZE(0..34))
    MAX-ACCESS read-only
    STATUS     current
    DESCRIPTION
            "-- empty --"
    ::= { lcsStatusXdslAdsl 42 }

-- {SCALAR} 1.3.6.1.4.1.2356.11.1.99.1.43
lcsStatusXdslAdslDslamSerialNumber OBJECT-TYPE
    SYNTAX     DisplayString (SIZE(0..66))
    MAX-ACCESS read-only
    STATUS     current
    DESCRIPTION
            "-- empty --"
    ::= { lcsStatusXdslAdsl 43 }

-- {SCALAR} 1.3.6.1.4.1.2356.11.1.99.1.53
lcsStatusXdslAdslConnectionCount OBJECT-TYPE
    SYNTAX     Integer32 (0..2147483647)
    MAX-ACCESS read-only
    STATUS     current
    DESCRIPTION
            "-- empty --"
    ::= { lcsStatusXdslAdsl 53 }

-- {SCALAR} 1.3.6.1.4.1.2356.11.1.99.1.54
lcsStatusXdslAdslConnectionDuration OBJECT-TYPE
    SYNTAX     Gauge32
    MAX-ACCESS read-only
    STATUS     current
    DESCRIPTION
            "-- empty --"
    ::= { lcsStatusXdslAdsl 54 }

-- {SCALAR} 1.3.6.1.4.1.2356.11.1.99.1.200
lcsStatusXdslAdslWanBridge OBJECT-TYPE
    SYNTAX     INTEGER {
                  eNo (0),
                  eYes (1)
            }
    MAX-ACCESS read-only
    STATUS     current
    DESCRIPTION
            "-- empty --"
    ::= { lcsStatusXdslAdsl 200 }

-- {NODE} 1.3.6.1.4.1.2356.11.1.99.1.500
lcsStatusXdslAdslModem OBJECT IDENTIFIER ::= { lcsStatusXdslAdsl 500 }

-- {SCALAR} 1.3.6.1.4.1.2356.11.1.99.1.500.1
lcsStatusXdslAdslModemModemState OBJECT-TYPE
    SYNTAX     INTEGER {
                  eNoCommunicationsPort (0),
                  eError (1),
                  eFileSystem (2),
                  eBootHeader (3),
                  eUploadingBootstrap (4),
                  eUploadingMemoryTest (5),
                  eMemoryTest (6),
                  eOptions (7),
                  eUploadingUBoot (8),
                  eQuickMemoryTest (9),
                  eUploadingKernel (10),
                  eUploadingRamdisk (11),
                  eUploadingFirmware (12),
                  eWaitForHeartbeat (13),
                  eRunning (14),
                  eUploadingGphyFirmware (15),
                  eDisabled (16)
            }
    MAX-ACCESS read-only
    STATUS     current
    DESCRIPTION
            "-- empty --"
    ::= { lcsStatusXdslAdslModem 1 }

-- {SCALAR} 1.3.6.1.4.1.2356.11.1.99.1.500.2
lcsStatusXdslAdslModemOptions OBJECT-TYPE
    SYNTAX     Integer32 (0..255)
    MAX-ACCESS read-only
    STATUS     current
    DESCRIPTION
            "-- empty --"
    ::= { lcsStatusXdslAdslModem 2 }

-- {SCALAR} 1.3.6.1.4.1.2356.11.1.99.1.500.3
lcsStatusXdslAdslModemMemoryTest OBJECT-TYPE
    SYNTAX     INTEGER {
                  eNotTested (0),
                  eTimeout (1),
                  eFailed (2),
                  eOk (3)
            }
    MAX-ACCESS read-only
    STATUS     current
    DESCRIPTION
            "-- empty --"
    ::= { lcsStatusXdslAdslModem 3 }

-- {SCALAR} 1.3.6.1.4.1.2356.11.1.99.1.500.4
lcsStatusXdslAdslModemRebootModem OBJECT-TYPE
    SYNTAX     DisplayString
    MAX-ACCESS read-write
    STATUS     current
    DESCRIPTION
            "-- empty --"
    ::= { lcsStatusXdslAdslModem 4 }

-- {SCALAR} 1.3.6.1.4.1.2356.11.1.99.1.500.5
lcsStatusXdslAdslModemLink OBJECT-TYPE
    SYNTAX     Integer32 (0..2147483647)
    MAX-ACCESS read-only
    STATUS     current
    DESCRIPTION
            "-- empty --"
    ::= { lcsStatusXdslAdslModem 5 }

-- {SCALAR} 1.3.6.1.4.1.2356.11.1.99.1.500.6
lcsStatusXdslAdslModemLastError OBJECT-TYPE
    SYNTAX     DisplayString (SIZE(0..63))
    MAX-ACCESS read-only
    STATUS     current
    DESCRIPTION
            "-- empty --"
    ::= { lcsStatusXdslAdslModem 6 }

-- {SCALAR} 1.3.6.1.4.1.2356.11.1.99.1.500.10
lcsStatusXdslAdslModemDslApiVersion OBJECT-TYPE
    SYNTAX     DisplayString (SIZE(0..31))
    MAX-ACCESS read-only
    STATUS     current
    DESCRIPTION
            "-- empty --"
    ::= { lcsStatusXdslAdslModem 10 }

-- {SCALAR} 1.3.6.1.4.1.2356.11.1.99.1.500.11
lcsStatusXdslAdslModemDspFirmwareVersion OBJECT-TYPE
    SYNTAX     DisplayString (SIZE(0..31))
    MAX-ACCESS read-only
    STATUS     current
    DESCRIPTION
            "-- empty --"
    ::= { lcsStatusXdslAdslModem 11 }

-- {SCALAR} 1.3.6.1.4.1.2356.11.1.99.1.500.12
lcsStatusXdslAdslModemHardwareVersion OBJECT-TYPE
    SYNTAX     DisplayString (SIZE(0..31))
    MAX-ACCESS read-only
    STATUS     current
    DESCRIPTION
            "-- empty --"
    ::= { lcsStatusXdslAdslModem 12 }

-- {SCALAR} 1.3.6.1.4.1.2356.11.1.99.1.500.13
lcsStatusXdslAdslModemChipsetType OBJECT-TYPE
    SYNTAX     DisplayString (SIZE(0..31))
    MAX-ACCESS read-only
    STATUS     current
    DESCRIPTION
            "-- empty --"
    ::= { lcsStatusXdslAdslModem 13 }

-- {SCALAR} 1.3.6.1.4.1.2356.11.1.99.1.500.14
lcsStatusXdslAdslModemDriverVersion OBJECT-TYPE
    SYNTAX     DisplayString (SIZE(0..31))
    MAX-ACCESS read-only
    STATUS     current
    DESCRIPTION
            "-- empty --"
    ::= { lcsStatusXdslAdslModem 14 }

-- {SCALAR} 1.3.6.1.4.1.2356.11.1.99.1.500.15
lcsStatusXdslAdslModemBootCount OBJECT-TYPE
    SYNTAX     Integer32 (0..2147483647)
    MAX-ACCESS read-only
    STATUS     current
    DESCRIPTION
            "-- empty --"
    ::= { lcsStatusXdslAdslModem 15 }

-- {SCALAR} 1.3.6.1.4.1.2356.11.1.99.1.500.16
lcsStatusXdslAdslModemHybrid OBJECT-TYPE
    SYNTAX     INTEGER {
                  eBJ (0),
                  eInvalid (1),
                  eB (2),
                  eA (3),
                  eUniversal (4),
                  eUnknown (256)
            }
    MAX-ACCESS read-only
    STATUS     current
    DESCRIPTION
            "-- empty --"
    ::= { lcsStatusXdslAdslModem 16 }

-- {SCALAR} 1.3.6.1.4.1.2356.11.1.99.1.500.20
lcsStatusXdslAdslModemDefaultLineType OBJECT-TYPE
    SYNTAX     INTEGER {
                  eUnknown (1),
                  eOverPots (2),
                  eOverIsdn (3)
            }
    MAX-ACCESS read-only
    STATUS     current
    DESCRIPTION
            "-- empty --"
    ::= { lcsStatusXdslAdslModem 20 }

-- {SCALAR} 1.3.6.1.4.1.2356.11.1.99.1.500.25
lcsStatusXdslAdslModemPotsFirmware OBJECT-TYPE
    SYNTAX     DisplayString (SIZE(0..71))
    MAX-ACCESS read-only
    STATUS     current
    DESCRIPTION
            "-- empty --"
    ::= { lcsStatusXdslAdslModem 25 }

-- {SCALAR} 1.3.6.1.4.1.2356.11.1.99.1.500.26
lcsStatusXdslAdslModemIsdnFirmware OBJECT-TYPE
    SYNTAX     DisplayString (SIZE(0..71))
    MAX-ACCESS read-only
    STATUS     current
    DESCRIPTION
            "-- empty --"
    ::= { lcsStatusXdslAdslModem 26 }

-- {SCALAR} 1.3.6.1.4.1.2356.11.1.99.1.500.28
lcsStatusXdslAdslModemWanAcceleration OBJECT-TYPE
    SYNTAX     INTEGER {
                  eNo (0),
                  eYes (1)
            }
    MAX-ACCESS read-only
    STATUS     current
    DESCRIPTION
            "-- empty --"
    ::= { lcsStatusXdslAdslModem 28 }

-- {NODE} 1.3.6.1.4.1.2356.11.1.99.2
lcsStatusXdslVdsl1 OBJECT IDENTIFIER ::= { lcsStatusXdsl 2 }

-- {SCALAR} 1.3.6.1.4.1.2356.11.1.99.2.1
lcsStatusXdslVdsl1LineState OBJECT-TYPE
    SYNTAX     INTEGER {
                  eUnknown (0),
                  eDown (1),
                  eIdle (2),
                  eHandshake (3),
                  eTraining (4),
                  eShowtime (5),
                  eShutdown (6)
            }
    MAX-ACCESS read-only
    STATUS     current
    DESCRIPTION
            "-- empty --"
    ::= { lcsStatusXdslVdsl1 1 }

-- {SCALAR} 1.3.6.1.4.1.2356.11.1.99.2.2
lcsStatusXdslVdsl1LineType OBJECT-TYPE
    SYNTAX     DisplayString
    MAX-ACCESS read-only
    STATUS     current
    DESCRIPTION
            "-- empty --"
    ::= { lcsStatusXdslVdsl1 2 }

-- {SCALAR} 1.3.6.1.4.1.2356.11.1.99.2.3
lcsStatusXdslVdsl1Standard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGFast (42),
                  eGVector (254),
                  eUnknown (255)
            }
    MAX-ACCESS read-only
    STATUS     current
    DESCRIPTION
            "-- empty --"
    ::= { lcsStatusXdslVdsl1 3 }

-- {SCALAR} 1.3.6.1.4.1.2356.11.1.99.2.4
lcsStatusXdslVdsl1DataRateUpstreamKbps OBJECT-TYPE
    SYNTAX     Integer32 (0..2147483647)
    MAX-ACCESS read-only
    STATUS     current
    DESCRIPTION
            "-- empty --"
    ::= { lcsStatusXdslVdsl1 4 }

-- {SCALAR} 1.3.6.1.4.1.2356.11.1.99.2.5
lcsStatusXdslVdsl1DataRateDownstreamKbps OBJECT-TYPE
    SYNTAX     Integer32 (0..2147483647)
    MAX-ACCESS read-only
    STATUS     current
    DESCRIPTION
            "-- empty --"
    ::= { lcsStatusXdslVdsl1 5 }

-- {SCALAR} 1.3.6.1.4.1.2356.11.1.99.2.6
lcsStatusXdslVdsl1SnrDownstreamDb OBJECT-TYPE
    SYNTAX     DisplayString (SIZE(0..3))
    MAX-ACCESS read-only
    STATUS     current
    DESCRIPTION
            "-- empty --"
    ::= { lcsStatusXdslVdsl1 6 }

-- {SCALAR} 1.3.6.1.4.1.2356.11.1.99.2.7
lcsStatusXdslVdsl1SnrUpstreamDb OBJECT-TYPE
    SYNTAX     DisplayString (SIZE(0..3))
    MAX-ACCESS read-only
    STATUS     current
    DESCRIPTION
            "-- empty --"
    ::= { lcsStatusXdslVdsl1 7 }

-- {SCALAR} 1.3.6.1.4.1.2356.11.1.99.2.8
lcsStatusXdslVdsl1AttenuationDownstreamDb OBJECT-TYPE
    SYNTAX     DisplayString (SIZE(0..3))
    MAX-ACCESS read-only
    STATUS     current
    DESCRIPTION
            "-- empty --"
    ::= { lcsStatusXdslVdsl1 8 }

-- {SCALAR} 1.3.6.1.4.1.2356.11.1.99.2.9
lcsStatusXdslVdsl1AttenuationUpstreamDb OBJECT-TYPE
    SYNTAX     DisplayString (SIZE(0..3))
    MAX-ACCESS read-only
    STATUS     current
    DESCRIPTION
            "-- empty --"
    ::= { lcsStatusXdslVdsl1 9 }

-- {SCALAR} 1.3.6.1.4.1.2356.11.1.99.2.10
lcsStatusXdslVdsl1InterleaveUpstreamMs OBJECT-TYPE
    SYNTAX     DisplayString
    MAX-ACCESS read-only
    STATUS     current
    DESCRIPTION
            "-- empty --"
    ::= { lcsStatusXdslVdsl1 10 }

-- {SCALAR} 1.3.6.1.4.1.2356.11.1.99.2.11
lcsStatusXdslVdsl1InterleaveDownstreamMs OBJECT-TYPE
    SYNTAX     DisplayString
    MAX-ACCESS read-only
    STATUS     current
    DESCRIPTION
            "-- empty --"
    ::= { lcsStatusXdslVdsl1 11 }

-- {TABLE} 1.3.6.1.4.1.2356.11.1.99.2.12
lcsStatusXdslVdsl1ConnectionHistoryTable OBJECT-TYPE
    SYNTAX     SEQUENCE OF LcsStatusXdslVdsl1ConnectionHistoryEntry
    MAX-ACCESS not-accessible
    STATUS     current
    DESCRIPTION
            "-- empty --"
    ::= { lcsStatusXdslVdsl1 12 }

-- {ROW} 1.3.6.1.4.1.2356.11.1.99.2.12.1
lcsStatusXdslVdsl1ConnectionHistoryEntry OBJECT-TYPE
    SYNTAX     LcsStatusXdslVdsl1ConnectionHistoryEntry
    MAX-ACCESS not-accessible
    STATUS     current
    DESCRIPTION
            ""
    INDEX {
            lcsStatusXdslVdsl1ConnectionHistoryEntryIndex
          }
    ::= { lcsStatusXdslVdsl1ConnectionHistoryTable 1 }

LcsStatusXdslVdsl1ConnectionHistoryEntry ::= SEQUENCE {
            lcsStatusXdslVdsl1ConnectionHistoryEntrySyncTime Gauge32,
            lcsStatusXdslVdsl1ConnectionHistoryEntryStandard INTEGER,
            lcsStatusXdslVdsl1ConnectionHistoryEntryDsDatarate Integer32,
            lcsStatusXdslVdsl1ConnectionHistoryEntryUsDatarate Integer32,
            lcsStatusXdslVdsl1ConnectionHistoryEntryDsAttenuation DisplayString,
            lcsStatusXdslVdsl1ConnectionHistoryEntryDsSnr DisplayString,
            lcsStatusXdslVdsl1ConnectionHistoryEntryDisconnectTime Gauge32,
            lcsStatusXdslVdsl1ConnectionHistoryEntryIndex Integer32,
            lcsStatusXdslVdsl1ConnectionHistoryEntryReason INTEGER,
            lcsStatusXdslVdsl1ConnectionHistoryEntryUsAttenuation DisplayString,
            lcsStatusXdslVdsl1ConnectionHistoryEntryUsSnr DisplayString,
            lcsStatusXdslVdsl1ConnectionHistoryEntryLinecode DisplayString,
            lcsStatusXdslVdsl1ConnectionHistoryEntryVdslProfile INTEGER,
            lcsStatusXdslVdsl1ConnectionHistoryEntryVectoring INTEGER
    }

-- {COLUMN} 1.3.6.1.4.1.2356.11.1.99.2.12.1.1
lcsStatusXdslVdsl1ConnectionHistoryEntrySyncTime OBJECT-TYPE
    SYNTAX     Gauge32
    MAX-ACCESS read-only
    STATUS     current
    DESCRIPTION
            "-- empty --"
    ::= { lcsStatusXdslVdsl1ConnectionHistoryEntry 1 }

-- {COLUMN} 1.3.6.1.4.1.2356.11.1.99.2.12.1.2
lcsStatusXdslVdsl1ConnectionHistoryEntryStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGFast (42),
                  eGVector (254),
                  eUnknown (255)
            }
    MAX-ACCESS read-only
    STATUS     current
    DESCRIPTION
            "-- empty --"
    ::= { lcsStatusXdslVdsl1ConnectionHistoryEntry 2 }

-- {COLUMN} 1.3.6.1.4.1.2356.11.1.99.2.12.1.3
lcsStatusXdslVdsl1ConnectionHistoryEntryDsDatarate OBJECT-TYPE
    SYNTAX     Integer32 (0..2147483647)
    MAX-ACCESS read-only
    STATUS     current
    DESCRIPTION
            "-- empty --"
    ::= { lcsStatusXdslVdsl1ConnectionHistoryEntry 3 }

-- {COLUMN} 1.3.6.1.4.1.2356.11.1.99.2.12.1.4
lcsStatusXdslVdsl1ConnectionHistoryEntryUsDatarate OBJECT-TYPE
    SYNTAX     Integer32 (0..2147483647)
    MAX-ACCESS read-only
    STATUS     current
    DESCRIPTION
            "-- empty --"
    ::= { lcsStatusXdslVdsl1ConnectionHistoryEntry 4 }

-- {COLUMN} 1.3.6.1.4.1.2356.11.1.99.2.12.1.5
lcsStatusXdslVdsl1ConnectionHistoryEntryDsAttenuation OBJECT-TYPE
    SYNTAX     DisplayString (SIZE(0..1))
    MAX-ACCESS read-only
    STATUS     current
    DESCRIPTION
            "-- empty --"
    ::= { lcsStatusXdslVdsl1ConnectionHistoryEntry 5 }

-- {COLUMN} 1.3.6.1.4.1.2356.11.1.99.2.12.1.6
lcsStatusXdslVdsl1ConnectionHistoryEntryDsSnr OBJECT-TYPE
    SYNTAX     DisplayString (SIZE(0..1))
    MAX-ACCESS read-only
    STATUS     current
    DESCRIPTION
            "-- empty --"
    ::= { lcsStatusXdslVdsl1ConnectionHistoryEntry 6 }

-- {COLUMN} 1.3.6.1.4.1.2356.11.1.99.2.12.1.7
lcsStatusXdslVdsl1ConnectionHistoryEntryDisconnectTime OBJECT-TYPE
    SYNTAX     Gauge32
    MAX-ACCESS read-only
    STATUS     current
    DESCRIPTION
            "-- empty --"
    ::= { lcsStatusXdslVdsl1ConnectionHistoryEntry 7 }

-- {COLUMN} 1.3.6.1.4.1.2356.11.1.99.2.12.1.8
lcsStatusXdslVdsl1ConnectionHistoryEntryIndex OBJECT-TYPE
    SYNTAX     Integer32 (0..2147483647)
    MAX-ACCESS read-only
    STATUS     current
    DESCRIPTION
            "-- empty --"
    ::= { lcsStatusXdslVdsl1ConnectionHistoryEntry 8 }

-- {COLUMN} 1.3.6.1.4.1.2356.11.1.99.2.12.1.9
lcsStatusXdslVdsl1ConnectionHistoryEntryReason OBJECT-TYPE
    SYNTAX     INTEGER {
                  eModemReboot (1),
                  eRetrain (2),
                  eSilence (3),
                  eLineError (4),
                  eProtocol (5),
                  eLineType (6),
                  eAutomode (7),
                  eTimeout (8),
                  eVcParameters (13)
            }
    MAX-ACCESS read-only
    STATUS     current
    DESCRIPTION
            "-- empty --"
    ::= { lcsStatusXdslVdsl1ConnectionHistoryEntry 9 }

-- {COLUMN} 1.3.6.1.4.1.2356.11.1.99.2.12.1.10
lcsStatusXdslVdsl1ConnectionHistoryEntryUsAttenuation OBJECT-TYPE
    SYNTAX     DisplayString (SIZE(0..1))
    MAX-ACCESS read-only
    STATUS     current
    DESCRIPTION
            "-- empty --"
    ::= { lcsStatusXdslVdsl1ConnectionHistoryEntry 10 }

-- {COLUMN} 1.3.6.1.4.1.2356.11.1.99.2.12.1.11
lcsStatusXdslVdsl1ConnectionHistoryEntryUsSnr OBJECT-TYPE
    SYNTAX     DisplayString (SIZE(0..1))
    MAX-ACCESS read-only
    STATUS     current
    DESCRIPTION
            "-- empty --"
    ::= { lcsStatusXdslVdsl1ConnectionHistoryEntry 11 }

-- {COLUMN} 1.3.6.1.4.1.2356.11.1.99.2.12.1.12
lcsStatusXdslVdsl1ConnectionHistoryEntryLinecode OBJECT-TYPE
    SYNTAX     DisplayString (SIZE(0..1))
    MAX-ACCESS read-only
    STATUS     current
    DESCRIPTION
            "-- empty --"
    ::= { lcsStatusXdslVdsl1ConnectionHistoryEntry 12 }

-- {COLUMN} 1.3.6.1.4.1.2356.11.1.99.2.12.1.13
lcsStatusXdslVdsl1ConnectionHistoryEntryVdslProfile OBJECT-TYPE
    SYNTAX     INTEGER {
                  eUnknown (0),
                  e8a (1),
                  e8b (2),
                  e8c (3),
                  e8d (4),
                  e12a (5),
                  e12b (6),
                  e17a (7),
                  e30a (8),
                  e35b (9)
            }
    MAX-ACCESS read-only
    STATUS     current
    DESCRIPTION
            "-- empty --"
    ::= { lcsStatusXdslVdsl1ConnectionHistoryEntry 13 }

-- {COLUMN} 1.3.6.1.4.1.2356.11.1.99.2.12.1.14
lcsStatusXdslVdsl1ConnectionHistoryEntryVectoring OBJECT-TYPE
    SYNTAX     INTEGER {
                  eNo (1),
                  eYes (2),
                  eFriendly (3)
            }
    MAX-ACCESS read-only
    STATUS     current
    DESCRIPTION
            "-- empty --"
    ::= { lcsStatusXdslVdsl1ConnectionHistoryEntry 14 }

-- {SCALAR} 1.3.6.1.4.1.2356.11.1.99.2.13
lcsStatusXdslVdsl1Retrain OBJECT-TYPE
    SYNTAX     DisplayString
    MAX-ACCESS read-write
    STATUS     current
    DESCRIPTION
            "-- empty --"
    ::= { lcsStatusXdslVdsl1 13 }

-- {SCALAR} 1.3.6.1.4.1.2356.11.1.99.2.14
lcsStatusXdslVdsl1DslamChipsetManufacturer OBJECT-TYPE
    SYNTAX     DisplayString (SIZE(0..63))
    MAX-ACCESS read-only
    STATUS     current
    DESCRIPTION
            "-- empty --"
    ::= { lcsStatusXdslVdsl1 14 }

-- {SCALAR} 1.3.6.1.4.1.2356.11.1.99.2.23
lcsStatusXdslVdsl1ModemType OBJECT-TYPE
    SYNTAX     DisplayString
    MAX-ACCESS read-only
    STATUS     current
    DESCRIPTION
            "-- empty --"
    ::= { lcsStatusXdslVdsl1 23 }

-- {NODE} 1.3.6.1.4.1.2356.11.1.99.2.25
lcsStatusXdslVdsl1Advanced OBJECT IDENTIFIER ::= { lcsStatusXdslVdsl1 25 }

-- {SCALAR} 1.3.6.1.4.1.2356.11.1.99.2.25.1
lcsStatusXdslVdsl1AdvancedLineState OBJECT-TYPE
    SYNTAX     INTEGER {
                  eUnknown (0),
                  eDown (1),
                  eIdle (2),
                  eHandshake (3),
                  eTraining (4),
                  eShowtime (5),
                  eShutdown (6)
            }
    MAX-ACCESS read-only
    STATUS     current
    DESCRIPTION
            "-- empty --"
    ::= { lcsStatusXdslVdsl1Advanced 1 }

-- {SCALAR} 1.3.6.1.4.1.2356.11.1.99.2.25.2
lcsStatusXdslVdsl1AdvancedStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGFast (42),
                  eGVector (254),
                  eUnknown (255)
            }
    MAX-ACCESS read-only
    STATUS     current
    DESCRIPTION
            "-- empty --"
    ::= { lcsStatusXdslVdsl1Advanced 2 }

-- {SCALAR} 1.3.6.1.4.1.2356.11.1.99.2.25.3
lcsStatusXdslVdsl1AdvancedDsDataRateKbps OBJECT-TYPE
    SYNTAX     Integer32 (0..2147483647)
    MAX-ACCESS read-only
    STATUS     current
    DESCRIPTION
            "-- empty --"
    ::= { lcsStatusXdslVdsl1Advanced 3 }

-- {SCALAR} 1.3.6.1.4.1.2356.11.1.99.2.25.4
lcsStatusXdslVdsl1AdvancedDsSnrMarginDb OBJECT-TYPE
    SYNTAX     DisplayString (SIZE(0..3))
    MAX-ACCESS read-only
    STATUS     current
    DESCRIPTION
            "-- empty --"
    ::= { lcsStatusXdslVdsl1Advanced 4 }

-- {SCALAR} 1.3.6.1.4.1.2356.11.1.99.2.25.5
lcsStatusXdslVdsl1AdvancedDsLineAttenuationDb OBJECT-TYPE
    SYNTAX     DisplayString (SIZE(0..3))
    MAX-ACCESS read-only
    STATUS     current
    DESCRIPTION
            "-- empty --"
    ::= { lcsStatusXdslVdsl1Advanced 5 }

-- {SCALAR} 1.3.6.1.4.1.2356.11.1.99.2.25.6
lcsStatusXdslVdsl1AdvancedDsInterleaveMs OBJECT-TYPE
    SYNTAX     DisplayString
    MAX-ACCESS read-only
    STATUS     current
    DESCRIPTION
            "-- empty --"
    ::= { lcsStatusXdslVdsl1Advanced 6 }

-- {TABLE} 1.3.6.1.4.1.2356.11.1.99.2.25.13
lcsStatusXdslVdsl1AdvancedDsBitLoadingTable OBJECT-TYPE
    SYNTAX     SEQUENCE OF LcsStatusXdslVdsl1AdvancedDsBitLoadingEntry
    MAX-ACCESS not-accessible
    STATUS     current
    DESCRIPTION
            "-- empty --"
    ::= { lcsStatusXdslVdsl1Advanced 13 }

-- {ROW} 1.3.6.1.4.1.2356.11.1.99.2.25.13.1
lcsStatusXdslVdsl1AdvancedDsBitLoadingEntry OBJECT-TYPE
    SYNTAX     LcsStatusXdslVdsl1AdvancedDsBitLoadingEntry
    MAX-ACCESS not-accessible
    STATUS     current
    DESCRIPTION
            ""
    INDEX {
            lcsStatusXdslVdsl1AdvancedDsBitLoadingEntryBinNumber
          }
    ::= { lcsStatusXdslVdsl1AdvancedDsBitLoadingTable 1 }

LcsStatusXdslVdsl1AdvancedDsBitLoadingEntry ::= SEQUENCE {
            lcsStatusXdslVdsl1AdvancedDsBitLoadingEntryBinNumber DisplayString,
            lcsStatusXdslVdsl1AdvancedDsBitLoadingEntryX0 Integer32,
            lcsStatusXdslVdsl1AdvancedDsBitLoadingEntryX1 Integer32,
            lcsStatusXdslVdsl1AdvancedDsBitLoadingEntryX2 Integer32,
            lcsStatusXdslVdsl1AdvancedDsBitLoadingEntryX3 Integer32,
            lcsStatusXdslVdsl1AdvancedDsBitLoadingEntryX4 Integer32,
            lcsStatusXdslVdsl1AdvancedDsBitLoadingEntryX5 Integer32,
            lcsStatusXdslVdsl1AdvancedDsBitLoadingEntryX6 Integer32,
            lcsStatusXdslVdsl1AdvancedDsBitLoadingEntryX7 Integer32,
            lcsStatusXdslVdsl1AdvancedDsBitLoadingEntryX8 Integer32,
            lcsStatusXdslVdsl1AdvancedDsBitLoadingEntryX9 Integer32,
            lcsStatusXdslVdsl1AdvancedDsBitLoadingEntryGraph DisplayString
    }

-- {COLUMN} 1.3.6.1.4.1.2356.11.1.99.2.25.13.1.1
lcsStatusXdslVdsl1AdvancedDsBitLoadingEntryBinNumber OBJECT-TYPE
    SYNTAX     DisplayString (SIZE(0..255))
    MAX-ACCESS read-only
    STATUS     current
    DESCRIPTION
            "-- empty --"
    ::= { lcsStatusXdslVdsl1AdvancedDsBitLoadingEntry 1 }

-- {COLUMN} 1.3.6.1.4.1.2356.11.1.99.2.25.13.1.2
lcsStatusXdslVdsl1AdvancedDsBitLoadingEntryX0 OBJECT-TYPE
    SYNTAX     Integer32 (0..2147483647)
    MAX-ACCESS read-only
    STATUS     current
    DESCRIPTION
            "-- empty --"
    ::= { lcsStatusXdslVdsl1AdvancedDsBitLoadingEntry 2 }

-- {COLUMN} 1.3.6.1.4.1.2356.11.1.99.2.25.13.1.3
lcsStatusXdslVdsl1AdvancedDsBitLoadingEntryX1 OBJECT-TYPE
    SYNTAX     Integer32 (0..2147483647)
    MAX-ACCESS read-only
    STATUS     current
    DESCRIPTION
            "-- empty --"
    ::= { lcsStatusXdslVdsl1AdvancedDsBitLoadingEntry 3 }

-- {COLUMN} 1.3.6.1.4.1.2356.11.1.99.2.25.13.1.4
lcsStatusXdslVdsl1AdvancedDsBitLoadingEntryX2 OBJECT-TYPE
    SYNTAX     Integer32 (0..2147483647)
    MAX-ACCESS read-only
    STATUS     current
    DESCRIPTION
            "-- empty --"
    ::= { lcsStatusXdslVdsl1AdvancedDsBitLoadingEntry 4 }

-- {COLUMN} 1.3.6.1.4.1.2356.11.1.99.2.25.13.1.5
lcsStatusXdslVdsl1AdvancedDsBitLoadingEntryX3 OBJECT-TYPE
    SYNTAX     Integer32 (0..2147483647)
    MAX-ACCESS read-only
    STATUS     current
    DESCRIPTION
            "-- empty --"
    ::= { lcsStatusXdslVdsl1AdvancedDsBitLoadingEntry 5 }

-- {COLUMN} 1.3.6.1.4.1.2356.11.1.99.2.25.13.1.6
lcsStatusXdslVdsl1AdvancedDsBitLoadingEntryX4 OBJECT-TYPE
    SYNTAX     Integer32 (0..2147483647)
    MAX-ACCESS read-only
    STATUS     current
    DESCRIPTION
            "-- empty --"
    ::= { lcsStatusXdslVdsl1AdvancedDsBitLoadingEntry 6 }

-- {COLUMN} 1.3.6.1.4.1.2356.11.1.99.2.25.13.1.7
lcsStatusXdslVdsl1AdvancedDsBitLoadingEntryX5 OBJECT-TYPE
    SYNTAX     Integer32 (0..2147483647)
    MAX-ACCESS read-only
    STATUS     current
    DESCRIPTION
            "-- empty --"
    ::= { lcsStatusXdslVdsl1AdvancedDsBitLoadingEntry 7 }

-- {COLUMN} 1.3.6.1.4.1.2356.11.1.99.2.25.13.1.8
lcsStatusXdslVdsl1AdvancedDsBitLoadingEntryX6 OBJECT-TYPE
    SYNTAX     Integer32 (0..2147483647)
    MAX-ACCESS read-only
    STATUS     current
    DESCRIPTION
            "-- empty --"
    ::= { lcsStatusXdslVdsl1AdvancedDsBitLoadingEntry 8 }

-- {COLUMN} 1.3.6.1.4.1.2356.11.1.99.2.25.13.1.9
lcsStatusXdslVdsl1AdvancedDsBitLoadingEntryX7 OBJECT-TYPE
    SYNTAX     Integer32 (0..2147483647)
    MAX-ACCESS read-only
    STATUS     current
    DESCRIPTION
            "-- empty --"
    ::= { lcsStatusXdslVdsl1AdvancedDsBitLoadingEntry 9 }

-- {COLUMN} 1.3.6.1.4.1.2356.11.1.99.2.25.13.1.10
lcsStatusXdslVdsl1AdvancedDsBitLoadingEntryX8 OBJECT-TYPE
    SYNTAX     Integer32 (0..2147483647)
    MAX-ACCESS read-only
    STATUS     current
    DESCRIPTION
            "-- empty --"
    ::= { lcsStatusXdslVdsl1AdvancedDsBitLoadingEntry 10 }

-- {COLUMN} 1.3.6.1.4.1.2356.11.1.99.2.25.13.1.11
lcsStatusXdslVdsl1AdvancedDsBitLoadingEntryX9 OBJECT-TYPE
    SYNTAX     Integer32 (0..2147483647)
    MAX-ACCESS read-only
    STATUS     current
    DESCRIPTION
            "-- empty --"
    ::= { lcsStatusXdslVdsl1AdvancedDsBitLoadingEntry 11 }

-- {COLUMN} 1.3.6.1.4.1.2356.11.1.99.2.25.13.1.12
lcsStatusXdslVdsl1AdvancedDsBitLoadingEntryGraph OBJECT-TYPE
    SYNTAX     DisplayString (SIZE(0..255))
    MAX-ACCESS read-only
    STATUS     current
    DESCRIPTION
            "-- empty --"
    ::= { lcsStatusXdslVdsl1AdvancedDsBitLoadingEntry 12 }

-- {SCALAR} 1.3.6.1.4.1.2356.11.1.99.2.25.15
lcsStatusXdslVdsl1AdvancedUsDataRateKbps OBJECT-TYPE
    SYNTAX     Integer32 (0..2147483647)
    MAX-ACCESS read-only
    STATUS     current
    DESCRIPTION
            "-- empty --"
    ::= { lcsStatusXdslVdsl1Advanced 15 }

-- {SCALAR} 1.3.6.1.4.1.2356.11.1.99.2.25.16
lcsStatusXdslVdsl1AdvancedUsSnrMarginDb OBJECT-TYPE
    SYNTAX     DisplayString (SIZE(0..3))
    MAX-ACCESS read-only
    STATUS     current
    DESCRIPTION
            "-- empty --"
    ::= { lcsStatusXdslVdsl1Advanced 16 }

-- {SCALAR} 1.3.6.1.4.1.2356.11.1.99.2.25.17
lcsStatusXdslVdsl1AdvancedUsLineAttenuationDb OBJECT-TYPE
    SYNTAX     DisplayString (SIZE(0..3))
    MAX-ACCESS read-only
    STATUS     current
    DESCRIPTION
            "-- empty --"
    ::= { lcsStatusXdslVdsl1Advanced 17 }

-- {SCALAR} 1.3.6.1.4.1.2356.11.1.99.2.25.18
lcsStatusXdslVdsl1AdvancedUsInterleaveMs OBJECT-TYPE
    SYNTAX     DisplayString
    MAX-ACCESS read-only
    STATUS     current
    DESCRIPTION
            "-- empty --"
    ::= { lcsStatusXdslVdsl1Advanced 18 }

-- {TABLE} 1.3.6.1.4.1.2356.11.1.99.2.25.25
lcsStatusXdslVdsl1AdvancedUsBitLoadingTable OBJECT-TYPE
    SYNTAX     SEQUENCE OF LcsStatusXdslVdsl1AdvancedUsBitLoadingEntry
    MAX-ACCESS not-accessible
    STATUS     current
    DESCRIPTION
            "-- empty --"
    ::= { lcsStatusXdslVdsl1Advanced 25 }

-- {ROW} 1.3.6.1.4.1.2356.11.1.99.2.25.25.1
lcsStatusXdslVdsl1AdvancedUsBitLoadingEntry OBJECT-TYPE
    SYNTAX     LcsStatusXdslVdsl1AdvancedUsBitLoadingEntry
    MAX-ACCESS not-accessible
    STATUS     current
    DESCRIPTION
            ""
    INDEX {
            lcsStatusXdslVdsl1AdvancedUsBitLoadingEntryBinNumber
          }
    ::= { lcsStatusXdslVdsl1AdvancedUsBitLoadingTable 1 }

LcsStatusXdslVdsl1AdvancedUsBitLoadingEntry ::= SEQUENCE {
            lcsStatusXdslVdsl1AdvancedUsBitLoadingEntryBinNumber DisplayString,
            lcsStatusXdslVdsl1AdvancedUsBitLoadingEntryX0 Integer32,
            lcsStatusXdslVdsl1AdvancedUsBitLoadingEntryX1 Integer32,
            lcsStatusXdslVdsl1AdvancedUsBitLoadingEntryX2 Integer32,
            lcsStatusXdslVdsl1AdvancedUsBitLoadingEntryX3 Integer32,
            lcsStatusXdslVdsl1AdvancedUsBitLoadingEntryX4 Integer32,
            lcsStatusXdslVdsl1AdvancedUsBitLoadingEntryX5 Integer32,
            lcsStatusXdslVdsl1AdvancedUsBitLoadingEntryX6 Integer32,
            lcsStatusXdslVdsl1AdvancedUsBitLoadingEntryX7 Integer32,
            lcsStatusXdslVdsl1AdvancedUsBitLoadingEntryX8 Integer32,
            lcsStatusXdslVdsl1AdvancedUsBitLoadingEntryX9 Integer32,
            lcsStatusXdslVdsl1AdvancedUsBitLoadingEntryGraph DisplayString
    }

-- {COLUMN} 1.3.6.1.4.1.2356.11.1.99.2.25.25.1.1
lcsStatusXdslVdsl1AdvancedUsBitLoadingEntryBinNumber OBJECT-TYPE
    SYNTAX     DisplayString (SIZE(0..255))
    MAX-ACCESS read-only
    STATUS     current
    DESCRIPTION
            "-- empty --"
    ::= { lcsStatusXdslVdsl1AdvancedUsBitLoadingEntry 1 }

-- {COLUMN} 1.3.6.1.4.1.2356.11.1.99.2.25.25.1.2
lcsStatusXdslVdsl1AdvancedUsBitLoadingEntryX0 OBJECT-TYPE
    SYNTAX     Integer32 (0..2147483647)
    MAX-ACCESS read-only
    STATUS     current
    DESCRIPTION
            "-- empty --"
    ::= { lcsStatusXdslVdsl1AdvancedUsBitLoadingEntry 2 }

-- {COLUMN} 1.3.6.1.4.1.2356.11.1.99.2.25.25.1.3
lcsStatusXdslVdsl1AdvancedUsBitLoadingEntryX1 OBJECT-TYPE
    SYNTAX     Integer32 (0..2147483647)
    MAX-ACCESS read-only
    STATUS     current
    DESCRIPTION
            "-- empty --"
    ::= { lcsStatusXdslVdsl1AdvancedUsBitLoadingEntry 3 }

-- {COLUMN} 1.3.6.1.4.1.2356.11.1.99.2.25.25.1.4
lcsStatusXdslVdsl1AdvancedUsBitLoadingEntryX2 OBJECT-TYPE
    SYNTAX     Integer32 (0..2147483647)
    MAX-ACCESS read-only
    STATUS     current
    DESCRIPTION
            "-- empty --"
    ::= { lcsStatusXdslVdsl1AdvancedUsBitLoadingEntry 4 }

-- {COLUMN} 1.3.6.1.4.1.2356.11.1.99.2.25.25.1.5
lcsStatusXdslVdsl1AdvancedUsBitLoadingEntryX3 OBJECT-TYPE
    SYNTAX     Integer32 (0..2147483647)
    MAX-ACCESS read-only
    STATUS     current
    DESCRIPTION
            "-- empty --"
    ::= { lcsStatusXdslVdsl1AdvancedUsBitLoadingEntry 5 }

-- {COLUMN} 1.3.6.1.4.1.2356.11.1.99.2.25.25.1.6
lcsStatusXdslVdsl1AdvancedUsBitLoadingEntryX4 OBJECT-TYPE
    SYNTAX     Integer32 (0..2147483647)
    MAX-ACCESS read-only
    STATUS     current
    DESCRIPTION
            "-- empty --"
    ::= { lcsStatusXdslVdsl1AdvancedUsBitLoadingEntry 6 }

-- {COLUMN} 1.3.6.1.4.1.2356.11.1.99.2.25.25.1.7
lcsStatusXdslVdsl1AdvancedUsBitLoadingEntryX5 OBJECT-TYPE
    SYNTAX     Integer32 (0..2147483647)
    MAX-ACCESS read-only
    STATUS     current
    DESCRIPTION
            "-- empty --"
    ::= { lcsStatusXdslVdsl1AdvancedUsBitLoadingEntry 7 }

-- {COLUMN} 1.3.6.1.4.1.2356.11.1.99.2.25.25.1.8
lcsStatusXdslVdsl1AdvancedUsBitLoadingEntryX6 OBJECT-TYPE
    SYNTAX     Integer32 (0..2147483647)
    MAX-ACCESS read-only
    STATUS     current
    DESCRIPTION
            "-- empty --"
    ::= { lcsStatusXdslVdsl1AdvancedUsBitLoadingEntry 8 }

-- {COLUMN} 1.3.6.1.4.1.2356.11.1.99.2.25.25.1.9
lcsStatusXdslVdsl1AdvancedUsBitLoadingEntryX7 OBJECT-TYPE
    SYNTAX     Integer32 (0..2147483647)
    MAX-ACCESS read-only
    STATUS     current
    DESCRIPTION
            "-- empty --"
    ::= { lcsStatusXdslVdsl1AdvancedUsBitLoadingEntry 9 }

-- {COLUMN} 1.3.6.1.4.1.2356.11.1.99.2.25.25.1.10
lcsStatusXdslVdsl1AdvancedUsBitLoadingEntryX8 OBJECT-TYPE
    SYNTAX     Integer32 (0..2147483647)
    MAX-ACCESS read-only
    STATUS     current
    DESCRIPTION
            "-- empty --"
    ::= { lcsStatusXdslVdsl1AdvancedUsBitLoadingEntry 10 }

-- {COLUMN} 1.3.6.1.4.1.2356.11.1.99.2.25.25.1.11
lcsStatusXdslVdsl1AdvancedUsBitLoadingEntryX9 OBJECT-TYPE
    SYNTAX     Integer32 (0..2147483647)
    MAX-ACCESS read-only
    STATUS     current
    DESCRIPTION
            "-- empty --"
    ::= { lcsStatusXdslVdsl1AdvancedUsBitLoadingEntry 11 }

-- {COLUMN} 1.3.6.1.4.1.2356.11.1.99.2.25.25.1.12
lcsStatusXdslVdsl1AdvancedUsBitLoadingEntryGraph OBJECT-TYPE
    SYNTAX     DisplayString (SIZE(0..255))
    MAX-ACCESS read-only
    STATUS     current
    DESCRIPTION
            "-- empty --"
    ::= { lcsStatusXdslVdsl1AdvancedUsBitLoadingEntry 12 }

-- {SCALAR} 1.3.6.1.4.1.2356.11.1.99.2.25.26
lcsStatusXdslVdsl1AdvancedRetrain OBJECT-TYPE
    SYNTAX     DisplayString
    MAX-ACCESS read-write
    STATUS     current
    DESCRIPTION
            "-- empty --"
    ::= { lcsStatusXdslVdsl1Advanced 26 }

-- {SCALAR} 1.3.6.1.4.1.2356.11.1.99.2.25.29
lcsStatusXdslVdsl1AdvancedTransmittedAtmCells OBJECT-TYPE
    SYNTAX     Integer32 (0..2147483647)
    MAX-ACCESS read-only
    STATUS     current
    DESCRIPTION
            "-- empty --"
    ::= { lcsStatusXdslVdsl1Advanced 29 }

-- {SCALAR} 1.3.6.1.4.1.2356.11.1.99.2.25.40
lcsStatusXdslVdsl1AdvancedVdslProfile OBJECT-TYPE
    SYNTAX     INTEGER {
                  eUnknown (0),
                  e8a (1),
                  e8b (2),
                  e8c (3),
                  e8d (4),
                  e12a (5),
                  e12b (6),
                  e17a (7),
                  e30a (8),
                  e35b (9)
            }
    MAX-ACCESS read-only
    STATUS     current
    DESCRIPTION
            "-- empty --"
    ::= { lcsStatusXdslVdsl1Advanced 40 }

-- {SCALAR} 1.3.6.1.4.1.2356.11.1.99.2.25.41
lcsStatusXdslVdsl1AdvancedDslamManufacturer OBJECT-TYPE
    SYNTAX     DisplayString (SIZE(0..63))
    MAX-ACCESS read-only
    STATUS     current
    DESCRIPTION
            "-- empty --"
    ::= { lcsStatusXdslVdsl1Advanced 41 }

-- {SCALAR} 1.3.6.1.4.1.2356.11.1.99.2.25.42
lcsStatusXdslVdsl1AdvancedDslamVersion OBJECT-TYPE
    SYNTAX     DisplayString (SIZE(0..34))
    MAX-ACCESS read-only
    STATUS     current
    DESCRIPTION
            "-- empty --"
    ::= { lcsStatusXdslVdsl1Advanced 42 }

-- {SCALAR} 1.3.6.1.4.1.2356.11.1.99.2.25.43
lcsStatusXdslVdsl1AdvancedDslamSerialNumber OBJECT-TYPE
    SYNTAX     DisplayString (SIZE(0..66))
    MAX-ACCESS read-only
    STATUS     current
    DESCRIPTION
            "-- empty --"
    ::= { lcsStatusXdslVdsl1Advanced 43 }

-- {SCALAR} 1.3.6.1.4.1.2356.11.1.99.2.25.44
lcsStatusXdslVdsl1AdvancedDslamChipsetManufacturer OBJECT-TYPE
    SYNTAX     DisplayString (SIZE(0..63))
    MAX-ACCESS read-only
    STATUS     current
    DESCRIPTION
            "-- empty --"
    ::= { lcsStatusXdslVdsl1Advanced 44 }

-- {SCALAR} 1.3.6.1.4.1.2356.11.1.99.2.25.45
lcsStatusXdslVdsl1AdvancedVectoringSupport OBJECT-TYPE
    SYNTAX     INTEGER {
                  eNo (1),
                  eYes (2),
                  eFriendly (3)
            }
    MAX-ACCESS read-only
    STATUS     current
    DESCRIPTION
            "-- empty --"
    ::= { lcsStatusXdslVdsl1Advanced 45 }

-- {SCALAR} 1.3.6.1.4.1.2356.11.1.99.2.25.46
lcsStatusXdslVdsl1AdvancedVectoring OBJECT-TYPE
    SYNTAX     INTEGER {
                  eNo (1),
                  eYes (2),
                  eFriendly (3)
            }
    MAX-ACCESS read-only
    STATUS     current
    DESCRIPTION
            "-- empty --"
    ::= { lcsStatusXdslVdsl1Advanced 46 }

-- {SCALAR} 1.3.6.1.4.1.2356.11.1.99.2.25.47
lcsStatusXdslVdsl1AdvancedDslamChipsetManufacturerDump OBJECT-TYPE
    SYNTAX     OCTET STRING
    MAX-ACCESS read-only
    STATUS     current
    DESCRIPTION
            "-- empty --"
    ::= { lcsStatusXdslVdsl1Advanced 47 }

-- {SCALAR} 1.3.6.1.4.1.2356.11.1.99.2.25.48
lcsStatusXdslVdsl1AdvancedDslamManufacturerDump OBJECT-TYPE
    SYNTAX     OCTET STRING
    MAX-ACCESS read-only
    STATUS     current
    DESCRIPTION
            "-- empty --"
    ::= { lcsStatusXdslVdsl1Advanced 48 }

-- {SCALAR} 1.3.6.1.4.1.2356.11.1.99.2.25.53
lcsStatusXdslVdsl1AdvancedConnectionCount OBJECT-TYPE
    SYNTAX     Integer32 (0..2147483647)
    MAX-ACCESS read-only
    STATUS     current
    DESCRIPTION
            "-- empty --"
    ::= { lcsStatusXdslVdsl1Advanced 53 }

-- {SCALAR} 1.3.6.1.4.1.2356.11.1.99.2.25.54
lcsStatusXdslVdsl1AdvancedConnectionDuration OBJECT-TYPE
    SYNTAX     Gauge32
    MAX-ACCESS read-only
    STATUS     current
    DESCRIPTION
            "-- empty --"
    ::= { lcsStatusXdslVdsl1Advanced 54 }

-- {SCALAR} 1.3.6.1.4.1.2356.11.1.99.2.25.100
lcsStatusXdslVdsl1AdvancedDsAttainableDataRateKbps OBJECT-TYPE
    SYNTAX     Integer32 (0..2147483647)
    MAX-ACCESS read-only
    STATUS     current
    DESCRIPTION
            "-- empty --"
    ::= { lcsStatusXdslVdsl1Advanced 100 }

-- {SCALAR} 1.3.6.1.4.1.2356.11.1.99.2.25.101
lcsStatusXdslVdsl1AdvancedDsInpSymbols OBJECT-TYPE
    SYNTAX     DisplayString (SIZE(0..3))
    MAX-ACCESS read-only
    STATUS     current
    DESCRIPTION
            "-- empty --"
    ::= { lcsStatusXdslVdsl1Advanced 101 }

-- {SCALAR} 1.3.6.1.4.1.2356.11.1.99.2.25.102
lcsStatusXdslVdsl1AdvancedDsCrcErrors OBJECT-TYPE
    SYNTAX     Integer32 (0..2147483647)
    MAX-ACCESS read-only
    STATUS     current
    DESCRIPTION
            "-- empty --"
    ::= { lcsStatusXdslVdsl1Advanced 102 }

-- {SCALAR} 1.3.6.1.4.1.2356.11.1.99.2.25.103
lcsStatusXdslVdsl1AdvancedDsFecErrors OBJECT-TYPE
    SYNTAX     Integer32 (0..2147483647)
    MAX-ACCESS read-only
    STATUS     current
    DESCRIPTION
            "-- empty --"
    ::= { lcsStatusXdslVdsl1Advanced 103 }

-- {SCALAR} 1.3.6.1.4.1.2356.11.1.99.2.25.104
lcsStatusXdslVdsl1AdvancedDsAtmHecErrors OBJECT-TYPE
    SYNTAX     Integer32 (0..2147483647)
    MAX-ACCESS read-only
    STATUS     current
    DESCRIPTION
            "-- empty --"
    ::= { lcsStatusXdslVdsl1Advanced 104 }

-- {SCALAR} 1.3.6.1.4.1.2356.11.1.99.2.25.105
lcsStatusXdslVdsl1AdvancedDsDataPathCrcpErrors OBJECT-TYPE
    SYNTAX     Integer32 (0..2147483647)
    MAX-ACCESS read-only
    STATUS     current
    DESCRIPTION
            "-- empty --"
    ::= { lcsStatusXdslVdsl1Advanced 105 }

-- {SCALAR} 1.3.6.1.4.1.2356.11.1.99.2.25.106
lcsStatusXdslVdsl1AdvancedDsDataPathCrcnpErrors OBJECT-TYPE
    SYNTAX     Integer32 (0..2147483647)
    MAX-ACCESS read-only
    STATUS     current
    DESCRIPTION
            "-- empty --"
    ::= { lcsStatusXdslVdsl1Advanced 106 }

-- {SCALAR} 1.3.6.1.4.1.2356.11.1.99.2.25.107
lcsStatusXdslVdsl1AdvancedDsDataPathCvpErrors OBJECT-TYPE
    SYNTAX     Integer32 (0..2147483647)
    MAX-ACCESS read-only
    STATUS     current
    DESCRIPTION
            "-- empty --"
    ::= { lcsStatusXdslVdsl1Advanced 107 }

-- {SCALAR} 1.3.6.1.4.1.2356.11.1.99.2.25.108
lcsStatusXdslVdsl1AdvancedDsDataPathCvnpErrors OBJECT-TYPE
    SYNTAX     Integer32 (0..2147483647)
    MAX-ACCESS read-only
    STATUS     current
    DESCRIPTION
            "-- empty --"
    ::= { lcsStatusXdslVdsl1Advanced 108 }

-- {SCALAR} 1.3.6.1.4.1.2356.11.1.99.2.25.109
lcsStatusXdslVdsl1AdvancedDsAtmIdleBitErrors OBJECT-TYPE
    SYNTAX     Integer32 (0..2147483647)
    MAX-ACCESS read-only
    STATUS     current
    DESCRIPTION
            "-- empty --"
    ::= { lcsStatusXdslVdsl1Advanced 109 }

-- {SCALAR} 1.3.6.1.4.1.2356.11.1.99.2.25.110
lcsStatusXdslVdsl1AdvancedDsAtmCells OBJECT-TYPE
    SYNTAX     Integer32 (0..2147483647)
    MAX-ACCESS read-only
    STATUS     current
    DESCRIPTION
            "-- empty --"
    ::= { lcsStatusXdslVdsl1Advanced 110 }

-- {SCALAR} 1.3.6.1.4.1.2356.11.1.99.2.25.120
lcsStatusXdslVdsl1AdvancedUsAttainableDataRateKbps OBJECT-TYPE
    SYNTAX     Integer32 (0..2147483647)
    MAX-ACCESS read-only
    STATUS     current
    DESCRIPTION
            "-- empty --"
    ::= { lcsStatusXdslVdsl1Advanced 120 }

-- {SCALAR} 1.3.6.1.4.1.2356.11.1.99.2.25.121
lcsStatusXdslVdsl1AdvancedUsInpSymbols OBJECT-TYPE
    SYNTAX     DisplayString (SIZE(0..3))
    MAX-ACCESS read-only
    STATUS     current
    DESCRIPTION
            "-- empty --"
    ::= { lcsStatusXdslVdsl1Advanced 121 }

-- {SCALAR} 1.3.6.1.4.1.2356.11.1.99.2.25.122
lcsStatusXdslVdsl1AdvancedUsCrcErrors OBJECT-TYPE
    SYNTAX     Integer32 (0..2147483647)
    MAX-ACCESS read-only
    STATUS     current
    DESCRIPTION
            "-- empty --"
    ::= { lcsStatusXdslVdsl1Advanced 122 }

-- {SCALAR} 1.3.6.1.4.1.2356.11.1.99.2.25.123
lcsStatusXdslVdsl1AdvancedUsFecErrors OBJECT-TYPE
    SYNTAX     Integer32 (0..2147483647)
    MAX-ACCESS read-only
    STATUS     current
    DESCRIPTION
            "-- empty --"
    ::= { lcsStatusXdslVdsl1Advanced 123 }

-- {SCALAR} 1.3.6.1.4.1.2356.11.1.99.2.25.124
lcsStatusXdslVdsl1AdvancedUsAtmHecErrors OBJECT-TYPE
    SYNTAX     Integer32 (0..2147483647)
    MAX-ACCESS read-only
    STATUS     current
    DESCRIPTION
            "-- empty --"
    ::= { lcsStatusXdslVdsl1Advanced 124 }

-- {SCALAR} 1.3.6.1.4.1.2356.11.1.99.2.25.125
lcsStatusXdslVdsl1AdvancedUsDataPathCrcpErrors OBJECT-TYPE
    SYNTAX     Integer32 (0..2147483647)
    MAX-ACCESS read-only
    STATUS     current
    DESCRIPTION
            "-- empty --"
    ::= { lcsStatusXdslVdsl1Advanced 125 }

-- {SCALAR} 1.3.6.1.4.1.2356.11.1.99.2.25.126
lcsStatusXdslVdsl1AdvancedUsDataPathCrcnpErrors OBJECT-TYPE
    SYNTAX     Integer32 (0..2147483647)
    MAX-ACCESS read-only
    STATUS     current
    DESCRIPTION
            "-- empty --"
    ::= { lcsStatusXdslVdsl1Advanced 126 }

-- {SCALAR} 1.3.6.1.4.1.2356.11.1.99.2.25.127
lcsStatusXdslVdsl1AdvancedUsDataPathCvpErrors OBJECT-TYPE
    SYNTAX     Integer32 (0..2147483647)
    MAX-ACCESS read-only
    STATUS     current
    DESCRIPTION
            "-- empty --"
    ::= { lcsStatusXdslVdsl1Advanced 127 }

-- {SCALAR} 1.3.6.1.4.1.2356.11.1.99.2.25.128
lcsStatusXdslVdsl1AdvancedUsDataPathCvnpErrors OBJECT-TYPE
    SYNTAX     Integer32 (0..2147483647)
    MAX-ACCESS read-only
    STATUS     current
    DESCRIPTION
            "-- empty --"
    ::= { lcsStatusXdslVdsl1Advanced 128 }

-- {SCALAR} 1.3.6.1.4.1.2356.11.1.99.2.25.129
lcsStatusXdslVdsl1AdvancedUsAtmIdleBitErrors OBJECT-TYPE
    SYNTAX     Integer32 (0..2147483647)
    MAX-ACCESS read-only
    STATUS     current
    DESCRIPTION
            "-- empty --"
    ::= { lcsStatusXdslVdsl1Advanced 129 }

-- {SCALAR} 1.3.6.1.4.1.2356.11.1.99.2.25.130
lcsStatusXdslVdsl1AdvancedUsAtmCells OBJECT-TYPE
    SYNTAX     Integer32 (0..2147483647)
    MAX-ACCESS read-only
    STATUS     current
    DESCRIPTION
            "-- empty --"
    ::= { lcsStatusXdslVdsl1Advanced 130 }

-- {SCALAR} 1.3.6.1.4.1.2356.11.1.99.2.25.140
lcsStatusXdslVdsl1AdvancedWanTxPacketCount OBJECT-TYPE
    SYNTAX     Integer32 (0..2147483647)
    MAX-ACCESS read-only
    STATUS     current
    DESCRIPTION
            "-- empty --"
    ::= { lcsStatusXdslVdsl1Advanced 140 }

-- {SCALAR} 1.3.6.1.4.1.2356.11.1.99.2.25.141
lcsStatusXdslVdsl1AdvancedWanTxPacketBytes OBJECT-TYPE
    SYNTAX     Integer32 (0..2147483647)
    MAX-ACCESS read-only
    STATUS     current
    DESCRIPTION
            "-- empty --"
    ::= { lcsStatusXdslVdsl1Advanced 141 }

-- {SCALAR} 1.3.6.1.4.1.2356.11.1.99.2.25.142
lcsStatusXdslVdsl1AdvancedWanTxPacketErrors OBJECT-TYPE
    SYNTAX     Integer32 (0..2147483647)
    MAX-ACCESS read-only
    STATUS     current
    DESCRIPTION
            "-- empty --"
    ::= { lcsStatusXdslVdsl1Advanced 142 }

-- {SCALAR} 1.3.6.1.4.1.2356.11.1.99.2.25.143
lcsStatusXdslVdsl1AdvancedWanTxPacketDrops OBJECT-TYPE
    SYNTAX     Integer32 (0..2147483647)
    MAX-ACCESS read-only
    STATUS     current
    DESCRIPTION
            "-- empty --"
    ::= { lcsStatusXdslVdsl1Advanced 143 }

-- {SCALAR} 1.3.6.1.4.1.2356.11.1.99.2.25.144
lcsStatusXdslVdsl1AdvancedWanTxOverruns OBJECT-TYPE
    SYNTAX     Integer32 (0..2147483647)
    MAX-ACCESS read-only
    STATUS     current
    DESCRIPTION
            "-- empty --"
    ::= { lcsStatusXdslVdsl1Advanced 144 }

-- {SCALAR} 1.3.6.1.4.1.2356.11.1.99.2.25.146
lcsStatusXdslVdsl1AdvancedTxPacketCount OBJECT-TYPE
    SYNTAX     Integer32 (0..2147483647)
    MAX-ACCESS read-only
    STATUS     current
    DESCRIPTION
            "-- empty --"
    ::= { lcsStatusXdslVdsl1Advanced 146 }

-- {SCALAR} 1.3.6.1.4.1.2356.11.1.99.2.25.148
lcsStatusXdslVdsl1AdvancedUsLineOptions OBJECT-TYPE
    SYNTAX     BITS {
                  eBitswap (4),
                  eTrellis (5),
                  eVirtualNoise (6),
                  eRetransmission (7)
            }
    MAX-ACCESS read-only
    STATUS     current
    DESCRIPTION
            "-- empty --"
    ::= { lcsStatusXdslVdsl1Advanced 148 }

-- {SCALAR} 1.3.6.1.4.1.2356.11.1.99.2.25.149
lcsStatusXdslVdsl1AdvancedTx-Packet-count-64 OBJECT-TYPE
    SYNTAX     Integer32 (0..2147483647)
    MAX-ACCESS read-only
    STATUS     current
    DESCRIPTION
            ""
    ::= { lcsStatusXdslVdsl1Advanced 149 }

-- {SCALAR} 1.3.6.1.4.1.2356.11.1.99.2.25.150
lcsStatusXdslVdsl1AdvancedWanRxPacketCount OBJECT-TYPE
    SYNTAX     Integer32 (0..2147483647)
    MAX-ACCESS read-only
    STATUS     current
    DESCRIPTION
            "-- empty --"
    ::= { lcsStatusXdslVdsl1Advanced 150 }

-- {SCALAR} 1.3.6.1.4.1.2356.11.1.99.2.25.151
lcsStatusXdslVdsl1AdvancedWanRxPacketBytes OBJECT-TYPE
    SYNTAX     Integer32 (0..2147483647)
    MAX-ACCESS read-only
    STATUS     current
    DESCRIPTION
            "-- empty --"
    ::= { lcsStatusXdslVdsl1Advanced 151 }

-- {SCALAR} 1.3.6.1.4.1.2356.11.1.99.2.25.152
lcsStatusXdslVdsl1AdvancedWanRxPacketErrors OBJECT-TYPE
    SYNTAX     Integer32 (0..2147483647)
    MAX-ACCESS read-only
    STATUS     current
    DESCRIPTION
            "-- empty --"
    ::= { lcsStatusXdslVdsl1Advanced 152 }

-- {SCALAR} 1.3.6.1.4.1.2356.11.1.99.2.25.153
lcsStatusXdslVdsl1AdvancedWanRxPacketDrops OBJECT-TYPE
    SYNTAX     Integer32 (0..2147483647)
    MAX-ACCESS read-only
    STATUS     current
    DESCRIPTION
            "-- empty --"
    ::= { lcsStatusXdslVdsl1Advanced 153 }

-- {SCALAR} 1.3.6.1.4.1.2356.11.1.99.2.25.154
lcsStatusXdslVdsl1AdvancedWanRxOverruns OBJECT-TYPE
    SYNTAX     Integer32 (0..2147483647)
    MAX-ACCESS read-only
    STATUS     current
    DESCRIPTION
            "-- empty --"
    ::= { lcsStatusXdslVdsl1Advanced 154 }

-- {SCALAR} 1.3.6.1.4.1.2356.11.1.99.2.25.156
lcsStatusXdslVdsl1AdvancedRxPacketCount OBJECT-TYPE
    SYNTAX     Integer32 (0..2147483647)
    MAX-ACCESS read-only
    STATUS     current
    DESCRIPTION
            "-- empty --"
    ::= { lcsStatusXdslVdsl1Advanced 156 }

-- {TABLE} 1.3.6.1.4.1.2356.11.1.99.2.25.157
lcsStatusXdslVdsl1AdvancedDsSnrPerSubCarrierTable OBJECT-TYPE
    SYNTAX     SEQUENCE OF LcsStatusXdslVdsl1AdvancedDsSnrPerSubCarrierEntry
    MAX-ACCESS not-accessible
    STATUS     current
    DESCRIPTION
            "-- empty --"
    ::= { lcsStatusXdslVdsl1Advanced 157 }

-- {ROW} 1.3.6.1.4.1.2356.11.1.99.2.25.157.1
lcsStatusXdslVdsl1AdvancedDsSnrPerSubCarrierEntry OBJECT-TYPE
    SYNTAX     LcsStatusXdslVdsl1AdvancedDsSnrPerSubCarrierEntry
    MAX-ACCESS not-accessible
    STATUS     current
    DESCRIPTION
            ""
    INDEX {
            lcsStatusXdslVdsl1AdvancedDsSnrPerSubCarrierEntrySubCarrier
          }
    ::= { lcsStatusXdslVdsl1AdvancedDsSnrPerSubCarrierTable 1 }

LcsStatusXdslVdsl1AdvancedDsSnrPerSubCarrierEntry ::= SEQUENCE {
            lcsStatusXdslVdsl1AdvancedDsSnrPerSubCarrierEntrySubCarrier DisplayString,
            lcsStatusXdslVdsl1AdvancedDsSnrPerSubCarrierEntryX0 Integer32,
            lcsStatusXdslVdsl1AdvancedDsSnrPerSubCarrierEntryX1 Integer32,
            lcsStatusXdslVdsl1AdvancedDsSnrPerSubCarrierEntryX2 Integer32,
            lcsStatusXdslVdsl1AdvancedDsSnrPerSubCarrierEntryX3 Integer32,
            lcsStatusXdslVdsl1AdvancedDsSnrPerSubCarrierEntryX4 Integer32,
            lcsStatusXdslVdsl1AdvancedDsSnrPerSubCarrierEntryX5 Integer32,
            lcsStatusXdslVdsl1AdvancedDsSnrPerSubCarrierEntryX6 Integer32,
            lcsStatusXdslVdsl1AdvancedDsSnrPerSubCarrierEntryX7 Integer32,
            lcsStatusXdslVdsl1AdvancedDsSnrPerSubCarrierEntryX8 Integer32,
            lcsStatusXdslVdsl1AdvancedDsSnrPerSubCarrierEntryX9 Integer32
    }

-- {COLUMN} 1.3.6.1.4.1.2356.11.1.99.2.25.157.1.1
lcsStatusXdslVdsl1AdvancedDsSnrPerSubCarrierEntrySubCarrier OBJECT-TYPE
    SYNTAX     DisplayString (SIZE(0..255))
    MAX-ACCESS read-only
    STATUS     current
    DESCRIPTION
            "-- empty --"
    ::= { lcsStatusXdslVdsl1AdvancedDsSnrPerSubCarrierEntry 1 }

-- {COLUMN} 1.3.6.1.4.1.2356.11.1.99.2.25.157.1.2
lcsStatusXdslVdsl1AdvancedDsSnrPerSubCarrierEntryX0 OBJECT-TYPE
    SYNTAX     Integer32 (0..2147483647)
    MAX-ACCESS read-only
    STATUS     current
    DESCRIPTION
            "-- empty --"
    ::= { lcsStatusXdslVdsl1AdvancedDsSnrPerSubCarrierEntry 2 }

-- {COLUMN} 1.3.6.1.4.1.2356.11.1.99.2.25.157.1.3
lcsStatusXdslVdsl1AdvancedDsSnrPerSubCarrierEntryX1 OBJECT-TYPE
    SYNTAX     Integer32 (0..2147483647)
    MAX-ACCESS read-only
    STATUS     current
    DESCRIPTION
            "-- empty --"
    ::= { lcsStatusXdslVdsl1AdvancedDsSnrPerSubCarrierEntry 3 }

-- {COLUMN} 1.3.6.1.4.1.2356.11.1.99.2.25.157.1.4
lcsStatusXdslVdsl1AdvancedDsSnrPerSubCarrierEntryX2 OBJECT-TYPE
    SYNTAX     Integer32 (0..2147483647)
    MAX-ACCESS read-only
    STATUS     current
    DESCRIPTION
            "-- empty --"
    ::= { lcsStatusXdslVdsl1AdvancedDsSnrPerSubCarrierEntry 4 }

-- {COLUMN} 1.3.6.1.4.1.2356.11.1.99.2.25.157.1.5
lcsStatusXdslVdsl1AdvancedDsSnrPerSubCarrierEntryX3 OBJECT-TYPE
    SYNTAX     Integer32 (0..2147483647)
    MAX-ACCESS read-only
    STATUS     current
    DESCRIPTION
            "-- empty --"
    ::= { lcsStatusXdslVdsl1AdvancedDsSnrPerSubCarrierEntry 5 }

-- {COLUMN} 1.3.6.1.4.1.2356.11.1.99.2.25.157.1.6
lcsStatusXdslVdsl1AdvancedDsSnrPerSubCarrierEntryX4 OBJECT-TYPE
    SYNTAX     Integer32 (0..2147483647)
    MAX-ACCESS read-only
    STATUS     current
    DESCRIPTION
            "-- empty --"
    ::= { lcsStatusXdslVdsl1AdvancedDsSnrPerSubCarrierEntry 6 }

-- {COLUMN} 1.3.6.1.4.1.2356.11.1.99.2.25.157.1.7
lcsStatusXdslVdsl1AdvancedDsSnrPerSubCarrierEntryX5 OBJECT-TYPE
    SYNTAX     Integer32 (0..2147483647)
    MAX-ACCESS read-only
    STATUS     current
    DESCRIPTION
            "-- empty --"
    ::= { lcsStatusXdslVdsl1AdvancedDsSnrPerSubCarrierEntry 7 }

-- {COLUMN} 1.3.6.1.4.1.2356.11.1.99.2.25.157.1.8
lcsStatusXdslVdsl1AdvancedDsSnrPerSubCarrierEntryX6 OBJECT-TYPE
    SYNTAX     Integer32 (0..2147483647)
    MAX-ACCESS read-only
    STATUS     current
    DESCRIPTION
            "-- empty --"
    ::= { lcsStatusXdslVdsl1AdvancedDsSnrPerSubCarrierEntry 8 }

-- {COLUMN} 1.3.6.1.4.1.2356.11.1.99.2.25.157.1.9
lcsStatusXdslVdsl1AdvancedDsSnrPerSubCarrierEntryX7 OBJECT-TYPE
    SYNTAX     Integer32 (0..2147483647)
    MAX-ACCESS read-only
    STATUS     current
    DESCRIPTION
            "-- empty --"
    ::= { lcsStatusXdslVdsl1AdvancedDsSnrPerSubCarrierEntry 9 }

-- {COLUMN} 1.3.6.1.4.1.2356.11.1.99.2.25.157.1.10
lcsStatusXdslVdsl1AdvancedDsSnrPerSubCarrierEntryX8 OBJECT-TYPE
    SYNTAX     Integer32 (0..2147483647)
    MAX-ACCESS read-only
    STATUS     current
    DESCRIPTION
            "-- empty --"
    ::= { lcsStatusXdslVdsl1AdvancedDsSnrPerSubCarrierEntry 10 }

-- {COLUMN} 1.3.6.1.4.1.2356.11.1.99.2.25.157.1.11
lcsStatusXdslVdsl1AdvancedDsSnrPerSubCarrierEntryX9 OBJECT-TYPE
    SYNTAX     Integer32 (0..2147483647)
    MAX-ACCESS read-only
    STATUS     current
    DESCRIPTION
            "-- empty --"
    ::= { lcsStatusXdslVdsl1AdvancedDsSnrPerSubCarrierEntry 11 }

-- {SCALAR} 1.3.6.1.4.1.2356.11.1.99.2.25.158
lcsStatusXdslVdsl1AdvancedDsLineOptions OBJECT-TYPE
    SYNTAX     BITS {
                  eBitswap (4),
                  eTrellis (5),
                  eVirtualNoise (6),
                  eRetransmission (7)
            }
    MAX-ACCESS read-only
    STATUS     current
    DESCRIPTION
            "-- empty --"
    ::= { lcsStatusXdslVdsl1Advanced 158 }

-- {SCALAR} 1.3.6.1.4.1.2356.11.1.99.2.25.159
lcsStatusXdslVdsl1AdvancedRx-Packet-count-64 OBJECT-TYPE
    SYNTAX     Integer32 (0..2147483647)
    MAX-ACCESS read-only
    STATUS     current
    DESCRIPTION
            ""
    ::= { lcsStatusXdslVdsl1Advanced 159 }

-- {SCALAR} 1.3.6.1.4.1.2356.11.1.99.2.25.160
lcsStatusXdslVdsl1AdvancedWAN-Tx-Packet-count-64 OBJECT-TYPE
    SYNTAX     Integer32 (0..2147483647)
    MAX-ACCESS read-only
    STATUS     current
    DESCRIPTION
            ""
    ::= { lcsStatusXdslVdsl1Advanced 160 }

-- {SCALAR} 1.3.6.1.4.1.2356.11.1.99.2.25.161
lcsStatusXdslVdsl1AdvancedWAN-Tx-Packet-bytes-64 OBJECT-TYPE
    SYNTAX     Integer32 (0..2147483647)
    MAX-ACCESS read-only
    STATUS     current
    DESCRIPTION
            ""
    ::= { lcsStatusXdslVdsl1Advanced 161 }

-- {SCALAR} 1.3.6.1.4.1.2356.11.1.99.2.25.170
lcsStatusXdslVdsl1AdvancedWAN-Rx-Packet-count-64 OBJECT-TYPE
    SYNTAX     Integer32 (0..2147483647)
    MAX-ACCESS read-only
    STATUS     current
    DESCRIPTION
            ""
    ::= { lcsStatusXdslVdsl1Advanced 170 }

-- {SCALAR} 1.3.6.1.4.1.2356.11.1.99.2.25.171
lcsStatusXdslVdsl1AdvancedWAN-Rx-Packet-bytes-64 OBJECT-TYPE
    SYNTAX     Integer32 (0..2147483647)
    MAX-ACCESS read-only
    STATUS     current
    DESCRIPTION
            ""
    ::= { lcsStatusXdslVdsl1Advanced 171 }

-- {SCALAR} 1.3.6.1.4.1.2356.11.1.99.2.34
lcsStatusXdslVdsl1InpDownstreamSymbols OBJECT-TYPE
    SYNTAX     DisplayString (SIZE(0..3))
    MAX-ACCESS read-only
    STATUS     current
    DESCRIPTION
            "-- empty --"
    ::= { lcsStatusXdslVdsl1 34 }

-- {SCALAR} 1.3.6.1.4.1.2356.11.1.99.2.35
lcsStatusXdslVdsl1InpUpstreamSymbols OBJECT-TYPE
    SYNTAX     DisplayString (SIZE(0..3))
    MAX-ACCESS read-only
    STATUS     current
    DESCRIPTION
            "-- empty --"
    ::= { lcsStatusXdslVdsl1 35 }

-- {SCALAR} 1.3.6.1.4.1.2356.11.1.99.2.36
lcsStatusXdslVdsl1AttainableDataRateDownstreamKbps OBJECT-TYPE
    SYNTAX     Integer32 (0..2147483647)
    MAX-ACCESS read-only
    STATUS     current
    DESCRIPTION
            "-- empty --"
    ::= { lcsStatusXdslVdsl1 36 }

-- {SCALAR} 1.3.6.1.4.1.2356.11.1.99.2.37
lcsStatusXdslVdsl1AttainableDataRateUpstreamKbps OBJECT-TYPE
    SYNTAX     Integer32 (0..2147483647)
    MAX-ACCESS read-only
    STATUS     current
    DESCRIPTION
            "-- empty --"
    ::= { lcsStatusXdslVdsl1 37 }

-- {SCALAR} 1.3.6.1.4.1.2356.11.1.99.2.40
lcsStatusXdslVdsl1VdslProfile OBJECT-TYPE
    SYNTAX     INTEGER {
                  eUnknown (0),
                  e8a (1),
                  e8b (2),
                  e8c (3),
                  e8d (4),
                  e12a (5),
                  e12b (6),
                  e17a (7),
                  e30a (8),
                  e35b (9)
            }
    MAX-ACCESS read-only
    STATUS     current
    DESCRIPTION
            "-- empty --"
    ::= { lcsStatusXdslVdsl1 40 }

-- {SCALAR} 1.3.6.1.4.1.2356.11.1.99.2.41
lcsStatusXdslVdsl1DslamManufacturer OBJECT-TYPE
    SYNTAX     DisplayString (SIZE(0..63))
    MAX-ACCESS read-only
    STATUS     current
    DESCRIPTION
            "-- empty --"
    ::= { lcsStatusXdslVdsl1 41 }

-- {SCALAR} 1.3.6.1.4.1.2356.11.1.99.2.42
lcsStatusXdslVdsl1DslamVersion OBJECT-TYPE
    SYNTAX     DisplayString (SIZE(0..34))
    MAX-ACCESS read-only
    STATUS     current
    DESCRIPTION
            "-- empty --"
    ::= { lcsStatusXdslVdsl1 42 }

-- {SCALAR} 1.3.6.1.4.1.2356.11.1.99.2.43
lcsStatusXdslVdsl1DslamSerialNumber OBJECT-TYPE
    SYNTAX     DisplayString (SIZE(0..66))
    MAX-ACCESS read-only
    STATUS     current
    DESCRIPTION
            "-- empty --"
    ::= { lcsStatusXdslVdsl1 43 }

-- {SCALAR} 1.3.6.1.4.1.2356.11.1.99.2.45
lcsStatusXdslVdsl1VectoringSupport OBJECT-TYPE
    SYNTAX     INTEGER {
                  eNo (1),
                  eYes (2),
                  eFriendly (3)
            }
    MAX-ACCESS read-only
    STATUS     current
    DESCRIPTION
            "-- empty --"
    ::= { lcsStatusXdslVdsl1 45 }

-- {SCALAR} 1.3.6.1.4.1.2356.11.1.99.2.46
lcsStatusXdslVdsl1Vectoring OBJECT-TYPE
    SYNTAX     INTEGER {
                  eNo (1),
                  eYes (2),
                  eFriendly (3)
            }
    MAX-ACCESS read-only
    STATUS     current
    DESCRIPTION
            "-- empty --"
    ::= { lcsStatusXdslVdsl1 46 }

-- {SCALAR} 1.3.6.1.4.1.2356.11.1.99.2.53
lcsStatusXdslVdsl1ConnectionCount OBJECT-TYPE
    SYNTAX     Integer32 (0..2147483647)
    MAX-ACCESS read-only
    STATUS     current
    DESCRIPTION
            "-- empty --"
    ::= { lcsStatusXdslVdsl1 53 }

-- {SCALAR} 1.3.6.1.4.1.2356.11.1.99.2.54
lcsStatusXdslVdsl1ConnectionDuration OBJECT-TYPE
    SYNTAX     Gauge32
    MAX-ACCESS read-only
    STATUS     current
    DESCRIPTION
            "-- empty --"
    ::= { lcsStatusXdslVdsl1 54 }

-- {SCALAR} 1.3.6.1.4.1.2356.11.1.99.2.200
lcsStatusXdslVdsl1WanBridge OBJECT-TYPE
    SYNTAX     INTEGER {
                  eNo (0),
                  eYes (1)
            }
    MAX-ACCESS read-only
    STATUS     current
    DESCRIPTION
            "-- empty --"
    ::= { lcsStatusXdslVdsl1 200 }

-- {NODE} 1.3.6.1.4.1.2356.11.1.99.2.500
lcsStatusXdslVdsl1Modem OBJECT IDENTIFIER ::= { lcsStatusXdslVdsl1 500 }

-- {SCALAR} 1.3.6.1.4.1.2356.11.1.99.2.500.1
lcsStatusXdslVdsl1ModemModemState OBJECT-TYPE
    SYNTAX     INTEGER {
                  eNoCommunicationsPort (0),
                  eError (1),
                  eFileSystem (2),
                  eBootHeader (3),
                  eUploadingBootstrap (4),
                  eUploadingMemoryTest (5),
                  eMemoryTest (6),
                  eOptions (7),
                  eUploadingUBoot (8),
                  eQuickMemoryTest (9),
                  eUploadingKernel (10),
                  eUploadingRamdisk (11),
                  eUploadingFirmware (12),
                  eWaitForHeartbeat (13),
                  eRunning (14),
                  eUploadingGphyFirmware (15),
                  eDisabled (16)
            }
    MAX-ACCESS read-only
    STATUS     current
    DESCRIPTION
            "-- empty --"
    ::= { lcsStatusXdslVdsl1Modem 1 }

-- {SCALAR} 1.3.6.1.4.1.2356.11.1.99.2.500.2
lcsStatusXdslVdsl1ModemOptions OBJECT-TYPE
    SYNTAX     Integer32 (0..255)
    MAX-ACCESS read-only
    STATUS     current
    DESCRIPTION
            "-- empty --"
    ::= { lcsStatusXdslVdsl1Modem 2 }

-- {SCALAR} 1.3.6.1.4.1.2356.11.1.99.2.500.3
lcsStatusXdslVdsl1ModemMemoryTest OBJECT-TYPE
    SYNTAX     INTEGER {
                  eNotTested (0),
                  eTimeout (1),
                  eFailed (2),
                  eOk (3)
            }
    MAX-ACCESS read-only
    STATUS     current
    DESCRIPTION
            "-- empty --"
    ::= { lcsStatusXdslVdsl1Modem 3 }

-- {SCALAR} 1.3.6.1.4.1.2356.11.1.99.2.500.4
lcsStatusXdslVdsl1ModemRebootModem OBJECT-TYPE
    SYNTAX     DisplayString
    MAX-ACCESS read-write
    STATUS     current
    DESCRIPTION
            "-- empty --"
    ::= { lcsStatusXdslVdsl1Modem 4 }

-- {SCALAR} 1.3.6.1.4.1.2356.11.1.99.2.500.5
lcsStatusXdslVdsl1ModemLink OBJECT-TYPE
    SYNTAX     Integer32 (0..2147483647)
    MAX-ACCESS read-only
    STATUS     current
    DESCRIPTION
            "-- empty --"
    ::= { lcsStatusXdslVdsl1Modem 5 }

-- {SCALAR} 1.3.6.1.4.1.2356.11.1.99.2.500.6
lcsStatusXdslVdsl1ModemLastError OBJECT-TYPE
    SYNTAX     DisplayString (SIZE(0..63))
    MAX-ACCESS read-only
    STATUS     current
    DESCRIPTION
            "-- empty --"
    ::= { lcsStatusXdslVdsl1Modem 6 }

-- {SCALAR} 1.3.6.1.4.1.2356.11.1.99.2.500.10
lcsStatusXdslVdsl1ModemDslApiVersion OBJECT-TYPE
    SYNTAX     DisplayString (SIZE(0..31))
    MAX-ACCESS read-only
    STATUS     current
    DESCRIPTION
            "-- empty --"
    ::= { lcsStatusXdslVdsl1Modem 10 }

-- {SCALAR} 1.3.6.1.4.1.2356.11.1.99.2.500.11
lcsStatusXdslVdsl1ModemDspFirmwareVersion OBJECT-TYPE
    SYNTAX     DisplayString (SIZE(0..31))
    MAX-ACCESS read-only
    STATUS     current
    DESCRIPTION
            "-- empty --"
    ::= { lcsStatusXdslVdsl1Modem 11 }

-- {SCALAR} 1.3.6.1.4.1.2356.11.1.99.2.500.12
lcsStatusXdslVdsl1ModemHardwareVersion OBJECT-TYPE
    SYNTAX     DisplayString (SIZE(0..31))
    MAX-ACCESS read-only
    STATUS     current
    DESCRIPTION
            "-- empty --"
    ::= { lcsStatusXdslVdsl1Modem 12 }

-- {SCALAR} 1.3.6.1.4.1.2356.11.1.99.2.500.13
lcsStatusXdslVdsl1ModemChipsetType OBJECT-TYPE
    SYNTAX     DisplayString (SIZE(0..31))
    MAX-ACCESS read-only
    STATUS     current
    DESCRIPTION
            "-- empty --"
    ::= { lcsStatusXdslVdsl1Modem 13 }

-- {SCALAR} 1.3.6.1.4.1.2356.11.1.99.2.500.14
lcsStatusXdslVdsl1ModemDriverVersion OBJECT-TYPE
    SYNTAX     DisplayString (SIZE(0..31))
    MAX-ACCESS read-only
    STATUS     current
    DESCRIPTION
            "-- empty --"
    ::= { lcsStatusXdslVdsl1Modem 14 }

-- {SCALAR} 1.3.6.1.4.1.2356.11.1.99.2.500.15
lcsStatusXdslVdsl1ModemBootCount OBJECT-TYPE
    SYNTAX     Integer32 (0..2147483647)
    MAX-ACCESS read-only
    STATUS     current
    DESCRIPTION
            "-- empty --"
    ::= { lcsStatusXdslVdsl1Modem 15 }

-- {SCALAR} 1.3.6.1.4.1.2356.11.1.99.2.500.16
lcsStatusXdslVdsl1ModemHybrid OBJECT-TYPE
    SYNTAX     INTEGER {
                  eBJ (0),
                  eInvalid (1),
                  eB (2),
                  eA (3),
                  eUniversal (4),
                  eUnknown (256)
            }
    MAX-ACCESS read-only
    STATUS     current
    DESCRIPTION
            "-- empty --"
    ::= { lcsStatusXdslVdsl1Modem 16 }

-- {SCALAR} 1.3.6.1.4.1.2356.11.1.99.2.500.21
lcsStatusXdslVdsl1ModemLoad OBJECT-TYPE
    SYNTAX     Integer32 (0..2147483647)
    MAX-ACCESS read-only
    STATUS     current
    DESCRIPTION
            "-- empty --"
    ::= { lcsStatusXdslVdsl1Modem 21 }

-- {SCALAR} 1.3.6.1.4.1.2356.11.1.99.2.500.22
lcsStatusXdslVdsl1ModemLoadUser OBJECT-TYPE
    SYNTAX     Integer32 (0..2147483647)
    MAX-ACCESS read-only
    STATUS     current
    DESCRIPTION
            "-- empty --"
    ::= { lcsStatusXdslVdsl1Modem 22 }

-- {SCALAR} 1.3.6.1.4.1.2356.11.1.99.2.500.23
lcsStatusXdslVdsl1ModemLoadSystem OBJECT-TYPE
    SYNTAX     Integer32 (0..2147483647)
    MAX-ACCESS read-only
    STATUS     current
    DESCRIPTION
            "-- empty --"
    ::= { lcsStatusXdslVdsl1Modem 23 }

-- {SCALAR} 1.3.6.1.4.1.2356.11.1.99.2.500.24
lcsStatusXdslVdsl1ModemLoadIdle OBJECT-TYPE
    SYNTAX     Integer32 (0..2147483647)
    MAX-ACCESS read-only
    STATUS     current
    DESCRIPTION
            "-- empty --"
    ::= { lcsStatusXdslVdsl1Modem 24 }

-- {SCALAR} 1.3.6.1.4.1.2356.11.1.99.2.500.25
lcsStatusXdslVdsl1ModemPotsFirmware OBJECT-TYPE
    SYNTAX     DisplayString (SIZE(0..71))
    MAX-ACCESS read-only
    STATUS     current
    DESCRIPTION
            "-- empty --"
    ::= { lcsStatusXdslVdsl1Modem 25 }

-- {SCALAR} 1.3.6.1.4.1.2356.11.1.99.2.500.26
lcsStatusXdslVdsl1ModemIsdnFirmware OBJECT-TYPE
    SYNTAX     DisplayString (SIZE(0..71))
    MAX-ACCESS read-only
    STATUS     current
    DESCRIPTION
            "-- empty --"
    ::= { lcsStatusXdslVdsl1Modem 26 }

-- {SCALAR} 1.3.6.1.4.1.2356.11.1.99.2.500.27
lcsStatusXdslVdsl1ModemTemperatureDegc OBJECT-TYPE
    SYNTAX     DisplayString (SIZE(0..3))
    MAX-ACCESS read-only
    STATUS     current
    DESCRIPTION
            "-- empty --"
    ::= { lcsStatusXdslVdsl1Modem 27 }

-- {SCALAR} 1.3.6.1.4.1.2356.11.1.99.2.500.28
lcsStatusXdslVdsl1ModemWanAcceleration OBJECT-TYPE
    SYNTAX     INTEGER {
                  eNo (0),
                  eYes (1)
            }
    MAX-ACCESS read-only
    STATUS     current
    DESCRIPTION
            "-- empty --"
    ::= { lcsStatusXdslVdsl1Modem 28 }

-- {NODE} 1.3.6.1.4.1.2356.11.1.99.3
lcsStatusXdslVdsl2 OBJECT IDENTIFIER ::= { lcsStatusXdsl 3 }

-- {SCALAR} 1.3.6.1.4.1.2356.11.1.99.3.1
lcsStatusXdslVdsl2LineState OBJECT-TYPE
    SYNTAX     INTEGER {
                  eUnknown (0),
                  eDown (1),
                  eIdle (2),
                  eHandshake (3),
                  eTraining (4),
                  eShowtime (5),
                  eShutdown (6)
            }
    MAX-ACCESS read-only
    STATUS     current
    DESCRIPTION
            "-- empty --"
    ::= { lcsStatusXdslVdsl2 1 }

-- {SCALAR} 1.3.6.1.4.1.2356.11.1.99.3.2
lcsStatusXdslVdsl2LineType OBJECT-TYPE
    SYNTAX     DisplayString (SIZE(0..3))
    MAX-ACCESS read-only
    STATUS     current
    DESCRIPTION
            "-- empty --"
    ::= { lcsStatusXdslVdsl2 2 }

-- {SCALAR} 1.3.6.1.4.1.2356.11.1.99.3.3
lcsStatusXdslVdsl2Standard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGFast (42),
                  eGVector (254),
                  eUnknown (255)
            }
    MAX-ACCESS read-only
    STATUS     current
    DESCRIPTION
            "-- empty --"
    ::= { lcsStatusXdslVdsl2 3 }

-- {SCALAR} 1.3.6.1.4.1.2356.11.1.99.3.4
lcsStatusXdslVdsl2DataRateUpstreamKbps OBJECT-TYPE
    SYNTAX     Integer32 (0..2147483647)
    MAX-ACCESS read-only
    STATUS     current
    DESCRIPTION
            "-- empty --"
    ::= { lcsStatusXdslVdsl2 4 }

-- {SCALAR} 1.3.6.1.4.1.2356.11.1.99.3.5
lcsStatusXdslVdsl2DataRateDownstreamKbps OBJECT-TYPE
    SYNTAX     Integer32 (0..2147483647)
    MAX-ACCESS read-only
    STATUS     current
    DESCRIPTION
            "-- empty --"
    ::= { lcsStatusXdslVdsl2 5 }

-- {SCALAR} 1.3.6.1.4.1.2356.11.1.99.3.6
lcsStatusXdslVdsl2SnrDownstreamDb OBJECT-TYPE
    SYNTAX     DisplayString (SIZE(0..3))
    MAX-ACCESS read-only
    STATUS     current
    DESCRIPTION
            "-- empty --"
    ::= { lcsStatusXdslVdsl2 6 }

-- {SCALAR} 1.3.6.1.4.1.2356.11.1.99.3.7
lcsStatusXdslVdsl2SnrUpstreamDb OBJECT-TYPE
    SYNTAX     DisplayString (SIZE(0..3))
    MAX-ACCESS read-only
    STATUS     current
    DESCRIPTION
            "-- empty --"
    ::= { lcsStatusXdslVdsl2 7 }

-- {SCALAR} 1.3.6.1.4.1.2356.11.1.99.3.8
lcsStatusXdslVdsl2AttenuationDownstreamDb OBJECT-TYPE
    SYNTAX     DisplayString (SIZE(0..3))
    MAX-ACCESS read-only
    STATUS     current
    DESCRIPTION
            "-- empty --"
    ::= { lcsStatusXdslVdsl2 8 }

-- {SCALAR} 1.3.6.1.4.1.2356.11.1.99.3.9
lcsStatusXdslVdsl2AttenuationUpstreamDb OBJECT-TYPE
    SYNTAX     DisplayString (SIZE(0..3))
    MAX-ACCESS read-only
    STATUS     current
    DESCRIPTION
            "-- empty --"
    ::= { lcsStatusXdslVdsl2 9 }

-- {SCALAR} 1.3.6.1.4.1.2356.11.1.99.3.10
lcsStatusXdslVdsl2InterleaveUpstreamMs OBJECT-TYPE
    SYNTAX     DisplayString (SIZE(0..3))
    MAX-ACCESS read-only
    STATUS     current
    DESCRIPTION
            "-- empty --"
    ::= { lcsStatusXdslVdsl2 10 }

-- {SCALAR} 1.3.6.1.4.1.2356.11.1.99.3.11
lcsStatusXdslVdsl2InterleaveDownstreamMs OBJECT-TYPE
    SYNTAX     DisplayString (SIZE(0..3))
    MAX-ACCESS read-only
    STATUS     current
    DESCRIPTION
            "-- empty --"
    ::= { lcsStatusXdslVdsl2 11 }

-- {TABLE} 1.3.6.1.4.1.2356.11.1.99.3.12
lcsStatusXdslVdsl2ConnectionHistoryTable OBJECT-TYPE
    SYNTAX     SEQUENCE OF LcsStatusXdslVdsl2ConnectionHistoryEntry
    MAX-ACCESS not-accessible
    STATUS     current
    DESCRIPTION
            "-- empty --"
    ::= { lcsStatusXdslVdsl2 12 }

-- {ROW} 1.3.6.1.4.1.2356.11.1.99.3.12.1
lcsStatusXdslVdsl2ConnectionHistoryEntry OBJECT-TYPE
    SYNTAX     LcsStatusXdslVdsl2ConnectionHistoryEntry
    MAX-ACCESS not-accessible
    STATUS     current
    DESCRIPTION
            ""
    INDEX {
            lcsStatusXdslVdsl2ConnectionHistoryEntryIndex
          }
    ::= { lcsStatusXdslVdsl2ConnectionHistoryTable 1 }

LcsStatusXdslVdsl2ConnectionHistoryEntry ::= SEQUENCE {
            lcsStatusXdslVdsl2ConnectionHistoryEntrySyncTime Gauge32,
            lcsStatusXdslVdsl2ConnectionHistoryEntryStandard INTEGER,
            lcsStatusXdslVdsl2ConnectionHistoryEntryDsDatarate Integer32,
            lcsStatusXdslVdsl2ConnectionHistoryEntryUsDatarate Integer32,
            lcsStatusXdslVdsl2ConnectionHistoryEntryDsAttenuation DisplayString,
            lcsStatusXdslVdsl2ConnectionHistoryEntryDsSnr DisplayString,
            lcsStatusXdslVdsl2ConnectionHistoryEntryDisconnectTime Gauge32,
            lcsStatusXdslVdsl2ConnectionHistoryEntryIndex Integer32,
            lcsStatusXdslVdsl2ConnectionHistoryEntryReason INTEGER,
            lcsStatusXdslVdsl2ConnectionHistoryEntryUsAttenuation DisplayString,
            lcsStatusXdslVdsl2ConnectionHistoryEntryUsSnr DisplayString,
            lcsStatusXdslVdsl2ConnectionHistoryEntryLinecode DisplayString,
            lcsStatusXdslVdsl2ConnectionHistoryEntryVdslProfile INTEGER,
            lcsStatusXdslVdsl2ConnectionHistoryEntryVectoring INTEGER
    }

-- {COLUMN} 1.3.6.1.4.1.2356.11.1.99.3.12.1.1
lcsStatusXdslVdsl2ConnectionHistoryEntrySyncTime OBJECT-TYPE
    SYNTAX     Gauge32
    MAX-ACCESS read-only
    STATUS     current
    DESCRIPTION
            "-- empty --"
    ::= { lcsStatusXdslVdsl2ConnectionHistoryEntry 1 }

-- {COLUMN} 1.3.6.1.4.1.2356.11.1.99.3.12.1.2
lcsStatusXdslVdsl2ConnectionHistoryEntryStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGFast (42),
                  eGVector (254),
                  eUnknown (255)
            }
    MAX-ACCESS read-only
    STATUS     current
    DESCRIPTION
            "-- empty --"
    ::= { lcsStatusXdslVdsl2ConnectionHistoryEntry 2 }

-- {COLUMN} 1.3.6.1.4.1.2356.11.1.99.3.12.1.3
lcsStatusXdslVdsl2ConnectionHistoryEntryDsDatarate OBJECT-TYPE
    SYNTAX     Integer32 (0..2147483647)
    MAX-ACCESS read-only
    STATUS     current
    DESCRIPTION
            "-- empty --"
    ::= { lcsStatusXdslVdsl2ConnectionHistoryEntry 3 }

-- {COLUMN} 1.3.6.1.4.1.2356.11.1.99.3.12.1.4
lcsStatusXdslVdsl2ConnectionHistoryEntryUsDatarate OBJECT-TYPE
    SYNTAX     Integer32 (0..2147483647)
    MAX-ACCESS read-only
    STATUS     current
    DESCRIPTION
            "-- empty --"
    ::= { lcsStatusXdslVdsl2ConnectionHistoryEntry 4 }

-- {COLUMN} 1.3.6.1.4.1.2356.11.1.99.3.12.1.5
lcsStatusXdslVdsl2ConnectionHistoryEntryDsAttenuation OBJECT-TYPE
    SYNTAX     DisplayString (SIZE(0..1))
    MAX-ACCESS read-only
    STATUS     current
    DESCRIPTION
            "-- empty --"
    ::= { lcsStatusXdslVdsl2ConnectionHistoryEntry 5 }

-- {COLUMN} 1.3.6.1.4.1.2356.11.1.99.3.12.1.6
lcsStatusXdslVdsl2ConnectionHistoryEntryDsSnr OBJECT-TYPE
    SYNTAX     DisplayString (SIZE(0..1))
    MAX-ACCESS read-only
    STATUS     current
    DESCRIPTION
            "-- empty --"
    ::= { lcsStatusXdslVdsl2ConnectionHistoryEntry 6 }

-- {COLUMN} 1.3.6.1.4.1.2356.11.1.99.3.12.1.7
lcsStatusXdslVdsl2ConnectionHistoryEntryDisconnectTime OBJECT-TYPE
    SYNTAX     Gauge32
    MAX-ACCESS read-only
    STATUS     current
    DESCRIPTION
            "-- empty --"
    ::= { lcsStatusXdslVdsl2ConnectionHistoryEntry 7 }

-- {COLUMN} 1.3.6.1.4.1.2356.11.1.99.3.12.1.8
lcsStatusXdslVdsl2ConnectionHistoryEntryIndex OBJECT-TYPE
    SYNTAX     Integer32 (0..2147483647)
    MAX-ACCESS read-only
    STATUS     current
    DESCRIPTION
            "-- empty --"
    ::= { lcsStatusXdslVdsl2ConnectionHistoryEntry 8 }

-- {COLUMN} 1.3.6.1.4.1.2356.11.1.99.3.12.1.9
lcsStatusXdslVdsl2ConnectionHistoryEntryReason OBJECT-TYPE
    SYNTAX     INTEGER {
                  eModemReboot (1),
                  eRetrain (2),
                  eSilence (3),
                  eLineError (4),
                  eProtocol (5),
                  eLineType (6),
                  eAutomode (7),
                  eTimeout (8),
                  eVcParameters (13)
            }
    MAX-ACCESS read-only
    STATUS     current
    DESCRIPTION
            "-- empty --"
    ::= { lcsStatusXdslVdsl2ConnectionHistoryEntry 9 }

-- {COLUMN} 1.3.6.1.4.1.2356.11.1.99.3.12.1.10
lcsStatusXdslVdsl2ConnectionHistoryEntryUsAttenuation OBJECT-TYPE
    SYNTAX     DisplayString (SIZE(0..1))
    MAX-ACCESS read-only
    STATUS     current
    DESCRIPTION
            "-- empty --"
    ::= { lcsStatusXdslVdsl2ConnectionHistoryEntry 10 }

-- {COLUMN} 1.3.6.1.4.1.2356.11.1.99.3.12.1.11
lcsStatusXdslVdsl2ConnectionHistoryEntryUsSnr OBJECT-TYPE
    SYNTAX     DisplayString (SIZE(0..1))
    MAX-ACCESS read-only
    STATUS     current
    DESCRIPTION
            "-- empty --"
    ::= { lcsStatusXdslVdsl2ConnectionHistoryEntry 11 }

-- {COLUMN} 1.3.6.1.4.1.2356.11.1.99.3.12.1.12
lcsStatusXdslVdsl2ConnectionHistoryEntryLinecode OBJECT-TYPE
    SYNTAX     DisplayString (SIZE(0..1))
    MAX-ACCESS read-only
    STATUS     current
    DESCRIPTION
            "-- empty --"
    ::= { lcsStatusXdslVdsl2ConnectionHistoryEntry 12 }

-- {COLUMN} 1.3.6.1.4.1.2356.11.1.99.3.12.1.13
lcsStatusXdslVdsl2ConnectionHistoryEntryVdslProfile OBJECT-TYPE
    SYNTAX     INTEGER {
                  eUnknown (0),
                  e8a (1),
                  e8b (2),
                  e8c (3),
                  e8d (4),
                  e12a (5),
                  e12b (6),
                  e17a (7),
                  e30a (8),
                  e35b (9)
            }
    MAX-ACCESS read-only
    STATUS     current
    DESCRIPTION
            "-- empty --"
    ::= { lcsStatusXdslVdsl2ConnectionHistoryEntry 13 }

-- {COLUMN} 1.3.6.1.4.1.2356.11.1.99.3.12.1.14
lcsStatusXdslVdsl2ConnectionHistoryEntryVectoring OBJECT-TYPE
    SYNTAX     INTEGER {
                  eNo (1),
                  eYes (2),
                  eFriendly (3)
            }
    MAX-ACCESS read-only
    STATUS     current
    DESCRIPTION
            "-- empty --"
    ::= { lcsStatusXdslVdsl2ConnectionHistoryEntry 14 }

-- {SCALAR} 1.3.6.1.4.1.2356.11.1.99.3.13
lcsStatusXdslVdsl2Retrain OBJECT-TYPE
    SYNTAX     DisplayString
    MAX-ACCESS read-write
    STATUS     current
    DESCRIPTION
            "-- empty --"
    ::= { lcsStatusXdslVdsl2 13 }

-- {SCALAR} 1.3.6.1.4.1.2356.11.1.99.3.14
lcsStatusXdslVdsl2DslamChipsetManufacturer OBJECT-TYPE
    SYNTAX     DisplayString (SIZE(0..63))
    MAX-ACCESS read-only
    STATUS     current
    DESCRIPTION
            "-- empty --"
    ::= { lcsStatusXdslVdsl2 14 }

-- {SCALAR} 1.3.6.1.4.1.2356.11.1.99.3.23
lcsStatusXdslVdsl2ModemType OBJECT-TYPE
    SYNTAX     DisplayString (SIZE(0..3))
    MAX-ACCESS read-only
    STATUS     current
    DESCRIPTION
            "-- empty --"
    ::= { lcsStatusXdslVdsl2 23 }

-- {NODE} 1.3.6.1.4.1.2356.11.1.99.3.25
lcsStatusXdslVdsl2Advanced OBJECT IDENTIFIER ::= { lcsStatusXdslVdsl2 25 }

-- {SCALAR} 1.3.6.1.4.1.2356.11.1.99.3.25.1
lcsStatusXdslVdsl2AdvancedLineState OBJECT-TYPE
    SYNTAX     INTEGER {
                  eUnknown (0),
                  eDown (1),
                  eIdle (2),
                  eHandshake (3),
                  eTraining (4),
                  eShowtime (5),
                  eShutdown (6)
            }
    MAX-ACCESS read-only
    STATUS     current
    DESCRIPTION
            "-- empty --"
    ::= { lcsStatusXdslVdsl2Advanced 1 }

-- {SCALAR} 1.3.6.1.4.1.2356.11.1.99.3.25.2
lcsStatusXdslVdsl2AdvancedStandard OBJECT-TYPE
    SYNTAX     INTEGER {
                  eOff (0),
                  eT1dot413 (2),
                  eGdotLite (3),
                  eGdotDMT (4),
                  eAdsl2 (21),
                  eAdsl2plus (22),
                  eAdsl2AnnexM (31),
                  eAdsl2plusAnnexM (32),
                  eAdsl2AnnexI (33),
                  eAdsl2plusAnnexI (34),
                  eAdsl2AnnexJ (35),
                  eAdsl2plusAnnexJ (36),
                  eAdsl2AnnexL (37),
                  eVdsl2 (40),
                  eGFast (42),
                  eGVector (254),
                  eUnknown (255)
            }
    MAX-ACCESS read-only
    STATUS     current
    DESCRIPTION
            "-- empty --"
    ::= { lcsStatusXdslVdsl2Advanced 2 }

-- {SCALAR} 1.3.6.1.4.1.2356.11.1.99.3.25.3
lcsStatusXdslVdsl2AdvancedDsDataRateKbps OBJECT-TYPE
    SYNTAX     Integer32 (0..2147483647)
    MAX-ACCESS read-only
    STATUS     current
    DESCRIPTION
            "-- empty --"
    ::= { lcsStatusXdslVdsl2Advanced 3 }

-- {SCALAR} 1.3.6.1.4.1.2356.11.1.99.3.25.4
lcsStatusXdslVdsl2AdvancedDsSnrMarginDb OBJECT-TYPE
    SYNTAX     DisplayString (SIZE(0..3))
    MAX-ACCESS read-only
    STATUS     current
    DESCRIPTION
            "-- empty --"
    ::= { lcsStatusXdslVdsl2Advanced 4 }

-- {SCALAR} 1.3.6.1.4.1.2356.11.1.99.3.25.5
lcsStatusXdslVdsl2AdvancedDsLineAttenuationDb OBJECT-TYPE
    SYNTAX     DisplayString (SIZE(0..3))
    MAX-ACCESS read-only
    STATUS     current
    DESCRIPTION
            "-- empty --"
    ::= { lcsStatusXdslVdsl2Advanced 5 }

-- {SCALAR} 1.3.6.1.4.1.2356.11.1.99.3.25.6
lcsStatusXdslVdsl2AdvancedDsInterleaveMs OBJECT-TYPE
    SYNTAX     DisplayString (SIZE(0..3))
    MAX-ACCESS read-only
    STATUS     current
    DESCRIPTION
            "-- empty --"
    ::= { lcsStatusXdslVdsl2Advanced 6 }

-- {TABLE} 1.3.6.1.4.1.2356.11.1.99.3.25.13
lcsStatusXdslVdsl2AdvancedDsBitLoadingTable OBJECT-TYPE
    SYNTAX     SEQUENCE OF LcsStatusXdslVdsl2AdvancedDsBitLoadingEntry
    MAX-ACCESS not-accessible
    STATUS     current
    DESCRIPTION
            "-- empty --"
    ::= { lcsStatusXdslVdsl2Advanced 13 }

-- {ROW} 1.3.6.1.4.1.2356.11.1.99.3.25.13.1
lcsStatusXdslVdsl2AdvancedDsBitLoadingEntry OBJECT-TYPE
    SYNTAX     LcsStatusXdslVdsl2AdvancedDsBitLoadingEntry
    MAX-ACCESS not-accessible
    STATUS     current
    DESCRIPTION
            ""
    INDEX {
            lcsStatusXdslVdsl2AdvancedDsBitLoadingEntryBinNumber
          }
    ::= { lcsStatusXdslVdsl2AdvancedDsBitLoadingTable 1 }

LcsStatusXdslVdsl2AdvancedDsBitLoadingEntry ::= SEQUENCE {
            lcsStatusXdslVdsl2AdvancedDsBitLoadingEntryBinNumber DisplayString,
            lcsStatusXdslVdsl2AdvancedDsBitLoadingEntryX0 Integer32,
            lcsStatusXdslVdsl2AdvancedDsBitLoadingEntryX1 Integer32,
            lcsStatusXdslVdsl2AdvancedDsBitLoadingEntryX2 Integer32,
            lcsStatusXdslVdsl2AdvancedDsBitLoadingEntryX3 Integer32,
            lcsStatusXdslVdsl2AdvancedDsBitLoadingEntryX4 Integer32,
            lcsStatusXdslVdsl2AdvancedDsBitLoadingEntryX5 Integer32,
            lcsStatusXdslVdsl2AdvancedDsBitLoadingEntryX6 Integer32,
            lcsStatusXdslVdsl2AdvancedDsBitLoadingEntryX7 Integer32,
            lcsStatusXdslVdsl2AdvancedDsBitLoadingEntryX8 Integer32,
            lcsStatusXdslVdsl2AdvancedDsBitLoadingEntryX9 Integer32,
            lcsStatusXdslVdsl2AdvancedDsBitLoadingEntryGraph DisplayString
    }

-- {COLUMN} 1.3.6.1.4.1.2356.11.1.99.3.25.13.1.1
lcsStatusXdslVdsl2AdvancedDsBitLoadingEntryBinNumber OBJECT-TYPE
    SYNTAX     DisplayString (SIZE(0..255))
    MAX-ACCESS read-only
    STATUS     current
    DESCRIPTION
            "-- empty --"
    ::= { lcsStatusXdslVdsl2AdvancedDsBitLoadingEntry 1 }

-- {COLUMN} 1.3.6.1.4.1.2356.11.1.99.3.25.13.1.2
lcsStatusXdslVdsl2AdvancedDsBitLoadingEntryX0 OBJECT-TYPE
    SYNTAX     Integer32 (0..2147483647)
    MAX-ACCESS read-only
    STATUS     current
    DESCRIPTION
            "-- empty --"
    ::= { lcsStatusXdslVdsl2AdvancedDsBitLoadingEntry 2 }

-- {COLUMN} 1.3.6.1.4.1.2356.11.1.99.3.25.13.1.3
lcsStatusXdslVdsl2AdvancedDsBitLoadingEntryX1 OBJECT-TYPE
    SYNTAX     Integer32 (0..2147483647)
    MAX-ACCESS read-only
    STATUS     current
    DESCRIPTION
            "-- empty --"
    ::= { lcsStatusXdslVdsl2AdvancedDsBitLoadingEntry 3 }

-- {COLUMN} 1.3.6.1.4.1.2356.11.1.99.3.25.13.1.4
lcsStatusXdslVdsl2AdvancedDsBitLoadingEntryX2 OBJECT-TYPE
    SYNTAX     Integer32 (0..2147483647)
    MAX-ACCESS read-only
    STATUS     current
    DESCRIPTION
            "-- empty --"
    ::= { lcsStatusXdslVdsl2AdvancedDsBitLoadingEntry 4 }

-- {COLUMN} 1.3.6.1.4.1.2356.11.1.99.3.25.13.1.5
lcsStatusXdslVdsl2AdvancedDsBitLoadingEntryX3 OBJECT-TYPE
    SYNTAX     Integer32 (0..2147483647)
    MAX-ACCESS read-only
    STATUS     current
    DESCRIPTION
            "-- empty --"
    ::= { lcsStatusXdslVdsl2AdvancedDsBitLoadingEntry 5 }

-- {COLUMN} 1.3.6.1.4.1.2356.11.1.99.3.25.13.1.6
lcsStatusXdslVdsl2AdvancedDsBitLoadingEntryX4 OBJECT-TYPE
    SYNTAX     Integer32 (0..2147483647)
    MAX-ACCESS read-only
    STATUS     current
    DESCRIPTION
            "-- empty --"
    ::= { lcsStatusXdslVdsl2AdvancedDsBitLoadingEntry 6 }

-- {COLUMN} 1.3.6.1.4.1.2356.11.1.99.3.25.13.1.7
lcsStatusXdslVdsl2AdvancedDsBitLoadingEntryX5 OBJECT-TYPE
    SYNTAX     Integer32 (0..2147483647)
    MAX-ACCESS read-only
    STATUS     current
    DESCRIPTION
            "-- empty --"
    ::= { lcsStatusXdslVdsl2AdvancedDsBitLoadingEntry 7 }

-- {COLUMN} 1.3.6.1.4.1.2356.11.1.99.3.25.13.1.8
lcsStatusXdslVdsl2AdvancedDsBitLoadingEntryX6 OBJECT-TYPE
    SYNTAX     Integer32 (0..2147483647)
    MAX-ACCESS read-only
    STATUS     current
    DESCRIPTION
            "-- empty --"
    ::= { lcsStatusXdslVdsl2AdvancedDsBitLoadingEntry 8 }

-- {COLUMN} 1.3.6.1.4.1.2356.11.1.99.3.25.13.1.9
lcsStatusXdslVdsl2AdvancedDsBitLoadingEntryX7 OBJECT-TYPE
    SYNTAX     Integer32 (0..2147483647)
    MAX-ACCESS read-only
    STATUS     current
    DESCRIPTION
            "-- empty --"
    ::= { lcsStatusXdslVdsl2AdvancedDsBitLoadingEntry 9 }

-- {COLUMN} 1.3.6.1.4.1.2356.11.1.99.3.25.13.1.10
lcsStatusXdslVdsl2AdvancedDsBitLoadingEntryX8 OBJECT-TYPE
    SYNTAX     Integer32 (0..2147483647)
    MAX-ACCESS read-only
    STATUS     current
    DESCRIPTION
            "-- empty --"
    ::= { lcsStatusXdslVdsl2AdvancedDsBitLoadingEntry 10 }

-- {COLUMN} 1.3.6.1.4.1.2356.11.1.99.3.25.13.1.11
lcsStatusXdslVdsl2AdvancedDsBitLoadingEntryX9 OBJECT-TYPE
    SYNTAX     Integer32 (0..2147483647)
    MAX-ACCESS read-only
    STATUS     current
    DESCRIPTION
            "-- empty --"
    ::= { lcsStatusXdslVdsl2AdvancedDsBitLoadingEntry 11 }

-- {COLUMN} 1.3.6.1.4.1.2356.11.1.99.3.25.13.1.12
lcsStatusXdslVdsl2AdvancedDsBitLoadingEntryGraph OBJECT-TYPE
    SYNTAX     DisplayString (SIZE(0..255))
    MAX-ACCESS read-only
    STATUS     current
    DESCRIPTION
            "-- empty --"
    ::= { lcsStatusXdslVdsl2AdvancedDsBitLoadingEntry 12 }

-- {SCALAR} 1.3.6.1.4.1.2356.11.1.99.3.25.15
lcsStatusXdslVdsl2AdvancedUsDataRateKbps OBJECT-TYPE
    SYNTAX     Integer32 (0..2147483647)
    MAX-ACCESS read-only
    STATUS     current
    DESCRIPTION
            "-- empty --"
    ::= { lcsStatusXdslVdsl2Advanced 15 }

-- {SCALAR} 1.3.6.1.4.1.2356.11.1.99.3.25.16
lcsStatusXdslVdsl2AdvancedUsSnrMarginDb OBJECT-TYPE
    SYNTAX     DisplayString (SIZE(0..3))
    MAX-ACCESS read-only
    STATUS     current
    DESCRIPTION
            "-- empty --"
    ::= { lcsStatusXdslVdsl2Advanced 16 }

-- {SCALAR} 1.3.6.1.4.1.2356.11.1.99.3.25.17
lcsStatusXdslVdsl2AdvancedUsLineAttenuationDb OBJECT-TYPE
    SYNTAX     DisplayString (SIZE(0..3))
    MAX-ACCESS read-only
    STATUS     current
    DESCRIPTION
            "-- empty --"
    ::= { lcsStatusXdslVdsl2Advanced 17 }

-- {SCALAR} 1.3.6.1.4.1.2356.11.1.99.3.25.18
lcsStatusXdslVdsl2AdvancedUsInterleaveMs OBJECT-TYPE
    SYNTAX     DisplayString (SIZE(0..3))
    MAX-ACCESS read-only
    STATUS     current
    DESCRIPTION
            "-- empty --"
    ::= { lcsStatusXdslVdsl2Advanced 18 }

-- {TABLE} 1.3.6.1.4.1.2356.11.1.99.3.25.25
lcsStatusXdslVdsl2AdvancedUsBitLoadingTable OBJECT-TYPE
    SYNTAX     SEQUENCE OF LcsStatusXdslVdsl2AdvancedUsBitLoadingEntry
    MAX-ACCESS not-accessible
    STATUS     current
    DESCRIPTION
            "-- empty --"
    ::= { lcsStatusXdslVdsl2Advanced 25 }

-- {ROW} 1.3.6.1.4.1.2356.11.1.99.3.25.25.1
lcsStatusXdslVdsl2AdvancedUsBitLoadingEntry OBJECT-TYPE
    SYNTAX     LcsStatusXdslVdsl2AdvancedUsBitLoadingEntry
    MAX-ACCESS not-accessible
    STATUS     current
    DESCRIPTION
            ""
    INDEX {
            lcsStatusXdslVdsl2AdvancedUsBitLoadingEntryBinNumber
          }
    ::= { lcsStatusXdslVdsl2AdvancedUsBitLoadingTable 1 }

LcsStatusXdslVdsl2AdvancedUsBitLoadingEntry ::= SEQUENCE {
            lcsStatusXdslVdsl2AdvancedUsBitLoadingEntryBinNumber DisplayString,
            lcsStatusXdslVdsl2AdvancedUsBitLoadingEntryX0 Integer32,
            lcsStatusXdslVdsl2AdvancedUsBitLoadingEntryX1 Integer32,
            lcsStatusXdslVdsl2AdvancedUsBitLoadingEntryX2 Integer32,
            lcsStatusXdslVdsl2AdvancedUsBitLoadingEntryX3 Integer32,
            lcsStatusXdslVdsl2AdvancedUsBitLoadingEntryX4 Integer32,
            lcsStatusXdslVdsl2AdvancedUsBitLoadingEntryX5 Integer32,
            lcsStatusXdslVdsl2AdvancedUsBitLoadingEntryX6 Integer32,
            lcsStatusXdslVdsl2AdvancedUsBitLoadingEntryX7 Integer32,
            lcsStatusXdslVdsl2AdvancedUsBitLoadingEntryX8 Integer32,
            lcsStatusXdslVdsl2AdvancedUsBitLoadingEntryX9 Integer32,
            lcsStatusXdslVdsl2AdvancedUsBitLoadingEntryGraph DisplayString
    }

-- {COLUMN} 1.3.6.1.4.1.2356.11.1.99.3.25.25.1.1
lcsStatusXdslVdsl2AdvancedUsBitLoadingEntryBinNumber OBJECT-TYPE
    SYNTAX     DisplayString (SIZE(0..255))
    MAX-ACCESS read-only
    STATUS     current
    DESCRIPTION
            "-- empty --"
    ::= { lcsStatusXdslVdsl2AdvancedUsBitLoadingEntry 1 }

-- {COLUMN} 1.3.6.1.4.1.2356.11.1.99.3.25.25.1.2
lcsStatusXdslVdsl2AdvancedUsBitLoadingEntryX0 OBJECT-TYPE
    SYNTAX     Integer32 (0..2147483647)
    MAX-ACCESS read-only
    STATUS     current
    DESCRIPTION
            "-- empty --"
    ::= { lcsStatusXdslVdsl2AdvancedUsBitLoadingEntry 2 }

-- {COLUMN} 1.3.6.1.4.1.2356.11.1.99.3.25.25.1.3
lcsStatusXdslVdsl2AdvancedUsBitLoadingEntryX1 OBJECT-TYPE
    SYNTAX     Integer32 (0..2147483647)
    MAX-ACCESS read-only
    STATUS     current
    DESCRIPTION
            "-- empty --"
    ::= { lcsStatusXdslVdsl2AdvancedUsBitLoadingEntry 3 }

-- {COLUMN} 1.3.6.1.4.1.2356.11.1.99.3.25.25.1.4
lcsStatusXdslVdsl2AdvancedUsBitLoadingEntryX2 OBJECT-TYPE
    SYNTAX     Integer32 (0..2147483647)
    MAX-ACCESS read-only
    STATUS     current
    DESCRIPTION
            "-- empty --"
    ::= { lcsStatusXdslVdsl2AdvancedUsBitLoadingEntry 4 }

-- {COLUMN} 1.3.6.1.4.1.2356.11.1.99.3.25.25.1.5
lcsStatusXdslVdsl2AdvancedUsBitLoadingEntryX3 OBJECT-TYPE
    SYNTAX     Integer32 (0..2147483647)
    MAX-ACCESS read-only
    STATUS     current
    DESCRIPTION
            "-- empty --"
    ::= { lcsStatusXdslVdsl2AdvancedUsBitLoadingEntry 5 }

-- {COLUMN} 1.3.6.1.4.1.2356.11.1.99.3.25.25.1.6
lcsStatusXdslVdsl2AdvancedUsBitLoadingEntryX4 OBJECT-TYPE
    SYNTAX     Integer32 (0..2147483647)
    MAX-ACCESS read-only
    STATUS     current
    DESCRIPTION
            "-- empty --"
    ::= { lcsStatusXdslVdsl2AdvancedUsBitLoadingEntry 6 }

-- {COLUMN} 1.3.6.1.4.1.2356.11.1.99.3.25.25.1.7
lcsStatusXdslVdsl2AdvancedUsBitLoadingEntryX5 OBJECT-TYPE
    SYNTAX     Integer32 (0..2147483647)
    MAX-ACCESS read-only
    STATUS     current
    DESCRIPTION
            "-- empty --"
    ::= { lcsStatusXdslVdsl2AdvancedUsBitLoadingEntry 7 }

-- {COLUMN} 1.3.6.1.4.1.2356.11.1.99.3.25.25.1.8
lcsStatusXdslVdsl2AdvancedUsBitLoadingEntryX6 OBJECT-TYPE
    SYNTAX     Integer32 (0..2147483647)
    MAX-ACCESS read-only
    STATUS     current
    DESCRIPTION
            "-- empty --"
    ::= { lcsStatusXdslVdsl2AdvancedUsBitLoadingEntry 8 }

-- {COLUMN} 1.3.6.1.4.1.2356.11.1.99.3.25.25.1.9
lcsStatusXdslVdsl2AdvancedUsBitLoadingEntryX7 OBJECT-TYPE
    SYNTAX     Integer32 (0..2147483647)
    MAX-ACCESS read-only
    STATUS     current
    DESCRIPTION
            "-- empty --"
    ::= { lcsStatusXdslVdsl2AdvancedUsBitLoadingEntry 9 }

-- {COLUMN} 1.3.6.1.4.1.2356.11.1.99.3.25.25.1.10
lcsStatusXdslVdsl2AdvancedUsBitLoadingEntryX8 OBJECT-TYPE
    SYNTAX     Integer32 (0..2147483647)
    MAX-ACCESS read-only
    STATUS     current
    DESCRIPTION
            "-- empty --"
    ::= { lcsStatusXdslVdsl2AdvancedUsBitLoadingEntry 10 }

-- {COLUMN} 1.3.6.1.4.1.2356.11.1.99.3.25.25.1.11
lcsStatusXdslVdsl2AdvancedUsBitLoadingEntryX9 OBJECT-TYPE
    SYNTAX     Integer32 (0..2147483647)
    MAX-ACCESS read-only
    STATUS     current
    DESCRIPTION
            "-- empty --"
    ::= { lcsStatusXdslVdsl2AdvancedUsBitLoadingEntry 11 }

-- {COLUMN} 1.3.6.1.4.1.2356.11.1.99.3.25.25.1.12
lcsStatusXdslVdsl2AdvancedUsBitLoadingEntryGraph OBJECT-TYPE
    SYNTAX     DisplayString (SIZE(0..255))
    MAX-ACCESS read-only
    STATUS     current
    DESCRIPTION
            "-- empty --"
    ::= { lcsStatusXdslVdsl2AdvancedUsBitLoadingEntry 12 }

-- {SCALAR} 1.3.6.1.4.1.2356.11.1.99.3.25.26
lcsStatusXdslVdsl2AdvancedRetrain OBJECT-TYPE
    SYNTAX     DisplayString
    MAX-ACCESS read-write
    STATUS     current
    DESCRIPTION
            "-- empty --"
    ::= { lcsStatusXdslVdsl2Advanced 26 }

-- {SCALAR} 1.3.6.1.4.1.2356.11.1.99.3.25.29
lcsStatusXdslVdsl2AdvancedTransmittedAtmCells OBJECT-TYPE
    SYNTAX     Integer32 (0..2147483647)
    MAX-ACCESS read-only
    STATUS     current
    DESCRIPTION
            "-- empty --"
    ::= { lcsStatusXdslVdsl2Advanced 29 }

-- {SCALAR} 1.3.6.1.4.1.2356.11.1.99.3.25.40
lcsStatusXdslVdsl2AdvancedVdslProfile OBJECT-TYPE
    SYNTAX     INTEGER {
                  eUnknown (0),
                  e8a (1),
                  e8b (2),
                  e8c (3),
                  e8d (4),
                  e12a (5),
                  e12b (6),
                  e17a (7),
                  e30a (8),
                  e35b (9)
            }
    MAX-ACCESS read-only
    STATUS     current
    DESCRIPTION
            "-- empty --"
    ::= { lcsStatusXdslVdsl2Advanced 40 }

-- {SCALAR} 1.3.6.1.4.1.2356.11.1.99.3.25.41
lcsStatusXdslVdsl2AdvancedDslamManufacturer OBJECT-TYPE
    SYNTAX     DisplayString (SIZE(0..63))
    MAX-ACCESS read-only
    STATUS     current
    DESCRIPTION
            "-- empty --"
    ::= { lcsStatusXdslVdsl2Advanced 41 }

-- {SCALAR} 1.3.6.1.4.1.2356.11.1.99.3.25.42
lcsStatusXdslVdsl2AdvancedDslamVersion OBJECT-TYPE
    SYNTAX     DisplayString (SIZE(0..34))
    MAX-ACCESS read-only
    STATUS     current
    DESCRIPTION
            "-- empty --"
    ::= { lcsStatusXdslVdsl2Advanced 42 }

-- {SCALAR} 1.3.6.1.4.1.2356.11.1.99.3.25.43
lcsStatusXdslVdsl2AdvancedDslamSerialNumber OBJECT-TYPE
    SYNTAX     DisplayString (SIZE(0..66))
    MAX-ACCESS read-only
    STATUS     current
    DESCRIPTION
            "-- empty --"
    ::= { lcsStatusXdslVdsl2Advanced 43 }

-- {SCALAR} 1.3.6.1.4.1.2356.11.1.99.3.25.44
lcsStatusXdslVdsl2AdvancedDslamChipsetManufacturer OBJECT-TYPE
    SYNTAX     DisplayString (SIZE(0..63))
    MAX-ACCESS read-only
    STATUS     current
    DESCRIPTION
            "-- empty --"
    ::= { lcsStatusXdslVdsl2Advanced 44 }

-- {SCALAR} 1.3.6.1.4.1.2356.11.1.99.3.25.45
lcsStatusXdslVdsl2AdvancedVectoringSupport OBJECT-TYPE
    SYNTAX     INTEGER {
                  eNo (1),
                  eYes (2),
                  eFriendly (3)
            }
    MAX-ACCESS read-only
    STATUS     current
    DESCRIPTION
            "-- empty --"
    ::= { lcsStatusXdslVdsl2Advanced 45 }

-- {SCALAR} 1.3.6.1.4.1.2356.11.1.99.3.25.46
lcsStatusXdslVdsl2AdvancedVectoring OBJECT-TYPE
    SYNTAX     INTEGER {
                  eNo (1),
                  eYes (2),
                  eFriendly (3)
            }
    MAX-ACCESS read-only
    STATUS     current
    DESCRIPTION
            "-- empty --"
    ::= { lcsStatusXdslVdsl2Advanced 46 }

-- {SCALAR} 1.3.6.1.4.1.2356.11.1.99.3.25.47
lcsStatusXdslVdsl2AdvancedDslamChipsetManufacturerDump OBJECT-TYPE
    SYNTAX     OCTET STRING
    MAX-ACCESS read-only
    STATUS     current
    DESCRIPTION
            "-- empty --"
    ::= { lcsStatusXdslVdsl2Advanced 47 }

-- {SCALAR} 1.3.6.1.4.1.2356.11.1.99.3.25.48
lcsStatusXdslVdsl2AdvancedDslamManufacturerDump OBJECT-TYPE
    SYNTAX     OCTET STRING
    MAX-ACCESS read-only
    STATUS     current
    DESCRIPTION
            "-- empty --"
    ::= { lcsStatusXdslVdsl2Advanced 48 }

-- {SCALAR} 1.3.6.1.4.1.2356.11.1.99.3.25.53
lcsStatusXdslVdsl2AdvancedConnectionCount OBJECT-TYPE
    SYNTAX     Integer32 (0..2147483647)
    MAX-ACCESS read-only
    STATUS     current
    DESCRIPTION
            "-- empty --"
    ::= { lcsStatusXdslVdsl2Advanced 53 }

-- {SCALAR} 1.3.6.1.4.1.2356.11.1.99.3.25.54
lcsStatusXdslVdsl2AdvancedConnectionDuration OBJECT-TYPE
    SYNTAX     Gauge32
    MAX-ACCESS read-only
    STATUS     current
    DESCRIPTION
            "-- empty --"
    ::= { lcsStatusXdslVdsl2Advanced 54 }

-- {SCALAR} 1.3.6.1.4.1.2356.11.1.99.3.25.100
lcsStatusXdslVdsl2AdvancedDsAttainableDataRateKbps OBJECT-TYPE
    SYNTAX     Integer32 (0..2147483647)
    MAX-ACCESS read-only
    STATUS     current
    DESCRIPTION
            "-- empty --"
    ::= { lcsStatusXdslVdsl2Advanced 100 }

-- {SCALAR} 1.3.6.1.4.1.2356.11.1.99.3.25.101
lcsStatusXdslVdsl2AdvancedDsInpSymbols OBJECT-TYPE
    SYNTAX     DisplayString (SIZE(0..3))
    MAX-ACCESS read-only
    STATUS     current
    DESCRIPTION
            "-- empty --"
    ::= { lcsStatusXdslVdsl2Advanced 101 }

-- {SCALAR} 1.3.6.1.4.1.2356.11.1.99.3.25.102
lcsStatusXdslVdsl2AdvancedDsCrcErrors OBJECT-TYPE
    SYNTAX     Integer32 (0..2147483647)
    MAX-ACCESS read-only
    STATUS     current
    DESCRIPTION
            "-- empty --"
    ::= { lcsStatusXdslVdsl2Advanced 102 }

-- {SCALAR} 1.3.6.1.4.1.2356.11.1.99.3.25.103
lcsStatusXdslVdsl2AdvancedDsFecErrors OBJECT-TYPE
    SYNTAX     Integer32 (0..2147483647)
    MAX-ACCESS read-only
    STATUS     current
    DESCRIPTION
            "-- empty --"
    ::= { lcsStatusXdslVdsl2Advanced 103 }

-- {SCALAR} 1.3.6.1.4.1.2356.11.1.99.3.25.104
lcsStatusXdslVdsl2AdvancedDsAtmHecErrors OBJECT-TYPE
    SYNTAX     Integer32 (0..2147483647)
    MAX-ACCESS read-only
    STATUS     current
    DESCRIPTION
            "-- empty --"
    ::= { lcsStatusXdslVdsl2Advanced 104 }

-- {SCALAR} 1.3.6.1.4.1.2356.11.1.99.3.25.105
lcsStatusXdslVdsl2AdvancedDsDataPathCrcpErrors OBJECT-TYPE
    SYNTAX     Integer32 (0..2147483647)
    MAX-ACCESS read-only
    STATUS     current
    DESCRIPTION
            "-- empty --"
    ::= { lcsStatusXdslVdsl2Advanced 105 }

-- {SCALAR} 1.3.6.1.4.1.2356.11.1.99.3.25.106
lcsStatusXdslVdsl2AdvancedDsDataPathCrcnpErrors OBJECT-TYPE
    SYNTAX     Integer32 (0..2147483647)
    MAX-ACCESS read-only
    STATUS     current
    DESCRIPTION
            "-- empty --"
    ::= { lcsStatusXdslVdsl2Advanced 106 }

-- {SCALAR} 1.3.6.1.4.1.2356.11.1.99.3.25.107
lcsStatusXdslVdsl2AdvancedDsDataPathCvpErrors OBJECT-TYPE
    SYNTAX     Integer32 (0..2147483647)
    MAX-ACCESS read-only
    STATUS     current
    DESCRIPTION
            "-- empty --"
    ::= { lcsStatusXdslVdsl2Advanced 107 }

-- {SCALAR} 1.3.6.1.4.1.2356.11.1.99.3.25.108
lcsStatusXdslVdsl2AdvancedDsDataPathCvnpErrors OBJECT-TYPE
    SYNTAX     Integer32 (0..2147483647)
    MAX-ACCESS read-only
    STATUS     current
    DESCRIPTION
            "-- empty --"
    ::= { lcsStatusXdslVdsl2Advanced 108 }

-- {SCALAR} 1.3.6.1.4.1.2356.11.1.99.3.25.109
lcsStatusXdslVdsl2AdvancedDsAtmIdleBitErrors OBJECT-TYPE
    SYNTAX     Integer32 (0..2147483647)
    MAX-ACCESS read-only
    STATUS     current
    DESCRIPTION
            "-- empty --"
    ::= { lcsStatusXdslVdsl2Advanced 109 }

-- {SCALAR} 1.3.6.1.4.1.2356.11.1.99.3.25.110
lcsStatusXdslVdsl2AdvancedDsAtmCells OBJECT-TYPE
    SYNTAX     Integer32 (0..2147483647)
    MAX-ACCESS read-only
    STATUS     current
    DESCRIPTION
            "-- empty --"
    ::= { lcsStatusXdslVdsl2Advanced 110 }

-- {SCALAR} 1.3.6.1.4.1.2356.11.1.99.3.25.120
lcsStatusXdslVdsl2AdvancedUsAttainableDataRateKbps OBJECT-TYPE
    SYNTAX     Integer32 (0..2147483647)
    MAX-ACCESS read-only
    STATUS     current
    DESCRIPTION
            "-- empty --"
    ::= { lcsStatusXdslVdsl2Advanced 120 }

-- {SCALAR} 1.3.6.1.4.1.2356.11.1.99.3.25.121
lcsStatusXdslVdsl2AdvancedUsInpSymbols OBJECT-TYPE
    SYNTAX     DisplayString (SIZE(0..3))
    MAX-ACCESS read-only
    STATUS     current
    DESCRIPTION
            "-- empty --"
    ::= { lcsStatusXdslVdsl2Advanced 121 }

-- {SCALAR} 1.3.6.1.4.1.2356.11.1.99.3.25.122
lcsStatusXdslVdsl2AdvancedUsCrcErrors OBJECT-TYPE
    SYNTAX     Integer32 (0..2147483647)
    MAX-ACCESS read-only
    STATUS     current
    DESCRIPTION
            "-- empty --"
    ::= { lcsStatusXdslVdsl2Advanced 122 }

-- {SCALAR} 1.3.6.1.4.1.2356.11.1.99.3.25.123
lcsStatusXdslVdsl2AdvancedUsFecErrors OBJECT-TYPE
    SYNTAX     Integer32 (0..2147483647)
    MAX-ACCESS read-only
    STATUS     current
    DESCRIPTION
            "-- empty --"
    ::= { lcsStatusXdslVdsl2Advanced 123 }

-- {SCALAR} 1.3.6.1.4.1.2356.11.1.99.3.25.124
lcsStatusXdslVdsl2AdvancedUsAtmHecErrors OBJECT-TYPE
    SYNTAX     Integer32 (0..2147483647)
    MAX-ACCESS read-only
    STATUS     current
    DESCRIPTION
            "-- empty --"
    ::= { lcsStatusXdslVdsl2Advanced 124 }

-- {SCALAR} 1.3.6.1.4.1.2356.11.1.99.3.25.125
lcsStatusXdslVdsl2AdvancedUsDataPathCrcpErrors OBJECT-TYPE
    SYNTAX     Integer32 (0..2147483647)
    MAX-ACCESS read-only
    STATUS     current
    DESCRIPTION
            "-- empty --"
    ::= { lcsStatusXdslVdsl2Advanced 125 }

-- {SCALAR} 1.3.6.1.4.1.2356.11.1.99.3.25.126
lcsStatusXdslVdsl2AdvancedUsDataPathCrcnpErrors OBJECT-TYPE
    SYNTAX     Integer32 (0..2147483647)
    MAX-ACCESS read-only
    STATUS     current
    DESCRIPTION
            "-- empty --"
    ::= { lcsStatusXdslVdsl2Advanced 126 }

-- {SCALAR} 1.3.6.1.4.1.2356.11.1.99.3.25.127
lcsStatusXdslVdsl2AdvancedUsDataPathCvpErrors OBJECT-TYPE
    SYNTAX     Integer32 (0..2147483647)
    MAX-ACCESS read-only
    STATUS     current
    DESCRIPTION
            "-- empty --"
    ::= { lcsStatusXdslVdsl2Advanced 127 }

-- {SCALAR} 1.3.6.1.4.1.2356.11.1.99.3.25.128
lcsStatusXdslVdsl2AdvancedUsDataPathCvnpErrors OBJECT-TYPE
    SYNTAX     Integer32 (0..2147483647)
    MAX-ACCESS read-only
    STATUS     current
    DESCRIPTION
            "-- empty --"
    ::= { lcsStatusXdslVdsl2Advanced 128 }

-- {SCALAR} 1.3.6.1.4.1.2356.11.1.99.3.25.129
lcsStatusXdslVdsl2AdvancedUsAtmIdleBitErrors OBJECT-TYPE
    SYNTAX     Integer32 (0..2147483647)
    MAX-ACCESS read-only
    STATUS     current
    DESCRIPTION
            "-- empty --"
    ::= { lcsStatusXdslVdsl2Advanced 129 }

-- {SCALAR} 1.3.6.1.4.1.2356.11.1.99.3.25.130
lcsStatusXdslVdsl2AdvancedUsAtmCells OBJECT-TYPE
    SYNTAX     Integer32 (0..2147483647)
    MAX-ACCESS read-only
    STATUS     current
    DESCRIPTION
            "-- empty --"
    ::= { lcsStatusXdslVdsl2Advanced 130 }

-- {SCALAR} 1.3.6.1.4.1.2356.11.1.99.3.25.140
lcsStatusXdslVdsl2AdvancedWanTxPacketCount OBJECT-TYPE
    SYNTAX     Integer32 (0..2147483647)
    MAX-ACCESS read-only
    STATUS     current
    DESCRIPTION
            "-- empty --"
    ::= { lcsStatusXdslVdsl2Advanced 140 }

-- {SCALAR} 1.3.6.1.4.1.2356.11.1.99.3.25.141
lcsStatusXdslVdsl2AdvancedWanTxPacketBytes OBJECT-TYPE
    SYNTAX     Integer32 (0..2147483647)
    MAX-ACCESS read-only
    STATUS     current
    DESCRIPTION
            "-- empty --"
    ::= { lcsStatusXdslVdsl2Advanced 141 }

-- {SCALAR} 1.3.6.1.4.1.2356.11.1.99.3.25.142
lcsStatusXdslVdsl2AdvancedWanTxPacketErrors OBJECT-TYPE
    SYNTAX     Integer32 (0..2147483647)
    MAX-ACCESS read-only
    STATUS     current
    DESCRIPTION
            "-- empty --"
    ::= { lcsStatusXdslVdsl2Advanced 142 }

-- {SCALAR} 1.3.6.1.4.1.2356.11.1.99.3.25.143
lcsStatusXdslVdsl2AdvancedWanTxPacketDrops OBJECT-TYPE
    SYNTAX     Integer32 (0..2147483647)
    MAX-ACCESS read-only
    STATUS     current
    DESCRIPTION
            "-- empty --"
    ::= { lcsStatusXdslVdsl2Advanced 143 }

-- {SCALAR} 1.3.6.1.4.1.2356.11.1.99.3.25.144
lcsStatusXdslVdsl2AdvancedWanTxOverruns OBJECT-TYPE
    SYNTAX     Integer32 (0..2147483647)
    MAX-ACCESS read-only
    STATUS     current
    DESCRIPTION
            "-- empty --"
    ::= { lcsStatusXdslVdsl2Advanced 144 }

-- {SCALAR} 1.3.6.1.4.1.2356.11.1.99.3.25.146
lcsStatusXdslVdsl2AdvancedTxPacketCount OBJECT-TYPE
    SYNTAX     Integer32 (0..2147483647)
    MAX-ACCESS read-only
    STATUS     current
    DESCRIPTION
            "-- empty --"
    ::= { lcsStatusXdslVdsl2Advanced 146 }

-- {SCALAR} 1.3.6.1.4.1.2356.11.1.99.3.25.148
lcsStatusXdslVdsl2AdvancedUsLineOptions OBJECT-TYPE
    SYNTAX     BITS {
                  eBitswap (4),
                  eTrellis (5),
                  eVirtualNoise (6),
                  eRetransmission (7)
            }
    MAX-ACCESS read-only
    STATUS     current
    DESCRIPTION
            "-- empty --"
    ::= { lcsStatusXdslVdsl2Advanced 148 }

-- {SCALAR} 1.3.6.1.4.1.2356.11.1.99.3.25.149
lcsStatusXdslVdsl2AdvancedTx-Packet-count-64 OBJECT-TYPE
    SYNTAX     Integer32 (0..2147483647)
    MAX-ACCESS read-only
    STATUS     current
    DESCRIPTION
            ""
    ::= { lcsStatusXdslVdsl2Advanced 149 }

-- {SCALAR} 1.3.6.1.4.1.2356.11.1.99.3.25.150
lcsStatusXdslVdsl2AdvancedWanRxPacketCount OBJECT-TYPE
    SYNTAX     Integer32 (0..2147483647)
    MAX-ACCESS read-only
    STATUS     current
    DESCRIPTION
            "-- empty --"
    ::= { lcsStatusXdslVdsl2Advanced 150 }

-- {SCALAR} 1.3.6.1.4.1.2356.11.1.99.3.25.151
lcsStatusXdslVdsl2AdvancedWanRxPacketBytes OBJECT-TYPE
    SYNTAX     Integer32 (0..2147483647)
    MAX-ACCESS read-only
    STATUS     current
    DESCRIPTION
            "-- empty --"
    ::= { lcsStatusXdslVdsl2Advanced 151 }

-- {SCALAR} 1.3.6.1.4.1.2356.11.1.99.3.25.152
lcsStatusXdslVdsl2AdvancedWanRxPacketErrors OBJECT-TYPE
    SYNTAX     Integer32 (0..2147483647)
    MAX-ACCESS read-only
    STATUS     current
    DESCRIPTION
            "-- empty --"
    ::= { lcsStatusXdslVdsl2Advanced 152 }

-- {SCALAR} 1.3.6.1.4.1.2356.11.1.99.3.25.153
lcsStatusXdslVdsl2AdvancedWanRxPacketDrops OBJECT-TYPE
    SYNTAX     Integer32 (0..2147483647)
    MAX-ACCESS read-only
    STATUS     current
    DESCRIPTION
            "-- empty --"
    ::= { lcsStatusXdslVdsl2Advanced 153 }

-- {SCALAR} 1.3.6.1.4.1.2356.11.1.99.3.25.154
lcsStatusXdslVdsl2AdvancedWanRxOverruns OBJECT-TYPE
    SYNTAX     Integer32 (0..2147483647)
    MAX-ACCESS read-only
    STATUS     current
    DESCRIPTION
            "-- empty --"
    ::= { lcsStatusXdslVdsl2Advanced 154 }

-- {SCALAR} 1.3.6.1.4.1.2356.11.1.99.3.25.156
lcsStatusXdslVdsl2AdvancedRxPacketCount OBJECT-TYPE
    SYNTAX     Integer32 (0..2147483647)
    MAX-ACCESS read-only
    STATUS     current
    DESCRIPTION
            "-- empty --"
    ::= { lcsStatusXdslVdsl2Advanced 156 }

-- {TABLE} 1.3.6.1.4.1.2356.11.1.99.3.25.157
lcsStatusXdslVdsl2AdvancedDsSnrPerSubCarrierTable OBJECT-TYPE
    SYNTAX     SEQUENCE OF LcsStatusXdslVdsl2AdvancedDsSnrPerSubCarrierEntry
    MAX-ACCESS not-accessible
    STATUS     current
    DESCRIPTION
            "-- empty --"
    ::= { lcsStatusXdslVdsl2Advanced 157 }

-- {ROW} 1.3.6.1.4.1.2356.11.1.99.3.25.157.1
lcsStatusXdslVdsl2AdvancedDsSnrPerSubCarrierEntry OBJECT-TYPE
    SYNTAX     LcsStatusXdslVdsl2AdvancedDsSnrPerSubCarrierEntry
    MAX-ACCESS not-accessible
    STATUS     current
    DESCRIPTION
            ""
    INDEX {
            lcsStatusXdslVdsl2AdvancedDsSnrPerSubCarrierEntrySubCarrier
          }
    ::= { lcsStatusXdslVdsl2AdvancedDsSnrPerSubCarrierTable 1 }

LcsStatusXdslVdsl2AdvancedDsSnrPerSubCarrierEntry ::= SEQUENCE {
            lcsStatusXdslVdsl2AdvancedDsSnrPerSubCarrierEntrySubCarrier DisplayString,
            lcsStatusXdslVdsl2AdvancedDsSnrPerSubCarrierEntryX0 Integer32,
            lcsStatusXdslVdsl2AdvancedDsSnrPerSubCarrierEntryX1 Integer32,
            lcsStatusXdslVdsl2AdvancedDsSnrPerSubCarrierEntryX2 Integer32,
            lcsStatusXdslVdsl2AdvancedDsSnrPerSubCarrierEntryX3 Integer32,
            lcsStatusXdslVdsl2AdvancedDsSnrPerSubCarrierEntryX4 Integer32,
            lcsStatusXdslVdsl2AdvancedDsSnrPerSubCarrierEntryX5 Integer32,
            lcsStatusXdslVdsl2AdvancedDsSnrPerSubCarrierEntryX6 Integer32,
            lcsStatusXdslVdsl2AdvancedDsSnrPerSubCarrierEntryX7 Integer32,
            lcsStatusXdslVdsl2AdvancedDsSnrPerSubCarrierEntryX8 Integer32,
            lcsStatusXdslVdsl2AdvancedDsSnrPerSubCarrierEntryX9 Integer32
    }

-- {COLUMN} 1.3.6.1.4.1.2356.11.1.99.3.25.157.1.1
lcsStatusXdslVdsl2AdvancedDsSnrPerSubCarrierEntrySubCarrier OBJECT-TYPE
    SYNTAX     DisplayString (SIZE(0..255))
    MAX-ACCESS read-only
    STATUS     current
    DESCRIPTION
            "-- empty --"
    ::= { lcsStatusXdslVdsl2AdvancedDsSnrPerSubCarrierEntry 1 }

-- {COLUMN} 1.3.6.1.4.1.2356.11.1.99.3.25.157.1.2
lcsStatusXdslVdsl2AdvancedDsSnrPerSubCarrierEntryX0 OBJECT-TYPE
    SYNTAX     Integer32 (0..2147483647)
    MAX-ACCESS read-only
    STATUS     current
    DESCRIPTION
            "-- empty --"
    ::= { lcsStatusXdslVdsl2AdvancedDsSnrPerSubCarrierEntry 2 }

-- {COLUMN} 1.3.6.1.4.1.2356.11.1.99.3.25.157.1.3
lcsStatusXdslVdsl2AdvancedDsSnrPerSubCarrierEntryX1 OBJECT-TYPE
    SYNTAX     Integer32 (0..2147483647)
    MAX-ACCESS read-only
    STATUS     current
    DESCRIPTION
            "-- empty --"
    ::= { lcsStatusXdslVdsl2AdvancedDsSnrPerSubCarrierEntry 3 }

-- {COLUMN} 1.3.6.1.4.1.2356.11.1.99.3.25.157.1.4
lcsStatusXdslVdsl2AdvancedDsSnrPerSubCarrierEntryX2 OBJECT-TYPE
    SYNTAX     Integer32 (0..2147483647)
    MAX-ACCESS read-only
    STATUS     current
    DESCRIPTION
            "-- empty --"
    ::= { lcsStatusXdslVdsl2AdvancedDsSnrPerSubCarrierEntry 4 }

-- {COLUMN} 1.3.6.1.4.1.2356.11.1.99.3.25.157.1.5
lcsStatusXdslVdsl2AdvancedDsSnrPerSubCarrierEntryX3 OBJECT-TYPE
    SYNTAX     Integer32 (0..2147483647)
    MAX-ACCESS read-only
    STATUS     current
    DESCRIPTION
            "-- empty --"
    ::= { lcsStatusXdslVdsl2AdvancedDsSnrPerSubCarrierEntry 5 }

-- {COLUMN} 1.3.6.1.4.1.2356.11.1.99.3.25.157.1.6
lcsStatusXdslVdsl2AdvancedDsSnrPerSubCarrierEntryX4 OBJECT-TYPE
    SYNTAX     Integer32 (0..2147483647)
    MAX-ACCESS read-only
    STATUS     current
    DESCRIPTION
            "-- empty --"
    ::= { lcsStatusXdslVdsl2AdvancedDsSnrPerSubCarrierEntry 6 }

-- {COLUMN} 1.3.6.1.4.1.2356.11.1.99.3.25.157.1.7
lcsStatusXdslVdsl2AdvancedDsSnrPerSubCarrierEntryX5 OBJECT-TYPE
    SYNTAX     Integer32 (0..2147483647)
    MAX-ACCESS read-only
    STATUS     current
    DESCRIPTION
            "-- empty --"
    ::= { lcsStatusXdslVdsl2AdvancedDsSnrPerSubCarrierEntry 7 }

-- {COLUMN} 1.3.6.1.4.1.2356.11.1.99.3.25.157.1.8
lcsStatusXdslVdsl2AdvancedDsSnrPerSubCarrierEntryX6 OBJECT-TYPE
    SYNTAX     Integer32 (0..2147483647)
    MAX-ACCESS read-only
    STATUS     current
    DESCRIPTION
            "-- empty --"
    ::= { lcsStatusXdslVdsl2AdvancedDsSnrPerSubCarrierEntry 8 }

-- {COLUMN} 1.3.6.1.4.1.2356.11.1.99.3.25.157.1.9
lcsStatusXdslVdsl2AdvancedDsSnrPerSubCarrierEntryX7 OBJECT-TYPE
    SYNTAX     Integer32 (0..2147483647)
    MAX-ACCESS read-only
    STATUS     current
    DESCRIPTION
            "-- empty --"
    ::= { lcsStatusXdslVdsl2AdvancedDsSnrPerSubCarrierEntry 9 }

-- {COLUMN} 1.3.6.1.4.1.2356.11.1.99.3.25.157.1.10
lcsStatusXdslVdsl2AdvancedDsSnrPerSubCarrierEntryX8 OBJECT-TYPE
    SYNTAX     Integer32 (0..2147483647)
    MAX-ACCESS read-only
    STATUS     current
    DESCRIPTION
            "-- empty --"
    ::= { lcsStatusXdslVdsl2AdvancedDsSnrPerSubCarrierEntry 10 }

-- {COLUMN} 1.3.6.1.4.1.2356.11.1.99.3.25.157.1.11
lcsStatusXdslVdsl2AdvancedDsSnrPerSubCarrierEntryX9 OBJECT-TYPE
    SYNTAX     Integer32 (0..2147483647)
    MAX-ACCESS read-only
    STATUS     current
    DESCRIPTION
            "-- empty --"
    ::= { lcsStatusXdslVdsl2AdvancedDsSnrPerSubCarrierEntry 11 }

-- {SCALAR} 1.3.6.1.4.1.2356.11.1.99.3.25.158
lcsStatusXdslVdsl2AdvancedDsLineOptions OBJECT-TYPE
    SYNTAX     BITS {
                  eBitswap (4),
                  eTrellis (5),
                  eVirtualNoise (6),
                  eRetransmission (7)
            }
    MAX-ACCESS read-only
    STATUS     current
    DESCRIPTION
            "-- empty --"
    ::= { lcsStatusXdslVdsl2Advanced 158 }

-- {SCALAR} 1.3.6.1.4.1.2356.11.1.99.3.25.159
lcsStatusXdslVdsl2AdvancedRx-Packet-count-64 OBJECT-TYPE
    SYNTAX     Integer32 (0..2147483647)
    MAX-ACCESS read-only
    STATUS     current
    DESCRIPTION
            ""
    ::= { lcsStatusXdslVdsl2Advanced 159 }

-- {SCALAR} 1.3.6.1.4.1.2356.11.1.99.3.25.160
lcsStatusXdslVdsl2AdvancedWAN-Tx-Packet-count-64 OBJECT-TYPE
    SYNTAX     Integer32 (0..2147483647)
    MAX-ACCESS read-only
    STATUS     current
    DESCRIPTION
            ""
    ::= { lcsStatusXdslVdsl2Advanced 160 }

-- {SCALAR} 1.3.6.1.4.1.2356.11.1.99.3.25.161
lcsStatusXdslVdsl2AdvancedWAN-Tx-Packet-bytes-64 OBJECT-TYPE
    SYNTAX     Integer32 (0..2147483647)
    MAX-ACCESS read-only
    STATUS     current
    DESCRIPTION
            ""
    ::= { lcsStatusXdslVdsl2Advanced 161 }

-- {SCALAR} 1.3.6.1.4.1.2356.11.1.99.3.25.170
lcsStatusXdslVdsl2AdvancedWAN-Rx-Packet-count-64 OBJECT-TYPE
    SYNTAX     Integer32 (0..2147483647)
    MAX-ACCESS read-only
    STATUS     current
    DESCRIPTION
            ""
    ::= { lcsStatusXdslVdsl2Advanced 170 }

-- {SCALAR} 1.3.6.1.4.1.2356.11.1.99.3.25.171
lcsStatusXdslVdsl2AdvancedWAN-Rx-Packet-bytes-64 OBJECT-TYPE
    SYNTAX     Integer32 (0..2147483647)
    MAX-ACCESS read-only
    STATUS     current
    DESCRIPTION
            ""
    ::= { lcsStatusXdslVdsl2Advanced 171 }

-- {SCALAR} 1.3.6.1.4.1.2356.11.1.99.3.34
lcsStatusXdslVdsl2InpDownstreamSymbols OBJECT-TYPE
    SYNTAX     DisplayString (SIZE(0..3))
    MAX-ACCESS read-only
    STATUS     current
    DESCRIPTION
            "-- empty --"
    ::= { lcsStatusXdslVdsl2 34 }

-- {SCALAR} 1.3.6.1.4.1.2356.11.1.99.3.35
lcsStatusXdslVdsl2InpUpstreamSymbols OBJECT-TYPE
    SYNTAX     DisplayString (SIZE(0..3))
    MAX-ACCESS read-only
    STATUS     current
    DESCRIPTION
            "-- empty --"
    ::= { lcsStatusXdslVdsl2 35 }

-- {SCALAR} 1.3.6.1.4.1.2356.11.1.99.3.36
lcsStatusXdslVdsl2AttainableDataRateDownstreamKbps OBJECT-TYPE
    SYNTAX     Integer32 (0..2147483647)
    MAX-ACCESS read-only
    STATUS     current
    DESCRIPTION
            "-- empty --"
    ::= { lcsStatusXdslVdsl2 36 }

-- {SCALAR} 1.3.6.1.4.1.2356.11.1.99.3.37
lcsStatusXdslVdsl2AttainableDataRateUpstreamKbps OBJECT-TYPE
    SYNTAX     Integer32 (0..2147483647)
    MAX-ACCESS read-only
    STATUS     current
    DESCRIPTION
            "-- empty --"
    ::= { lcsStatusXdslVdsl2 37 }

-- {SCALAR} 1.3.6.1.4.1.2356.11.1.99.3.40
lcsStatusXdslVdsl2VdslProfile OBJECT-TYPE
    SYNTAX     INTEGER {
                  eUnknown (0),
                  e8a (1),
                  e8b (2),
                  e8c (3),
                  e8d (4),
                  e12a (5),
                  e12b (6),
                  e17a (7),
                  e30a (8),
                  e35b (9)
            }
    MAX-ACCESS read-only
    STATUS     current
    DESCRIPTION
            "-- empty --"
    ::= { lcsStatusXdslVdsl2 40 }

-- {SCALAR} 1.3.6.1.4.1.2356.11.1.99.3.41
lcsStatusXdslVdsl2DslamManufacturer OBJECT-TYPE
    SYNTAX     DisplayString (SIZE(0..63))
    MAX-ACCESS read-only
    STATUS     current
    DESCRIPTION
            "-- empty --"
    ::= { lcsStatusXdslVdsl2 41 }

-- {SCALAR} 1.3.6.1.4.1.2356.11.1.99.3.42
lcsStatusXdslVdsl2DslamVersion OBJECT-TYPE
    SYNTAX     DisplayString (SIZE(0..34))
    MAX-ACCESS read-only
    STATUS     current
    DESCRIPTION
            "-- empty --"
    ::= { lcsStatusXdslVdsl2 42 }

-- {SCALAR} 1.3.6.1.4.1.2356.11.1.99.3.43
lcsStatusXdslVdsl2DslamSerialNumber OBJECT-TYPE
    SYNTAX     DisplayString (SIZE(0..66))
    MAX-ACCESS read-only
    STATUS     current
    DESCRIPTION
            "-- empty --"
    ::= { lcsStatusXdslVdsl2 43 }

-- {SCALAR} 1.3.6.1.4.1.2356.11.1.99.3.45
lcsStatusXdslVdsl2VectoringSupport OBJECT-TYPE
    SYNTAX     INTEGER {
                  eNo (1),
                  eYes (2),
                  eFriendly (3)
            }
    MAX-ACCESS read-only
    STATUS     current
    DESCRIPTION
            "-- empty --"
    ::= { lcsStatusXdslVdsl2 45 }

-- {SCALAR} 1.3.6.1.4.1.2356.11.1.99.3.46
lcsStatusXdslVdsl2Vectoring OBJECT-TYPE
    SYNTAX     INTEGER {
                  eNo (1),
                  eYes (2),
                  eFriendly (3)
            }
    MAX-ACCESS read-only
    STATUS     current
    DESCRIPTION
            "-- empty --"
    ::= { lcsStatusXdslVdsl2 46 }

-- {SCALAR} 1.3.6.1.4.1.2356.11.1.99.3.53
lcsStatusXdslVdsl2ConnectionCount OBJECT-TYPE
    SYNTAX     Integer32 (0..2147483647)
    MAX-ACCESS read-only
    STATUS     current
    DESCRIPTION
            "-- empty --"
    ::= { lcsStatusXdslVdsl2 53 }

-- {SCALAR} 1.3.6.1.4.1.2356.11.1.99.3.54
lcsStatusXdslVdsl2ConnectionDuration OBJECT-TYPE
    SYNTAX     Gauge32
    MAX-ACCESS read-only
    STATUS     current
    DESCRIPTION
            "-- empty --"
    ::= { lcsStatusXdslVdsl2 54 }

-- {SCALAR} 1.3.6.1.4.1.2356.11.1.99.3.200
lcsStatusXdslVdsl2WanBridge OBJECT-TYPE
    SYNTAX     INTEGER {
                  eNo (0),
                  eYes (1)
            }
    MAX-ACCESS read-only
    STATUS     current
    DESCRIPTION
            "-- empty --"
    ::= { lcsStatusXdslVdsl2 200 }

-- {NODE} 1.3.6.1.4.1.2356.11.1.99.3.500
lcsStatusXdslVdsl2Modem OBJECT IDENTIFIER ::= { lcsStatusXdslVdsl2 500 }

-- {SCALAR} 1.3.6.1.4.1.2356.11.1.99.3.500.1
lcsStatusXdslVdsl2ModemModemState OBJECT-TYPE
    SYNTAX     INTEGER {
                  eNoCommunicationsPort (0),
                  eError (1),
                  eFileSystem (2),
                  eBootHeader (3),
                  eUploadingBootstrap (4),
                  eUploadingMemoryTest (5),
                  eMemoryTest (6),
                  eOptions (7),
                  eUploadingUBoot (8),
                  eQuickMemoryTest (9),
                  eUploadingKernel (10),
                  eUploadingRamdisk (11),
                  eUploadingFirmware (12),
                  eWaitForHeartbeat (13),
                  eRunning (14),
                  eUploadingGphyFirmware (15),
                  eDisabled (16)
            }
    MAX-ACCESS read-only
    STATUS     current
    DESCRIPTION
            "-- empty --"
    ::= { lcsStatusXdslVdsl2Modem 1 }

-- {SCALAR} 1.3.6.1.4.1.2356.11.1.99.3.500.2
lcsStatusXdslVdsl2ModemOptions OBJECT-TYPE
    SYNTAX     Integer32 (0..255)
    MAX-ACCESS read-only
    STATUS     current
    DESCRIPTION
            "-- empty --"
    ::= { lcsStatusXdslVdsl2Modem 2 }

-- {SCALAR} 1.3.6.1.4.1.2356.11.1.99.3.500.3
lcsStatusXdslVdsl2ModemMemoryTest OBJECT-TYPE
    SYNTAX     INTEGER {
                  eNotTested (0),
                  eTimeout (1),
                  eFailed (2),
                  eOk (3)
            }
    MAX-ACCESS read-only
    STATUS     current
    DESCRIPTION
            "-- empty --"
    ::= { lcsStatusXdslVdsl2Modem 3 }

-- {SCALAR} 1.3.6.1.4.1.2356.11.1.99.3.500.4
lcsStatusXdslVdsl2ModemRebootModem OBJECT-TYPE
    SYNTAX     DisplayString
    MAX-ACCESS read-write
    STATUS     current
    DESCRIPTION
            "-- empty --"
    ::= { lcsStatusXdslVdsl2Modem 4 }

-- {SCALAR} 1.3.6.1.4.1.2356.11.1.99.3.500.5
lcsStatusXdslVdsl2ModemLink OBJECT-TYPE
    SYNTAX     Integer32 (0..2147483647)
    MAX-ACCESS read-only
    STATUS     current
    DESCRIPTION
            "-- empty --"
    ::= { lcsStatusXdslVdsl2Modem 5 }

-- {SCALAR} 1.3.6.1.4.1.2356.11.1.99.3.500.6
lcsStatusXdslVdsl2ModemLastError OBJECT-TYPE
    SYNTAX     DisplayString (SIZE(0..63))
    MAX-ACCESS read-only
    STATUS     current
    DESCRIPTION
            "-- empty --"
    ::= { lcsStatusXdslVdsl2Modem 6 }

-- {SCALAR} 1.3.6.1.4.1.2356.11.1.99.3.500.10
lcsStatusXdslVdsl2ModemDslApiVersion OBJECT-TYPE
    SYNTAX     DisplayString (SIZE(0..31))
    MAX-ACCESS read-only
    STATUS     current
    DESCRIPTION
            "-- empty --"
    ::= { lcsStatusXdslVdsl2Modem 10 }

-- {SCALAR} 1.3.6.1.4.1.2356.11.1.99.3.500.11
lcsStatusXdslVdsl2ModemDspFirmwareVersion OBJECT-TYPE
    SYNTAX     DisplayString (SIZE(0..31))
    MAX-ACCESS read-only
    STATUS     current
    DESCRIPTION
            "-- empty --"
    ::= { lcsStatusXdslVdsl2Modem 11 }

-- {SCALAR} 1.3.6.1.4.1.2356.11.1.99.3.500.12
lcsStatusXdslVdsl2ModemHardwareVersion OBJECT-TYPE
    SYNTAX     DisplayString (SIZE(0..31))
    MAX-ACCESS read-only
    STATUS     current
    DESCRIPTION
            "-- empty --"
    ::= { lcsStatusXdslVdsl2Modem 12 }

-- {SCALAR} 1.3.6.1.4.1.2356.11.1.99.3.500.13
lcsStatusXdslVdsl2ModemChipsetType OBJECT-TYPE
    SYNTAX     DisplayString (SIZE(0..31))
    MAX-ACCESS read-only
    STATUS     current
    DESCRIPTION
            "-- empty --"
    ::= { lcsStatusXdslVdsl2Modem 13 }

-- {SCALAR} 1.3.6.1.4.1.2356.11.1.99.3.500.14
lcsStatusXdslVdsl2ModemDriverVersion OBJECT-TYPE
    SYNTAX     DisplayString (SIZE(0..31))
    MAX-ACCESS read-only
    STATUS     current
    DESCRIPTION
            "-- empty --"
    ::= { lcsStatusXdslVdsl2Modem 14 }

-- {SCALAR} 1.3.6.1.4.1.2356.11.1.99.3.500.15
lcsStatusXdslVdsl2ModemBootCount OBJECT-TYPE
    SYNTAX     Integer32 (0..2147483647)
    MAX-ACCESS read-only
    STATUS     current
    DESCRIPTION
            "-- empty --"
    ::= { lcsStatusXdslVdsl2Modem 15 }

-- {SCALAR} 1.3.6.1.4.1.2356.11.1.99.3.500.16
lcsStatusXdslVdsl2ModemHybrid OBJECT-TYPE
    SYNTAX     INTEGER {
                  eBJ (0),
                  eInvalid (1),
                  eB (2),
                  eA (3),
                  eUniversal (4),
                  eUnknown (256)
            }
    MAX-ACCESS read-only
    STATUS     current
    DESCRIPTION
            "-- empty --"
    ::= { lcsStatusXdslVdsl2Modem 16 }

-- {SCALAR} 1.3.6.1.4.1.2356.11.1.99.3.500.21
lcsStatusXdslVdsl2ModemLoad OBJECT-TYPE
    SYNTAX     Integer32 (0..2147483647)
    MAX-ACCESS read-only
    STATUS     current
    DESCRIPTION
            "-- empty --"
    ::= { lcsStatusXdslVdsl2Modem 21 }

-- {SCALAR} 1.3.6.1.4.1.2356.11.1.99.3.500.22
lcsStatusXdslVdsl2ModemLoadUser OBJECT-TYPE
    SYNTAX     Integer32 (0..2147483647)
    MAX-ACCESS read-only
    STATUS     current
    DESCRIPTION
            "-- empty --"
    ::= { lcsStatusXdslVdsl2Modem 22 }

-- {SCALAR} 1.3.6.1.4.1.2356.11.1.99.3.500.23
lcsStatusXdslVdsl2ModemLoadSystem OBJECT-TYPE
    SYNTAX     Integer32 (0..2147483647)
    MAX-ACCESS read-only
    STATUS     current
    DESCRIPTION
            "-- empty --"
    ::= { lcsStatusXdslVdsl2Modem 23 }

-- {SCALAR} 1.3.6.1.4.1.2356.11.1.99.3.500.24
lcsStatusXdslVdsl2ModemLoadIdle OBJECT-TYPE
    SYNTAX     Integer32 (0..2147483647)
    MAX-ACCESS read-only
    STATUS     current
    DESCRIPTION
            "-- empty --"
    ::= { lcsStatusXdslVdsl2Modem 24 }

-- {SCALAR} 1.3.6.1.4.1.2356.11.1.99.3.500.25
lcsStatusXdslVdsl2ModemPotsFirmware OBJECT-TYPE
    SYNTAX     DisplayString (SIZE(0..71))
    MAX-ACCESS read-only
    STATUS     current
    DESCRIPTION
            "-- empty --"
    ::= { lcsStatusXdslVdsl2Modem 25 }

-- {SCALAR} 1.3.6.1.4.1.2356.11.1.99.3.500.26
lcsStatusXdslVdsl2ModemIsdnFirmware OBJECT-TYPE
    SYNTAX     DisplayString (SIZE(0..71))
    MAX-ACCESS read-only
    STATUS     current
    DESCRIPTION
            "-- empty --"
    ::= { lcsStatusXdslVdsl2Modem 26 }

-- {SCALAR} 1.3.6.1.4.1.2356.11.1.99.3.500.27
lcsStatusXdslVdsl2ModemTemperatureDegc OBJECT-TYPE
    SYNTAX     DisplayString (SIZE(0..3))
    MAX-ACCESS read-only
    STATUS     current
    DESCRIPTION
            "-- empty --"
    ::= { lcsStatusXdslVdsl2Modem 27 }

-- {SCALAR} 1.3.6.1.4.1.2356.11.1.99.3.500.28
lcsStatusXdslVdsl2ModemWanAcceleration OBJECT-TYPE
    SYNTAX     INTEGER {
                  eNo (0),
                  eYes (1)
            }
    MAX-ACCESS read-only
    STATUS     current
    DESCRIPTION
            "-- empty --"
    ::= { lcsStatusXdslVdsl2Modem 28 }

-- {SCALAR} 1.3.6.1.4.1.2356.11.1.100
lcsStatusDeleteValues OBJECT-TYPE
    SYNTAX     DisplayString
    MAX-ACCESS read-write
    STATUS     current
    DESCRIPTION
            ""
    ::= { lcsStatus 100 }

-- {NODE} 1.3.6.1.4.1.2356.11.1.101
lcsStatusLbs OBJECT IDENTIFIER ::= { lcsStatus 101 }

-- {TABLE} 1.3.6.1.4.1.2356.11.1.101.1
lcsStatusLbsLogTableTable OBJECT-TYPE
    SYNTAX     SEQUENCE OF LcsStatusLbsLogTableEntry
    MAX-ACCESS not-accessible
    STATUS     current
    DESCRIPTION
            "-- empty --"
    ::= { lcsStatusLbs 1 }

-- {ROW} 1.3.6.1.4.1.2356.11.1.101.1.1
lcsStatusLbsLogTableEntry OBJECT-TYPE
    SYNTAX     LcsStatusLbsLogTableEntry
    MAX-ACCESS not-accessible
    STATUS     current
    DESCRIPTION
            ""
    INDEX {
            lcsStatusLbsLogTableEntryIndex
          }
    ::= { lcsStatusLbsLogTableTable 1 }

LcsStatusLbsLogTableEntry ::= SEQUENCE {
            lcsStatusLbsLogTableEntryIndex Integer32,
            lcsStatusLbsLogTableEntryTime DisplayString,
            lcsStatusLbsLogTableEntryEvent DisplayString
    }

-- {COLUMN} 1.3.6.1.4.1.2356.11.1.101.1.1.1
lcsStatusLbsLogTableEntryIndex OBJECT-TYPE
    SYNTAX     Integer32 (0..2147483647)
    MAX-ACCESS read-only
    STATUS     current
    DESCRIPTION
            "-- empty --"
    ::= { lcsStatusLbsLogTableEntry 1 }

-- {COLUMN} 1.3.6.1.4.1.2356.11.1.101.1.1.2
lcsStatusLbsLogTableEntryTime OBJECT-TYPE
    SYNTAX     DisplayString (SIZE(0..19))
    MAX-ACCESS read-only
    STATUS     current
    DESCRIPTION
            "-- empty --"
    ::= { lcsStatusLbsLogTableEntry 2 }

-- {COLUMN} 1.3.6.1.4.1.2356.11.1.101.1.1.3
lcsStatusLbsLogTableEntryEvent OBJECT-TYPE
    SYNTAX     DisplayString (SIZE(0..200))
    MAX-ACCESS read-only
    STATUS     current
    DESCRIPTION
            "-- empty --"
    ::= { lcsStatusLbsLogTableEntry 3 }

-- {SCALAR} 1.3.6.1.4.1.2356.11.1.101.2
lcsStatusLbsCacheMaxSize OBJECT-TYPE
    SYNTAX     Integer32 (0..2147483647)
    MAX-ACCESS read-only
    STATUS     current
    DESCRIPTION
            "-- empty --"
    ::= { lcsStatusLbs 2 }

-- {SCALAR} 1.3.6.1.4.1.2356.11.1.101.3
lcsStatusLbsCacheOccupied OBJECT-TYPE
    SYNTAX     Integer32 (0..2147483647)
    MAX-ACCESS read-only
    STATUS     current
    DESCRIPTION
            "-- empty --"
    ::= { lcsStatusLbs 3 }

-- {SCALAR} 1.3.6.1.4.1.2356.11.1.101.4
lcsStatusLbsCacheCount OBJECT-TYPE
    SYNTAX     Integer32 (0..2147483647)
    MAX-ACCESS read-only
    STATUS     current
    DESCRIPTION
            "-- empty --"
    ::= { lcsStatusLbs 4 }

-- {SCALAR} 1.3.6.1.4.1.2356.11.1.101.5
lcsStatusLbsRxMeasurements OBJECT-TYPE
    SYNTAX     Integer32 (0..2147483647)
    MAX-ACCESS read-only
    STATUS     current
    DESCRIPTION
            "-- empty --"
    ::= { lcsStatusLbs 5 }

-- {SCALAR} 1.3.6.1.4.1.2356.11.1.101.6
lcsStatusLbsTxMeasurements OBJECT-TYPE
    SYNTAX     Integer32 (0..2147483647)
    MAX-ACCESS read-only
    STATUS     current
    DESCRIPTION
            "-- empty --"
    ::= { lcsStatusLbs 6 }

-- {SCALAR} 1.3.6.1.4.1.2356.11.1.101.7
lcsStatusLbsReconnects OBJECT-TYPE
    SYNTAX     Integer32 (0..2147483647)
    MAX-ACCESS read-only
    STATUS     current
    DESCRIPTION
            "-- empty --"
    ::= { lcsStatusLbs 7 }

-- {SCALAR} 1.3.6.1.4.1.2356.11.1.101.8
lcsStatusLbsTxAggregates OBJECT-TYPE
    SYNTAX     Integer32 (0..2147483647)
    MAX-ACCESS read-only
    STATUS     current
    DESCRIPTION
            "-- empty --"
    ::= { lcsStatusLbs 8 }

-- {SCALAR} 1.3.6.1.4.1.2356.11.1.101.9
lcsStatusLbsDeleteValues OBJECT-TYPE
    SYNTAX     DisplayString
    MAX-ACCESS read-write
    STATUS     current
    DESCRIPTION
            "-- empty --"
    ::= { lcsStatusLbs 9 }

-- {SCALAR} 1.3.6.1.4.1.2356.11.1.101.10
lcsStatusLbsConnected OBJECT-TYPE
    SYNTAX     INTEGER {
                  eNo (0),
                  eYes (1)
            }
    MAX-ACCESS read-only
    STATUS     current
    DESCRIPTION
            "-- empty --"
    ::= { lcsStatusLbs 10 }

-- {SCALAR} 1.3.6.1.4.1.2356.11.1.101.11
lcsStatusLbsOperating OBJECT-TYPE
    SYNTAX     INTEGER {
                  eNo (0),
                  eYes (1)
            }
    MAX-ACCESS read-only
    STATUS     current
    DESCRIPTION
            "-- empty --"
    ::= { lcsStatusLbs 11 }

-- {NODE} 1.3.6.1.4.1.2356.11.1.103
lcsStatusProvisioningServer OBJECT IDENTIFIER ::= { lcsStatus 103 }

-- {SCALAR} 1.3.6.1.4.1.2356.11.1.103.1
lcsStatusProvisioningServerOperating OBJECT-TYPE
    SYNTAX     INTEGER {
                  eNo (0),
                  eYes (1)
            }
    MAX-ACCESS read-only
    STATUS     current
    DESCRIPTION
            "-- empty --"
    ::= { lcsStatusProvisioningServer 1 }

-- {TABLE} 1.3.6.1.4.1.2356.11.1.103.2
lcsStatusProvisioningServerBasestationTable OBJECT-TYPE
    SYNTAX     SEQUENCE OF LcsStatusProvisioningServerBasestationEntry
    MAX-ACCESS not-accessible
    STATUS     current
    DESCRIPTION
            "-- empty --"
    ::= { lcsStatusProvisioningServer 2 }

-- {ROW} 1.3.6.1.4.1.2356.11.1.103.2.1
lcsStatusProvisioningServerBasestationEntry OBJECT-TYPE
    SYNTAX     LcsStatusProvisioningServerBasestationEntry
    MAX-ACCESS not-accessible
    STATUS     current
    DESCRIPTION
            ""
    INDEX {
            lcsStatusProvisioningServerBasestationEntryMacAddress
          }
    ::= { lcsStatusProvisioningServerBasestationTable 1 }

LcsStatusProvisioningServerBasestationEntry ::= SEQUENCE {
            lcsStatusProvisioningServerBasestationEntryMacAddress DisplayString,
            lcsStatusProvisioningServerBasestationEntryIpAddress DisplayString,
            lcsStatusProvisioningServerBasestationEntryConfig DisplayString,
            lcsStatusProvisioningServerBasestationEntryType DisplayString,
            lcsStatusProvisioningServerBasestationEntryRoutingTag Integer32,
            lcsStatusProvisioningServerBasestationEntryLastSeen Gauge32,
            lcsStatusProvisioningServerBasestationEntryFirmware DisplayString
    }

-- {COLUMN} 1.3.6.1.4.1.2356.11.1.103.2.1.1
lcsStatusProvisioningServerBasestationEntryMacAddress OBJECT-TYPE
    SYNTAX     DisplayString (SIZE(0..17))
    MAX-ACCESS read-only
    STATUS     current
    DESCRIPTION
            "-- empty --"
    ::= { lcsStatusProvisioningServerBasestationEntry 1 }

-- {COLUMN} 1.3.6.1.4.1.2356.11.1.103.2.1.2
lcsStatusProvisioningServerBasestationEntryIpAddress OBJECT-TYPE
    SYNTAX     DisplayString (SIZE(0..39))
    MAX-ACCESS read-only
    STATUS     current
    DESCRIPTION
            "-- empty --"
    ::= { lcsStatusProvisioningServerBasestationEntry 2 }

-- {COLUMN} 1.3.6.1.4.1.2356.11.1.103.2.1.3
lcsStatusProvisioningServerBasestationEntryConfig OBJECT-TYPE
    SYNTAX     DisplayString (SIZE(0..15))
    MAX-ACCESS read-only
    STATUS     current
    DESCRIPTION
            "-- empty --"
    ::= { lcsStatusProvisioningServerBasestationEntry 3 }

-- {COLUMN} 1.3.6.1.4.1.2356.11.1.103.2.1.4
lcsStatusProvisioningServerBasestationEntryType OBJECT-TYPE
    SYNTAX     DisplayString (SIZE(0..19))
    MAX-ACCESS read-only
    STATUS     current
    DESCRIPTION
            "-- empty --"
    ::= { lcsStatusProvisioningServerBasestationEntry 4 }

-- {COLUMN} 1.3.6.1.4.1.2356.11.1.103.2.1.5
lcsStatusProvisioningServerBasestationEntryRoutingTag OBJECT-TYPE
    SYNTAX     Integer32 (0..65535)
    MAX-ACCESS read-only
    STATUS     current
    DESCRIPTION
            "-- empty --"
    ::= { lcsStatusProvisioningServerBasestationEntry 5 }

-- {COLUMN} 1.3.6.1.4.1.2356.11.1.103.2.1.6
lcsStatusProvisioningServerBasestationEntryLastSeen OBJECT-TYPE
    SYNTAX     Gauge32
    MAX-ACCESS read-only
    STATUS     current
    DESCRIPTION
            "-- empty --"
    ::= { lcsStatusProvisioningServerBasestationEntry 6 }

-- {COLUMN} 1.3.6.1.4.1.2356.11.1.103.2.1.7
lcsStatusProvisioningServerBasestationEntryFirmware OBJECT-TYPE
    SYNTAX     DisplayString (SIZE(0..15))
    MAX-ACCESS read-only
    STATUS     current
    DESCRIPTION
            "-- empty --"
    ::= { lcsStatusProvisioningServerBasestationEntry 7 }

-- {SCALAR} 1.3.6.1.4.1.2356.11.1.103.3
lcsStatusProvisioningServerDeleteBase OBJECT-TYPE
    SYNTAX     DisplayString
    MAX-ACCESS read-write
    STATUS     current
    DESCRIPTION
            "-- empty --"
    ::= { lcsStatusProvisioningServer 3 }

-- {NODE} 1.3.6.1.4.1.2356.11.1.104
lcsStatusBonjourProxy OBJECT IDENTIFIER ::= { lcsStatus 104 }

-- {SCALAR} 1.3.6.1.4.1.2356.11.1.104.1
lcsStatusBonjourProxyInstanceCount OBJECT-TYPE
    SYNTAX     Integer32 (0..2147483647)
    MAX-ACCESS read-only
    STATUS     current
    DESCRIPTION
            "-- empty --"
    ::= { lcsStatusBonjourProxy 1 }

-- {SCALAR} 1.3.6.1.4.1.2356.11.1.104.4
lcsStatusBonjourProxyClearCache OBJECT-TYPE
    SYNTAX     DisplayString
    MAX-ACCESS read-write
    STATUS     current
    DESCRIPTION
            "-- empty --"
    ::= { lcsStatusBonjourProxy 4 }

-- {NODE} 1.3.6.1.4.1.2356.11.1.105
lcsStatusOam OBJECT IDENTIFIER ::= { lcsStatus 105 }

-- {TABLE} 1.3.6.1.4.1.2356.11.1.105.1
lcsStatusOamInterfacesTable OBJECT-TYPE
    SYNTAX     SEQUENCE OF LcsStatusOamInterfacesEntry
    MAX-ACCESS not-accessible
    STATUS     current
    DESCRIPTION
            "-- empty --"
    ::= { lcsStatusOam 1 }

-- {ROW} 1.3.6.1.4.1.2356.11.1.105.1.1
lcsStatusOamInterfacesEntry OBJECT-TYPE
    SYNTAX     LcsStatusOamInterfacesEntry
    MAX-ACCESS not-accessible
    STATUS     current
    DESCRIPTION
            ""
    INDEX {
            lcsStatusOamInterfacesEntryName
          }
    ::= { lcsStatusOamInterfacesTable 1 }

LcsStatusOamInterfacesEntry ::= SEQUENCE {
            lcsStatusOamInterfacesEntryName DisplayString,
            lcsStatusOamInterfacesEntryStatus INTEGER
    }

-- {COLUMN} 1.3.6.1.4.1.2356.11.1.105.1.1.1
lcsStatusOamInterfacesEntryName OBJECT-TYPE
    SYNTAX     DisplayString (SIZE(0..255))
    MAX-ACCESS read-only
    STATUS     current
    DESCRIPTION
            "-- empty --"
    ::= { lcsStatusOamInterfacesEntry 1 }

-- {COLUMN} 1.3.6.1.4.1.2356.11.1.105.1.1.2
lcsStatusOamInterfacesEntryStatus OBJECT-TYPE
    SYNTAX     INTEGER {
                  eFault (0),
                  eDiscovery (1),
                  ePeerPresent (2),
                  eSynchronized (3)
            }
    MAX-ACCESS read-only
    STATUS     current
    DESCRIPTION
            "-- empty --"
    ::= { lcsStatusOamInterfacesEntry 2 }

-- {TABLE} 1.3.6.1.4.1.2356.11.1.105.2
lcsStatusOamPeersTable OBJECT-TYPE
    SYNTAX     SEQUENCE OF LcsStatusOamPeersEntry
    MAX-ACCESS not-accessible
    STATUS     current
    DESCRIPTION
            "-- empty --"
    ::= { lcsStatusOam 2 }

-- {ROW} 1.3.6.1.4.1.2356.11.1.105.2.1
lcsStatusOamPeersEntry OBJECT-TYPE
    SYNTAX     LcsStatusOamPeersEntry
    MAX-ACCESS not-accessible
    STATUS     current
    DESCRIPTION
            ""
    INDEX {
            lcsStatusOamPeersEntryName
          }
    ::= { lcsStatusOamPeersTable 1 }

LcsStatusOamPeersEntry ::= SEQUENCE {
            lcsStatusOamPeersEntryName DisplayString,
            lcsStatusOamPeersEntryMacAddress MacAddress,
            lcsStatusOamPeersEntryOui OCTET STRING,
            lcsStatusOamPeersEntryMode INTEGER,
            lcsStatusOamPeersEntryLinkMonitor INTEGER,
            lcsStatusOamPeersEntryRemoteLoopback INTEGER,
            lcsStatusOamPeersEntryMibRetrieval INTEGER,
            lcsStatusOamPeersEntryMtu Integer32,
            lcsStatusOamPeersEntryUnidirection INTEGER,
            lcsStatusOamPeersEntryVendorInfo Integer32
    }

-- {COLUMN} 1.3.6.1.4.1.2356.11.1.105.2.1.1
lcsStatusOamPeersEntryName OBJECT-TYPE
    SYNTAX     DisplayString (SIZE(0..255))
    MAX-ACCESS read-only
    STATUS     current
    DESCRIPTION
            "-- empty --"
    ::= { lcsStatusOamPeersEntry 1 }

-- {COLUMN} 1.3.6.1.4.1.2356.11.1.105.2.1.2
lcsStatusOamPeersEntryMacAddress OBJECT-TYPE
    SYNTAX     MacAddress
    MAX-ACCESS read-only
    STATUS     current
    DESCRIPTION
            "-- empty --"
    ::= { lcsStatusOamPeersEntry 2 }

-- {COLUMN} 1.3.6.1.4.1.2356.11.1.105.2.1.3
lcsStatusOamPeersEntryOui OBJECT-TYPE
    SYNTAX     OCTET STRING
    MAX-ACCESS read-only
    STATUS     current
    DESCRIPTION
            "-- empty --"
    ::= { lcsStatusOamPeersEntry 3 }

-- {COLUMN} 1.3.6.1.4.1.2356.11.1.105.2.1.4
lcsStatusOamPeersEntryMode OBJECT-TYPE
    SYNTAX     INTEGER {
                  ePassive (0),
                  eActive (1)
            }
    MAX-ACCESS read-only
    STATUS     current
    DESCRIPTION
            "-- empty --"
    ::= { lcsStatusOamPeersEntry 4 }

-- {COLUMN} 1.3.6.1.4.1.2356.11.1.105.2.1.5
lcsStatusOamPeersEntryLinkMonitor OBJECT-TYPE
    SYNTAX     INTEGER {
                  eNo (0),
                  eYes (1)
            }
    MAX-ACCESS read-only
    STATUS     current
    DESCRIPTION
            "-- empty --"
    ::= { lcsStatusOamPeersEntry 5 }

-- {COLUMN} 1.3.6.1.4.1.2356.11.1.105.2.1.6
lcsStatusOamPeersEntryRemoteLoopback OBJECT-TYPE
    SYNTAX     INTEGER {
                  eNo (0),
                  eYes (1)
            }
    MAX-ACCESS read-only
    STATUS     current
    DESCRIPTION
            "-- empty --"
    ::= { lcsStatusOamPeersEntry 6 }

-- {COLUMN} 1.3.6.1.4.1.2356.11.1.105.2.1.7
lcsStatusOamPeersEntryMibRetrieval OBJECT-TYPE
    SYNTAX     INTEGER {
                  eNo (0),
                  eYes (1)
            }
    MAX-ACCESS read-only
    STATUS     current
    DESCRIPTION
            "-- empty --"
    ::= { lcsStatusOamPeersEntry 7 }

-- {COLUMN} 1.3.6.1.4.1.2356.11.1.105.2.1.8
lcsStatusOamPeersEntryMtu OBJECT-TYPE
    SYNTAX     Integer32 (0..65535)
    MAX-ACCESS read-only
    STATUS     current
    DESCRIPTION
            "-- empty --"
    ::= { lcsStatusOamPeersEntry 8 }

-- {COLUMN} 1.3.6.1.4.1.2356.11.1.105.2.1.9
lcsStatusOamPeersEntryUnidirection OBJECT-TYPE
    SYNTAX     INTEGER {
                  eNo (0),
                  eYes (1)
            }
    MAX-ACCESS read-only
    STATUS     current
    DESCRIPTION
            "-- empty --"
    ::= { lcsStatusOamPeersEntry 9 }

-- {COLUMN} 1.3.6.1.4.1.2356.11.1.105.2.1.10
lcsStatusOamPeersEntryVendorInfo OBJECT-TYPE
    SYNTAX     Integer32 (0..2147483647)
    MAX-ACCESS read-only
    STATUS     current
    DESCRIPTION
            "-- empty --"
    ::= { lcsStatusOamPeersEntry 10 }

-- {NODE} 1.3.6.1.4.1.2356.11.1.107
lcsStatusAfu OBJECT IDENTIFIER ::= { lcsStatus 107 }

-- {SCALAR} 1.3.6.1.4.1.2356.11.1.107.1
lcsStatusAfuMode OBJECT-TYPE
    SYNTAX     INTEGER {
                  eManual (0),
                  eCheck (1),
                  eCheckAndUpdate (2)
            }
    MAX-ACCESS read-only
    STATUS     current
    DESCRIPTION
            "-- empty --"
    ::= { lcsStatusAfu 1 }

-- {SCALAR} 1.3.6.1.4.1.2356.11.1.107.2
lcsStatusAfuLastCheck OBJECT-TYPE
    SYNTAX     DisplayString
    MAX-ACCESS read-only
    STATUS     current
    DESCRIPTION
            "-- empty --"
    ::= { lcsStatusAfu 2 }

-- {SCALAR} 1.3.6.1.4.1.2356.11.1.107.3
lcsStatusAfuNextCheck OBJECT-TYPE
    SYNTAX     DisplayString
    MAX-ACCESS read-only
    STATUS     current
    DESCRIPTION
            "-- empty --"
    ::= { lcsStatusAfu 3 }

-- {SCALAR} 1.3.6.1.4.1.2356.11.1.107.4
lcsStatusAfuUpdateCandidate OBJECT-TYPE
    SYNTAX     DisplayString
    MAX-ACCESS read-only
    STATUS     current
    DESCRIPTION
            "-- empty --"
    ::= { lcsStatusAfu 4 }

-- {SCALAR} 1.3.6.1.4.1.2356.11.1.107.5
lcsStatusAfuState OBJECT-TYPE
    SYNTAX     INTEGER {
                  eClosed (0),
                  eClosing (1),
                  eCancel (2),
                  eIdle (3),
                  eInitializing (4),
                  eWorking (5),
                  eTesting (6),
                  eRequesting (7),
                  eContactingUpdateserver (8),
                  eProcessingResponse (9),
                  eDownloading (10),
                  eVerifyingDownload (11),
                  eInstalling (12),
                  eReboot (13),
                  eContinueInstallation (14),
                  ePrepareVerifyingInstallation (15),
                  eVerifyingInstallation (16),
                  eResetting (17),
                  eWaiting (18),
                  eWaitingForInstallation (19)
            }
    MAX-ACCESS read-only
    STATUS     current
    DESCRIPTION
            "-- empty --"
    ::= { lcsStatusAfu 5 }

-- {SCALAR} 1.3.6.1.4.1.2356.11.1.107.6
lcsStatusAfuCurrentAction OBJECT-TYPE
    SYNTAX     INTEGER {
                  eStartup (0),
                  eNone (2),
                  eAutomaticUpdateCheck (3),
                  eManualUpdateCheck (4),
                  eAutomaticUpdate (5),
                  eManualUpdate (6),
                  eReset (7)
            }
    MAX-ACCESS read-only
    STATUS     current
    DESCRIPTION
            "-- empty --"
    ::= { lcsStatusAfu 6 }

-- {SCALAR} 1.3.6.1.4.1.2356.11.1.107.7
lcsStatusAfuLastResult OBJECT-TYPE
    SYNTAX     INTEGER {
                  eOk (0),
                  eUnknownErrorOccured (30),
                  eActionCancelledByUser (31),
                  eFailedToLoadUpdateServerResponse (32),
                  eInvalidUpdateServerResponse (33),
                  eUpdateServerError (34),
                  eInternalLogicError (35),
                  eInternalMissingDataError (36),
                  eInternalProcessingError (37),
                  eUpdateFileChecksumInvalid (38),
                  eUpdateInstallationFailed (39),
                  eSystemRebootedUnexpectedly (40),
                  eWrongActionHasBeenDetectedWithinGivenContext (41),
                  eWrongStateHasBeenDetectedWithinGivenContext (42),
                  eUpdateServerOfferedBlacklistedFirmware (43),
                  eFirmwareVerificationFailedRetrying (44),
                  eFirmwareVerificationFailed (45),
                  eFirmwareInstallationFailed (46),
                  eRepeatedUpdateSearchHasFailed (47),
                  eUpdateServerUnavailable (48),
                  eUpdateServerBusyRepeating (49),
                  eUpdateServerRepeatedlyBusy (50),
                  eUpdateServerBusyRetryLater (51),
                  eActionCancelledOutOfTimeRange (52),
                  eActionCancelledByUpdateInstallation (53),
                  eActionCancelledByRequest (54),
                  eFailedToQueueAction (55),
                  eFirmwareFallback (56),
                  eActionCancelledByConfigChange (57),
                  eActionCancelledByShutdown (58),
                  eUnknownDownloadErrorOccured (300),
                  eServerUrlInvalid (301),
                  eDownloadFailedInvalidTarget (302),
                  eFailedToCreateDownloadTask (303),
                  eFailedToRequestDownload (304),
                  eFailedToWriteDownloadToFile (305),
                  eFailedToOpenDownloadFile (306),
                  eDownloadCancelled (307),
                  eDownloadTimeout (308),
                  eFailedToConnectToTheServer (309),
                  eDownloadProtocolError (310),
                  eDnsError (311),
                  eOutOfMemory (312),
                  eTooManyConnections (313),
                  eTruststoreNotAvailable (314),
                  eSecureConnectionFailed (315),
                  eFailedToAttachDownloadEventHandles (316),
                  eFailedToReadDownloadStream (317),
                  eUpdateServerEmptyError (401),
                  eServerResponseMismatchesInitialRequest (402),
                  eServerResponseIdMismatch (403),
                  eServerResponseHeaderIncomplete (404),
                  eServerResponseHasInvalidStructure (405),
                  eServerResponseInvalid (406),
                  eServerResponseBodyIncomplete (407),
                  eInternalParameterError (408),
                  eUnsupportedFirmwareTypeProvided (409),
                  eWritingMainConfigurationHasFailed (501),
                  eInvalidMainConfiguration (502),
                  eModifyingMainConfigurationFailed (503),
                  eModifyingBlacklistFailed (504)
            }
    MAX-ACCESS read-only
    STATUS     current
    DESCRIPTION
            "-- empty --"
    ::= { lcsStatusAfu 7 }

-- {SCALAR} 1.3.6.1.4.1.2356.11.1.107.8
lcsStatusAfuPlannedInstall OBJECT-TYPE
    SYNTAX     DisplayString
    MAX-ACCESS read-only
    STATUS     current
    DESCRIPTION
            "Planned-Installation"
    ::= { lcsStatusAfu 8 }

-- {SCALAR} 1.3.6.1.4.1.2356.11.1.107.9
lcsStatusAfuPlannedInstallSec OBJECT-TYPE
    SYNTAX     Counter32
    MAX-ACCESS read-only
    STATUS     current
    DESCRIPTION
            "Planned-Installation-Seconds"
    ::= { lcsStatusAfu 9 }

-- {SCALAR} 1.3.6.1.4.1.2356.11.1.107.10
lcsStatusAfuLastCheckSeconds OBJECT-TYPE
    SYNTAX     Counter32
    MAX-ACCESS read-only
    STATUS     current
    DESCRIPTION
            "-- empty --"
    ::= { lcsStatusAfu 10 }

-- {SCALAR} 1.3.6.1.4.1.2356.11.1.107.11
lcsStatusAfuNextCheckSeconds OBJECT-TYPE
    SYNTAX     Counter32
    MAX-ACCESS read-only
    STATUS     current
    DESCRIPTION
            "-- empty --"
    ::= { lcsStatusAfu 11 }

-- {SCALAR} 1.3.6.1.4.1.2356.11.1.107.12
lcsStatusAfuCurrentVersion OBJECT-TYPE
    SYNTAX     DisplayString
    MAX-ACCESS read-only
    STATUS     current
    DESCRIPTION
            "-- empty --"
    ::= { lcsStatusAfu 12 }

-- {TABLE} 1.3.6.1.4.1.2356.11.1.107.13
lcsStatusAfuLogTableTable OBJECT-TYPE
    SYNTAX     SEQUENCE OF LcsStatusAfuLogTableEntry
    MAX-ACCESS not-accessible
    STATUS     current
    DESCRIPTION
            "-- empty --"
    ::= { lcsStatusAfu 13 }

-- {ROW} 1.3.6.1.4.1.2356.11.1.107.13.1
lcsStatusAfuLogTableEntry OBJECT-TYPE
    SYNTAX     LcsStatusAfuLogTableEntry
    MAX-ACCESS not-accessible
    STATUS     current
    DESCRIPTION
            ""
    INDEX {
            lcsStatusAfuLogTableEntryIndex
          }
    ::= { lcsStatusAfuLogTableTable 1 }

LcsStatusAfuLogTableEntry ::= SEQUENCE {
            lcsStatusAfuLogTableEntryIndex OCTET STRING,
            lcsStatusAfuLogTableEntryTime OCTET STRING,
            lcsStatusAfuLogTableEntryModule OCTET STRING,
            lcsStatusAfuLogTableEntryLogLevel OCTET STRING,
            lcsStatusAfuLogTableEntryLogMessage OCTET STRING
    }

-- {COLUMN} 1.3.6.1.4.1.2356.11.1.107.13.1.1
lcsStatusAfuLogTableEntryIndex OBJECT-TYPE
    SYNTAX     OCTET STRING (SIZE(0..9))
    MAX-ACCESS read-only
    STATUS     current
    DESCRIPTION
            "-- empty --"
    ::= { lcsStatusAfuLogTableEntry 1 }

-- {COLUMN} 1.3.6.1.4.1.2356.11.1.107.13.1.2
lcsStatusAfuLogTableEntryTime OBJECT-TYPE
    SYNTAX     OCTET STRING (SIZE(0..20))
    MAX-ACCESS read-only
    STATUS     current
    DESCRIPTION
            "-- empty --"
    ::= { lcsStatusAfuLogTableEntry 2 }

-- {COLUMN} 1.3.6.1.4.1.2356.11.1.107.13.1.3
lcsStatusAfuLogTableEntryModule OBJECT-TYPE
    SYNTAX     OCTET STRING (SIZE(0..35))
    MAX-ACCESS read-only
    STATUS     current
    DESCRIPTION
            "-- empty --"
    ::= { lcsStatusAfuLogTableEntry 3 }

-- {COLUMN} 1.3.6.1.4.1.2356.11.1.107.13.1.4
lcsStatusAfuLogTableEntryLogLevel OBJECT-TYPE
    SYNTAX     OCTET STRING (SIZE(0..10))
    MAX-ACCESS read-only
    STATUS     current
    DESCRIPTION
            "-- empty --"
    ::= { lcsStatusAfuLogTableEntry 4 }

-- {COLUMN} 1.3.6.1.4.1.2356.11.1.107.13.1.5
lcsStatusAfuLogTableEntryLogMessage OBJECT-TYPE
    SYNTAX     OCTET STRING (SIZE(0..151))
    MAX-ACCESS read-only
    STATUS     current
    DESCRIPTION
            "-- empty --"
    ::= { lcsStatusAfuLogTableEntry 5 }

-- {SCALAR} 1.3.6.1.4.1.2356.11.1.107.14
lcsStatusAfuClearLogTable OBJECT-TYPE
    SYNTAX     DisplayString
    MAX-ACCESS read-write
    STATUS     current
    DESCRIPTION
            "-- empty --"
    ::= { lcsStatusAfu 14 }

-- {SCALAR} 1.3.6.1.4.1.2356.11.1.107.15
lcsStatusAfuLifecycleState OBJECT-TYPE
    SYNTAX     INTEGER {
                  eUnknown (0),
                  eActive (1),
                  eEndOfSale (2),
                  eEndOfLife (3)
            }
    MAX-ACCESS read-only
    STATUS     current
    DESCRIPTION
            "-- empty --"
    ::= { lcsStatusAfu 15 }

-- {NODE} 1.3.6.1.4.1.2356.11.1.108
lcsStatusMCast OBJECT IDENTIFIER ::= { lcsStatus 108 }

-- {NODE} 1.3.6.1.4.1.2356.11.1.108.1
lcsStatusMCastIgmp OBJECT IDENTIFIER ::= { lcsStatusMCast 1 }

-- {TABLE} 1.3.6.1.4.1.2356.11.1.108.1.1
lcsStatusMCastIgmpIgmpProxyTable OBJECT-TYPE
    SYNTAX     SEQUENCE OF LcsStatusMCastIgmpIgmpProxyEntry
    MAX-ACCESS not-accessible
    STATUS     current
    DESCRIPTION
            "-- empty --"
    ::= { lcsStatusMCastIgmp 1 }

-- {ROW} 1.3.6.1.4.1.2356.11.1.108.1.1.1
lcsStatusMCastIgmpIgmpProxyEntry OBJECT-TYPE
    SYNTAX     LcsStatusMCastIgmpIgmpProxyEntry
    MAX-ACCESS not-accessible
    STATUS     current
    DESCRIPTION
            ""
    INDEX {
            lcsStatusMCastIgmpIgmpProxyEntryDownstreamInterface,
            lcsStatusMCastIgmpIgmpProxyEntryUpstreamInterface,
            lcsStatusMCastIgmpIgmpProxyEntryGroup
          }
    ::= { lcsStatusMCastIgmpIgmpProxyTable 1 }

LcsStatusMCastIgmpIgmpProxyEntry ::= SEQUENCE {
            lcsStatusMCastIgmpIgmpProxyEntryDownstreamInterface OCTET STRING,
            lcsStatusMCastIgmpIgmpProxyEntryUpstreamInterface OCTET STRING,
            lcsStatusMCastIgmpIgmpProxyEntryGroup IpAddress
    }

-- {COLUMN} 1.3.6.1.4.1.2356.11.1.108.1.1.1.1
lcsStatusMCastIgmpIgmpProxyEntryDownstreamInterface OBJECT-TYPE
    SYNTAX     OCTET STRING (SIZE(0..26))
    MAX-ACCESS read-only
    STATUS     current
    DESCRIPTION
            "-- empty --"
    ::= { lcsStatusMCastIgmpIgmpProxyEntry 1 }

-- {COLUMN} 1.3.6.1.4.1.2356.11.1.108.1.1.1.2
lcsStatusMCastIgmpIgmpProxyEntryUpstreamInterface OBJECT-TYPE
    SYNTAX     OCTET STRING (SIZE(0..26))
    MAX-ACCESS read-only
    STATUS     current
    DESCRIPTION
            "-- empty --"
    ::= { lcsStatusMCastIgmpIgmpProxyEntry 2 }

-- {COLUMN} 1.3.6.1.4.1.2356.11.1.108.1.1.1.3
lcsStatusMCastIgmpIgmpProxyEntryGroup OBJECT-TYPE
    SYNTAX     IpAddress
    MAX-ACCESS read-only
    STATUS     current
    DESCRIPTION
            "-- empty --"
    ::= { lcsStatusMCastIgmpIgmpProxyEntry 3 }

-- {NODE} 1.3.6.1.4.1.2356.11.1.108.2
lcsStatusMCastMld OBJECT IDENTIFIER ::= { lcsStatusMCast 2 }

-- {TABLE} 1.3.6.1.4.1.2356.11.1.108.2.1
lcsStatusMCastMldMldProxyTable OBJECT-TYPE
    SYNTAX     SEQUENCE OF LcsStatusMCastMldMldProxyEntry
    MAX-ACCESS not-accessible
    STATUS     current
    DESCRIPTION
            "-- empty --"
    ::= { lcsStatusMCastMld 1 }

-- {ROW} 1.3.6.1.4.1.2356.11.1.108.2.1.1
lcsStatusMCastMldMldProxyEntry OBJECT-TYPE
    SYNTAX     LcsStatusMCastMldMldProxyEntry
    MAX-ACCESS not-accessible
    STATUS     current
    DESCRIPTION
            ""
    INDEX {
            lcsStatusMCastMldMldProxyEntryDownstreamInterface,
            lcsStatusMCastMldMldProxyEntryUpstreamInterface,
            lcsStatusMCastMldMldProxyEntryGroup
          }
    ::= { lcsStatusMCastMldMldProxyTable 1 }

LcsStatusMCastMldMldProxyEntry ::= SEQUENCE {
            lcsStatusMCastMldMldProxyEntryDownstreamInterface OCTET STRING,
            lcsStatusMCastMldMldProxyEntryUpstreamInterface OCTET STRING,
            lcsStatusMCastMldMldProxyEntryGroup OCTET STRING
    }

-- {COLUMN} 1.3.6.1.4.1.2356.11.1.108.2.1.1.1
lcsStatusMCastMldMldProxyEntryDownstreamInterface OBJECT-TYPE
    SYNTAX     OCTET STRING (SIZE(0..26))
    MAX-ACCESS read-only
    STATUS     current
    DESCRIPTION
            "-- empty --"
    ::= { lcsStatusMCastMldMldProxyEntry 1 }

-- {COLUMN} 1.3.6.1.4.1.2356.11.1.108.2.1.1.2
lcsStatusMCastMldMldProxyEntryUpstreamInterface OBJECT-TYPE
    SYNTAX     OCTET STRING (SIZE(0..26))
    MAX-ACCESS read-only
    STATUS     current
    DESCRIPTION
            "-- empty --"
    ::= { lcsStatusMCastMldMldProxyEntry 2 }

-- {COLUMN} 1.3.6.1.4.1.2356.11.1.108.2.1.1.3
lcsStatusMCastMldMldProxyEntryGroup OBJECT-TYPE
    SYNTAX     OCTET STRING (SIZE(16..16))
    MAX-ACCESS read-only
    STATUS     current
    DESCRIPTION
            "-- empty --"
    ::= { lcsStatusMCastMldMldProxyEntry 3 }

-- {NODE} 1.3.6.1.4.1.2356.11.1.108.4
lcsStatusMCastPim OBJECT IDENTIFIER ::= { lcsStatusMCast 4 }

-- {NODE} 1.3.6.1.4.1.2356.11.1.108.4.1
lcsStatusMCastPimIpv4 OBJECT IDENTIFIER ::= { lcsStatusMCastPim 1 }

-- {TABLE} 1.3.6.1.4.1.2356.11.1.108.4.1.1
lcsStatusMCastPimIpv4AsmGroupsTable OBJECT-TYPE
    SYNTAX     SEQUENCE OF LcsStatusMCastPimIpv4AsmGroupsEntry
    MAX-ACCESS not-accessible
    STATUS     current
    DESCRIPTION
            "-- empty --"
    ::= { lcsStatusMCastPimIpv4 1 }

-- {ROW} 1.3.6.1.4.1.2356.11.1.108.4.1.1.1
lcsStatusMCastPimIpv4AsmGroupsEntry OBJECT-TYPE
    SYNTAX     LcsStatusMCastPimIpv4AsmGroupsEntry
    MAX-ACCESS not-accessible
    STATUS     current
    DESCRIPTION
            ""
    INDEX {
            lcsStatusMCastPimIpv4AsmGroupsEntryGroup,
            lcsStatusMCastPimIpv4AsmGroupsEntryRtgTag
          }
    ::= { lcsStatusMCastPimIpv4AsmGroupsTable 1 }

LcsStatusMCastPimIpv4AsmGroupsEntry ::= SEQUENCE {
            lcsStatusMCastPimIpv4AsmGroupsEntryGroup IpAddress,
            lcsStatusMCastPimIpv4AsmGroupsEntryRtgTag Unsigned32,
            lcsStatusMCastPimIpv4AsmGroupsEntryRpAddress IpAddress,
            lcsStatusMCastPimIpv4AsmGroupsEntrySsmSourceIp IpAddress,
            lcsStatusMCastPimIpv4AsmGroupsEntryUpstreamRpInterface OCTET STRING,
            lcsStatusMCastPimIpv4AsmGroupsEntryUpstreamSsmInterface OCTET STRING,
            lcsStatusMCastPimIpv4AsmGroupsEntryUpstreamAsmState OCTET STRING,
            lcsStatusMCastPimIpv4AsmGroupsEntryUpstreamSsmState OCTET STRING,
            lcsStatusMCastPimIpv4AsmGroupsEntryDownstreamIfcs Unsigned32
    }

-- {COLUMN} 1.3.6.1.4.1.2356.11.1.108.4.1.1.1.1
lcsStatusMCastPimIpv4AsmGroupsEntryGroup OBJECT-TYPE
    SYNTAX     IpAddress
    MAX-ACCESS read-only
    STATUS     current
    DESCRIPTION
            "-- empty --"
    ::= { lcsStatusMCastPimIpv4AsmGroupsEntry 1 }

-- {COLUMN} 1.3.6.1.4.1.2356.11.1.108.4.1.1.1.2
lcsStatusMCastPimIpv4AsmGroupsEntryRtgTag OBJECT-TYPE
    SYNTAX     Unsigned32 (0..65535)
    MAX-ACCESS read-only
    STATUS     current
    DESCRIPTION
            "-- empty --"
    ::= { lcsStatusMCastPimIpv4AsmGroupsEntry 2 }

-- {COLUMN} 1.3.6.1.4.1.2356.11.1.108.4.1.1.1.3
lcsStatusMCastPimIpv4AsmGroupsEntryRpAddress OBJECT-TYPE
    SYNTAX     IpAddress
    MAX-ACCESS read-only
    STATUS     current
    DESCRIPTION
            "-- empty --"
    ::= { lcsStatusMCastPimIpv4AsmGroupsEntry 3 }

-- {COLUMN} 1.3.6.1.4.1.2356.11.1.108.4.1.1.1.4
lcsStatusMCastPimIpv4AsmGroupsEntrySsmSourceIp OBJECT-TYPE
    SYNTAX     IpAddress
    MAX-ACCESS read-only
    STATUS     current
    DESCRIPTION
            "-- empty --"
    ::= { lcsStatusMCastPimIpv4AsmGroupsEntry 4 }

-- {COLUMN} 1.3.6.1.4.1.2356.11.1.108.4.1.1.1.5
lcsStatusMCastPimIpv4AsmGroupsEntryUpstreamRpInterface OBJECT-TYPE
    SYNTAX     OCTET STRING (SIZE(0..26))
    MAX-ACCESS read-only
    STATUS     current
    DESCRIPTION
            "-- empty --"
    ::= { lcsStatusMCastPimIpv4AsmGroupsEntry 5 }

-- {COLUMN} 1.3.6.1.4.1.2356.11.1.108.4.1.1.1.6
lcsStatusMCastPimIpv4AsmGroupsEntryUpstreamSsmInterface OBJECT-TYPE
    SYNTAX     OCTET STRING (SIZE(0..26))
    MAX-ACCESS read-only
    STATUS     current
    DESCRIPTION
            "-- empty --"
    ::= { lcsStatusMCastPimIpv4AsmGroupsEntry 6 }

-- {COLUMN} 1.3.6.1.4.1.2356.11.1.108.4.1.1.1.7
lcsStatusMCastPimIpv4AsmGroupsEntryUpstreamAsmState OBJECT-TYPE
    SYNTAX     OCTET STRING (SIZE(0..20))
    MAX-ACCESS read-only
    STATUS     current
    DESCRIPTION
            "-- empty --"
    ::= { lcsStatusMCastPimIpv4AsmGroupsEntry 7 }

-- {COLUMN} 1.3.6.1.4.1.2356.11.1.108.4.1.1.1.8
lcsStatusMCastPimIpv4AsmGroupsEntryUpstreamSsmState OBJECT-TYPE
    SYNTAX     OCTET STRING (SIZE(0..20))
    MAX-ACCESS read-only
    STATUS     current
    DESCRIPTION
            "-- empty --"
    ::= { lcsStatusMCastPimIpv4AsmGroupsEntry 8 }

-- {COLUMN} 1.3.6.1.4.1.2356.11.1.108.4.1.1.1.9
lcsStatusMCastPimIpv4AsmGroupsEntryDownstreamIfcs OBJECT-TYPE
    SYNTAX     Unsigned32 (0..4294967295)
    MAX-ACCESS read-only
    STATUS     current
    DESCRIPTION
            "-- empty --"
    ::= { lcsStatusMCastPimIpv4AsmGroupsEntry 9 }

-- {TABLE} 1.3.6.1.4.1.2356.11.1.108.4.1.2
lcsStatusMCastPimIpv4ASMDownIfcsTable OBJECT-TYPE
    SYNTAX     SEQUENCE OF LcsStatusMCastPimIpv4ASMDownIfcsEntry
    MAX-ACCESS not-accessible
    STATUS     current
    DESCRIPTION
            ""
    ::= { lcsStatusMCastPimIpv4 2 }

-- {ROW} 1.3.6.1.4.1.2356.11.1.108.4.1.2.1
lcsStatusMCastPimIpv4ASMDownIfcsEntry OBJECT-TYPE
    SYNTAX     LcsStatusMCastPimIpv4ASMDownIfcsEntry
    MAX-ACCESS not-accessible
    STATUS     current
    DESCRIPTION
            ""
    INDEX {
            lcsStatusMCastPimIpv4ASMDownIfcsEntryGroup,
            lcsStatusMCastPimIpv4ASMDownIfcsEntryRtgTag,
            lcsStatusMCastPimIpv4ASMDownIfcsEntryDownstreamInterface
          }
    ::= { lcsStatusMCastPimIpv4ASMDownIfcsTable 1 }

LcsStatusMCastPimIpv4ASMDownIfcsEntry ::= SEQUENCE {
            lcsStatusMCastPimIpv4ASMDownIfcsEntryGroup IpAddress,
            lcsStatusMCastPimIpv4ASMDownIfcsEntryRtgTag Unsigned32,
            lcsStatusMCastPimIpv4ASMDownIfcsEntryDownstreamInterface OCTET STRING
    }

-- {COLUMN} 1.3.6.1.4.1.2356.11.1.108.4.1.2.1.1
lcsStatusMCastPimIpv4ASMDownIfcsEntryGroup OBJECT-TYPE
    SYNTAX     IpAddress
    MAX-ACCESS read-only
    STATUS     current
    DESCRIPTION
            "-- empty --"
    ::= { lcsStatusMCastPimIpv4ASMDownIfcsEntry 1 }

-- {COLUMN} 1.3.6.1.4.1.2356.11.1.108.4.1.2.1.2
lcsStatusMCastPimIpv4ASMDownIfcsEntryRtgTag OBJECT-TYPE
    SYNTAX     Unsigned32 (0..65535)
    MAX-ACCESS read-only
    STATUS     current
    DESCRIPTION
            "-- empty --"
    ::= { lcsStatusMCastPimIpv4ASMDownIfcsEntry 2 }

-- {COLUMN} 1.3.6.1.4.1.2356.11.1.108.4.1.2.1.3
lcsStatusMCastPimIpv4ASMDownIfcsEntryDownstreamInterface OBJECT-TYPE
    SYNTAX     OCTET STRING (SIZE(0..26))
    MAX-ACCESS read-only
    STATUS     current
    DESCRIPTION
            "-- empty --"
    ::= { lcsStatusMCastPimIpv4ASMDownIfcsEntry 3 }

-- {TABLE} 1.3.6.1.4.1.2356.11.1.108.4.1.3
lcsStatusMCastPimIpv4SsmGroupsTable OBJECT-TYPE
    SYNTAX     SEQUENCE OF LcsStatusMCastPimIpv4SsmGroupsEntry
    MAX-ACCESS not-accessible
    STATUS     current
    DESCRIPTION
            "-- empty --"
    ::= { lcsStatusMCastPimIpv4 3 }

-- {ROW} 1.3.6.1.4.1.2356.11.1.108.4.1.3.1
lcsStatusMCastPimIpv4SsmGroupsEntry OBJECT-TYPE
    SYNTAX     LcsStatusMCastPimIpv4SsmGroupsEntry
    MAX-ACCESS not-accessible
    STATUS     current
    DESCRIPTION
            ""
    INDEX {
            lcsStatusMCastPimIpv4SsmGroupsEntryGroup,
            lcsStatusMCastPimIpv4SsmGroupsEntrySsmSourceIp,
            lcsStatusMCastPimIpv4SsmGroupsEntryRtgTag
          }
    ::= { lcsStatusMCastPimIpv4SsmGroupsTable 1 }

LcsStatusMCastPimIpv4SsmGroupsEntry ::= SEQUENCE {
            lcsStatusMCastPimIpv4SsmGroupsEntryGroup IpAddress,
            lcsStatusMCastPimIpv4SsmGroupsEntrySsmSourceIp IpAddress,
            lcsStatusMCastPimIpv4SsmGroupsEntryRtgTag Unsigned32,
            lcsStatusMCastPimIpv4SsmGroupsEntryUpstreamSsmInterface OCTET STRING,
            lcsStatusMCastPimIpv4SsmGroupsEntryUpstreamSsmState OCTET STRING,
            lcsStatusMCastPimIpv4SsmGroupsEntryDownstreamIfcs Unsigned32
    }

-- {COLUMN} 1.3.6.1.4.1.2356.11.1.108.4.1.3.1.1
lcsStatusMCastPimIpv4SsmGroupsEntryGroup OBJECT-TYPE
    SYNTAX     IpAddress
    MAX-ACCESS read-only
    STATUS     current
    DESCRIPTION
            "-- empty --"
    ::= { lcsStatusMCastPimIpv4SsmGroupsEntry 1 }

-- {COLUMN} 1.3.6.1.4.1.2356.11.1.108.4.1.3.1.2
lcsStatusMCastPimIpv4SsmGroupsEntrySsmSourceIp OBJECT-TYPE
    SYNTAX     IpAddress
    MAX-ACCESS read-only
    STATUS     current
    DESCRIPTION
            "-- empty --"
    ::= { lcsStatusMCastPimIpv4SsmGroupsEntry 2 }

-- {COLUMN} 1.3.6.1.4.1.2356.11.1.108.4.1.3.1.3
lcsStatusMCastPimIpv4SsmGroupsEntryRtgTag OBJECT-TYPE
    SYNTAX     Unsigned32 (0..65535)
    MAX-ACCESS read-only
    STATUS     current
    DESCRIPTION
            "-- empty --"
    ::= { lcsStatusMCastPimIpv4SsmGroupsEntry 3 }

-- {COLUMN} 1.3.6.1.4.1.2356.11.1.108.4.1.3.1.4
lcsStatusMCastPimIpv4SsmGroupsEntryUpstreamSsmInterface OBJECT-TYPE
    SYNTAX     OCTET STRING (SIZE(0..26))
    MAX-ACCESS read-only
    STATUS     current
    DESCRIPTION
            "-- empty --"
    ::= { lcsStatusMCastPimIpv4SsmGroupsEntry 4 }

-- {COLUMN} 1.3.6.1.4.1.2356.11.1.108.4.1.3.1.5
lcsStatusMCastPimIpv4SsmGroupsEntryUpstreamSsmState OBJECT-TYPE
    SYNTAX     OCTET STRING (SIZE(0..20))
    MAX-ACCESS read-only
    STATUS     current
    DESCRIPTION
            "-- empty --"
    ::= { lcsStatusMCastPimIpv4SsmGroupsEntry 5 }

-- {COLUMN} 1.3.6.1.4.1.2356.11.1.108.4.1.3.1.6
lcsStatusMCastPimIpv4SsmGroupsEntryDownstreamIfcs OBJECT-TYPE
    SYNTAX     Unsigned32 (0..4294967295)
    MAX-ACCESS read-only
    STATUS     current
    DESCRIPTION
            "-- empty --"
    ::= { lcsStatusMCastPimIpv4SsmGroupsEntry 6 }

-- {TABLE} 1.3.6.1.4.1.2356.11.1.108.4.1.4
lcsStatusMCastPimIpv4SSMDownIfcsTable OBJECT-TYPE
    SYNTAX     SEQUENCE OF LcsStatusMCastPimIpv4SSMDownIfcsEntry
    MAX-ACCESS not-accessible
    STATUS     current
    DESCRIPTION
            ""
    ::= { lcsStatusMCastPimIpv4 4 }

-- {ROW} 1.3.6.1.4.1.2356.11.1.108.4.1.4.1
lcsStatusMCastPimIpv4SSMDownIfcsEntry OBJECT-TYPE
    SYNTAX     LcsStatusMCastPimIpv4SSMDownIfcsEntry
    MAX-ACCESS not-accessible
    STATUS     current
    DESCRIPTION
            ""
    INDEX {
            lcsStatusMCastPimIpv4SSMDownIfcsEntryGroup,
            lcsStatusMCastPimIpv4SSMDownIfcsEntrySsmSourceIp,
            lcsStatusMCastPimIpv4SSMDownIfcsEntryRtgTag,
            lcsStatusMCastPimIpv4SSMDownIfcsEntryDownstreamInterface
          }
    ::= { lcsStatusMCastPimIpv4SSMDownIfcsTable 1 }

LcsStatusMCastPimIpv4SSMDownIfcsEntry ::= SEQUENCE {
            lcsStatusMCastPimIpv4SSMDownIfcsEntryGroup IpAddress,
            lcsStatusMCastPimIpv4SSMDownIfcsEntrySsmSourceIp IpAddress,
            lcsStatusMCastPimIpv4SSMDownIfcsEntryRtgTag Unsigned32,
            lcsStatusMCastPimIpv4SSMDownIfcsEntryDownstreamInterface OCTET STRING
    }

-- {COLUMN} 1.3.6.1.4.1.2356.11.1.108.4.1.4.1.1
lcsStatusMCastPimIpv4SSMDownIfcsEntryGroup OBJECT-TYPE
    SYNTAX     IpAddress
    MAX-ACCESS read-only
    STATUS     current
    DESCRIPTION
            "-- empty --"
    ::= { lcsStatusMCastPimIpv4SSMDownIfcsEntry 1 }

-- {COLUMN} 1.3.6.1.4.1.2356.11.1.108.4.1.4.1.2
lcsStatusMCastPimIpv4SSMDownIfcsEntrySsmSourceIp OBJECT-TYPE
    SYNTAX     IpAddress
    MAX-ACCESS read-only
    STATUS     current
    DESCRIPTION
            "-- empty --"
    ::= { lcsStatusMCastPimIpv4SSMDownIfcsEntry 2 }

-- {COLUMN} 1.3.6.1.4.1.2356.11.1.108.4.1.4.1.3
lcsStatusMCastPimIpv4SSMDownIfcsEntryRtgTag OBJECT-TYPE
    SYNTAX     Unsigned32 (0..65535)
    MAX-ACCESS read-only
    STATUS     current
    DESCRIPTION
            "-- empty --"
    ::= { lcsStatusMCastPimIpv4SSMDownIfcsEntry 3 }

-- {COLUMN} 1.3.6.1.4.1.2356.11.1.108.4.1.4.1.4
lcsStatusMCastPimIpv4SSMDownIfcsEntryDownstreamInterface OBJECT-TYPE
    SYNTAX     OCTET STRING (SIZE(0..26))
    MAX-ACCESS read-only
    STATUS     current
    DESCRIPTION
            "-- empty --"
    ::= { lcsStatusMCastPimIpv4SSMDownIfcsEntry 4 }

-- {TABLE} 1.3.6.1.4.1.2356.11.1.108.4.1.5
lcsStatusMCastPimIpv4NeighborsTable OBJECT-TYPE
    SYNTAX     SEQUENCE OF LcsStatusMCastPimIpv4NeighborsEntry
    MAX-ACCESS not-accessible
    STATUS     current
    DESCRIPTION
            "-- empty --"
    ::= { lcsStatusMCastPimIpv4 5 }

-- {ROW} 1.3.6.1.4.1.2356.11.1.108.4.1.5.1
lcsStatusMCastPimIpv4NeighborsEntry OBJECT-TYPE
    SYNTAX     LcsStatusMCastPimIpv4NeighborsEntry
    MAX-ACCESS not-accessible
    STATUS     current
    DESCRIPTION
            ""
    INDEX {
            lcsStatusMCastPimIpv4NeighborsEntryInterface,
            lcsStatusMCastPimIpv4NeighborsEntryNeighbor
          }
    ::= { lcsStatusMCastPimIpv4NeighborsTable 1 }

LcsStatusMCastPimIpv4NeighborsEntry ::= SEQUENCE {
            lcsStatusMCastPimIpv4NeighborsEntryInterface OCTET STRING,
            lcsStatusMCastPimIpv4NeighborsEntryNeighbor IpAddress,
            lcsStatusMCastPimIpv4NeighborsEntryUptime OCTET STRING,
            lcsStatusMCastPimIpv4NeighborsEntryFlags OCTET STRING,
            lcsStatusMCastPimIpv4NeighborsEntryExpires OCTET STRING,
            lcsStatusMCastPimIpv4NeighborsEntryHoldtime OCTET STRING,
            lcsStatusMCastPimIpv4NeighborsEntryDrPriority Unsigned32,
            lcsStatusMCastPimIpv4NeighborsEntryDr INTEGER
    }

-- {COLUMN} 1.3.6.1.4.1.2356.11.1.108.4.1.5.1.1
lcsStatusMCastPimIpv4NeighborsEntryInterface OBJECT-TYPE
    SYNTAX     OCTET STRING (SIZE(0..26))
    MAX-ACCESS read-only
    STATUS     current
    DESCRIPTION
            "-- empty --"
    ::= { lcsStatusMCastPimIpv4NeighborsEntry 1 }

-- {COLUMN} 1.3.6.1.4.1.2356.11.1.108.4.1.5.1.2
lcsStatusMCastPimIpv4NeighborsEntryNeighbor OBJECT-TYPE
    SYNTAX     IpAddress
    MAX-ACCESS read-only
    STATUS     current
    DESCRIPTION
            "-- empty --"
    ::= { lcsStatusMCastPimIpv4NeighborsEntry 2 }

-- {COLUMN} 1.3.6.1.4.1.2356.11.1.108.4.1.5.1.3
lcsStatusMCastPimIpv4NeighborsEntryUptime OBJECT-TYPE
    SYNTAX     OCTET STRING (SIZE(0..14))
    MAX-ACCESS read-only
    STATUS     current
    DESCRIPTION
            "-- empty --"
    ::= { lcsStatusMCastPimIpv4NeighborsEntry 3 }

-- {COLUMN} 1.3.6.1.4.1.2356.11.1.108.4.1.5.1.4
lcsStatusMCastPimIpv4NeighborsEntryFlags OBJECT-TYPE
    SYNTAX     OCTET STRING (SIZE(0..6))
    MAX-ACCESS read-only
    STATUS     current
    DESCRIPTION
            "-- empty --"
    ::= { lcsStatusMCastPimIpv4NeighborsEntry 4 }

-- {COLUMN} 1.3.6.1.4.1.2356.11.1.108.4.1.5.1.5
lcsStatusMCastPimIpv4NeighborsEntryExpires OBJECT-TYPE
    SYNTAX     OCTET STRING (SIZE(0..16))
    MAX-ACCESS read-only
    STATUS     current
    DESCRIPTION
            "-- empty --"
    ::= { lcsStatusMCastPimIpv4NeighborsEntry 5 }

-- {COLUMN} 1.3.6.1.4.1.2356.11.1.108.4.1.5.1.6
lcsStatusMCastPimIpv4NeighborsEntryHoldtime OBJECT-TYPE
    SYNTAX     OCTET STRING (SIZE(0..14))
    MAX-ACCESS read-only
    STATUS     current
    DESCRIPTION
            "-- empty --"
    ::= { lcsStatusMCastPimIpv4NeighborsEntry 6 }

-- {COLUMN} 1.3.6.1.4.1.2356.11.1.108.4.1.5.1.7
lcsStatusMCastPimIpv4NeighborsEntryDrPriority OBJECT-TYPE
    SYNTAX     Unsigned32 (0..65535)
    MAX-ACCESS read-only
    STATUS     current
    DESCRIPTION
            "-- empty --"
    ::= { lcsStatusMCastPimIpv4NeighborsEntry 7 }

-- {COLUMN} 1.3.6.1.4.1.2356.11.1.108.4.1.5.1.8
lcsStatusMCastPimIpv4NeighborsEntryDr OBJECT-TYPE
    SYNTAX     INTEGER {
                  eNo (0),
                  eYes (1)
            }
    MAX-ACCESS read-only
    STATUS     current
    DESCRIPTION
            "-- empty --"
    ::= { lcsStatusMCastPimIpv4NeighborsEntry 8 }

-- {NODE} 1.3.6.1.4.1.2356.11.1.108.4.2
lcsStatusMCastPimIpv6 OBJECT IDENTIFIER ::= { lcsStatusMCastPim 2 }

-- {TABLE} 1.3.6.1.4.1.2356.11.1.108.4.2.1
lcsStatusMCastPimIpv6AsmGroupsTable OBJECT-TYPE
    SYNTAX     SEQUENCE OF LcsStatusMCastPimIpv6AsmGroupsEntry
    MAX-ACCESS not-accessible
    STATUS     current
    DESCRIPTION
            "-- empty --"
    ::= { lcsStatusMCastPimIpv6 1 }

-- {ROW} 1.3.6.1.4.1.2356.11.1.108.4.2.1.1
lcsStatusMCastPimIpv6AsmGroupsEntry OBJECT-TYPE
    SYNTAX     LcsStatusMCastPimIpv6AsmGroupsEntry
    MAX-ACCESS not-accessible
    STATUS     current
    DESCRIPTION
            ""
    INDEX {
            lcsStatusMCastPimIpv6AsmGroupsEntryGroup,
            lcsStatusMCastPimIpv6AsmGroupsEntryRtgTag
          }
    ::= { lcsStatusMCastPimIpv6AsmGroupsTable 1 }

LcsStatusMCastPimIpv6AsmGroupsEntry ::= SEQUENCE {
            lcsStatusMCastPimIpv6AsmGroupsEntryGroup OCTET STRING,
            lcsStatusMCastPimIpv6AsmGroupsEntryRtgTag Unsigned32,
            lcsStatusMCastPimIpv6AsmGroupsEntryRpAddress OCTET STRING,
            lcsStatusMCastPimIpv6AsmGroupsEntrySsmSourceIp OCTET STRING,
            lcsStatusMCastPimIpv6AsmGroupsEntryUpstreamRpInterface OCTET STRING,
            lcsStatusMCastPimIpv6AsmGroupsEntryUpstreamSsmInterface OCTET STRING,
            lcsStatusMCastPimIpv6AsmGroupsEntryUpstreamAsmState OCTET STRING,
            lcsStatusMCastPimIpv6AsmGroupsEntryUpstreamSsmState OCTET STRING,
            lcsStatusMCastPimIpv6AsmGroupsEntryDownstreamIfcs Unsigned32
    }

-- {COLUMN} 1.3.6.1.4.1.2356.11.1.108.4.2.1.1.1
lcsStatusMCastPimIpv6AsmGroupsEntryGroup OBJECT-TYPE
    SYNTAX     OCTET STRING (SIZE(16..16))
    MAX-ACCESS read-only
    STATUS     current
    DESCRIPTION
            "-- empty --"
    ::= { lcsStatusMCastPimIpv6AsmGroupsEntry 1 }

-- {COLUMN} 1.3.6.1.4.1.2356.11.1.108.4.2.1.1.2
lcsStatusMCastPimIpv6AsmGroupsEntryRtgTag OBJECT-TYPE
    SYNTAX     Unsigned32 (0..65535)
    MAX-ACCESS read-only
    STATUS     current
    DESCRIPTION
            "-- empty --"
    ::= { lcsStatusMCastPimIpv6AsmGroupsEntry 2 }

-- {COLUMN} 1.3.6.1.4.1.2356.11.1.108.4.2.1.1.3
lcsStatusMCastPimIpv6AsmGroupsEntryRpAddress OBJECT-TYPE
    SYNTAX     OCTET STRING (SIZE(16..16))
    MAX-ACCESS read-only
    STATUS     current
    DESCRIPTION
            "-- empty --"
    ::= { lcsStatusMCastPimIpv6AsmGroupsEntry 3 }

-- {COLUMN} 1.3.6.1.4.1.2356.11.1.108.4.2.1.1.4
lcsStatusMCastPimIpv6AsmGroupsEntrySsmSourceIp OBJECT-TYPE
    SYNTAX     OCTET STRING (SIZE(16..16))
    MAX-ACCESS read-only
    STATUS     current
    DESCRIPTION
            "-- empty --"
    ::= { lcsStatusMCastPimIpv6AsmGroupsEntry 4 }

-- {COLUMN} 1.3.6.1.4.1.2356.11.1.108.4.2.1.1.5
lcsStatusMCastPimIpv6AsmGroupsEntryUpstreamRpInterface OBJECT-TYPE
    SYNTAX     OCTET STRING (SIZE(0..26))
    MAX-ACCESS read-only
    STATUS     current
    DESCRIPTION
            "-- empty --"
    ::= { lcsStatusMCastPimIpv6AsmGroupsEntry 5 }

-- {COLUMN} 1.3.6.1.4.1.2356.11.1.108.4.2.1.1.6
lcsStatusMCastPimIpv6AsmGroupsEntryUpstreamSsmInterface OBJECT-TYPE
    SYNTAX     OCTET STRING (SIZE(0..26))
    MAX-ACCESS read-only
    STATUS     current
    DESCRIPTION
            "-- empty --"
    ::= { lcsStatusMCastPimIpv6AsmGroupsEntry 6 }

-- {COLUMN} 1.3.6.1.4.1.2356.11.1.108.4.2.1.1.7
lcsStatusMCastPimIpv6AsmGroupsEntryUpstreamAsmState OBJECT-TYPE
    SYNTAX     OCTET STRING (SIZE(0..20))
    MAX-ACCESS read-only
    STATUS     current
    DESCRIPTION
            "-- empty --"
    ::= { lcsStatusMCastPimIpv6AsmGroupsEntry 7 }

-- {COLUMN} 1.3.6.1.4.1.2356.11.1.108.4.2.1.1.8
lcsStatusMCastPimIpv6AsmGroupsEntryUpstreamSsmState OBJECT-TYPE
    SYNTAX     OCTET STRING (SIZE(0..20))
    MAX-ACCESS read-only
    STATUS     current
    DESCRIPTION
            "-- empty --"
    ::= { lcsStatusMCastPimIpv6AsmGroupsEntry 8 }

-- {COLUMN} 1.3.6.1.4.1.2356.11.1.108.4.2.1.1.9
lcsStatusMCastPimIpv6AsmGroupsEntryDownstreamIfcs OBJECT-TYPE
    SYNTAX     Unsigned32 (0..4294967295)
    MAX-ACCESS read-only
    STATUS     current
    DESCRIPTION
            "-- empty --"
    ::= { lcsStatusMCastPimIpv6AsmGroupsEntry 9 }

-- {TABLE} 1.3.6.1.4.1.2356.11.1.108.4.2.2
lcsStatusMCastPimIpv6ASMDownIfcsTable OBJECT-TYPE
    SYNTAX     SEQUENCE OF LcsStatusMCastPimIpv6ASMDownIfcsEntry
    MAX-ACCESS not-accessible
    STATUS     current
    DESCRIPTION
            ""
    ::= { lcsStatusMCastPimIpv6 2 }

-- {ROW} 1.3.6.1.4.1.2356.11.1.108.4.2.2.1
lcsStatusMCastPimIpv6ASMDownIfcsEntry OBJECT-TYPE
    SYNTAX     LcsStatusMCastPimIpv6ASMDownIfcsEntry
    MAX-ACCESS not-accessible
    STATUS     current
    DESCRIPTION
            ""
    INDEX {
            lcsStatusMCastPimIpv6ASMDownIfcsEntryGroup,
            lcsStatusMCastPimIpv6ASMDownIfcsEntryRtgTag,
            lcsStatusMCastPimIpv6ASMDownIfcsEntryDownstreamInterface
          }
    ::= { lcsStatusMCastPimIpv6ASMDownIfcsTable 1 }

LcsStatusMCastPimIpv6ASMDownIfcsEntry ::= SEQUENCE {
            lcsStatusMCastPimIpv6ASMDownIfcsEntryGroup OCTET STRING,
            lcsStatusMCastPimIpv6ASMDownIfcsEntryRtgTag Unsigned32,
            lcsStatusMCastPimIpv6ASMDownIfcsEntryDownstreamInterface OCTET STRING
    }

-- {COLUMN} 1.3.6.1.4.1.2356.11.1.108.4.2.2.1.1
lcsStatusMCastPimIpv6ASMDownIfcsEntryGroup OBJECT-TYPE
    SYNTAX     OCTET STRING (SIZE(16..16))
    MAX-ACCESS read-only
    STATUS     current
    DESCRIPTION
            "-- empty --"
    ::= { lcsStatusMCastPimIpv6ASMDownIfcsEntry 1 }

-- {COLUMN} 1.3.6.1.4.1.2356.11.1.108.4.2.2.1.2
lcsStatusMCastPimIpv6ASMDownIfcsEntryRtgTag OBJECT-TYPE
    SYNTAX     Unsigned32 (0..65535)
    MAX-ACCESS read-only
    STATUS     current
    DESCRIPTION
            "-- empty --"
    ::= { lcsStatusMCastPimIpv6ASMDownIfcsEntry 2 }

-- {COLUMN} 1.3.6.1.4.1.2356.11.1.108.4.2.2.1.3
lcsStatusMCastPimIpv6ASMDownIfcsEntryDownstreamInterface OBJECT-TYPE
    SYNTAX     OCTET STRING (SIZE(0..26))
    MAX-ACCESS read-only
    STATUS     current
    DESCRIPTION
            "-- empty --"
    ::= { lcsStatusMCastPimIpv6ASMDownIfcsEntry 3 }

-- {TABLE} 1.3.6.1.4.1.2356.11.1.108.4.2.3
lcsStatusMCastPimIpv6SsmGroupsTable OBJECT-TYPE
    SYNTAX     SEQUENCE OF LcsStatusMCastPimIpv6SsmGroupsEntry
    MAX-ACCESS not-accessible
    STATUS     current
    DESCRIPTION
            "-- empty --"
    ::= { lcsStatusMCastPimIpv6 3 }

-- {ROW} 1.3.6.1.4.1.2356.11.1.108.4.2.3.1
lcsStatusMCastPimIpv6SsmGroupsEntry OBJECT-TYPE
    SYNTAX     LcsStatusMCastPimIpv6SsmGroupsEntry
    MAX-ACCESS not-accessible
    STATUS     current
    DESCRIPTION
            ""
    INDEX {
            lcsStatusMCastPimIpv6SsmGroupsEntryGroup,
            lcsStatusMCastPimIpv6SsmGroupsEntrySsmSourceIp,
            lcsStatusMCastPimIpv6SsmGroupsEntryRtgTag
          }
    ::= { lcsStatusMCastPimIpv6SsmGroupsTable 1 }

LcsStatusMCastPimIpv6SsmGroupsEntry ::= SEQUENCE {
            lcsStatusMCastPimIpv6SsmGroupsEntryGroup OCTET STRING,
            lcsStatusMCastPimIpv6SsmGroupsEntrySsmSourceIp OCTET STRING,
            lcsStatusMCastPimIpv6SsmGroupsEntryRtgTag Unsigned32,
            lcsStatusMCastPimIpv6SsmGroupsEntryUpstreamSsmInterface OCTET STRING,
            lcsStatusMCastPimIpv6SsmGroupsEntryUpstreamSsmState OCTET STRING,
            lcsStatusMCastPimIpv6SsmGroupsEntryDownstreamIfcs Unsigned32
    }

-- {COLUMN} 1.3.6.1.4.1.2356.11.1.108.4.2.3.1.1
lcsStatusMCastPimIpv6SsmGroupsEntryGroup OBJECT-TYPE
    SYNTAX     OCTET STRING (SIZE(16..16))
    MAX-ACCESS read-only
    STATUS     current
    DESCRIPTION
            "-- empty --"
    ::= { lcsStatusMCastPimIpv6SsmGroupsEntry 1 }

-- {COLUMN} 1.3.6.1.4.1.2356.11.1.108.4.2.3.1.2
lcsStatusMCastPimIpv6SsmGroupsEntrySsmSourceIp OBJECT-TYPE
    SYNTAX     OCTET STRING (SIZE(16..16))
    MAX-ACCESS read-only
    STATUS     current
    DESCRIPTION
            "-- empty --"
    ::= { lcsStatusMCastPimIpv6SsmGroupsEntry 2 }

-- {COLUMN} 1.3.6.1.4.1.2356.11.1.108.4.2.3.1.3
lcsStatusMCastPimIpv6SsmGroupsEntryRtgTag OBJECT-TYPE
    SYNTAX     Unsigned32 (0..65535)
    MAX-ACCESS read-only
    STATUS     current
    DESCRIPTION
            "-- empty --"
    ::= { lcsStatusMCastPimIpv6SsmGroupsEntry 3 }

-- {COLUMN} 1.3.6.1.4.1.2356.11.1.108.4.2.3.1.4
lcsStatusMCastPimIpv6SsmGroupsEntryUpstreamSsmInterface OBJECT-TYPE
    SYNTAX     OCTET STRING (SIZE(0..26))
    MAX-ACCESS read-only
    STATUS     current
    DESCRIPTION
            "-- empty --"
    ::= { lcsStatusMCastPimIpv6SsmGroupsEntry 4 }

-- {COLUMN} 1.3.6.1.4.1.2356.11.1.108.4.2.3.1.5
lcsStatusMCastPimIpv6SsmGroupsEntryUpstreamSsmState OBJECT-TYPE
    SYNTAX     OCTET STRING (SIZE(0..20))
    MAX-ACCESS read-only
    STATUS     current
    DESCRIPTION
            "-- empty --"
    ::= { lcsStatusMCastPimIpv6SsmGroupsEntry 5 }

-- {COLUMN} 1.3.6.1.4.1.2356.11.1.108.4.2.3.1.6
lcsStatusMCastPimIpv6SsmGroupsEntryDownstreamIfcs OBJECT-TYPE
    SYNTAX     Unsigned32 (0..4294967295)
    MAX-ACCESS read-only
    STATUS     current
    DESCRIPTION
            "-- empty --"
    ::= { lcsStatusMCastPimIpv6SsmGroupsEntry 6 }

-- {TABLE} 1.3.6.1.4.1.2356.11.1.108.4.2.4
lcsStatusMCastPimIpv6SSMDownIfcsTable OBJECT-TYPE
    SYNTAX     SEQUENCE OF LcsStatusMCastPimIpv6SSMDownIfcsEntry
    MAX-ACCESS not-accessible
    STATUS     current
    DESCRIPTION
            ""
    ::= { lcsStatusMCastPimIpv6 4 }

-- {ROW} 1.3.6.1.4.1.2356.11.1.108.4.2.4.1
lcsStatusMCastPimIpv6SSMDownIfcsEntry OBJECT-TYPE
    SYNTAX     LcsStatusMCastPimIpv6SSMDownIfcsEntry
    MAX-ACCESS not-accessible
    STATUS     current
    DESCRIPTION
            ""
    INDEX {
            lcsStatusMCastPimIpv6SSMDownIfcsEntryGroup,
            lcsStatusMCastPimIpv6SSMDownIfcsEntrySsmSourceIp,
            lcsStatusMCastPimIpv6SSMDownIfcsEntryRtgTag,
            lcsStatusMCastPimIpv6SSMDownIfcsEntryDownstreamInterface
          }
    ::= { lcsStatusMCastPimIpv6SSMDownIfcsTable 1 }

LcsStatusMCastPimIpv6SSMDownIfcsEntry ::= SEQUENCE {
            lcsStatusMCastPimIpv6SSMDownIfcsEntryGroup OCTET STRING,
            lcsStatusMCastPimIpv6SSMDownIfcsEntrySsmSourceIp OCTET STRING,
            lcsStatusMCastPimIpv6SSMDownIfcsEntryRtgTag Unsigned32,
            lcsStatusMCastPimIpv6SSMDownIfcsEntryDownstreamInterface OCTET STRING
    }

-- {COLUMN} 1.3.6.1.4.1.2356.11.1.108.4.2.4.1.1
lcsStatusMCastPimIpv6SSMDownIfcsEntryGroup OBJECT-TYPE
    SYNTAX     OCTET STRING (SIZE(16..16))
    MAX-ACCESS read-only
    STATUS     current
    DESCRIPTION
            "-- empty --"
    ::= { lcsStatusMCastPimIpv6SSMDownIfcsEntry 1 }

-- {COLUMN} 1.3.6.1.4.1.2356.11.1.108.4.2.4.1.2
lcsStatusMCastPimIpv6SSMDownIfcsEntrySsmSourceIp OBJECT-TYPE
    SYNTAX     OCTET STRING (SIZE(16..16))
    MAX-ACCESS read-only
    STATUS     current
    DESCRIPTION
            "-- empty --"
    ::= { lcsStatusMCastPimIpv6SSMDownIfcsEntry 2 }

-- {COLUMN} 1.3.6.1.4.1.2356.11.1.108.4.2.4.1.3
lcsStatusMCastPimIpv6SSMDownIfcsEntryRtgTag OBJECT-TYPE
    SYNTAX     Unsigned32 (0..65535)
    MAX-ACCESS read-only
    STATUS     current
    DESCRIPTION
            "-- empty --"
    ::= { lcsStatusMCastPimIpv6SSMDownIfcsEntry 3 }

-- {COLUMN} 1.3.6.1.4.1.2356.11.1.108.4.2.4.1.4
lcsStatusMCastPimIpv6SSMDownIfcsEntryDownstreamInterface OBJECT-TYPE
    SYNTAX     OCTET STRING (SIZE(0..26))
    MAX-ACCESS read-only
    STATUS     current
    DESCRIPTION
            "-- empty --"
    ::= { lcsStatusMCastPimIpv6SSMDownIfcsEntry 4 }

-- {TABLE} 1.3.6.1.4.1.2356.11.1.108.4.2.5
lcsStatusMCastPimIpv6NeighborsTable OBJECT-TYPE
    SYNTAX     SEQUENCE OF LcsStatusMCastPimIpv6NeighborsEntry
    MAX-ACCESS not-accessible
    STATUS     current
    DESCRIPTION
            "-- empty --"
    ::= { lcsStatusMCastPimIpv6 5 }

-- {ROW} 1.3.6.1.4.1.2356.11.1.108.4.2.5.1
lcsStatusMCastPimIpv6NeighborsEntry OBJECT-TYPE
    SYNTAX     LcsStatusMCastPimIpv6NeighborsEntry
    MAX-ACCESS not-accessible
    STATUS     current
    DESCRIPTION
            ""
    INDEX {
            lcsStatusMCastPimIpv6NeighborsEntryInterface,
            lcsStatusMCastPimIpv6NeighborsEntryNeighbor
          }
    ::= { lcsStatusMCastPimIpv6NeighborsTable 1 }

LcsStatusMCastPimIpv6NeighborsEntry ::= SEQUENCE {
            lcsStatusMCastPimIpv6NeighborsEntryInterface OCTET STRING,
            lcsStatusMCastPimIpv6NeighborsEntryNeighbor OCTET STRING,
            lcsStatusMCastPimIpv6NeighborsEntryUptime OCTET STRING,
            lcsStatusMCastPimIpv6NeighborsEntryFlags OCTET STRING,
            lcsStatusMCastPimIpv6NeighborsEntryExpires OCTET STRING,
            lcsStatusMCastPimIpv6NeighborsEntryHoldtime OCTET STRING,
            lcsStatusMCastPimIpv6NeighborsEntryDrPriority Unsigned32,
            lcsStatusMCastPimIpv6NeighborsEntryDr INTEGER
    }

-- {COLUMN} 1.3.6.1.4.1.2356.11.1.108.4.2.5.1.1
lcsStatusMCastPimIpv6NeighborsEntryInterface OBJECT-TYPE
    SYNTAX     OCTET STRING (SIZE(0..26))
    MAX-ACCESS read-only
    STATUS     current
    DESCRIPTION
            "-- empty --"
    ::= { lcsStatusMCastPimIpv6NeighborsEntry 1 }

-- {COLUMN} 1.3.6.1.4.1.2356.11.1.108.4.2.5.1.2
lcsStatusMCastPimIpv6NeighborsEntryNeighbor OBJECT-TYPE
    SYNTAX     OCTET STRING (SIZE(16..16))
    MAX-ACCESS read-only
    STATUS     current
    DESCRIPTION
            "-- empty --"
    ::= { lcsStatusMCastPimIpv6NeighborsEntry 2 }

-- {COLUMN} 1.3.6.1.4.1.2356.11.1.108.4.2.5.1.3
lcsStatusMCastPimIpv6NeighborsEntryUptime OBJECT-TYPE
    SYNTAX     OCTET STRING (SIZE(0..14))
    MAX-ACCESS read-only
    STATUS     current
    DESCRIPTION
            "-- empty --"
    ::= { lcsStatusMCastPimIpv6NeighborsEntry 3 }

-- {COLUMN} 1.3.6.1.4.1.2356.11.1.108.4.2.5.1.4
lcsStatusMCastPimIpv6NeighborsEntryFlags OBJECT-TYPE
    SYNTAX     OCTET STRING (SIZE(0..6))
    MAX-ACCESS read-only
    STATUS     current
    DESCRIPTION
            "-- empty --"
    ::= { lcsStatusMCastPimIpv6NeighborsEntry 4 }

-- {COLUMN} 1.3.6.1.4.1.2356.11.1.108.4.2.5.1.5
lcsStatusMCastPimIpv6NeighborsEntryExpires OBJECT-TYPE
    SYNTAX     OCTET STRING (SIZE(0..16))
    MAX-ACCESS read-only
    STATUS     current
    DESCRIPTION
            "-- empty --"
    ::= { lcsStatusMCastPimIpv6NeighborsEntry 5 }

-- {COLUMN} 1.3.6.1.4.1.2356.11.1.108.4.2.5.1.6
lcsStatusMCastPimIpv6NeighborsEntryHoldtime OBJECT-TYPE
    SYNTAX     OCTET STRING (SIZE(0..14))
    MAX-ACCESS read-only
    STATUS     current
    DESCRIPTION
            "-- empty --"
    ::= { lcsStatusMCastPimIpv6NeighborsEntry 6 }

-- {COLUMN} 1.3.6.1.4.1.2356.11.1.108.4.2.5.1.7
lcsStatusMCastPimIpv6NeighborsEntryDrPriority OBJECT-TYPE
    SYNTAX     Unsigned32 (0..65535)
    MAX-ACCESS read-only
    STATUS     current
    DESCRIPTION
            "-- empty --"
    ::= { lcsStatusMCastPimIpv6NeighborsEntry 7 }

-- {COLUMN} 1.3.6.1.4.1.2356.11.1.108.4.2.5.1.8
lcsStatusMCastPimIpv6NeighborsEntryDr OBJECT-TYPE
    SYNTAX     INTEGER {
                  eNo (0),
                  eYes (1)
            }
    MAX-ACCESS read-only
    STATUS     current
    DESCRIPTION
            "-- empty --"
    ::= { lcsStatusMCastPimIpv6NeighborsEntry 8 }

-- {NODE} 1.3.6.1.4.1.2356.11.1.108.5
lcsStatusMCastIpv4 OBJECT IDENTIFIER ::= { lcsStatusMCast 5 }

-- {TABLE} 1.3.6.1.4.1.2356.11.1.108.5.1
lcsStatusMCastIpv4DropCounterTable OBJECT-TYPE
    SYNTAX     SEQUENCE OF LcsStatusMCastIpv4DropCounterEntry
    MAX-ACCESS not-accessible
    STATUS     current
    DESCRIPTION
            "-- empty --"
    ::= { lcsStatusMCastIpv4 1 }

-- {ROW} 1.3.6.1.4.1.2356.11.1.108.5.1.1
lcsStatusMCastIpv4DropCounterEntry OBJECT-TYPE
    SYNTAX     LcsStatusMCastIpv4DropCounterEntry
    MAX-ACCESS not-accessible
    STATUS     current
    DESCRIPTION
            ""
    INDEX {
            lcsStatusMCastIpv4DropCounterEntryInterfaceName
          }
    ::= { lcsStatusMCastIpv4DropCounterTable 1 }

LcsStatusMCastIpv4DropCounterEntry ::= SEQUENCE {
            lcsStatusMCastIpv4DropCounterEntryInterfaceName OCTET STRING,
            lcsStatusMCastIpv4DropCounterEntryNoRoute Counter64,
            lcsStatusMCastIpv4DropCounterEntryNoRouteForSource Counter64,
            lcsStatusMCastIpv4DropCounterEntryNoReversePath Counter64,
            lcsStatusMCastIpv4DropCounterEntryOtherDrops Counter64
    }

-- {COLUMN} 1.3.6.1.4.1.2356.11.1.108.5.1.1.1
lcsStatusMCastIpv4DropCounterEntryInterfaceName OBJECT-TYPE
    SYNTAX     OCTET STRING (SIZE(0..26))
    MAX-ACCESS read-only
    STATUS     current
    DESCRIPTION
            "-- empty --"
    ::= { lcsStatusMCastIpv4DropCounterEntry 1 }

-- {COLUMN} 1.3.6.1.4.1.2356.11.1.108.5.1.1.2
lcsStatusMCastIpv4DropCounterEntryNoRoute OBJECT-TYPE
    SYNTAX     Counter64
    MAX-ACCESS read-only
    STATUS     current
    DESCRIPTION
            "-- empty --"
    ::= { lcsStatusMCastIpv4DropCounterEntry 2 }

-- {COLUMN} 1.3.6.1.4.1.2356.11.1.108.5.1.1.3
lcsStatusMCastIpv4DropCounterEntryNoRouteForSource OBJECT-TYPE
    SYNTAX     Counter64
    MAX-ACCESS read-only
    STATUS     current
    DESCRIPTION
            "-- empty --"
    ::= { lcsStatusMCastIpv4DropCounterEntry 3 }

-- {COLUMN} 1.3.6.1.4.1.2356.11.1.108.5.1.1.4
lcsStatusMCastIpv4DropCounterEntryNoReversePath OBJECT-TYPE
    SYNTAX     Counter64
    MAX-ACCESS read-only
    STATUS     current
    DESCRIPTION
            "-- empty --"
    ::= { lcsStatusMCastIpv4DropCounterEntry 4 }

-- {COLUMN} 1.3.6.1.4.1.2356.11.1.108.5.1.1.5
lcsStatusMCastIpv4DropCounterEntryOtherDrops OBJECT-TYPE
    SYNTAX     Counter64
    MAX-ACCESS read-only
    STATUS     current
    DESCRIPTION
            "-- empty --"
    ::= { lcsStatusMCastIpv4DropCounterEntry 5 }

-- {TABLE} 1.3.6.1.4.1.2356.11.1.108.5.2
lcsStatusMCastIpv4DownstreamCounterTable OBJECT-TYPE
    SYNTAX     SEQUENCE OF LcsStatusMCastIpv4DownstreamCounterEntry
    MAX-ACCESS not-accessible
    STATUS     current
    DESCRIPTION
            "-- empty --"
    ::= { lcsStatusMCastIpv4 2 }

-- {ROW} 1.3.6.1.4.1.2356.11.1.108.5.2.1
lcsStatusMCastIpv4DownstreamCounterEntry OBJECT-TYPE
    SYNTAX     LcsStatusMCastIpv4DownstreamCounterEntry
    MAX-ACCESS not-accessible
    STATUS     current
    DESCRIPTION
            ""
    INDEX {
            lcsStatusMCastIpv4DownstreamCounterEntryInterfaceName,
            lcsStatusMCastIpv4DownstreamCounterEntryRtgTag,
            lcsStatusMCastIpv4DownstreamCounterEntryGroup
          }
    ::= { lcsStatusMCastIpv4DownstreamCounterTable 1 }

LcsStatusMCastIpv4DownstreamCounterEntry ::= SEQUENCE {
            lcsStatusMCastIpv4DownstreamCounterEntryInterfaceName OCTET STRING,
            lcsStatusMCastIpv4DownstreamCounterEntryRtgTag Unsigned32,
            lcsStatusMCastIpv4DownstreamCounterEntryGroup IpAddress,
            lcsStatusMCastIpv4DownstreamCounterEntrySourceCount Counter64,
            lcsStatusMCastIpv4DownstreamCounterEntryForwarded Counter64,
            lcsStatusMCastIpv4DownstreamCounterEntryTtlExpired Counter64,
            lcsStatusMCastIpv4DownstreamCounterEntryOtherDrops Counter64,
            lcsStatusMCastIpv4DownstreamCounterEntryKbitS Counter64
    }

-- {COLUMN} 1.3.6.1.4.1.2356.11.1.108.5.2.1.1
lcsStatusMCastIpv4DownstreamCounterEntryInterfaceName OBJECT-TYPE
    SYNTAX     OCTET STRING (SIZE(0..26))
    MAX-ACCESS read-only
    STATUS     current
    DESCRIPTION
            "-- empty --"
    ::= { lcsStatusMCastIpv4DownstreamCounterEntry 1 }

-- {COLUMN} 1.3.6.1.4.1.2356.11.1.108.5.2.1.2
lcsStatusMCastIpv4DownstreamCounterEntryRtgTag OBJECT-TYPE
    SYNTAX     Unsigned32 (0..65535)
    MAX-ACCESS read-only
    STATUS     current
    DESCRIPTION
            "-- empty --"
    ::= { lcsStatusMCastIpv4DownstreamCounterEntry 2 }

-- {COLUMN} 1.3.6.1.4.1.2356.11.1.108.5.2.1.3
lcsStatusMCastIpv4DownstreamCounterEntryGroup OBJECT-TYPE
    SYNTAX     IpAddress
    MAX-ACCESS read-only
    STATUS     current
    DESCRIPTION
            "-- empty --"
    ::= { lcsStatusMCastIpv4DownstreamCounterEntry 3 }

-- {COLUMN} 1.3.6.1.4.1.2356.11.1.108.5.2.1.4
lcsStatusMCastIpv4DownstreamCounterEntrySourceCount OBJECT-TYPE
    SYNTAX     Counter64
    MAX-ACCESS read-only
    STATUS     current
    DESCRIPTION
            "-- empty --"
    ::= { lcsStatusMCastIpv4DownstreamCounterEntry 4 }

-- {COLUMN} 1.3.6.1.4.1.2356.11.1.108.5.2.1.5
lcsStatusMCastIpv4DownstreamCounterEntryForwarded OBJECT-TYPE
    SYNTAX     Counter64
    MAX-ACCESS read-only
    STATUS     current
    DESCRIPTION
            "-- empty --"
    ::= { lcsStatusMCastIpv4DownstreamCounterEntry 5 }

-- {COLUMN} 1.3.6.1.4.1.2356.11.1.108.5.2.1.6
lcsStatusMCastIpv4DownstreamCounterEntryTtlExpired OBJECT-TYPE
    SYNTAX     Counter64
    MAX-ACCESS read-only
    STATUS     current
    DESCRIPTION
            "-- empty --"
    ::= { lcsStatusMCastIpv4DownstreamCounterEntry 6 }

-- {COLUMN} 1.3.6.1.4.1.2356.11.1.108.5.2.1.7
lcsStatusMCastIpv4DownstreamCounterEntryOtherDrops OBJECT-TYPE
    SYNTAX     Counter64
    MAX-ACCESS read-only
    STATUS     current
    DESCRIPTION
            "-- empty --"
    ::= { lcsStatusMCastIpv4DownstreamCounterEntry 7 }

-- {COLUMN} 1.3.6.1.4.1.2356.11.1.108.5.2.1.8
lcsStatusMCastIpv4DownstreamCounterEntryKbitS OBJECT-TYPE
    SYNTAX     Counter64
    MAX-ACCESS read-only
    STATUS     current
    DESCRIPTION
            "-- empty --"
    ::= { lcsStatusMCastIpv4DownstreamCounterEntry 8 }

-- {TABLE} 1.3.6.1.4.1.2356.11.1.108.5.3
lcsStatusMCastIpv4UpstreamCounterTable OBJECT-TYPE
    SYNTAX     SEQUENCE OF LcsStatusMCastIpv4UpstreamCounterEntry
    MAX-ACCESS not-accessible
    STATUS     current
    DESCRIPTION
            "-- empty --"
    ::= { lcsStatusMCastIpv4 3 }

-- {ROW} 1.3.6.1.4.1.2356.11.1.108.5.3.1
lcsStatusMCastIpv4UpstreamCounterEntry OBJECT-TYPE
    SYNTAX     LcsStatusMCastIpv4UpstreamCounterEntry
    MAX-ACCESS not-accessible
    STATUS     current
    DESCRIPTION
            ""
    INDEX {
            lcsStatusMCastIpv4UpstreamCounterEntryInterfaceName,
            lcsStatusMCastIpv4UpstreamCounterEntryRtgTag,
            lcsStatusMCastIpv4UpstreamCounterEntryGroup
          }
    ::= { lcsStatusMCastIpv4UpstreamCounterTable 1 }

LcsStatusMCastIpv4UpstreamCounterEntry ::= SEQUENCE {
            lcsStatusMCastIpv4UpstreamCounterEntryInterfaceName OCTET STRING,
            lcsStatusMCastIpv4UpstreamCounterEntryRtgTag Unsigned32,
            lcsStatusMCastIpv4UpstreamCounterEntryGroup IpAddress,
            lcsStatusMCastIpv4UpstreamCounterEntrySourceCount Counter64,
            lcsStatusMCastIpv4UpstreamCounterEntryReceived Counter64,
            lcsStatusMCastIpv4UpstreamCounterEntryForwarded Counter64,
            lcsStatusMCastIpv4UpstreamCounterEntryReversePathFail Counter64,
            lcsStatusMCastIpv4UpstreamCounterEntryTtlExpired Counter64,
            lcsStatusMCastIpv4UpstreamCounterEntryOtherDrops Counter64,
            lcsStatusMCastIpv4UpstreamCounterEntryKbitS Counter64
    }

-- {COLUMN} 1.3.6.1.4.1.2356.11.1.108.5.3.1.1
lcsStatusMCastIpv4UpstreamCounterEntryInterfaceName OBJECT-TYPE
    SYNTAX     OCTET STRING (SIZE(0..26))
    MAX-ACCESS read-only
    STATUS     current
    DESCRIPTION
            "-- empty --"
    ::= { lcsStatusMCastIpv4UpstreamCounterEntry 1 }

-- {COLUMN} 1.3.6.1.4.1.2356.11.1.108.5.3.1.2
lcsStatusMCastIpv4UpstreamCounterEntryRtgTag OBJECT-TYPE
    SYNTAX     Unsigned32 (0..65535)
    MAX-ACCESS read-only
    STATUS     current
    DESCRIPTION
            "-- empty --"
    ::= { lcsStatusMCastIpv4UpstreamCounterEntry 2 }

-- {COLUMN} 1.3.6.1.4.1.2356.11.1.108.5.3.1.3
lcsStatusMCastIpv4UpstreamCounterEntryGroup OBJECT-TYPE
    SYNTAX     IpAddress
    MAX-ACCESS read-only
    STATUS     current
    DESCRIPTION
            "-- empty --"
    ::= { lcsStatusMCastIpv4UpstreamCounterEntry 3 }

-- {COLUMN} 1.3.6.1.4.1.2356.11.1.108.5.3.1.4
lcsStatusMCastIpv4UpstreamCounterEntrySourceCount OBJECT-TYPE
    SYNTAX     Counter64
    MAX-ACCESS read-only
    STATUS     current
    DESCRIPTION
            "-- empty --"
    ::= { lcsStatusMCastIpv4UpstreamCounterEntry 4 }

-- {COLUMN} 1.3.6.1.4.1.2356.11.1.108.5.3.1.5
lcsStatusMCastIpv4UpstreamCounterEntryReceived OBJECT-TYPE
    SYNTAX     Counter64
    MAX-ACCESS read-only
    STATUS     current
    DESCRIPTION
            "-- empty --"
    ::= { lcsStatusMCastIpv4UpstreamCounterEntry 5 }

-- {COLUMN} 1.3.6.1.4.1.2356.11.1.108.5.3.1.6
lcsStatusMCastIpv4UpstreamCounterEntryForwarded OBJECT-TYPE
    SYNTAX     Counter64
    MAX-ACCESS read-only
    STATUS     current
    DESCRIPTION
            "-- empty --"
    ::= { lcsStatusMCastIpv4UpstreamCounterEntry 6 }

-- {COLUMN} 1.3.6.1.4.1.2356.11.1.108.5.3.1.7
lcsStatusMCastIpv4UpstreamCounterEntryReversePathFail OBJECT-TYPE
    SYNTAX     Counter64
    MAX-ACCESS read-only
    STATUS     current
    DESCRIPTION
            "-- empty --"
    ::= { lcsStatusMCastIpv4UpstreamCounterEntry 7 }

-- {COLUMN} 1.3.6.1.4.1.2356.11.1.108.5.3.1.8
lcsStatusMCastIpv4UpstreamCounterEntryTtlExpired OBJECT-TYPE
    SYNTAX     Counter64
    MAX-ACCESS read-only
    STATUS     current
    DESCRIPTION
            "-- empty --"
    ::= { lcsStatusMCastIpv4UpstreamCounterEntry 8 }

-- {COLUMN} 1.3.6.1.4.1.2356.11.1.108.5.3.1.9
lcsStatusMCastIpv4UpstreamCounterEntryOtherDrops OBJECT-TYPE
    SYNTAX     Counter64
    MAX-ACCESS read-only
    STATUS     current
    DESCRIPTION
            "-- empty --"
    ::= { lcsStatusMCastIpv4UpstreamCounterEntry 9 }

-- {COLUMN} 1.3.6.1.4.1.2356.11.1.108.5.3.1.10
lcsStatusMCastIpv4UpstreamCounterEntryKbitS OBJECT-TYPE
    SYNTAX     Counter64
    MAX-ACCESS read-only
    STATUS     current
    DESCRIPTION
            "-- empty --"
    ::= { lcsStatusMCastIpv4UpstreamCounterEntry 10 }

-- {TABLE} 1.3.6.1.4.1.2356.11.1.108.5.4
lcsStatusMCastIpv4DownstreamMfibTable OBJECT-TYPE
    SYNTAX     SEQUENCE OF LcsStatusMCastIpv4DownstreamMfibEntry
    MAX-ACCESS not-accessible
    STATUS     current
    DESCRIPTION
            "-- empty --"
    ::= { lcsStatusMCastIpv4 4 }

-- {ROW} 1.3.6.1.4.1.2356.11.1.108.5.4.1
lcsStatusMCastIpv4DownstreamMfibEntry OBJECT-TYPE
    SYNTAX     LcsStatusMCastIpv4DownstreamMfibEntry
    MAX-ACCESS not-accessible
    STATUS     current
    DESCRIPTION
            ""
    INDEX {
            lcsStatusMCastIpv4DownstreamMfibEntryRtgTag,
            lcsStatusMCastIpv4DownstreamMfibEntrySourceAddress,
            lcsStatusMCastIpv4DownstreamMfibEntryGroup,
            lcsStatusMCastIpv4DownstreamMfibEntryInterface,
            lcsStatusMCastIpv4DownstreamMfibEntrySource
          }
    ::= { lcsStatusMCastIpv4DownstreamMfibTable 1 }

LcsStatusMCastIpv4DownstreamMfibEntry ::= SEQUENCE {
            lcsStatusMCastIpv4DownstreamMfibEntryRtgTag Unsigned32,
            lcsStatusMCastIpv4DownstreamMfibEntrySourceAddress IpAddress,
            lcsStatusMCastIpv4DownstreamMfibEntryGroup OCTET STRING,
            lcsStatusMCastIpv4DownstreamMfibEntryInterface OCTET STRING,
            lcsStatusMCastIpv4DownstreamMfibEntrySource INTEGER
    }

-- {COLUMN} 1.3.6.1.4.1.2356.11.1.108.5.4.1.1
lcsStatusMCastIpv4DownstreamMfibEntryRtgTag OBJECT-TYPE
    SYNTAX     Unsigned32 (0..65535)
    MAX-ACCESS read-only
    STATUS     current
    DESCRIPTION
            "-- empty --"
    ::= { lcsStatusMCastIpv4DownstreamMfibEntry 1 }

-- {COLUMN} 1.3.6.1.4.1.2356.11.1.108.5.4.1.2
lcsStatusMCastIpv4DownstreamMfibEntrySourceAddress OBJECT-TYPE
    SYNTAX     IpAddress
    MAX-ACCESS read-only
    STATUS     current
    DESCRIPTION
            "-- empty --"
    ::= { lcsStatusMCastIpv4DownstreamMfibEntry 2 }

-- {COLUMN} 1.3.6.1.4.1.2356.11.1.108.5.4.1.3
lcsStatusMCastIpv4DownstreamMfibEntryGroup OBJECT-TYPE
    SYNTAX     OCTET STRING (SIZE(5..5))
    MAX-ACCESS read-only
    STATUS     current
    DESCRIPTION
            "-- empty --"
    ::= { lcsStatusMCastIpv4DownstreamMfibEntry 3 }

-- {COLUMN} 1.3.6.1.4.1.2356.11.1.108.5.4.1.4
lcsStatusMCastIpv4DownstreamMfibEntryInterface OBJECT-TYPE
    SYNTAX     OCTET STRING (SIZE(0..26))
    MAX-ACCESS read-only
    STATUS     current
    DESCRIPTION
            "-- empty --"
    ::= { lcsStatusMCastIpv4DownstreamMfibEntry 4 }

-- {COLUMN} 1.3.6.1.4.1.2356.11.1.108.5.4.1.5
lcsStatusMCastIpv4DownstreamMfibEntrySource OBJECT-TYPE
    SYNTAX     INTEGER {
                  eUnknown (0),
                  eStatic (1),
                  ePim (2),
                  eApplication (3),
                  eManagement (4),
                  eIgmp (5),
                  eMld (6),
                  eProxy (7)
            }
    MAX-ACCESS read-only
    STATUS     current
    DESCRIPTION
            "-- empty --"
    ::= { lcsStatusMCastIpv4DownstreamMfibEntry 5 }

-- {TABLE} 1.3.6.1.4.1.2356.11.1.108.5.5
lcsStatusMCastIpv4UpstreamMfibTable OBJECT-TYPE
    SYNTAX     SEQUENCE OF LcsStatusMCastIpv4UpstreamMfibEntry
    MAX-ACCESS not-accessible
    STATUS     current
    DESCRIPTION
            "-- empty --"
    ::= { lcsStatusMCastIpv4 5 }

-- {ROW} 1.3.6.1.4.1.2356.11.1.108.5.5.1
lcsStatusMCastIpv4UpstreamMfibEntry OBJECT-TYPE
    SYNTAX     LcsStatusMCastIpv4UpstreamMfibEntry
    MAX-ACCESS not-accessible
    STATUS     current
    DESCRIPTION
            ""
    INDEX {
            lcsStatusMCastIpv4UpstreamMfibEntryRtgTag,
            lcsStatusMCastIpv4UpstreamMfibEntrySourceAddress,
            lcsStatusMCastIpv4UpstreamMfibEntryGroup,
            lcsStatusMCastIpv4UpstreamMfibEntryInterface,
            lcsStatusMCastIpv4UpstreamMfibEntrySource
          }
    ::= { lcsStatusMCastIpv4UpstreamMfibTable 1 }

LcsStatusMCastIpv4UpstreamMfibEntry ::= SEQUENCE {
            lcsStatusMCastIpv4UpstreamMfibEntryRtgTag Unsigned32,
            lcsStatusMCastIpv4UpstreamMfibEntrySourceAddress IpAddress,
            lcsStatusMCastIpv4UpstreamMfibEntryGroup OCTET STRING,
            lcsStatusMCastIpv4UpstreamMfibEntryInterface OCTET STRING,
            lcsStatusMCastIpv4UpstreamMfibEntrySource INTEGER
    }

-- {COLUMN} 1.3.6.1.4.1.2356.11.1.108.5.5.1.1
lcsStatusMCastIpv4UpstreamMfibEntryRtgTag OBJECT-TYPE
    SYNTAX     Unsigned32 (0..65535)
    MAX-ACCESS read-only
    STATUS     current
    DESCRIPTION
            "-- empty --"
    ::= { lcsStatusMCastIpv4UpstreamMfibEntry 1 }

-- {COLUMN} 1.3.6.1.4.1.2356.11.1.108.5.5.1.2
lcsStatusMCastIpv4UpstreamMfibEntrySourceAddress OBJECT-TYPE
    SYNTAX     IpAddress
    MAX-ACCESS read-only
    STATUS     current
    DESCRIPTION
            "-- empty --"
    ::= { lcsStatusMCastIpv4UpstreamMfibEntry 2 }

-- {COLUMN} 1.3.6.1.4.1.2356.11.1.108.5.5.1.3
lcsStatusMCastIpv4UpstreamMfibEntryGroup OBJECT-TYPE
    SYNTAX     OCTET STRING (SIZE(5..5))
    MAX-ACCESS read-only
    STATUS     current
    DESCRIPTION
            "-- empty --"
    ::= { lcsStatusMCastIpv4UpstreamMfibEntry 3 }

-- {COLUMN} 1.3.6.1.4.1.2356.11.1.108.5.5.1.4
lcsStatusMCastIpv4UpstreamMfibEntryInterface OBJECT-TYPE
    SYNTAX     OCTET STRING (SIZE(0..26))
    MAX-ACCESS read-only
    STATUS     current
    DESCRIPTION
            "-- empty --"
    ::= { lcsStatusMCastIpv4UpstreamMfibEntry 4 }

-- {COLUMN} 1.3.6.1.4.1.2356.11.1.108.5.5.1.5
lcsStatusMCastIpv4UpstreamMfibEntrySource OBJECT-TYPE
    SYNTAX     INTEGER {
                  eUnknown (0),
                  eStatic (1),
                  ePim (2),
                  eApplication (3),
                  eManagement (4),
                  eIgmp (5),
                  eMld (6),
                  eProxy (7)
            }
    MAX-ACCESS read-only
    STATUS     current
    DESCRIPTION
            "-- empty --"
    ::= { lcsStatusMCastIpv4UpstreamMfibEntry 5 }

-- {NODE} 1.3.6.1.4.1.2356.11.1.108.6
lcsStatusMCastIpv6 OBJECT IDENTIFIER ::= { lcsStatusMCast 6 }

-- {TABLE} 1.3.6.1.4.1.2356.11.1.108.6.1
lcsStatusMCastIpv6DropCounterTable OBJECT-TYPE
    SYNTAX     SEQUENCE OF LcsStatusMCastIpv6DropCounterEntry
    MAX-ACCESS not-accessible
    STATUS     current
    DESCRIPTION
            "-- empty --"
    ::= { lcsStatusMCastIpv6 1 }

-- {ROW} 1.3.6.1.4.1.2356.11.1.108.6.1.1
lcsStatusMCastIpv6DropCounterEntry OBJECT-TYPE
    SYNTAX     LcsStatusMCastIpv6DropCounterEntry
    MAX-ACCESS not-accessible
    STATUS     current
    DESCRIPTION
            ""
    INDEX {
            lcsStatusMCastIpv6DropCounterEntryInterfaceName
          }
    ::= { lcsStatusMCastIpv6DropCounterTable 1 }

LcsStatusMCastIpv6DropCounterEntry ::= SEQUENCE {
            lcsStatusMCastIpv6DropCounterEntryInterfaceName OCTET STRING,
            lcsStatusMCastIpv6DropCounterEntryNoRoute Counter64,
            lcsStatusMCastIpv6DropCounterEntryNoRouteForSource Counter64,
            lcsStatusMCastIpv6DropCounterEntryNoReversePath Counter64,
            lcsStatusMCastIpv6DropCounterEntryOtherDrops Counter64
    }

-- {COLUMN} 1.3.6.1.4.1.2356.11.1.108.6.1.1.1
lcsStatusMCastIpv6DropCounterEntryInterfaceName OBJECT-TYPE
    SYNTAX     OCTET STRING (SIZE(0..26))
    MAX-ACCESS read-only
    STATUS     current
    DESCRIPTION
            "-- empty --"
    ::= { lcsStatusMCastIpv6DropCounterEntry 1 }

-- {COLUMN} 1.3.6.1.4.1.2356.11.1.108.6.1.1.2
lcsStatusMCastIpv6DropCounterEntryNoRoute OBJECT-TYPE
    SYNTAX     Counter64
    MAX-ACCESS read-only
    STATUS     current
    DESCRIPTION
            "-- empty --"
    ::= { lcsStatusMCastIpv6DropCounterEntry 2 }

-- {COLUMN} 1.3.6.1.4.1.2356.11.1.108.6.1.1.3
lcsStatusMCastIpv6DropCounterEntryNoRouteForSource OBJECT-TYPE
    SYNTAX     Counter64
    MAX-ACCESS read-only
    STATUS     current
    DESCRIPTION
            "-- empty --"
    ::= { lcsStatusMCastIpv6DropCounterEntry 3 }

-- {COLUMN} 1.3.6.1.4.1.2356.11.1.108.6.1.1.4
lcsStatusMCastIpv6DropCounterEntryNoReversePath OBJECT-TYPE
    SYNTAX     Counter64
    MAX-ACCESS read-only
    STATUS     current
    DESCRIPTION
            "-- empty --"
    ::= { lcsStatusMCastIpv6DropCounterEntry 4 }

-- {COLUMN} 1.3.6.1.4.1.2356.11.1.108.6.1.1.5
lcsStatusMCastIpv6DropCounterEntryOtherDrops OBJECT-TYPE
    SYNTAX     Counter64
    MAX-ACCESS read-only
    STATUS     current
    DESCRIPTION
            "-- empty --"
    ::= { lcsStatusMCastIpv6DropCounterEntry 5 }

-- {TABLE} 1.3.6.1.4.1.2356.11.1.108.6.2
lcsStatusMCastIpv6DownstreamCounterTable OBJECT-TYPE
    SYNTAX     SEQUENCE OF LcsStatusMCastIpv6DownstreamCounterEntry
    MAX-ACCESS not-accessible
    STATUS     current
    DESCRIPTION
            "-- empty --"
    ::= { lcsStatusMCastIpv6 2 }

-- {ROW} 1.3.6.1.4.1.2356.11.1.108.6.2.1
lcsStatusMCastIpv6DownstreamCounterEntry OBJECT-TYPE
    SYNTAX     LcsStatusMCastIpv6DownstreamCounterEntry
    MAX-ACCESS not-accessible
    STATUS     current
    DESCRIPTION
            ""
    INDEX {
            lcsStatusMCastIpv6DownstreamCounterEntryInterfaceName,
            lcsStatusMCastIpv6DownstreamCounterEntryRtgTag,
            lcsStatusMCastIpv6DownstreamCounterEntryGroup
          }
    ::= { lcsStatusMCastIpv6DownstreamCounterTable 1 }

LcsStatusMCastIpv6DownstreamCounterEntry ::= SEQUENCE {
            lcsStatusMCastIpv6DownstreamCounterEntryInterfaceName OCTET STRING,
            lcsStatusMCastIpv6DownstreamCounterEntryRtgTag Unsigned32,
            lcsStatusMCastIpv6DownstreamCounterEntryGroup OCTET STRING,
            lcsStatusMCastIpv6DownstreamCounterEntrySourceCount Counter64,
            lcsStatusMCastIpv6DownstreamCounterEntryForwarded Counter64,
            lcsStatusMCastIpv6DownstreamCounterEntryTtlExpired Counter64,
            lcsStatusMCastIpv6DownstreamCounterEntryOtherDrops Counter64,
            lcsStatusMCastIpv6DownstreamCounterEntryKbitS Counter64
    }

-- {COLUMN} 1.3.6.1.4.1.2356.11.1.108.6.2.1.1
lcsStatusMCastIpv6DownstreamCounterEntryInterfaceName OBJECT-TYPE
    SYNTAX     OCTET STRING (SIZE(0..26))
    MAX-ACCESS read-only
    STATUS     current
    DESCRIPTION
            "-- empty --"
    ::= { lcsStatusMCastIpv6DownstreamCounterEntry 1 }

-- {COLUMN} 1.3.6.1.4.1.2356.11.1.108.6.2.1.2
lcsStatusMCastIpv6DownstreamCounterEntryRtgTag OBJECT-TYPE
    SYNTAX     Unsigned32 (0..65535)
    MAX-ACCESS read-only
    STATUS     current
    DESCRIPTION
            "-- empty --"
    ::= { lcsStatusMCastIpv6DownstreamCounterEntry 2 }

-- {COLUMN} 1.3.6.1.4.1.2356.11.1.108.6.2.1.3
lcsStatusMCastIpv6DownstreamCounterEntryGroup OBJECT-TYPE
    SYNTAX     OCTET STRING (SIZE(16..16))
    MAX-ACCESS read-only
    STATUS     current
    DESCRIPTION
            "-- empty --"
    ::= { lcsStatusMCastIpv6DownstreamCounterEntry 3 }

-- {COLUMN} 1.3.6.1.4.1.2356.11.1.108.6.2.1.4
lcsStatusMCastIpv6DownstreamCounterEntrySourceCount OBJECT-TYPE
    SYNTAX     Counter64
    MAX-ACCESS read-only
    STATUS     current
    DESCRIPTION
            "-- empty --"
    ::= { lcsStatusMCastIpv6DownstreamCounterEntry 4 }

-- {COLUMN} 1.3.6.1.4.1.2356.11.1.108.6.2.1.5
lcsStatusMCastIpv6DownstreamCounterEntryForwarded OBJECT-TYPE
    SYNTAX     Counter64
    MAX-ACCESS read-only
    STATUS     current
    DESCRIPTION
            "-- empty --"
    ::= { lcsStatusMCastIpv6DownstreamCounterEntry 5 }

-- {COLUMN} 1.3.6.1.4.1.2356.11.1.108.6.2.1.6
lcsStatusMCastIpv6DownstreamCounterEntryTtlExpired OBJECT-TYPE
    SYNTAX     Counter64
    MAX-ACCESS read-only
    STATUS     current
    DESCRIPTION
            "-- empty --"
    ::= { lcsStatusMCastIpv6DownstreamCounterEntry 6 }

-- {COLUMN} 1.3.6.1.4.1.2356.11.1.108.6.2.1.7
lcsStatusMCastIpv6DownstreamCounterEntryOtherDrops OBJECT-TYPE
    SYNTAX     Counter64
    MAX-ACCESS read-only
    STATUS     current
    DESCRIPTION
            "-- empty --"
    ::= { lcsStatusMCastIpv6DownstreamCounterEntry 7 }

-- {COLUMN} 1.3.6.1.4.1.2356.11.1.108.6.2.1.8
lcsStatusMCastIpv6DownstreamCounterEntryKbitS OBJECT-TYPE
    SYNTAX     Counter64
    MAX-ACCESS read-only
    STATUS     current
    DESCRIPTION
            "-- empty --"
    ::= { lcsStatusMCastIpv6DownstreamCounterEntry 8 }

-- {TABLE} 1.3.6.1.4.1.2356.11.1.108.6.3
lcsStatusMCastIpv6UpstreamCounterTable OBJECT-TYPE
    SYNTAX     SEQUENCE OF LcsStatusMCastIpv6UpstreamCounterEntry
    MAX-ACCESS not-accessible
    STATUS     current
    DESCRIPTION
            "-- empty --"
    ::= { lcsStatusMCastIpv6 3 }

-- {ROW} 1.3.6.1.4.1.2356.11.1.108.6.3.1
lcsStatusMCastIpv6UpstreamCounterEntry OBJECT-TYPE
    SYNTAX     LcsStatusMCastIpv6UpstreamCounterEntry
    MAX-ACCESS not-accessible
    STATUS     current
    DESCRIPTION
            ""
    INDEX {
            lcsStatusMCastIpv6UpstreamCounterEntryInterfaceName,
            lcsStatusMCastIpv6UpstreamCounterEntryRtgTag,
            lcsStatusMCastIpv6UpstreamCounterEntryGroup
          }
    ::= { lcsStatusMCastIpv6UpstreamCounterTable 1 }

LcsStatusMCastIpv6UpstreamCounterEntry ::= SEQUENCE {
            lcsStatusMCastIpv6UpstreamCounterEntryInterfaceName OCTET STRING,
            lcsStatusMCastIpv6UpstreamCounterEntryRtgTag Unsigned32,
            lcsStatusMCastIpv6UpstreamCounterEntryGroup OCTET STRING,
            lcsStatusMCastIpv6UpstreamCounterEntrySourceCount Counter64,
            lcsStatusMCastIpv6UpstreamCounterEntryReceived Counter64,
            lcsStatusMCastIpv6UpstreamCounterEntryForwarded Counter64,
            lcsStatusMCastIpv6UpstreamCounterEntryReversePathFail Counter64,
            lcsStatusMCastIpv6UpstreamCounterEntryTtlExpired Counter64,
            lcsStatusMCastIpv6UpstreamCounterEntryOtherDrops Counter64,
            lcsStatusMCastIpv6UpstreamCounterEntryKbitS Counter64
    }

-- {COLUMN} 1.3.6.1.4.1.2356.11.1.108.6.3.1.1
lcsStatusMCastIpv6UpstreamCounterEntryInterfaceName OBJECT-TYPE
    SYNTAX     OCTET STRING (SIZE(0..26))
    MAX-ACCESS read-only
    STATUS     current
    DESCRIPTION
            "-- empty --"
    ::= { lcsStatusMCastIpv6UpstreamCounterEntry 1 }

-- {COLUMN} 1.3.6.1.4.1.2356.11.1.108.6.3.1.2
lcsStatusMCastIpv6UpstreamCounterEntryRtgTag OBJECT-TYPE
    SYNTAX     Unsigned32 (0..65535)
    MAX-ACCESS read-only
    STATUS     current
    DESCRIPTION
            "-- empty --"
    ::= { lcsStatusMCastIpv6UpstreamCounterEntry 2 }

-- {COLUMN} 1.3.6.1.4.1.2356.11.1.108.6.3.1.3
lcsStatusMCastIpv6UpstreamCounterEntryGroup OBJECT-TYPE
    SYNTAX     OCTET STRING (SIZE(16..16))
    MAX-ACCESS read-only
    STATUS     current
    DESCRIPTION
            "-- empty --"
    ::= { lcsStatusMCastIpv6UpstreamCounterEntry 3 }

-- {COLUMN} 1.3.6.1.4.1.2356.11.1.108.6.3.1.4
lcsStatusMCastIpv6UpstreamCounterEntrySourceCount OBJECT-TYPE
    SYNTAX     Counter64
    MAX-ACCESS read-only
    STATUS     current
    DESCRIPTION
            "-- empty --"
    ::= { lcsStatusMCastIpv6UpstreamCounterEntry 4 }

-- {COLUMN} 1.3.6.1.4.1.2356.11.1.108.6.3.1.5
lcsStatusMCastIpv6UpstreamCounterEntryReceived OBJECT-TYPE
    SYNTAX     Counter64
    MAX-ACCESS read-only
    STATUS     current
    DESCRIPTION
            "-- empty --"
    ::= { lcsStatusMCastIpv6UpstreamCounterEntry 5 }

-- {COLUMN} 1.3.6.1.4.1.2356.11.1.108.6.3.1.6
lcsStatusMCastIpv6UpstreamCounterEntryForwarded OBJECT-TYPE
    SYNTAX     Counter64
    MAX-ACCESS read-only
    STATUS     current
    DESCRIPTION
            "-- empty --"
    ::= { lcsStatusMCastIpv6UpstreamCounterEntry 6 }

-- {COLUMN} 1.3.6.1.4.1.2356.11.1.108.6.3.1.7
lcsStatusMCastIpv6UpstreamCounterEntryReversePathFail OBJECT-TYPE
    SYNTAX     Counter64
    MAX-ACCESS read-only
    STATUS     current
    DESCRIPTION
            "-- empty --"
    ::= { lcsStatusMCastIpv6UpstreamCounterEntry 7 }

-- {COLUMN} 1.3.6.1.4.1.2356.11.1.108.6.3.1.8
lcsStatusMCastIpv6UpstreamCounterEntryTtlExpired OBJECT-TYPE
    SYNTAX     Counter64
    MAX-ACCESS read-only
    STATUS     current
    DESCRIPTION
            "-- empty --"
    ::= { lcsStatusMCastIpv6UpstreamCounterEntry 8 }

-- {COLUMN} 1.3.6.1.4.1.2356.11.1.108.6.3.1.9
lcsStatusMCastIpv6UpstreamCounterEntryOtherDrops OBJECT-TYPE
    SYNTAX     Counter64
    MAX-ACCESS read-only
    STATUS     current
    DESCRIPTION
            "-- empty --"
    ::= { lcsStatusMCastIpv6UpstreamCounterEntry 9 }

-- {COLUMN} 1.3.6.1.4.1.2356.11.1.108.6.3.1.10
lcsStatusMCastIpv6UpstreamCounterEntryKbitS OBJECT-TYPE
    SYNTAX     Counter64
    MAX-ACCESS read-only
    STATUS     current
    DESCRIPTION
            "-- empty --"
    ::= { lcsStatusMCastIpv6UpstreamCounterEntry 10 }

-- {TABLE} 1.3.6.1.4.1.2356.11.1.108.6.4
lcsStatusMCastIpv6DownstreamMfibTable OBJECT-TYPE
    SYNTAX     SEQUENCE OF LcsStatusMCastIpv6DownstreamMfibEntry
    MAX-ACCESS not-accessible
    STATUS     current
    DESCRIPTION
            "-- empty --"
    ::= { lcsStatusMCastIpv6 4 }

-- {ROW} 1.3.6.1.4.1.2356.11.1.108.6.4.1
lcsStatusMCastIpv6DownstreamMfibEntry OBJECT-TYPE
    SYNTAX     LcsStatusMCastIpv6DownstreamMfibEntry
    MAX-ACCESS not-accessible
    STATUS     current
    DESCRIPTION
            ""
    INDEX {
            lcsStatusMCastIpv6DownstreamMfibEntryRtgTag,
            lcsStatusMCastIpv6DownstreamMfibEntrySourceAddress,
            lcsStatusMCastIpv6DownstreamMfibEntryGroup,
            lcsStatusMCastIpv6DownstreamMfibEntryInterface,
            lcsStatusMCastIpv6DownstreamMfibEntrySource
          }
    ::= { lcsStatusMCastIpv6DownstreamMfibTable 1 }

LcsStatusMCastIpv6DownstreamMfibEntry ::= SEQUENCE {
            lcsStatusMCastIpv6DownstreamMfibEntryRtgTag Unsigned32,
            lcsStatusMCastIpv6DownstreamMfibEntrySourceAddress OCTET STRING,
            lcsStatusMCastIpv6DownstreamMfibEntryGroup OCTET STRING,
            lcsStatusMCastIpv6DownstreamMfibEntryInterface OCTET STRING,
            lcsStatusMCastIpv6DownstreamMfibEntrySource INTEGER
    }

-- {COLUMN} 1.3.6.1.4.1.2356.11.1.108.6.4.1.1
lcsStatusMCastIpv6DownstreamMfibEntryRtgTag OBJECT-TYPE
    SYNTAX     Unsigned32 (0..65535)
    MAX-ACCESS read-only
    STATUS     current
    DESCRIPTION
            "-- empty --"
    ::= { lcsStatusMCastIpv6DownstreamMfibEntry 1 }

-- {COLUMN} 1.3.6.1.4.1.2356.11.1.108.6.4.1.2
lcsStatusMCastIpv6DownstreamMfibEntrySourceAddress OBJECT-TYPE
    SYNTAX     OCTET STRING (SIZE(16..16))
    MAX-ACCESS read-only
    STATUS     current
    DESCRIPTION
            "-- empty --"
    ::= { lcsStatusMCastIpv6DownstreamMfibEntry 2 }

-- {COLUMN} 1.3.6.1.4.1.2356.11.1.108.6.4.1.3
lcsStatusMCastIpv6DownstreamMfibEntryGroup OBJECT-TYPE
    SYNTAX     OCTET STRING (SIZE(17..17))
    MAX-ACCESS read-only
    STATUS     current
    DESCRIPTION
            "-- empty --"
    ::= { lcsStatusMCastIpv6DownstreamMfibEntry 3 }

-- {COLUMN} 1.3.6.1.4.1.2356.11.1.108.6.4.1.4
lcsStatusMCastIpv6DownstreamMfibEntryInterface OBJECT-TYPE
    SYNTAX     OCTET STRING (SIZE(0..26))
    MAX-ACCESS read-only
    STATUS     current
    DESCRIPTION
            "-- empty --"
    ::= { lcsStatusMCastIpv6DownstreamMfibEntry 4 }

-- {COLUMN} 1.3.6.1.4.1.2356.11.1.108.6.4.1.5
lcsStatusMCastIpv6DownstreamMfibEntrySource OBJECT-TYPE
    SYNTAX     INTEGER {
                  eUnknown (0),
                  eStatic (1),
                  ePim (2),
                  eApplication (3),
                  eManagement (4),
                  eIgmp (5),
                  eMld (6),
                  eProxy (7)
            }
    MAX-ACCESS read-only
    STATUS     current
    DESCRIPTION
            "-- empty --"
    ::= { lcsStatusMCastIpv6DownstreamMfibEntry 5 }

-- {TABLE} 1.3.6.1.4.1.2356.11.1.108.6.5
lcsStatusMCastIpv6UpstreamMfibTable OBJECT-TYPE
    SYNTAX     SEQUENCE OF LcsStatusMCastIpv6UpstreamMfibEntry
    MAX-ACCESS not-accessible
    STATUS     current
    DESCRIPTION
            "-- empty --"
    ::= { lcsStatusMCastIpv6 5 }

-- {ROW} 1.3.6.1.4.1.2356.11.1.108.6.5.1
lcsStatusMCastIpv6UpstreamMfibEntry OBJECT-TYPE
    SYNTAX     LcsStatusMCastIpv6UpstreamMfibEntry
    MAX-ACCESS not-accessible
    STATUS     current
    DESCRIPTION
            ""
    INDEX {
            lcsStatusMCastIpv6UpstreamMfibEntryRtgTag,
            lcsStatusMCastIpv6UpstreamMfibEntrySourceAddress,
            lcsStatusMCastIpv6UpstreamMfibEntryGroup,
            lcsStatusMCastIpv6UpstreamMfibEntryInterface,
            lcsStatusMCastIpv6UpstreamMfibEntrySource
          }
    ::= { lcsStatusMCastIpv6UpstreamMfibTable 1 }

LcsStatusMCastIpv6UpstreamMfibEntry ::= SEQUENCE {
            lcsStatusMCastIpv6UpstreamMfibEntryRtgTag Unsigned32,
            lcsStatusMCastIpv6UpstreamMfibEntrySourceAddress OCTET STRING,
            lcsStatusMCastIpv6UpstreamMfibEntryGroup OCTET STRING,
            lcsStatusMCastIpv6UpstreamMfibEntryInterface OCTET STRING,
            lcsStatusMCastIpv6UpstreamMfibEntrySource INTEGER
    }

-- {COLUMN} 1.3.6.1.4.1.2356.11.1.108.6.5.1.1
lcsStatusMCastIpv6UpstreamMfibEntryRtgTag OBJECT-TYPE
    SYNTAX     Unsigned32 (0..65535)
    MAX-ACCESS read-only
    STATUS     current
    DESCRIPTION
            "-- empty --"
    ::= { lcsStatusMCastIpv6UpstreamMfibEntry 1 }

-- {COLUMN} 1.3.6.1.4.1.2356.11.1.108.6.5.1.2
lcsStatusMCastIpv6UpstreamMfibEntrySourceAddress OBJECT-TYPE
    SYNTAX     OCTET STRING (SIZE(16..16))
    MAX-ACCESS read-only
    STATUS     current
    DESCRIPTION
            "-- empty --"
    ::= { lcsStatusMCastIpv6UpstreamMfibEntry 2 }

-- {COLUMN} 1.3.6.1.4.1.2356.11.1.108.6.5.1.3
lcsStatusMCastIpv6UpstreamMfibEntryGroup OBJECT-TYPE
    SYNTAX     OCTET STRING (SIZE(17..17))
    MAX-ACCESS read-only
    STATUS     current
    DESCRIPTION
            "-- empty --"
    ::= { lcsStatusMCastIpv6UpstreamMfibEntry 3 }

-- {COLUMN} 1.3.6.1.4.1.2356.11.1.108.6.5.1.4
lcsStatusMCastIpv6UpstreamMfibEntryInterface OBJECT-TYPE
    SYNTAX     OCTET STRING (SIZE(0..26))
    MAX-ACCESS read-only
    STATUS     current
    DESCRIPTION
            "-- empty --"
    ::= { lcsStatusMCastIpv6UpstreamMfibEntry 4 }

-- {COLUMN} 1.3.6.1.4.1.2356.11.1.108.6.5.1.5
lcsStatusMCastIpv6UpstreamMfibEntrySource OBJECT-TYPE
    SYNTAX     INTEGER {
                  eUnknown (0),
                  eStatic (1),
                  ePim (2),
                  eApplication (3),
                  eManagement (4),
                  eIgmp (5),
                  eMld (6),
                  eProxy (7)
            }
    MAX-ACCESS read-only
    STATUS     current
    DESCRIPTION
            "-- empty --"
    ::= { lcsStatusMCastIpv6UpstreamMfibEntry 5 }

-- {NODE} 1.3.6.1.4.1.2356.11.1.109
lcsStatusNetflow OBJECT IDENTIFIER ::= { lcsStatus 109 }

-- {TABLE} 1.3.6.1.4.1.2356.11.1.109.1
lcsStatusNetflowExportersTable OBJECT-TYPE
    SYNTAX     SEQUENCE OF LcsStatusNetflowExportersEntry
    MAX-ACCESS not-accessible
    STATUS     current
    DESCRIPTION
            "-- empty --"
    ::= { lcsStatusNetflow 1 }

-- {ROW} 1.3.6.1.4.1.2356.11.1.109.1.1
lcsStatusNetflowExportersEntry OBJECT-TYPE
    SYNTAX     LcsStatusNetflowExportersEntry
    MAX-ACCESS not-accessible
    STATUS     current
    DESCRIPTION
            ""
    INDEX {
            lcsStatusNetflowExportersEntryName
          }
    ::= { lcsStatusNetflowExportersTable 1 }

LcsStatusNetflowExportersEntry ::= SEQUENCE {
            lcsStatusNetflowExportersEntryName OCTET STRING,
            lcsStatusNetflowExportersEntryTransportStatus INTEGER,
            lcsStatusNetflowExportersEntryProtocol INTEGER,
            lcsStatusNetflowExportersEntryTemplatePackets Unsigned32,
            lcsStatusNetflowExportersEntryDataPackets Unsigned32
    }

-- {COLUMN} 1.3.6.1.4.1.2356.11.1.109.1.1.1
lcsStatusNetflowExportersEntryName OBJECT-TYPE
    SYNTAX     OCTET STRING (SIZE(0..20))
    MAX-ACCESS read-only
    STATUS     current
    DESCRIPTION
            "-- empty --"
    ::= { lcsStatusNetflowExportersEntry 1 }

-- {COLUMN} 1.3.6.1.4.1.2356.11.1.109.1.1.2
lcsStatusNetflowExportersEntryTransportStatus OBJECT-TYPE
    SYNTAX     INTEGER {
                  eInactive (0),
                  eConnecting (1),
                  eWaiting (2),
                  eReady (3)
            }
    MAX-ACCESS read-only
    STATUS     current
    DESCRIPTION
            "-- empty --"
    ::= { lcsStatusNetflowExportersEntry 2 }

-- {COLUMN} 1.3.6.1.4.1.2356.11.1.109.1.1.3
lcsStatusNetflowExportersEntryProtocol OBJECT-TYPE
    SYNTAX     INTEGER {
                  eIpfixUdp (0),
                  eNetflow9Udp (16)
            }
    MAX-ACCESS read-only
    STATUS     current
    DESCRIPTION
            "-- empty --"
    ::= { lcsStatusNetflowExportersEntry 3 }

-- {COLUMN} 1.3.6.1.4.1.2356.11.1.109.1.1.4
lcsStatusNetflowExportersEntryTemplatePackets OBJECT-TYPE
    SYNTAX     Unsigned32 (0..4294967295)
    MAX-ACCESS read-only
    STATUS     current
    DESCRIPTION
            "-- empty --"
    ::= { lcsStatusNetflowExportersEntry 4 }

-- {COLUMN} 1.3.6.1.4.1.2356.11.1.109.1.1.5
lcsStatusNetflowExportersEntryDataPackets OBJECT-TYPE
    SYNTAX     Unsigned32 (0..4294967295)
    MAX-ACCESS read-only
    STATUS     current
    DESCRIPTION
            "-- empty --"
    ::= { lcsStatusNetflowExportersEntry 5 }

-- {NODE} 1.3.6.1.4.1.2356.11.1.110
lcsStatusFirewall OBJECT IDENTIFIER ::= { lcsStatus 110 }

-- {NODE} 1.3.6.1.4.1.2356.11.1.110.1
lcsStatusFirewallDnsDb OBJECT IDENTIFIER ::= { lcsStatusFirewall 1 }

-- {TABLE} 1.3.6.1.4.1.2356.11.1.110.1.1
lcsStatusFirewallDnsDbDestinationAddressesTable OBJECT-TYPE
    SYNTAX     SEQUENCE OF LcsStatusFirewallDnsDbDestinationAddressesEntry
    MAX-ACCESS not-accessible
    STATUS     current
    DESCRIPTION
            "-- empty --"
    ::= { lcsStatusFirewallDnsDb 1 }

-- {ROW} 1.3.6.1.4.1.2356.11.1.110.1.1.1
lcsStatusFirewallDnsDbDestinationAddressesEntry OBJECT-TYPE
    SYNTAX     LcsStatusFirewallDnsDbDestinationAddressesEntry
    MAX-ACCESS not-accessible
    STATUS     current
    DESCRIPTION
            ""
    INDEX {
            lcsStatusFirewallDnsDbDestinationAddressesEntryName,
            lcsStatusFirewallDnsDbDestinationAddressesEntryAddress
          }
    ::= { lcsStatusFirewallDnsDbDestinationAddressesTable 1 }

LcsStatusFirewallDnsDbDestinationAddressesEntry ::= SEQUENCE {
            lcsStatusFirewallDnsDbDestinationAddressesEntryName OCTET STRING,
            lcsStatusFirewallDnsDbDestinationAddressesEntryAddress OCTET STRING
    }

-- {COLUMN} 1.3.6.1.4.1.2356.11.1.110.1.1.1.1
lcsStatusFirewallDnsDbDestinationAddressesEntryName OBJECT-TYPE
    SYNTAX     OCTET STRING (SIZE(0..32))
    MAX-ACCESS read-only
    STATUS     current
    DESCRIPTION
            "-- empty --"
    ::= { lcsStatusFirewallDnsDbDestinationAddressesEntry 1 }

-- {COLUMN} 1.3.6.1.4.1.2356.11.1.110.1.1.1.2
lcsStatusFirewallDnsDbDestinationAddressesEntryAddress OBJECT-TYPE
    SYNTAX     OCTET STRING (SIZE(0..39))
    MAX-ACCESS read-only
    STATUS     current
    DESCRIPTION
            "-- empty --"
    ::= { lcsStatusFirewallDnsDbDestinationAddressesEntry 2 }

-- {TABLE} 1.3.6.1.4.1.2356.11.1.110.1.2
lcsStatusFirewallDnsDbDestinationUsageTable OBJECT-TYPE
    SYNTAX     SEQUENCE OF LcsStatusFirewallDnsDbDestinationUsageEntry
    MAX-ACCESS not-accessible
    STATUS     current
    DESCRIPTION
            "-- empty --"
    ::= { lcsStatusFirewallDnsDb 2 }

-- {ROW} 1.3.6.1.4.1.2356.11.1.110.1.2.1
lcsStatusFirewallDnsDbDestinationUsageEntry OBJECT-TYPE
    SYNTAX     LcsStatusFirewallDnsDbDestinationUsageEntry
    MAX-ACCESS not-accessible
    STATUS     current
    DESCRIPTION
            ""
    INDEX {
            lcsStatusFirewallDnsDbDestinationUsageEntryName
          }
    ::= { lcsStatusFirewallDnsDbDestinationUsageTable 1 }

LcsStatusFirewallDnsDbDestinationUsageEntry ::= SEQUENCE {
            lcsStatusFirewallDnsDbDestinationUsageEntryName OCTET STRING,
            lcsStatusFirewallDnsDbDestinationUsageEntryTotalV4Sessions Unsigned32,
            lcsStatusFirewallDnsDbDestinationUsageEntryCurrentV4Sessions Unsigned32,
            lcsStatusFirewallDnsDbDestinationUsageEntryTotalV6Sessions Unsigned32,
            lcsStatusFirewallDnsDbDestinationUsageEntryCurrentV6Sessions Unsigned32
    }

-- {COLUMN} 1.3.6.1.4.1.2356.11.1.110.1.2.1.1
lcsStatusFirewallDnsDbDestinationUsageEntryName OBJECT-TYPE
    SYNTAX     OCTET STRING (SIZE(0..32))
    MAX-ACCESS read-only
    STATUS     current
    DESCRIPTION
            "-- empty --"
    ::= { lcsStatusFirewallDnsDbDestinationUsageEntry 1 }

-- {COLUMN} 1.3.6.1.4.1.2356.11.1.110.1.2.1.2
lcsStatusFirewallDnsDbDestinationUsageEntryTotalV4Sessions OBJECT-TYPE
    SYNTAX     Unsigned32 (0..4294967295)
    MAX-ACCESS read-only
    STATUS     current
    DESCRIPTION
            "-- empty --"
    ::= { lcsStatusFirewallDnsDbDestinationUsageEntry 2 }

-- {COLUMN} 1.3.6.1.4.1.2356.11.1.110.1.2.1.3
lcsStatusFirewallDnsDbDestinationUsageEntryCurrentV4Sessions OBJECT-TYPE
    SYNTAX     Unsigned32 (0..4294967295)
    MAX-ACCESS read-only
    STATUS     current
    DESCRIPTION
            "-- empty --"
    ::= { lcsStatusFirewallDnsDbDestinationUsageEntry 3 }

-- {COLUMN} 1.3.6.1.4.1.2356.11.1.110.1.2.1.4
lcsStatusFirewallDnsDbDestinationUsageEntryTotalV6Sessions OBJECT-TYPE
    SYNTAX     Unsigned32 (0..4294967295)
    MAX-ACCESS read-only
    STATUS     current
    DESCRIPTION
            "-- empty --"
    ::= { lcsStatusFirewallDnsDbDestinationUsageEntry 4 }

-- {COLUMN} 1.3.6.1.4.1.2356.11.1.110.1.2.1.5
lcsStatusFirewallDnsDbDestinationUsageEntryCurrentV6Sessions OBJECT-TYPE
    SYNTAX     Unsigned32 (0..4294967295)
    MAX-ACCESS read-only
    STATUS     current
    DESCRIPTION
            "-- empty --"
    ::= { lcsStatusFirewallDnsDbDestinationUsageEntry 5 }

-- {TABLE} 1.3.6.1.4.1.2356.11.1.110.1.3
lcsStatusFirewallDnsDbWildcardAddressesTable OBJECT-TYPE
    SYNTAX     SEQUENCE OF LcsStatusFirewallDnsDbWildcardAddressesEntry
    MAX-ACCESS not-accessible
    STATUS     current
    DESCRIPTION
            "-- empty --"
    ::= { lcsStatusFirewallDnsDb 3 }

-- {ROW} 1.3.6.1.4.1.2356.11.1.110.1.3.1
lcsStatusFirewallDnsDbWildcardAddressesEntry OBJECT-TYPE
    SYNTAX     LcsStatusFirewallDnsDbWildcardAddressesEntry
    MAX-ACCESS not-accessible
    STATUS     current
    DESCRIPTION
            ""
    INDEX {
            lcsStatusFirewallDnsDbWildcardAddressesEntryWildcardExpression,
            lcsStatusFirewallDnsDbWildcardAddressesEntryAddress
          }
    ::= { lcsStatusFirewallDnsDbWildcardAddressesTable 1 }

LcsStatusFirewallDnsDbWildcardAddressesEntry ::= SEQUENCE {
            lcsStatusFirewallDnsDbWildcardAddressesEntryWildcardExpression OCTET STRING,
            lcsStatusFirewallDnsDbWildcardAddressesEntryAddress OCTET STRING
    }

-- {COLUMN} 1.3.6.1.4.1.2356.11.1.110.1.3.1.1
lcsStatusFirewallDnsDbWildcardAddressesEntryWildcardExpression OBJECT-TYPE
    SYNTAX     OCTET STRING (SIZE(0..379))
    MAX-ACCESS read-only
    STATUS     current
    DESCRIPTION
            "-- empty --"
    ::= { lcsStatusFirewallDnsDbWildcardAddressesEntry 1 }

-- {COLUMN} 1.3.6.1.4.1.2356.11.1.110.1.3.1.2
lcsStatusFirewallDnsDbWildcardAddressesEntryAddress OBJECT-TYPE
    SYNTAX     OCTET STRING (SIZE(0..39))
    MAX-ACCESS read-only
    STATUS     current
    DESCRIPTION
            "-- empty --"
    ::= { lcsStatusFirewallDnsDbWildcardAddressesEntry 2 }

-- {TABLE} 1.3.6.1.4.1.2356.11.1.110.1.4
lcsStatusFirewallDnsDbWildcardRecordsTable OBJECT-TYPE
    SYNTAX     SEQUENCE OF LcsStatusFirewallDnsDbWildcardRecordsEntry
    MAX-ACCESS not-accessible
    STATUS     current
    DESCRIPTION
            "-- empty --"
    ::= { lcsStatusFirewallDnsDb 4 }

-- {ROW} 1.3.6.1.4.1.2356.11.1.110.1.4.1
lcsStatusFirewallDnsDbWildcardRecordsEntry OBJECT-TYPE
    SYNTAX     LcsStatusFirewallDnsDbWildcardRecordsEntry
    MAX-ACCESS not-accessible
    STATUS     current
    DESCRIPTION
            ""
    INDEX {
            lcsStatusFirewallDnsDbWildcardRecordsEntryWildcardExpression,
            lcsStatusFirewallDnsDbWildcardRecordsEntryName,
            lcsStatusFirewallDnsDbWildcardRecordsEntryType,
            lcsStatusFirewallDnsDbWildcardRecordsEntryValue
          }
    ::= { lcsStatusFirewallDnsDbWildcardRecordsTable 1 }

LcsStatusFirewallDnsDbWildcardRecordsEntry ::= SEQUENCE {
            lcsStatusFirewallDnsDbWildcardRecordsEntryWildcardExpression OCTET STRING,
            lcsStatusFirewallDnsDbWildcardRecordsEntryName OCTET STRING,
            lcsStatusFirewallDnsDbWildcardRecordsEntryType INTEGER,
            lcsStatusFirewallDnsDbWildcardRecordsEntryValue OCTET STRING,
            lcsStatusFirewallDnsDbWildcardRecordsEntryTtlSec Integer32,
            lcsStatusFirewallDnsDbWildcardRecordsEntryRemainingSec Integer32
    }

-- {COLUMN} 1.3.6.1.4.1.2356.11.1.110.1.4.1.1
lcsStatusFirewallDnsDbWildcardRecordsEntryWildcardExpression OBJECT-TYPE
    SYNTAX     OCTET STRING (SIZE(0..379))
    MAX-ACCESS read-only
    STATUS     current
    DESCRIPTION
            "-- empty --"
    ::= { lcsStatusFirewallDnsDbWildcardRecordsEntry 1 }

-- {COLUMN} 1.3.6.1.4.1.2356.11.1.110.1.4.1.2
lcsStatusFirewallDnsDbWildcardRecordsEntryName OBJECT-TYPE
    SYNTAX     OCTET STRING (SIZE(0..1420))
    MAX-ACCESS read-only
    STATUS     current
    DESCRIPTION
            "-- empty --"
    ::= { lcsStatusFirewallDnsDbWildcardRecordsEntry 2 }

-- {COLUMN} 1.3.6.1.4.1.2356.11.1.110.1.4.1.3
lcsStatusFirewallDnsDbWildcardRecordsEntryType OBJECT-TYPE
    SYNTAX     INTEGER {
                  eA (1),
                  eCname (5),
                  eAaaa (28),
                  eSrv (33)
            }
    MAX-ACCESS read-only
    STATUS     current
    DESCRIPTION
            "-- empty --"
    ::= { lcsStatusFirewallDnsDbWildcardRecordsEntry 3 }

-- {COLUMN} 1.3.6.1.4.1.2356.11.1.110.1.4.1.4
lcsStatusFirewallDnsDbWildcardRecordsEntryValue OBJECT-TYPE
    SYNTAX     OCTET STRING (SIZE(0..1420))
    MAX-ACCESS read-only
    STATUS     current
    DESCRIPTION
            "-- empty --"
    ::= { lcsStatusFirewallDnsDbWildcardRecordsEntry 4 }

-- {COLUMN} 1.3.6.1.4.1.2356.11.1.110.1.4.1.5
lcsStatusFirewallDnsDbWildcardRecordsEntryTtlSec OBJECT-TYPE
    SYNTAX     Integer32 (-2147483648..2147483647)
    MAX-ACCESS read-only
    STATUS     current
    DESCRIPTION
            "-- empty --"
    ::= { lcsStatusFirewallDnsDbWildcardRecordsEntry 5 }

-- {COLUMN} 1.3.6.1.4.1.2356.11.1.110.1.4.1.6
lcsStatusFirewallDnsDbWildcardRecordsEntryRemainingSec OBJECT-TYPE
    SYNTAX     Integer32 (-2147483648..2147483647)
    MAX-ACCESS read-only
    STATUS     current
    DESCRIPTION
            "-- empty --"
    ::= { lcsStatusFirewallDnsDbWildcardRecordsEntry 6 }

-- {TABLE} 1.3.6.1.4.1.2356.11.1.110.1.5
lcsStatusFirewallDnsDbRecordsTable OBJECT-TYPE
    SYNTAX     SEQUENCE OF LcsStatusFirewallDnsDbRecordsEntry
    MAX-ACCESS not-accessible
    STATUS     current
    DESCRIPTION
            "-- empty --"
    ::= { lcsStatusFirewallDnsDb 5 }

-- {ROW} 1.3.6.1.4.1.2356.11.1.110.1.5.1
lcsStatusFirewallDnsDbRecordsEntry OBJECT-TYPE
    SYNTAX     LcsStatusFirewallDnsDbRecordsEntry
    MAX-ACCESS not-accessible
    STATUS     current
    DESCRIPTION
            ""
    INDEX {
            lcsStatusFirewallDnsDbRecordsEntryName,
            lcsStatusFirewallDnsDbRecordsEntryType,
            lcsStatusFirewallDnsDbRecordsEntryValue
          }
    ::= { lcsStatusFirewallDnsDbRecordsTable 1 }

LcsStatusFirewallDnsDbRecordsEntry ::= SEQUENCE {
            lcsStatusFirewallDnsDbRecordsEntryName OCTET STRING,
            lcsStatusFirewallDnsDbRecordsEntryType INTEGER,
            lcsStatusFirewallDnsDbRecordsEntryValue OCTET STRING,
            lcsStatusFirewallDnsDbRecordsEntryTtlSec Integer32,
            lcsStatusFirewallDnsDbRecordsEntryRemainingSec Integer32
    }

-- {COLUMN} 1.3.6.1.4.1.2356.11.1.110.1.5.1.1
lcsStatusFirewallDnsDbRecordsEntryName OBJECT-TYPE
    SYNTAX     OCTET STRING (SIZE(0..1420))
    MAX-ACCESS read-only
    STATUS     current
    DESCRIPTION
            "-- empty --"
    ::= { lcsStatusFirewallDnsDbRecordsEntry 1 }

-- {COLUMN} 1.3.6.1.4.1.2356.11.1.110.1.5.1.2
lcsStatusFirewallDnsDbRecordsEntryType OBJECT-TYPE
    SYNTAX     INTEGER {
                  eA (1),
                  eCname (5),
                  eAaaa (28),
                  eSrv (33)
            }
    MAX-ACCESS read-only
    STATUS     current
    DESCRIPTION
            "-- empty --"
    ::= { lcsStatusFirewallDnsDbRecordsEntry 2 }

-- {COLUMN} 1.3.6.1.4.1.2356.11.1.110.1.5.1.3
lcsStatusFirewallDnsDbRecordsEntryValue OBJECT-TYPE
    SYNTAX     OCTET STRING (SIZE(0..1420))
    MAX-ACCESS read-only
    STATUS     current
    DESCRIPTION
            "-- empty --"
    ::= { lcsStatusFirewallDnsDbRecordsEntry 3 }

-- {COLUMN} 1.3.6.1.4.1.2356.11.1.110.1.5.1.4
lcsStatusFirewallDnsDbRecordsEntryTtlSec OBJECT-TYPE
    SYNTAX     Integer32 (-2147483648..2147483647)
    MAX-ACCESS read-only
    STATUS     current
    DESCRIPTION
            "-- empty --"
    ::= { lcsStatusFirewallDnsDbRecordsEntry 4 }

-- {COLUMN} 1.3.6.1.4.1.2356.11.1.110.1.5.1.5
lcsStatusFirewallDnsDbRecordsEntryRemainingSec OBJECT-TYPE
    SYNTAX     Integer32 (-2147483648..2147483647)
    MAX-ACCESS read-only
    STATUS     current
    DESCRIPTION
            "-- empty --"
    ::= { lcsStatusFirewallDnsDbRecordsEntry 5 }

-- {TABLE} 1.3.6.1.4.1.2356.11.1.110.1.6
lcsStatusFirewallDnsDbReverseResolutionsTable OBJECT-TYPE
    SYNTAX     SEQUENCE OF LcsStatusFirewallDnsDbReverseResolutionsEntry
    MAX-ACCESS not-accessible
    STATUS     current
    DESCRIPTION
            "-- empty --"
    ::= { lcsStatusFirewallDnsDb 6 }

-- {ROW} 1.3.6.1.4.1.2356.11.1.110.1.6.1
lcsStatusFirewallDnsDbReverseResolutionsEntry OBJECT-TYPE
    SYNTAX     LcsStatusFirewallDnsDbReverseResolutionsEntry
    MAX-ACCESS not-accessible
    STATUS     current
    DESCRIPTION
            ""
    INDEX {
            lcsStatusFirewallDnsDbReverseResolutionsEntryValue,
            lcsStatusFirewallDnsDbReverseResolutionsEntryName
          }
    ::= { lcsStatusFirewallDnsDbReverseResolutionsTable 1 }

LcsStatusFirewallDnsDbReverseResolutionsEntry ::= SEQUENCE {
            lcsStatusFirewallDnsDbReverseResolutionsEntryValue OCTET STRING,
            lcsStatusFirewallDnsDbReverseResolutionsEntryName OCTET STRING
    }

-- {COLUMN} 1.3.6.1.4.1.2356.11.1.110.1.6.1.1
lcsStatusFirewallDnsDbReverseResolutionsEntryValue OBJECT-TYPE
    SYNTAX     OCTET STRING (SIZE(0..1420))
    MAX-ACCESS read-only
    STATUS     current
    DESCRIPTION
            "-- empty --"
    ::= { lcsStatusFirewallDnsDbReverseResolutionsEntry 1 }

-- {COLUMN} 1.3.6.1.4.1.2356.11.1.110.1.6.1.2
lcsStatusFirewallDnsDbReverseResolutionsEntryName OBJECT-TYPE
    SYNTAX     OCTET STRING (SIZE(0..1420))
    MAX-ACCESS read-only
    STATUS     current
    DESCRIPTION
            "-- empty --"
    ::= { lcsStatusFirewallDnsDbReverseResolutionsEntry 2 }

-- {SCALAR} 1.3.6.1.4.1.2356.11.1.110.1.7
lcsStatusFirewallDnsDbDeleteValues OBJECT-TYPE
    SYNTAX     DisplayString
    MAX-ACCESS read-write
    STATUS     current
    DESCRIPTION
            "-- empty --"
    ::= { lcsStatusFirewallDnsDb 7 }

-- {NODE} 1.3.6.1.4.1.2356.11.1.111
lcsStatusIot OBJECT IDENTIFIER ::= { lcsStatus 111 }

-- {NODE} 1.3.6.1.4.1.2356.11.1.111.88
lcsStatusIotWirelessEpaper OBJECT IDENTIFIER ::= { lcsStatusIot 88 }

-- {SCALAR} 1.3.6.1.4.1.2356.11.1.111.88.1
lcsStatusIotWirelessEpaperState OBJECT-TYPE
    SYNTAX     INTEGER {
                  eInactive (1),
                  eWaitingForControllerConnection (2),
                  eRunning (3),
                  eTransmitting (4),
                  eError (5),
                  eWaitingForEpaperModule (6),
                  eRunningDisconnected (7)
            }
    MAX-ACCESS read-only
    STATUS     current
    DESCRIPTION
            "-- empty --"
    ::= { lcsStatusIotWirelessEpaper 1 }

-- {SCALAR} 1.3.6.1.4.1.2356.11.1.111.88.2
lcsStatusIotWirelessEpaperOperating OBJECT-TYPE
    SYNTAX     INTEGER {
                  eNo (0),
                  eYes (1)
            }
    MAX-ACCESS read-only
    STATUS     current
    DESCRIPTION
            "-- empty --"
    ::= { lcsStatusIotWirelessEpaper 2 }

-- {SCALAR} 1.3.6.1.4.1.2356.11.1.111.88.3
lcsStatusIotWirelessEpaperAccesspointId OBJECT-TYPE
    SYNTAX     Integer32 (0..2147483647)
    MAX-ACCESS read-only
    STATUS     current
    DESCRIPTION
            "-- empty --"
    ::= { lcsStatusIotWirelessEpaper 3 }

-- {SCALAR} 1.3.6.1.4.1.2356.11.1.111.88.4
lcsStatusIotWirelessEpaperFirmwareVersion OBJECT-TYPE
    SYNTAX     DisplayString (SIZE(0..13))
    MAX-ACCESS read-only
    STATUS     current
    DESCRIPTION
            "-- empty --"
    ::= { lcsStatusIotWirelessEpaper 4 }

-- {SCALAR} 1.3.6.1.4.1.2356.11.1.111.88.5
lcsStatusIotWirelessEpaperCurrentChannel OBJECT-TYPE
    SYNTAX     INTEGER {
                  e2404mhz (0),
                  e2410mhz (1),
                  e2422mhz (2),
                  e2425mhz (3),
                  e2442mhz (4),
                  e2450mhz (5),
                  e2462mhz (6),
                  e2470mhz (7),
                  e2474mhz (8),
                  e2477mhz (9),
                  e2480mhz (10),
                  eNone (255)
            }
    MAX-ACCESS read-only
    STATUS     current
    DESCRIPTION
            "-- empty --"
    ::= { lcsStatusIotWirelessEpaper 5 }

-- {NODE} 1.3.6.1.4.1.2356.11.1.111.88.6
lcsStatusIotWirelessEpaperStats OBJECT IDENTIFIER ::= { lcsStatusIotWirelessEpaper 6 }

-- {SCALAR} 1.3.6.1.4.1.2356.11.1.111.88.6.1
lcsStatusIotWirelessEpaperStatsUartErrorCounter OBJECT-TYPE
    SYNTAX     Integer32 (0..2147483647)
    MAX-ACCESS read-only
    STATUS     current
    DESCRIPTION
            "-- empty --"
    ::= { lcsStatusIotWirelessEpaperStats 1 }

-- {SCALAR} 1.3.6.1.4.1.2356.11.1.111.88.6.2
lcsStatusIotWirelessEpaperStatsControllerLateResponseCounter OBJECT-TYPE
    SYNTAX     Integer32 (0..2147483647)
    MAX-ACCESS read-only
    STATUS     current
    DESCRIPTION
            "-- empty --"
    ::= { lcsStatusIotWirelessEpaperStats 2 }

-- {SCALAR} 1.3.6.1.4.1.2356.11.1.111.88.6.3
lcsStatusIotWirelessEpaperStatsControllerTimeoutCounter OBJECT-TYPE
    SYNTAX     Integer32 (0..2147483647)
    MAX-ACCESS read-only
    STATUS     current
    DESCRIPTION
            "-- empty --"
    ::= { lcsStatusIotWirelessEpaperStats 3 }

-- {SCALAR} 1.3.6.1.4.1.2356.11.1.111.88.6.4
lcsStatusIotWirelessEpaperStatsCoexistenceActiveCounter OBJECT-TYPE
    SYNTAX     Integer32 (0..2147483647)
    MAX-ACCESS read-only
    STATUS     current
    DESCRIPTION
            "-- empty --"
    ::= { lcsStatusIotWirelessEpaperStats 4 }

-- {SCALAR} 1.3.6.1.4.1.2356.11.1.111.88.6.5
lcsStatusIotWirelessEpaperStatsCoexistenceStuckCounter OBJECT-TYPE
    SYNTAX     Integer32 (0..2147483647)
    MAX-ACCESS read-only
    STATUS     current
    DESCRIPTION
            "-- empty --"
    ::= { lcsStatusIotWirelessEpaperStats 5 }

-- {SCALAR} 1.3.6.1.4.1.2356.11.1.111.88.7
lcsStatusIotWirelessEpaperControllerIp OBJECT-TYPE
    SYNTAX     DisplayString (SIZE(0..63))
    MAX-ACCESS read-only
    STATUS     current
    DESCRIPTION
            "-- empty --"
    ::= { lcsStatusIotWirelessEpaper 7 }

-- {SCALAR} 1.3.6.1.4.1.2356.11.1.111.88.8
lcsStatusIotWirelessEpaperPort OBJECT-TYPE
    SYNTAX     Integer32 (0..65535)
    MAX-ACCESS read-only
    STATUS     current
    DESCRIPTION
            "-- empty --"
    ::= { lcsStatusIotWirelessEpaper 8 }

-- {SCALAR} 1.3.6.1.4.1.2356.11.1.111.88.10
lcsStatusIotWirelessEpaperControllerProtocolVersion OBJECT-TYPE
    SYNTAX     INTEGER {
                  eNone (0),
                  eThinap10Udp (1),
                  eThinap20Tcp (2)
            }
    MAX-ACCESS read-only
    STATUS     current
    DESCRIPTION
            "-- empty --"
    ::= { lcsStatusIotWirelessEpaper 10 }

-- {NODE} 1.3.6.1.4.1.2356.11.1.111.90
lcsStatusIotBluetooth OBJECT IDENTIFIER ::= { lcsStatusIot 90 }

-- {TABLE} 1.3.6.1.4.1.2356.11.1.111.90.2
lcsStatusIotBluetoothScanResultsTable OBJECT-TYPE
    SYNTAX     SEQUENCE OF LcsStatusIotBluetoothScanResultsEntry
    MAX-ACCESS not-accessible
    STATUS     current
    DESCRIPTION
            "-- empty --"
    ::= { lcsStatusIotBluetooth 2 }

-- {ROW} 1.3.6.1.4.1.2356.11.1.111.90.2.1
lcsStatusIotBluetoothScanResultsEntry OBJECT-TYPE
    SYNTAX     LcsStatusIotBluetoothScanResultsEntry
    MAX-ACCESS not-accessible
    STATUS     current
    DESCRIPTION
            ""
    INDEX {
            lcsStatusIotBluetoothScanResultsEntryDeviceAddress
          }
    ::= { lcsStatusIotBluetoothScanResultsTable 1 }

LcsStatusIotBluetoothScanResultsEntry ::= SEQUENCE {
            lcsStatusIotBluetoothScanResultsEntryDeviceAddress MacAddress,
            lcsStatusIotBluetoothScanResultsEntryAddressType INTEGER,
            lcsStatusIotBluetoothScanResultsEntryRssi Integer32,
            lcsStatusIotBluetoothScanResultsEntryLastSeen Gauge32,
            lcsStatusIotBluetoothScanResultsEntryAdvertisingData OCTET STRING,
            lcsStatusIotBluetoothScanResultsEntryScanResponseData OCTET STRING,
            lcsStatusIotBluetoothScanResultsEntryManufacturer OCTET STRING,
            lcsStatusIotBluetoothScanResultsEntryLocalNameType INTEGER,
            lcsStatusIotBluetoothScanResultsEntryAsciiLocalName OCTET STRING,
            lcsStatusIotBluetoothScanResultsEntryIbeacon INTEGER,
            lcsStatusIotBluetoothScanResultsEntryIbeaconUuid OCTET STRING,
            lcsStatusIotBluetoothScanResultsEntryIbeaconMajor Unsigned32,
            lcsStatusIotBluetoothScanResultsEntryIbeaconMinor Unsigned32,
            lcsStatusIotBluetoothScanResultsEntryIbeaconMeasuredPower Integer32
    }

-- {COLUMN} 1.3.6.1.4.1.2356.11.1.111.90.2.1.1
lcsStatusIotBluetoothScanResultsEntryDeviceAddress OBJECT-TYPE
    SYNTAX     MacAddress
    MAX-ACCESS read-only
    STATUS     current
    DESCRIPTION
            "-- empty --"
    ::= { lcsStatusIotBluetoothScanResultsEntry 1 }

-- {COLUMN} 1.3.6.1.4.1.2356.11.1.111.90.2.1.2
lcsStatusIotBluetoothScanResultsEntryAddressType OBJECT-TYPE
    SYNTAX     INTEGER {
                  ePublic (0),
                  eRandom (1)
            }
    MAX-ACCESS read-only
    STATUS     current
    DESCRIPTION
            "-- empty --"
    ::= { lcsStatusIotBluetoothScanResultsEntry 2 }

-- {COLUMN} 1.3.6.1.4.1.2356.11.1.111.90.2.1.3
lcsStatusIotBluetoothScanResultsEntryRssi OBJECT-TYPE
    SYNTAX     Integer32 (-128..127)
    MAX-ACCESS read-only
    STATUS     current
    DESCRIPTION
            "-- empty --"
    ::= { lcsStatusIotBluetoothScanResultsEntry 3 }

-- {COLUMN} 1.3.6.1.4.1.2356.11.1.111.90.2.1.4
lcsStatusIotBluetoothScanResultsEntryLastSeen OBJECT-TYPE
    SYNTAX     Gauge32
    MAX-ACCESS read-only
    STATUS     current
    DESCRIPTION
            "-- empty --"
    ::= { lcsStatusIotBluetoothScanResultsEntry 4 }

-- {COLUMN} 1.3.6.1.4.1.2356.11.1.111.90.2.1.5
lcsStatusIotBluetoothScanResultsEntryAdvertisingData OBJECT-TYPE
    SYNTAX     OCTET STRING (SIZE(0..63))
    MAX-ACCESS read-only
    STATUS     current
    DESCRIPTION
            "-- empty --"
    ::= { lcsStatusIotBluetoothScanResultsEntry 5 }

-- {COLUMN} 1.3.6.1.4.1.2356.11.1.111.90.2.1.6
lcsStatusIotBluetoothScanResultsEntryScanResponseData OBJECT-TYPE
    SYNTAX     OCTET STRING (SIZE(0..63))
    MAX-ACCESS read-only
    STATUS     current
    DESCRIPTION
            "-- empty --"
    ::= { lcsStatusIotBluetoothScanResultsEntry 6 }

-- {COLUMN} 1.3.6.1.4.1.2356.11.1.111.90.2.1.7
lcsStatusIotBluetoothScanResultsEntryManufacturer OBJECT-TYPE
    SYNTAX     OCTET STRING (SIZE(0..30))
    MAX-ACCESS read-only
    STATUS     current
    DESCRIPTION
            "-- empty --"
    ::= { lcsStatusIotBluetoothScanResultsEntry 7 }

-- {COLUMN} 1.3.6.1.4.1.2356.11.1.111.90.2.1.8
lcsStatusIotBluetoothScanResultsEntryLocalNameType OBJECT-TYPE
    SYNTAX     INTEGER {
                  eNone (0),
                  eShortened (1),
                  eComplete (2)
            }
    MAX-ACCESS read-only
    STATUS     current
    DESCRIPTION
            "-- empty --"
    ::= { lcsStatusIotBluetoothScanResultsEntry 8 }

-- {COLUMN} 1.3.6.1.4.1.2356.11.1.111.90.2.1.9
lcsStatusIotBluetoothScanResultsEntryAsciiLocalName OBJECT-TYPE
    SYNTAX     OCTET STRING (SIZE(0..30))
    MAX-ACCESS read-only
    STATUS     current
    DESCRIPTION
            "-- empty --"
    ::= { lcsStatusIotBluetoothScanResultsEntry 9 }

-- {COLUMN} 1.3.6.1.4.1.2356.11.1.111.90.2.1.10
lcsStatusIotBluetoothScanResultsEntryIbeacon OBJECT-TYPE
    SYNTAX     INTEGER {
                  eNo (0),
                  eYes (1)
            }
    MAX-ACCESS read-only
    STATUS     current
    DESCRIPTION
            "-- empty --"
    ::= { lcsStatusIotBluetoothScanResultsEntry 10 }

-- {COLUMN} 1.3.6.1.4.1.2356.11.1.111.90.2.1.11
lcsStatusIotBluetoothScanResultsEntryIbeaconUuid OBJECT-TYPE
    SYNTAX     OCTET STRING (SIZE(0..37))
    MAX-ACCESS read-only
    STATUS     current
    DESCRIPTION
            "-- empty --"
    ::= { lcsStatusIotBluetoothScanResultsEntry 11 }

-- {COLUMN} 1.3.6.1.4.1.2356.11.1.111.90.2.1.12
lcsStatusIotBluetoothScanResultsEntryIbeaconMajor OBJECT-TYPE
    SYNTAX     Unsigned32 (0..65535)
    MAX-ACCESS read-only
    STATUS     current
    DESCRIPTION
            "-- empty --"
    ::= { lcsStatusIotBluetoothScanResultsEntry 12 }

-- {COLUMN} 1.3.6.1.4.1.2356.11.1.111.90.2.1.13
lcsStatusIotBluetoothScanResultsEntryIbeaconMinor OBJECT-TYPE
    SYNTAX     Unsigned32 (0..65535)
    MAX-ACCESS read-only
    STATUS     current
    DESCRIPTION
            "-- empty --"
    ::= { lcsStatusIotBluetoothScanResultsEntry 13 }

-- {COLUMN} 1.3.6.1.4.1.2356.11.1.111.90.2.1.14
lcsStatusIotBluetoothScanResultsEntryIbeaconMeasuredPower OBJECT-TYPE
    SYNTAX     Integer32 (-128..127)
    MAX-ACCESS read-only
    STATUS     current
    DESCRIPTION
            "-- empty --"
    ::= { lcsStatusIotBluetoothScanResultsEntry 14 }

-- {TABLE} 1.3.6.1.4.1.2356.11.1.111.90.3
lcsStatusIotBluetoothInterfacesTable OBJECT-TYPE
    SYNTAX     SEQUENCE OF LcsStatusIotBluetoothInterfacesEntry
    MAX-ACCESS not-accessible
    STATUS     current
    DESCRIPTION
            "-- empty --"
    ::= { lcsStatusIotBluetooth 3 }

-- {ROW} 1.3.6.1.4.1.2356.11.1.111.90.3.1
lcsStatusIotBluetoothInterfacesEntry OBJECT-TYPE
    SYNTAX     LcsStatusIotBluetoothInterfacesEntry
    MAX-ACCESS not-accessible
    STATUS     current
    DESCRIPTION
            ""
    INDEX {
            lcsStatusIotBluetoothInterfacesEntryIfc
          }
    ::= { lcsStatusIotBluetoothInterfacesTable 1 }

LcsStatusIotBluetoothInterfacesEntry ::= SEQUENCE {
            lcsStatusIotBluetoothInterfacesEntryIfc DisplayString,
            lcsStatusIotBluetoothInterfacesEntryState INTEGER,
            lcsStatusIotBluetoothInterfacesEntryResetReason DisplayString,
            lcsStatusIotBluetoothInterfacesEntryResetReasonValue OCTET STRING,
            lcsStatusIotBluetoothInterfacesEntryChipRevision Integer32,
            lcsStatusIotBluetoothInterfacesEntryHardwareMac MacAddress,
            lcsStatusIotBluetoothInterfacesEntrySoftwareVersion DisplayString
    }

-- {COLUMN} 1.3.6.1.4.1.2356.11.1.111.90.3.1.1
lcsStatusIotBluetoothInterfacesEntryIfc OBJECT-TYPE
    SYNTAX     DisplayString (SIZE(0..255))
    MAX-ACCESS read-only
    STATUS     current
    DESCRIPTION
            "-- empty --"
    ::= { lcsStatusIotBluetoothInterfacesEntry 1 }

-- {COLUMN} 1.3.6.1.4.1.2356.11.1.111.90.3.1.2
lcsStatusIotBluetoothInterfacesEntryState OBJECT-TYPE
    SYNTAX     INTEGER {
                  eUnknown (0),
                  eCheckFlashFw (1),
                  eTestMode (2),
                  eUpdateError (3),
                  eStarting (4),
                  eInitializing (5),
                  eChangingState (6),
                  eReady (7),
                  eBleBeacon (8),
                  eScanner (9),
                  eTestCmd (10)
            }
    MAX-ACCESS read-only
    STATUS     current
    DESCRIPTION
            "-- empty --"
    ::= { lcsStatusIotBluetoothInterfacesEntry 2 }

-- {COLUMN} 1.3.6.1.4.1.2356.11.1.111.90.3.1.3
lcsStatusIotBluetoothInterfacesEntryResetReason OBJECT-TYPE
    SYNTAX     DisplayString (SIZE(0..255))
    MAX-ACCESS read-only
    STATUS     current
    DESCRIPTION
            "-- empty --"
    ::= { lcsStatusIotBluetoothInterfacesEntry 3 }

-- {COLUMN} 1.3.6.1.4.1.2356.11.1.111.90.3.1.4
lcsStatusIotBluetoothInterfacesEntryResetReasonValue OBJECT-TYPE
    SYNTAX     OCTET STRING
    MAX-ACCESS read-only
    STATUS     current
    DESCRIPTION
            "-- empty --"
    ::= { lcsStatusIotBluetoothInterfacesEntry 4 }

-- {COLUMN} 1.3.6.1.4.1.2356.11.1.111.90.3.1.5
lcsStatusIotBluetoothInterfacesEntryChipRevision OBJECT-TYPE
    SYNTAX     Integer32 (0..255)
    MAX-ACCESS read-only
    STATUS     current
    DESCRIPTION
            "-- empty --"
    ::= { lcsStatusIotBluetoothInterfacesEntry 5 }

-- {COLUMN} 1.3.6.1.4.1.2356.11.1.111.90.3.1.6
lcsStatusIotBluetoothInterfacesEntryHardwareMac OBJECT-TYPE
    SYNTAX     MacAddress
    MAX-ACCESS read-only
    STATUS     current
    DESCRIPTION
            "-- empty --"
    ::= { lcsStatusIotBluetoothInterfacesEntry 6 }

-- {COLUMN} 1.3.6.1.4.1.2356.11.1.111.90.3.1.7
lcsStatusIotBluetoothInterfacesEntrySoftwareVersion OBJECT-TYPE
    SYNTAX     DisplayString (SIZE(0..255))
    MAX-ACCESS read-only
    STATUS     current
    DESCRIPTION
            "-- empty --"
    ::= { lcsStatusIotBluetoothInterfacesEntry 7 }

-- {TABLE} 1.3.6.1.4.1.2356.11.1.111.90.4
lcsStatusIotBluetoothStatisticsTable OBJECT-TYPE
    SYNTAX     SEQUENCE OF LcsStatusIotBluetoothStatisticsEntry
    MAX-ACCESS not-accessible
    STATUS     current
    DESCRIPTION
            "-- empty --"
    ::= { lcsStatusIotBluetooth 4 }

-- {ROW} 1.3.6.1.4.1.2356.11.1.111.90.4.1
lcsStatusIotBluetoothStatisticsEntry OBJECT-TYPE
    SYNTAX     LcsStatusIotBluetoothStatisticsEntry
    MAX-ACCESS not-accessible
    STATUS     current
    DESCRIPTION
            ""
    INDEX {
            lcsStatusIotBluetoothStatisticsEntryIfc
          }
    ::= { lcsStatusIotBluetoothStatisticsTable 1 }

LcsStatusIotBluetoothStatisticsEntry ::= SEQUENCE {
            lcsStatusIotBluetoothStatisticsEntryIfc DisplayString,
            lcsStatusIotBluetoothStatisticsEntryResetIndications Integer32,
            lcsStatusIotBluetoothStatisticsEntryScanIndications Integer32,
            lcsStatusIotBluetoothStatisticsEntryErrorIndications Integer32,
            lcsStatusIotBluetoothStatisticsEntryCrcErrors Integer32
    }

-- {COLUMN} 1.3.6.1.4.1.2356.11.1.111.90.4.1.1
lcsStatusIotBluetoothStatisticsEntryIfc OBJECT-TYPE
    SYNTAX     DisplayString (SIZE(0..255))
    MAX-ACCESS read-only
    STATUS     current
    DESCRIPTION
            "-- empty --"
    ::= { lcsStatusIotBluetoothStatisticsEntry 1 }

-- {COLUMN} 1.3.6.1.4.1.2356.11.1.111.90.4.1.2
lcsStatusIotBluetoothStatisticsEntryResetIndications OBJECT-TYPE
    SYNTAX     Integer32 (0..2147483647)
    MAX-ACCESS read-only
    STATUS     current
    DESCRIPTION
            "-- empty --"
    ::= { lcsStatusIotBluetoothStatisticsEntry 2 }

-- {COLUMN} 1.3.6.1.4.1.2356.11.1.111.90.4.1.3
lcsStatusIotBluetoothStatisticsEntryScanIndications OBJECT-TYPE
    SYNTAX     Integer32 (0..2147483647)
    MAX-ACCESS read-only
    STATUS     current
    DESCRIPTION
            "-- empty --"
    ::= { lcsStatusIotBluetoothStatisticsEntry 3 }

-- {COLUMN} 1.3.6.1.4.1.2356.11.1.111.90.4.1.4
lcsStatusIotBluetoothStatisticsEntryErrorIndications OBJECT-TYPE
    SYNTAX     Integer32 (0..2147483647)
    MAX-ACCESS read-only
    STATUS     current
    DESCRIPTION
            "-- empty --"
    ::= { lcsStatusIotBluetoothStatisticsEntry 4 }

-- {COLUMN} 1.3.6.1.4.1.2356.11.1.111.90.4.1.5
lcsStatusIotBluetoothStatisticsEntryCrcErrors OBJECT-TYPE
    SYNTAX     Integer32 (0..2147483647)
    MAX-ACCESS read-only
    STATUS     current
    DESCRIPTION
            "-- empty --"
    ::= { lcsStatusIotBluetoothStatisticsEntry 5 }

-- {NODE} 1.3.6.1.4.1.2356.11.1.112
lcsStatusIeee80211u OBJECT IDENTIFIER ::= { lcsStatus 112 }

-- {NODE} 1.3.6.1.4.1.2356.11.1.112.7
lcsStatusIeee80211uHotspot20 OBJECT IDENTIFIER ::= { lcsStatusIeee80211u 7 }

-- {TABLE} 1.3.6.1.4.1.2356.11.1.112.7.1
lcsStatusIeee80211uHotspot20OsuIconsTable OBJECT-TYPE
    SYNTAX     SEQUENCE OF LcsStatusIeee80211uHotspot20OsuIconsEntry
    MAX-ACCESS not-accessible
    STATUS     current
    DESCRIPTION
            "-- empty --"
    ::= { lcsStatusIeee80211uHotspot20 1 }

-- {ROW} 1.3.6.1.4.1.2356.11.1.112.7.1.1
lcsStatusIeee80211uHotspot20OsuIconsEntry OBJECT-TYPE
    SYNTAX     LcsStatusIeee80211uHotspot20OsuIconsEntry
    MAX-ACCESS not-accessible
    STATUS     current
    DESCRIPTION
            ""
    INDEX {
            lcsStatusIeee80211uHotspot20OsuIconsEntryName
          }
    ::= { lcsStatusIeee80211uHotspot20OsuIconsTable 1 }

LcsStatusIeee80211uHotspot20OsuIconsEntry ::= SEQUENCE {
            lcsStatusIeee80211uHotspot20OsuIconsEntryName INTEGER,
            lcsStatusIeee80211uHotspot20OsuIconsEntrySize Integer32,
            lcsStatusIeee80211uHotspot20OsuIconsEntryFileName DisplayString
    }

-- {COLUMN} 1.3.6.1.4.1.2356.11.1.112.7.1.1.1
lcsStatusIeee80211uHotspot20OsuIconsEntryName OBJECT-TYPE
    SYNTAX     INTEGER {
                  eNone (0),
                  eOsuProvImg1 (1),
                  eOsuProvImg2 (2),
                  eOsuProvImg3 (3),
                  eOsuProvImg4 (4),
                  eOsuProvImg5 (5),
                  eOsuProvImg6 (6),
                  eOsuProvImg7 (7),
                  eOsuProvImg8 (8),
                  eOsuProvImg9 (9),
                  eOsuProvImg10 (10),
                  eOsuProvImg11 (11),
                  eOsuProvImg12 (12),
                  eOsuProvImg13 (13),
                  eOsuProvImg14 (14),
                  eOsuProvImg15 (15),
                  eOsuProvImg16 (16)
            }
    MAX-ACCESS read-only
    STATUS     current
    DESCRIPTION
            "-- empty --"
    ::= { lcsStatusIeee80211uHotspot20OsuIconsEntry 1 }

-- {COLUMN} 1.3.6.1.4.1.2356.11.1.112.7.1.1.2
lcsStatusIeee80211uHotspot20OsuIconsEntrySize OBJECT-TYPE
    SYNTAX     Integer32 (0..2147483647)
    MAX-ACCESS read-only
    STATUS     current
    DESCRIPTION
            "-- empty --"
    ::= { lcsStatusIeee80211uHotspot20OsuIconsEntry 2 }

-- {COLUMN} 1.3.6.1.4.1.2356.11.1.112.7.1.1.3
lcsStatusIeee80211uHotspot20OsuIconsEntryFileName OBJECT-TYPE
    SYNTAX     DisplayString (SIZE(0..255))
    MAX-ACCESS read-only
    STATUS     current
    DESCRIPTION
            "-- empty --"
    ::= { lcsStatusIeee80211uHotspot20OsuIconsEntry 3 }

-- {NODE} 1.3.6.1.4.1.2356.11.1.201
lcsStatusSipAlg OBJECT IDENTIFIER ::= { lcsStatus 201 }

-- {SCALAR} 1.3.6.1.4.1.2356.11.1.201.1
lcsStatusSipAlgOperating OBJECT-TYPE
    SYNTAX     INTEGER {
                  eNo (0),
                  eYes (1)
            }
    MAX-ACCESS read-only
    STATUS     current
    DESCRIPTION
            "-- empty --"
    ::= { lcsStatusSipAlg 1 }

-- {TABLE} 1.3.6.1.4.1.2356.11.1.201.2
lcsStatusSipAlgRegistrationsTable OBJECT-TYPE
    SYNTAX     SEQUENCE OF LcsStatusSipAlgRegistrationsEntry
    MAX-ACCESS not-accessible
    STATUS     current
    DESCRIPTION
            "-- empty --"
    ::= { lcsStatusSipAlg 2 }

-- {ROW} 1.3.6.1.4.1.2356.11.1.201.2.1
lcsStatusSipAlgRegistrationsEntry OBJECT-TYPE
    SYNTAX     LcsStatusSipAlgRegistrationsEntry
    MAX-ACCESS not-accessible
    STATUS     current
    DESCRIPTION
            ""
    INDEX {
            lcsStatusSipAlgRegistrationsEntryIndex
          }
    ::= { lcsStatusSipAlgRegistrationsTable 1 }

LcsStatusSipAlgRegistrationsEntry ::= SEQUENCE {
            lcsStatusSipAlgRegistrationsEntryIndex Integer32,
            lcsStatusSipAlgRegistrationsEntrySipId DisplayString,
            lcsStatusSipAlgRegistrationsEntryRegistrarDomain DisplayString,
            lcsStatusSipAlgRegistrationsEntryRegistrarAddress DisplayString,
            lcsStatusSipAlgRegistrationsEntryClientAddress DisplayString,
            lcsStatusSipAlgRegistrationsEntryClientPort Integer32,
            lcsStatusSipAlgRegistrationsEntryWanAddress DisplayString,
            lcsStatusSipAlgRegistrationsEntryWanPort Integer32,
            lcsStatusSipAlgRegistrationsEntryRegisterMethod DisplayString,
            lcsStatusSipAlgRegistrationsEntryExpirationTime Integer32
    }

-- {COLUMN} 1.3.6.1.4.1.2356.11.1.201.2.1.1
lcsStatusSipAlgRegistrationsEntryIndex OBJECT-TYPE
    SYNTAX     Integer32 (0..255)
    MAX-ACCESS read-only
    STATUS     current
    DESCRIPTION
            "-- empty --"
    ::= { lcsStatusSipAlgRegistrationsEntry 1 }

-- {COLUMN} 1.3.6.1.4.1.2356.11.1.201.2.1.2
lcsStatusSipAlgRegistrationsEntrySipId OBJECT-TYPE
    SYNTAX     DisplayString (SIZE(0..19))
    MAX-ACCESS read-only
    STATUS     current
    DESCRIPTION
            "-- empty --"
    ::= { lcsStatusSipAlgRegistrationsEntry 2 }

-- {COLUMN} 1.3.6.1.4.1.2356.11.1.201.2.1.3
lcsStatusSipAlgRegistrationsEntryRegistrarDomain OBJECT-TYPE
    SYNTAX     DisplayString (SIZE(0..63))
    MAX-ACCESS read-only
    STATUS     current
    DESCRIPTION
            "-- empty --"
    ::= { lcsStatusSipAlgRegistrationsEntry 3 }

-- {COLUMN} 1.3.6.1.4.1.2356.11.1.201.2.1.4
lcsStatusSipAlgRegistrationsEntryRegistrarAddress OBJECT-TYPE
    SYNTAX     DisplayString (SIZE(0..63))
    MAX-ACCESS read-only
    STATUS     current
    DESCRIPTION
            "-- empty --"
    ::= { lcsStatusSipAlgRegistrationsEntry 4 }

-- {COLUMN} 1.3.6.1.4.1.2356.11.1.201.2.1.5
lcsStatusSipAlgRegistrationsEntryClientAddress OBJECT-TYPE
    SYNTAX     DisplayString (SIZE(0..63))
    MAX-ACCESS read-only
    STATUS     current
    DESCRIPTION
            "-- empty --"
    ::= { lcsStatusSipAlgRegistrationsEntry 5 }

-- {COLUMN} 1.3.6.1.4.1.2356.11.1.201.2.1.6
lcsStatusSipAlgRegistrationsEntryClientPort OBJECT-TYPE
    SYNTAX     Integer32 (0..65535)
    MAX-ACCESS read-only
    STATUS     current
    DESCRIPTION
            "-- empty --"
    ::= { lcsStatusSipAlgRegistrationsEntry 6 }

-- {COLUMN} 1.3.6.1.4.1.2356.11.1.201.2.1.7
lcsStatusSipAlgRegistrationsEntryWanAddress OBJECT-TYPE
    SYNTAX     DisplayString (SIZE(0..63))
    MAX-ACCESS read-only
    STATUS     current
    DESCRIPTION
            "-- empty --"
    ::= { lcsStatusSipAlgRegistrationsEntry 7 }

-- {COLUMN} 1.3.6.1.4.1.2356.11.1.201.2.1.8
lcsStatusSipAlgRegistrationsEntryWanPort OBJECT-TYPE
    SYNTAX     Integer32 (0..65535)
    MAX-ACCESS read-only
    STATUS     current
    DESCRIPTION
            "-- empty --"
    ::= { lcsStatusSipAlgRegistrationsEntry 8 }

-- {COLUMN} 1.3.6.1.4.1.2356.11.1.201.2.1.9
lcsStatusSipAlgRegistrationsEntryRegisterMethod OBJECT-TYPE
    SYNTAX     DisplayString (SIZE(0..20))
    MAX-ACCESS read-only
    STATUS     current
    DESCRIPTION
            "-- empty --"
    ::= { lcsStatusSipAlgRegistrationsEntry 9 }

-- {COLUMN} 1.3.6.1.4.1.2356.11.1.201.2.1.10
lcsStatusSipAlgRegistrationsEntryExpirationTime OBJECT-TYPE
    SYNTAX     Integer32 (0..65535)
    MAX-ACCESS read-only
    STATUS     current
    DESCRIPTION
            "-- empty --"
    ::= { lcsStatusSipAlgRegistrationsEntry 10 }

-- {TABLE} 1.3.6.1.4.1.2356.11.1.201.3
lcsStatusSipAlgCallsTable OBJECT-TYPE
    SYNTAX     SEQUENCE OF LcsStatusSipAlgCallsEntry
    MAX-ACCESS not-accessible
    STATUS     current
    DESCRIPTION
            "-- empty --"
    ::= { lcsStatusSipAlg 3 }

-- {ROW} 1.3.6.1.4.1.2356.11.1.201.3.1
lcsStatusSipAlgCallsEntry OBJECT-TYPE
    SYNTAX     LcsStatusSipAlgCallsEntry
    MAX-ACCESS not-accessible
    STATUS     current
    DESCRIPTION
            ""
    INDEX {
            lcsStatusSipAlgCallsEntryIndex
          }
    ::= { lcsStatusSipAlgCallsTable 1 }

LcsStatusSipAlgCallsEntry ::= SEQUENCE {
            lcsStatusSipAlgCallsEntryIndex Integer32,
            lcsStatusSipAlgCallsEntryCallId DisplayString,
            lcsStatusSipAlgCallsEntrySipDstAddress DisplayString,
            lcsStatusSipAlgCallsEntrySipSrcAddress DisplayString,
            lcsStatusSipAlgCallsEntrySipSrcPort Integer32,
            lcsStatusSipAlgCallsEntryWanAddress DisplayString,
            lcsStatusSipAlgCallsEntrySipWanPort Integer32,
            lcsStatusSipAlgCallsEntryRtpDstAddress DisplayString,
            lcsStatusSipAlgCallsEntryRtpDstPort Integer32,
            lcsStatusSipAlgCallsEntryRtpSrcAddress DisplayString,
            lcsStatusSipAlgCallsEntryRtpSrcPort Integer32,
            lcsStatusSipAlgCallsEntryRtpWanPort Integer32
    }

-- {COLUMN} 1.3.6.1.4.1.2356.11.1.201.3.1.1
lcsStatusSipAlgCallsEntryIndex OBJECT-TYPE
    SYNTAX     Integer32 (0..255)
    MAX-ACCESS read-only
    STATUS     current
    DESCRIPTION
            "-- empty --"
    ::= { lcsStatusSipAlgCallsEntry 1 }

-- {COLUMN} 1.3.6.1.4.1.2356.11.1.201.3.1.2
lcsStatusSipAlgCallsEntryCallId OBJECT-TYPE
    SYNTAX     DisplayString (SIZE(0..32))
    MAX-ACCESS read-only
    STATUS     current
    DESCRIPTION
            "-- empty --"
    ::= { lcsStatusSipAlgCallsEntry 2 }

-- {COLUMN} 1.3.6.1.4.1.2356.11.1.201.3.1.3
lcsStatusSipAlgCallsEntrySipDstAddress OBJECT-TYPE
    SYNTAX     DisplayString (SIZE(0..63))
    MAX-ACCESS read-only
    STATUS     current
    DESCRIPTION
            "-- empty --"
    ::= { lcsStatusSipAlgCallsEntry 3 }

-- {COLUMN} 1.3.6.1.4.1.2356.11.1.201.3.1.4
lcsStatusSipAlgCallsEntrySipSrcAddress OBJECT-TYPE
    SYNTAX     DisplayString (SIZE(0..63))
    MAX-ACCESS read-only
    STATUS     current
    DESCRIPTION
            "-- empty --"
    ::= { lcsStatusSipAlgCallsEntry 4 }

-- {COLUMN} 1.3.6.1.4.1.2356.11.1.201.3.1.5
lcsStatusSipAlgCallsEntrySipSrcPort OBJECT-TYPE
    SYNTAX     Integer32 (0..65535)
    MAX-ACCESS read-only
    STATUS     current
    DESCRIPTION
            "-- empty --"
    ::= { lcsStatusSipAlgCallsEntry 5 }

-- {COLUMN} 1.3.6.1.4.1.2356.11.1.201.3.1.6
lcsStatusSipAlgCallsEntryWanAddress OBJECT-TYPE
    SYNTAX     DisplayString (SIZE(0..63))
    MAX-ACCESS read-only
    STATUS     current
    DESCRIPTION
            "-- empty --"
    ::= { lcsStatusSipAlgCallsEntry 6 }

-- {COLUMN} 1.3.6.1.4.1.2356.11.1.201.3.1.7
lcsStatusSipAlgCallsEntrySipWanPort OBJECT-TYPE
    SYNTAX     Integer32 (0..65535)
    MAX-ACCESS read-only
    STATUS     current
    DESCRIPTION
            "-- empty --"
    ::= { lcsStatusSipAlgCallsEntry 7 }

-- {COLUMN} 1.3.6.1.4.1.2356.11.1.201.3.1.8
lcsStatusSipAlgCallsEntryRtpDstAddress OBJECT-TYPE
    SYNTAX     DisplayString (SIZE(0..63))
    MAX-ACCESS read-only
    STATUS     current
    DESCRIPTION
            "-- empty --"
    ::= { lcsStatusSipAlgCallsEntry 8 }

-- {COLUMN} 1.3.6.1.4.1.2356.11.1.201.3.1.9
lcsStatusSipAlgCallsEntryRtpDstPort OBJECT-TYPE
    SYNTAX     Integer32 (0..65535)
    MAX-ACCESS read-only
    STATUS     current
    DESCRIPTION
            "-- empty --"
    ::= { lcsStatusSipAlgCallsEntry 9 }

-- {COLUMN} 1.3.6.1.4.1.2356.11.1.201.3.1.10
lcsStatusSipAlgCallsEntryRtpSrcAddress OBJECT-TYPE
    SYNTAX     DisplayString (SIZE(0..63))
    MAX-ACCESS read-only
    STATUS     current
    DESCRIPTION
            "-- empty --"
    ::= { lcsStatusSipAlgCallsEntry 10 }

-- {COLUMN} 1.3.6.1.4.1.2356.11.1.201.3.1.11
lcsStatusSipAlgCallsEntryRtpSrcPort OBJECT-TYPE
    SYNTAX     Integer32 (0..65535)
    MAX-ACCESS read-only
    STATUS     current
    DESCRIPTION
            "-- empty --"
    ::= { lcsStatusSipAlgCallsEntry 11 }

-- {COLUMN} 1.3.6.1.4.1.2356.11.1.201.3.1.12
lcsStatusSipAlgCallsEntryRtpWanPort OBJECT-TYPE
    SYNTAX     Integer32 (0..65535)
    MAX-ACCESS read-only
    STATUS     current
    DESCRIPTION
            "-- empty --"
    ::= { lcsStatusSipAlgCallsEntry 12 }

-- {TABLE} 1.3.6.1.4.1.2356.11.1.301
lcsStatusLastAdminLoginsTable OBJECT-TYPE
    SYNTAX     SEQUENCE OF LcsStatusLastAdminLoginsEntry
    MAX-ACCESS not-accessible
    STATUS     current
    DESCRIPTION
            "-- empty --"
    ::= { lcsStatus 301 }

-- {ROW} 1.3.6.1.4.1.2356.11.1.301.1
lcsStatusLastAdminLoginsEntry OBJECT-TYPE
    SYNTAX     LcsStatusLastAdminLoginsEntry
    MAX-ACCESS not-accessible
    STATUS     current
    DESCRIPTION
            ""
    INDEX {
            lcsStatusLastAdminLoginsEntryIpAddress,
            lcsStatusLastAdminLoginsEntryProtocol,
            lcsStatusLastAdminLoginsEntryUserName,
            lcsStatusLastAdminLoginsEntryTimestamp
          }
    ::= { lcsStatusLastAdminLoginsTable 1 }

LcsStatusLastAdminLoginsEntry ::= SEQUENCE {
            lcsStatusLastAdminLoginsEntryIpAddress OCTET STRING,
            lcsStatusLastAdminLoginsEntryProtocol OCTET STRING,
            lcsStatusLastAdminLoginsEntryUserName OCTET STRING,
            lcsStatusLastAdminLoginsEntryTimestamp Gauge32,
            lcsStatusLastAdminLoginsEntryAction INTEGER
    }

-- {COLUMN} 1.3.6.1.4.1.2356.11.1.301.1.1
lcsStatusLastAdminLoginsEntryIpAddress OBJECT-TYPE
    SYNTAX     OCTET STRING (SIZE(0..43))
    MAX-ACCESS read-only
    STATUS     current
    DESCRIPTION
            "-- empty --"
    ::= { lcsStatusLastAdminLoginsEntry 1 }

-- {COLUMN} 1.3.6.1.4.1.2356.11.1.301.1.2
lcsStatusLastAdminLoginsEntryProtocol OBJECT-TYPE
    SYNTAX     OCTET STRING (SIZE(0..20))
    MAX-ACCESS read-only
    STATUS     current
    DESCRIPTION
            "-- empty --"
    ::= { lcsStatusLastAdminLoginsEntry 2 }

-- {COLUMN} 1.3.6.1.4.1.2356.11.1.301.1.3
lcsStatusLastAdminLoginsEntryUserName OBJECT-TYPE
    SYNTAX     OCTET STRING (SIZE(0..20))
    MAX-ACCESS read-only
    STATUS     current
    DESCRIPTION
            "-- empty --"
    ::= { lcsStatusLastAdminLoginsEntry 3 }

-- {COLUMN} 1.3.6.1.4.1.2356.11.1.301.1.4
lcsStatusLastAdminLoginsEntryTimestamp OBJECT-TYPE
    SYNTAX     Gauge32
    MAX-ACCESS read-only
    STATUS     current
    DESCRIPTION
            "-- empty --"
    ::= { lcsStatusLastAdminLoginsEntry 4 }

-- {COLUMN} 1.3.6.1.4.1.2356.11.1.301.1.5
lcsStatusLastAdminLoginsEntryAction OBJECT-TYPE
    SYNTAX     INTEGER {
                  eLogin (0),
                  eLogout (1),
                  eErrlogin (2)
            }
    MAX-ACCESS read-only
    STATUS     current
    DESCRIPTION
            "-- empty --"
    ::= { lcsStatusLastAdminLoginsEntry 5 }

-- {NODE} 1.3.6.1.4.1.2356.11.2
lcsSetup OBJECT IDENTIFIER ::= { lcos 2 }

-- {SCALAR} 1.3.6.1.4.1.2356.11.2.1
lcsSetupName OBJECT-TYPE
    SYNTAX     DisplayString (SIZE(0..64))
    MAX-ACCESS read-write
    STATUS     current
    DESCRIPTION
            ""
    ::= { lcsSetup 1 }

-- {NODE} 1.3.6.1.4.1.2356.11.2.2
lcsSetupWan OBJECT IDENTIFIER ::= { lcsSetup 2 }

-- {TABLE} 1.3.6.1.4.1.2356.11.2.2.2
lcsSetupWanDialupPeersTable OBJECT-TYPE
    SYNTAX     SEQUENCE OF LcsSetupWanDialupPeersEntry
    MAX-ACCESS not-accessible
    STATUS     current
    DESCRIPTION
            ""
    ::= { lcsSetupWan 2 }

-- {ROW} 1.3.6.1.4.1.2356.11.2.2.2.1
lcsSetupWanDialupPeersEntry OBJECT-TYPE
    SYNTAX     LcsSetupWanDialupPeersEntry
    MAX-ACCESS not-accessible
    STATUS     current
    DESCRIPTION
            ""
    INDEX {
            lcsSetupWanDialupPeersEntryPeer
          }
    ::= { lcsSetupWanDialupPeersTable 1 }

LcsSetupWanDialupPeersEntry ::= SEQUENCE {
            lcsSetupWanDialupPeersEntryPeer DisplayString,
            lcsSetupWanDialupPeersEntryDialupRemote DisplayString,
            lcsSetupWanDialupPeersEntryB1Dt Integer32,
            lcsSetupWanDialupPeersEntryB2Dt Integer32,
            lcsSetupWanDialupPeersEntryWanLayer DisplayString,
            lcsSetupWanDialupPeersEntryCallback INTEGER,
            lcsSetupWanDialupPeersEntryIpv6 DisplayString
    }

-- {COLUMN} 1.3.6.1.4.1.2356.11.2.2.2.1.1
lcsSetupWanDialupPeersEntryPeer OBJECT-TYPE
    SYNTAX     DisplayString (SIZE(0..16))
    MAX-ACCESS read-write
    STATUS     current
    DESCRIPTION
            ""
    ::= { lcsSetupWanDialupPeersEntry 1 }

-- {COLUMN} 1.3.6.1.4.1.2356.11.2.2.2.1.2
lcsSetupWanDialupPeersEntryDialupRemote OBJECT-TYPE
    SYNTAX     DisplayString (SIZE(0..31))
    MAX-ACCESS read-write
    STATUS     current
    DESCRIPTION
            ""
    ::= { lcsSetupWanDialupPeersEntry 2 }

-- {COLUMN} 1.3.6.1.4.1.2356.11.2.2.2.1.3
lcsSetupWanDialupPeersEntryB1Dt OBJECT-TYPE
    SYNTAX     Integer32 (0..65535)
    MAX-ACCESS read-write
    STATUS     current
    DESCRIPTION
            ""
    ::= { lcsSetupWanDialupPeersEntry 3 }

-- {COLUMN} 1.3.6.1.4.1.2356.11.2.2.2.1.4
lcsSetupWanDialupPeersEntryB2Dt OBJECT-TYPE
    SYNTAX     Integer32 (0..65535)
    MAX-ACCESS read-write
    STATUS     current
    DESCRIPTION
            ""
    ::= { lcsSetupWanDialupPeersEntry 4 }

-- {COLUMN} 1.3.6.1.4.1.2356.11.2.2.2.1.5
lcsSetupWanDialupPeersEntryWanLayer OBJECT-TYPE
    SYNTAX     DisplayString (SIZE(0..9))
    MAX-ACCESS read-write
    STATUS     current
    DESCRIPTION
            ""
    ::= { lcsSetupWanDialupPeersEntry 5 }

-- {COLUMN} 1.3.6.1.4.1.2356.11.2.2.2.1.6
lcsSetupWanDialupPeersEntryCallback OBJECT-TYPE
    SYNTAX     INTEGER {
                  eNo (0),
                  eAuto (1),
                  eLooser (2),
                  eName (5),
                  eFast (9)
            }
    MAX-ACCESS read-write
    STATUS     current
    DESCRIPTION
            ""
    ::= { lcsSetupWanDialupPeersEntry 6 }

-- {COLUMN} 1.3.6.1.4.1.2356.11.2.2.2.1.8
lcsSetupWanDialupPeersEntryIpv6 OBJECT-TYPE
    SYNTAX     DisplayString (SIZE(0..16))
    MAX-ACCESS read-write
    STATUS     current
    DESCRIPTION
            "-- empty --"
    ::= { lcsSetupWanDialupPeersEntry 8 }

-- {TABLE} 1.3.6.1.4.1.2356.11.2.2.3
lcsSetupWanRoundrobinTable OBJECT-TYPE
    SYNTAX     SEQUENCE OF LcsSetupWanRoundrobinEntry
    MAX-ACCESS not-accessible
    STATUS     current
    DESCRIPTION
            ""
    ::= { lcsSetupWan 3 }

-- {ROW} 1.3.6.1.4.1.2356.11.2.2.3.1
lcsSetupWanRoundrobinEntry OBJECT-TYPE
    SYNTAX     LcsSetupWanRoundrobinEntry
    MAX-ACCESS not-accessible
    STATUS     current
    DESCRIPTION
            ""
    INDEX {
            lcsSetupWanRoundrobinEntryPeer
          }
    ::= { lcsSetupWanRoundrobinTable 1 }

LcsSetupWanRoundrobinEntry ::= SEQUENCE {
            lcsSetupWanRoundrobinEntryPeer DisplayString,
            lcsSetupWanRoundrobinEntryRoundRobin DisplayString,
            lcsSetupWanRoundrobinEntryHead INTEGER
    }

-- {COLUMN} 1.3.6.1.4.1.2356.11.2.2.3.1.1
lcsSetupWanRoundrobinEntryPeer OBJECT-TYPE
    SYNTAX     DisplayString (SIZE(0..18))
    MAX-ACCESS read-write
    STATUS     current
    DESCRIPTION
            ""
    ::= { lcsSetupWanRoundrobinEntry 1 }

-- {COLUMN} 1.3.6.1.4.1.2356.11.2.2.3.1.2
lcsSetupWanRoundrobinEntryRoundRobin OBJECT-TYPE
    SYNTAX     DisplayString (SIZE(0..53))
    MAX-ACCESS read-write
    STATUS     current
    DESCRIPTION
            ""
    ::= { lcsSetupWanRoundrobinEntry 2 }

-- {COLUMN} 1.3.6.1.4.1.2356.11.2.2.3.1.3
lcsSetupWanRoundrobinEntryHead OBJECT-TYPE
    SYNTAX     INTEGER {
                  eLast (0),
                  eFirst (1)
            }
    MAX-ACCESS read-write
    STATUS     current
    DESCRIPTION
            ""
    ::= { lcsSetupWanRoundrobinEntry 3 }

-- {TABLE} 1.3.6.1.4.1.2356.11.2.2.4
lcsSetupWanLayerTable OBJECT-TYPE
    SYNTAX     SEQUENCE OF LcsSetupWanLayerEntry
    MAX-ACCESS not-accessible
    STATUS     current
    DESCRIPTION
            ""
    ::= { lcsSetupWan 4 }

-- {ROW} 1.3.6.1.4.1.2356.11.2.2.4.1
lcsSetupWanLayerEntry OBJECT-TYPE
    SYNTAX     LcsSetupWanLayerEntry
    MAX-ACCESS not-accessible
    STATUS     current
    DESCRIPTION
            ""
    INDEX {
            lcsSetupWanLayerEntryWanLayer
          }
    ::= { lcsSetupWanLayerTable 1 }

LcsSetupWanLayerEntry ::= SEQUENCE {
            lcsSetupWanLayerEntryWanLayer DisplayString,
            lcsSetupWanLayerEntryEncaps INTEGER,
            lcsSetupWanLayerEntryLay3 INTEGER,
            lcsSetupWanLayerEntryLay2 INTEGER,
            lcsSetupWanLayerEntryL2Opt INTEGER,
            lcsSetupWanLayerEntryLay1 INTEGER
    }

-- {COLUMN} 1.3.6.1.4.1.2356.11.2.2.4.1.1
lcsSetupWanLayerEntryWanLayer OBJECT-TYPE
    SYNTAX     DisplayString (SIZE(0..9))
    MAX-ACCESS read-write
    STATUS     current
    DESCRIPTION
            ""
    ::= { lcsSetupWanLayerEntry 1 }

-- {COLUMN} 1.3.6.1.4.1.2356.11.2.2.4.1.2
lcsSetupWanLayerEntryEncaps OBJECT-TYPE
    SYNTAX     INTEGER {
                  eEther (0),
                  eLlcMux (1),
                  eLlcEth (3),
                  eVcMux (4),
                  eTrans (255)
            }
    MAX-ACCESS read-write
    STATUS     current
    DESCRIPTION
            ""
    ::= { lcsSetupWanLayerEntry 2 }

-- {COLUMN} 1.3.6.1.4.1.2356.11.2.2.4.1.3
lcsSetupWanLayerEntryLay3 OBJECT-TYPE
    SYNTAX     INTEGER {
                  ePpp (4),
                  eAppp (5),
                  eScppp (6),
                  eScappp (7),
                  eSctrans (8),
                  eDhcp (9),
                  eTRANS (255)
            }
    MAX-ACCESS read-write
    STATUS     current
    DESCRIPTION
            ""
    ::= { lcsSetupWanLayerEntry 3 }

-- {COLUMN} 1.3.6.1.4.1.2356.11.2.2.4.1.4
lcsSetupWanLayerEntryLay2 OBJECT-TYPE
    SYNTAX     INTEGER {
                  eX75lapb (0),
                  eTrans (1),
                  ePppoe (5)
            }
    MAX-ACCESS read-write
    STATUS     current
    DESCRIPTION
            ""
    ::= { lcsSetupWanLayerEntry 4 }

-- {COLUMN} 1.3.6.1.4.1.2356.11.2.2.4.1.5
lcsSetupWanLayerEntryL2Opt OBJECT-TYPE
    SYNTAX     INTEGER {
                  eCompr (0),
                  eBundle (1),
                  eBndPlusCmpr (2),
                  eNone (255)
            }
    MAX-ACCESS read-write
    STATUS     current
    DESCRIPTION
            ""
    ::= { lcsSetupWanLayerEntry 5 }

-- {COLUMN} 1.3.6.1.4.1.2356.11.2.2.4.1.6
lcsSetupWanLayerEntryLay1 OBJECT-TYPE
    SYNTAX     INTEGER {
                  eHdlc64k (0),
                  eHdlc56k (1),
                  eAdsl (2),
                  eV1109k6 (3),
                  eEth (4),
                  eSerial (6),
                  eVdsl (9),
                  eV11019k2 (67),
                  eV11038k4 (131)
            }
    MAX-ACCESS read-write
    STATUS     current
    DESCRIPTION
            ""
    ::= { lcsSetupWanLayerEntry 6 }

-- {TABLE} 1.3.6.1.4.1.2356.11.2.2.5
lcsSetupWanPppTable OBJECT-TYPE
    SYNTAX     SEQUENCE OF LcsSetupWanPppEntry
    MAX-ACCESS not-accessible
    STATUS     current
    DESCRIPTION
            ""
    ::= { lcsSetupWan 5 }

-- {ROW} 1.3.6.1.4.1.2356.11.2.2.5.1
lcsSetupWanPppEntry OBJECT-TYPE
    SYNTAX     LcsSetupWanPppEntry
    MAX-ACCESS not-accessible
    STATUS     current
    DESCRIPTION
            ""
    INDEX {
            lcsSetupWanPppEntryPeer
          }
    ::= { lcsSetupWanPppTable 1 }

LcsSetupWanPppEntry ::= SEQUENCE {
            lcsSetupWanPppEntryPeer DisplayString,
            lcsSetupWanPppEntryAuthentRequest BITS,
            lcsSetupWanPppEntryKey DisplayString,
            lcsSetupWanPppEntryTime Integer32,
            lcsSetupWanPppEntryTry Integer32,
            lcsSetupWanPppEntryUsername DisplayString,
            lcsSetupWanPppEntryConf Integer32,
            lcsSetupWanPppEntryFail Integer32,
            lcsSetupWanPppEntryTerm Integer32,
            lcsSetupWanPppEntryRights BITS,
            lcsSetupWanPppEntryAuthentResponse BITS
    }

-- {COLUMN} 1.3.6.1.4.1.2356.11.2.2.5.1.1
lcsSetupWanPppEntryPeer OBJECT-TYPE
    SYNTAX     DisplayString (SIZE(0..16))
    MAX-ACCESS read-write
    STATUS     current
    DESCRIPTION
            ""
    ::= { lcsSetupWanPppEntry 1 }

-- {COLUMN} 1.3.6.1.4.1.2356.11.2.2.5.1.2
lcsSetupWanPppEntryAuthentRequest OBJECT-TYPE
    SYNTAX     BITS {
                  eNone (0),
                  eMsChapv2 (2),
                  eMsChap (3),
                  eChap (4),
                  ePap (5)
            }
    MAX-ACCESS read-write
    STATUS     current
    DESCRIPTION
            ""
    ::= { lcsSetupWanPppEntry 2 }

-- {COLUMN} 1.3.6.1.4.1.2356.11.2.2.5.1.3
lcsSetupWanPppEntryKey OBJECT-TYPE
    SYNTAX     DisplayString (SIZE(0..32))
    MAX-ACCESS read-write
    STATUS     current
    DESCRIPTION
            ""
    ::= { lcsSetupWanPppEntry 3 }

-- {COLUMN} 1.3.6.1.4.1.2356.11.2.2.5.1.4
lcsSetupWanPppEntryTime OBJECT-TYPE
    SYNTAX     Integer32 (0..255)
    MAX-ACCESS read-write
    STATUS     current
    DESCRIPTION
            ""
    ::= { lcsSetupWanPppEntry 4 }

-- {COLUMN} 1.3.6.1.4.1.2356.11.2.2.5.1.5
lcsSetupWanPppEntryTry OBJECT-TYPE
    SYNTAX     Integer32 (0..255)
    MAX-ACCESS read-write
    STATUS     current
    DESCRIPTION
            ""
    ::= { lcsSetupWanPppEntry 5 }

-- {COLUMN} 1.3.6.1.4.1.2356.11.2.2.5.1.6
lcsSetupWanPppEntryUsername OBJECT-TYPE
    SYNTAX     DisplayString (SIZE(0..64))
    MAX-ACCESS read-write
    STATUS     current
    DESCRIPTION
            ""
    ::= { lcsSetupWanPppEntry 6 }

-- {COLUMN} 1.3.6.1.4.1.2356.11.2.2.5.1.7
lcsSetupWanPppEntryConf OBJECT-TYPE
    SYNTAX     Integer32 (0..255)
    MAX-ACCESS read-write
    STATUS     current
    DESCRIPTION
            ""
    ::= { lcsSetupWanPppEntry 7 }

-- {COLUMN} 1.3.6.1.4.1.2356.11.2.2.5.1.8
lcsSetupWanPppEntryFail OBJECT-TYPE
    SYNTAX     Integer32 (0..255)
    MAX-ACCESS read-write
    STATUS     current
    DESCRIPTION
            ""
    ::= { lcsSetupWanPppEntry 8 }

-- {COLUMN} 1.3.6.1.4.1.2356.11.2.2.5.1.9
lcsSetupWanPppEntryTerm OBJECT-TYPE
    SYNTAX     Integer32 (0..255)
    MAX-ACCESS read-write
    STATUS     current
    DESCRIPTION
            ""
    ::= { lcsSetupWanPppEntry 9 }

-- {COLUMN} 1.3.6.1.4.1.2356.11.2.2.5.1.10
lcsSetupWanPppEntryRights OBJECT-TYPE
    SYNTAX     BITS {
                  eNone (0),
                  eIpv6 (3),
                  eNbt (6),
                  eIp (7)
            }
    MAX-ACCESS read-write
    STATUS     current
    DESCRIPTION
            "-- empty --"
    ::= { lcsSetupWanPppEntry 10 }

-- {COLUMN} 1.3.6.1.4.1.2356.11.2.2.5.1.11
lcsSetupWanPppEntryAuthentResponse OBJECT-TYPE
    SYNTAX     BITS {
                  eNone (0),
                  eMsChapv2 (2),
                  eMsChap (3),
                  eChap (4),
                  ePap (5)
            }
    MAX-ACCESS read-write
    STATUS     current
    DESCRIPTION
            ""
    ::= { lcsSetupWanPppEntry 11 }

-- {TABLE} 1.3.6.1.4.1.2356.11.2.2.6
lcsSetupWanIncomingCallingNumbersTable OBJECT-TYPE
    SYNTAX     SEQUENCE OF LcsSetupWanIncomingCallingNumbersEntry
    MAX-ACCESS not-accessible
    STATUS     current
    DESCRIPTION
            ""
    ::= { lcsSetupWan 6 }

-- {ROW} 1.3.6.1.4.1.2356.11.2.2.6.1
lcsSetupWanIncomingCallingNumbersEntry OBJECT-TYPE
    SYNTAX     LcsSetupWanIncomingCallingNumbersEntry
    MAX-ACCESS not-accessible
    STATUS     current
    DESCRIPTION
            ""
    INDEX {
            lcsSetupWanIncomingCallingNumbersEntryDialupRemote
          }
    ::= { lcsSetupWanIncomingCallingNumbersTable 1 }

LcsSetupWanIncomingCallingNumbersEntry ::= SEQUENCE {
            lcsSetupWanIncomingCallingNumbersEntryDialupRemote DisplayString,
            lcsSetupWanIncomingCallingNumbersEntryPeer DisplayString
    }

-- {COLUMN} 1.3.6.1.4.1.2356.11.2.2.6.1.1
lcsSetupWanIncomingCallingNumbersEntryDialupRemote OBJECT-TYPE
    SYNTAX     DisplayString (SIZE(0..31))
    MAX-ACCESS read-write
    STATUS     current
    DESCRIPTION
            ""
    ::= { lcsSetupWanIncomingCallingNumbersEntry 1 }

-- {COLUMN} 1.3.6.1.4.1.2356.11.2.2.6.1.2
lcsSetupWanIncomingCallingNumbersEntryPeer OBJECT-TYPE
    SYNTAX     DisplayString (SIZE(0..16))
    MAX-ACCESS read-write
    STATUS     current
    DESCRIPTION
            ""
    ::= { lcsSetupWanIncomingCallingNumbersEntry 2 }

-- {SCALAR} 1.3.6.1.4.1.2356.11.2.2.7
lcsSetupWanDialPrefix OBJECT-TYPE
    SYNTAX     DisplayString (SIZE(0..8))
    MAX-ACCESS read-only
    STATUS     current
    DESCRIPTION
            ""
    ::= { lcsSetupWan 7 }

-- {TABLE} 1.3.6.1.4.1.2356.11.2.2.8
lcsSetupWanScriptsTable OBJECT-TYPE
    SYNTAX     SEQUENCE OF LcsSetupWanScriptsEntry
    MAX-ACCESS not-accessible
    STATUS     current
    DESCRIPTION
            ""
    ::= { lcsSetupWan 8 }

-- {ROW} 1.3.6.1.4.1.2356.11.2.2.8.1
lcsSetupWanScriptsEntry OBJECT-TYPE
    SYNTAX     LcsSetupWanScriptsEntry
    MAX-ACCESS not-accessible
    STATUS     current
    DESCRIPTION
            ""
    INDEX {
            lcsSetupWanScriptsEntryPeer
          }
    ::= { lcsSetupWanScriptsTable 1 }

LcsSetupWanScriptsEntry ::= SEQUENCE {
            lcsSetupWanScriptsEntryPeer DisplayString,
            lcsSetupWanScriptsEntryScript DisplayString
    }

-- {COLUMN} 1.3.6.1.4.1.2356.11.2.2.8.1.1
lcsSetupWanScriptsEntryPeer OBJECT-TYPE
    SYNTAX     DisplayString (SIZE(0..18))
    MAX-ACCESS read-write
    STATUS     current
    DESCRIPTION
            ""
    ::= { lcsSetupWanScriptsEntry 1 }

-- {COLUMN} 1.3.6.1.4.1.2356.11.2.2.8.1.2
lcsSetupWanScriptsEntryScript OBJECT-TYPE
    SYNTAX     DisplayString (SIZE(0..58))
    MAX-ACCESS read-write
    STATUS     current
    DESCRIPTION
            ""
    ::= { lcsSetupWanScriptsEntry 2 }

-- {SCALAR} 1.3.6.1.4.1.2356.11.2.2.9
lcsSetupWanProtect OBJECT-TYPE
    SYNTAX     INTEGER {
                  eNone (0),
                  eNumber (2),
                  eScreened (4)
            }
    MAX-ACCESS read-write
    STATUS     current
    DESCRIPTION
            ""
    ::= { lcsSetupWan 9 }

-- {SCALAR} 1.3.6.1.4.1.2356.11.2.2.10
lcsSetupWanCallbackAttempts OBJECT-TYPE
    SYNTAX     Integer32 (0..255)
    MAX-ACCESS read-write
    STATUS     current
    DESCRIPTION
            ""
    ::= { lcsSetupWan 10 }

-- {TABLE} 1.3.6.1.4.1.2356.11.2.2.11
lcsSetupWanRouterInterfaceTable OBJECT-TYPE
    SYNTAX     SEQUENCE OF LcsSetupWanRouterInterfaceEntry
    MAX-ACCESS not-accessible
    STATUS     current
    DESCRIPTION
            ""
    ::= { lcsSetupWan 11 }

-- {ROW} 1.3.6.1.4.1.2356.11.2.2.11.1
lcsSetupWanRouterInterfaceEntry OBJECT-TYPE
    SYNTAX     LcsSetupWanRouterInterfaceEntry
    MAX-ACCESS not-accessible
    STATUS     current
    DESCRIPTION
            ""
    INDEX {
            lcsSetupWanRouterInterfaceEntryIfc
          }
    ::= { lcsSetupWanRouterInterfaceTable 1 }

LcsSetupWanRouterInterfaceEntry ::= SEQUENCE {
            lcsSetupWanRouterInterfaceEntryIfc INTEGER,
            lcsSetupWanRouterInterfaceEntryMsnEaz DisplayString,
            lcsSetupWanRouterInterfaceEntryClip INTEGER,
            lcsSetupWanRouterInterfaceEntryYc INTEGER,
            lcsSetupWanRouterInterfaceEntryAcceptCalls INTEGER,
            lcsSetupWanRouterInterfaceEntryTypeOfInterface Integer32
    }

-- {COLUMN} 1.3.6.1.4.1.2356.11.2.2.11.1.1
lcsSetupWanRouterInterfaceEntryIfc OBJECT-TYPE
    SYNTAX     INTEGER {
                  eS01 (257),
                  eS02 (258),
                  eModem (513),
                  eDsl1 (2049),
                  eDsl2 (2050),
                  eDsl3 (2051),
                  eDsl4 (2052),
                  eDsl5 (2053),
                  eAdsl (8193),
                  eVdsl (16385),
                  eVdsl2 (16386)
            }
    MAX-ACCESS read-only
    STATUS     current
    DESCRIPTION
            ""
    ::= { lcsSetupWanRouterInterfaceEntry 1 }

-- {COLUMN} 1.3.6.1.4.1.2356.11.2.2.11.1.2
lcsSetupWanRouterInterfaceEntryMsnEaz OBJECT-TYPE
    SYNTAX     DisplayString (SIZE(0..30))
    MAX-ACCESS read-write
    STATUS     current
    DESCRIPTION
            ""
    ::= { lcsSetupWanRouterInterfaceEntry 2 }

-- {COLUMN} 1.3.6.1.4.1.2356.11.2.2.11.1.3
lcsSetupWanRouterInterfaceEntryClip OBJECT-TYPE
    SYNTAX     INTEGER {
                  eYes (0),
                  eNo (1)
            }
    MAX-ACCESS read-write
    STATUS     current
    DESCRIPTION
            ""
    ::= { lcsSetupWanRouterInterfaceEntry 3 }

-- {COLUMN} 1.3.6.1.4.1.2356.11.2.2.11.1.8
lcsSetupWanRouterInterfaceEntryYc OBJECT-TYPE
    SYNTAX     INTEGER {
                  eYes (0),
                  eNo (1)
            }
    MAX-ACCESS read-write
    STATUS     current
    DESCRIPTION
            ""
    ::= { lcsSetupWanRouterInterfaceEntry 8 }

-- {COLUMN} 1.3.6.1.4.1.2356.11.2.2.11.1.9
lcsSetupWanRouterInterfaceEntryAcceptCalls OBJECT-TYPE
    SYNTAX     INTEGER {
                  eAll (0),
                  eDigital (1),
                  eAnalog (2),
                  eNone (128)
            }
    MAX-ACCESS read-write
    STATUS     current
    DESCRIPTION
            ""
    ::= { lcsSetupWanRouterInterfaceEntry 9 }

-- {COLUMN} 1.3.6.1.4.1.2356.11.2.2.11.1.10
lcsSetupWanRouterInterfaceEntryTypeOfInterface OBJECT-TYPE
    SYNTAX     Integer32 (0..2147483647)
    MAX-ACCESS read-only
    STATUS     current
    DESCRIPTION
            ""
    ::= { lcsSetupWanRouterInterfaceEntry 10 }

-- {NODE} 1.3.6.1.4.1.2356.11.2.2.13
lcsSetupWanManualDialing OBJECT IDENTIFIER ::= { lcsSetupWan 13 }

-- {SCALAR} 1.3.6.1.4.1.2356.11.2.2.13.1
lcsSetupWanManualDialingConnect OBJECT-TYPE
    SYNTAX     DisplayString
    MAX-ACCESS read-write
    STATUS     current
    DESCRIPTION
            ""
    ::= { lcsSetupWanManualDialing 1 }

-- {SCALAR} 1.3.6.1.4.1.2356.11.2.2.13.2
lcsSetupWanManualDialingDisconnect OBJECT-TYPE
    SYNTAX     DisplayString
    MAX-ACCESS read-write
    STATUS     current
    DESCRIPTION
            ""
    ::= { lcsSetupWanManualDialing 2 }

-- {SCALAR} 1.3.6.1.4.1.2356.11.2.2.15
lcsSetupWanKeepaliveWithoutRoute OBJECT-TYPE
    SYNTAX     INTEGER {
                  eNo (0),
                  eYes (1)
            }
    MAX-ACCESS read-write
    STATUS     current
    DESCRIPTION
            "-- empty --"
    ::= { lcsSetupWan 15 }

-- {SCALAR} 1.3.6.1.4.1.2356.11.2.2.18
lcsSetupWanBackupDelaySeconds OBJECT-TYPE
    SYNTAX     Integer32 (0..65535)
    MAX-ACCESS read-write
    STATUS     current
    DESCRIPTION
            ""
    ::= { lcsSetupWan 18 }

-- {TABLE} 1.3.6.1.4.1.2356.11.2.2.19
lcsSetupWanDslBroadbandPeersTable OBJECT-TYPE
    SYNTAX     SEQUENCE OF LcsSetupWanDslBroadbandPeersEntry
    MAX-ACCESS not-accessible
    STATUS     current
    DESCRIPTION
            ""
    ::= { lcsSetupWan 19 }

-- {ROW} 1.3.6.1.4.1.2356.11.2.2.19.1
lcsSetupWanDslBroadbandPeersEntry OBJECT-TYPE
    SYNTAX     LcsSetupWanDslBroadbandPeersEntry
    MAX-ACCESS not-accessible
    STATUS     current
    DESCRIPTION
            ""
    INDEX {
            lcsSetupWanDslBroadbandPeersEntryPeer
          }
    ::= { lcsSetupWanDslBroadbandPeersTable 1 }

LcsSetupWanDslBroadbandPeersEntry ::= SEQUENCE {
            lcsSetupWanDslBroadbandPeersEntryPeer DisplayString,
            lcsSetupWanDslBroadbandPeersEntryShTime Integer32,
            lcsSetupWanDslBroadbandPeersEntryWanLayer DisplayString,
            lcsSetupWanDslBroadbandPeersEntryAcName DisplayString,
            lcsSetupWanDslBroadbandPeersEntryServicename DisplayString,
            lcsSetupWanDslBroadbandPeersEntryAtmVpi Integer32,
            lcsSetupWanDslBroadbandPeersEntryAtmVci Integer32,
            lcsSetupWanDslBroadbandPeersEntryUserDefMac MacAddress,
            lcsSetupWanDslBroadbandPeersEntryDslIfcS DisplayString,
            lcsSetupWanDslBroadbandPeersEntryMacType INTEGER,
            lcsSetupWanDslBroadbandPeersEntryVlanId Integer32,
            lcsSetupWanDslBroadbandPeersEntryPrioMapping INTEGER,
            lcsSetupWanDslBroadbandPeersEntryIpv6 DisplayString
    }

-- {COLUMN} 1.3.6.1.4.1.2356.11.2.2.19.1.1
lcsSetupWanDslBroadbandPeersEntryPeer OBJECT-TYPE
    SYNTAX     DisplayString (SIZE(0..16))
    MAX-ACCESS read-write
    STATUS     current
    DESCRIPTION
            ""
    ::= { lcsSetupWanDslBroadbandPeersEntry 1 }

-- {COLUMN} 1.3.6.1.4.1.2356.11.2.2.19.1.3
lcsSetupWanDslBroadbandPeersEntryShTime OBJECT-TYPE
    SYNTAX     Integer32 (0..65535)
    MAX-ACCESS read-write
    STATUS     current
    DESCRIPTION
            ""
    ::= { lcsSetupWanDslBroadbandPeersEntry 3 }

-- {COLUMN} 1.3.6.1.4.1.2356.11.2.2.19.1.5
lcsSetupWanDslBroadbandPeersEntryWanLayer OBJECT-TYPE
    SYNTAX     DisplayString (SIZE(0..9))
    MAX-ACCESS read-write
    STATUS     current
    DESCRIPTION
            ""
    ::= { lcsSetupWanDslBroadbandPeersEntry 5 }

-- {COLUMN} 1.3.6.1.4.1.2356.11.2.2.19.1.9
lcsSetupWanDslBroadbandPeersEntryAcName OBJECT-TYPE
    SYNTAX     DisplayString (SIZE(0..64))
    MAX-ACCESS read-write
    STATUS     current
    DESCRIPTION
            ""
    ::= { lcsSetupWanDslBroadbandPeersEntry 9 }

-- {COLUMN} 1.3.6.1.4.1.2356.11.2.2.19.1.10
lcsSetupWanDslBroadbandPeersEntryServicename OBJECT-TYPE
    SYNTAX     DisplayString (SIZE(0..32))
    MAX-ACCESS read-write
    STATUS     current
    DESCRIPTION
            ""
    ::= { lcsSetupWanDslBroadbandPeersEntry 10 }

-- {COLUMN} 1.3.6.1.4.1.2356.11.2.2.19.1.11
lcsSetupWanDslBroadbandPeersEntryAtmVpi OBJECT-TYPE
    SYNTAX     Integer32 (0..255)
    MAX-ACCESS read-write
    STATUS     current
    DESCRIPTION
            ""
    ::= { lcsSetupWanDslBroadbandPeersEntry 11 }

-- {COLUMN} 1.3.6.1.4.1.2356.11.2.2.19.1.12
lcsSetupWanDslBroadbandPeersEntryAtmVci OBJECT-TYPE
    SYNTAX     Integer32 (0..65535)
    MAX-ACCESS read-write
    STATUS     current
    DESCRIPTION
            ""
    ::= { lcsSetupWanDslBroadbandPeersEntry 12 }

-- {COLUMN} 1.3.6.1.4.1.2356.11.2.2.19.1.13
lcsSetupWanDslBroadbandPeersEntryUserDefMac OBJECT-TYPE
    SYNTAX     MacAddress
    MAX-ACCESS read-write
    STATUS     current
    DESCRIPTION
            ""
    ::= { lcsSetupWanDslBroadbandPeersEntry 13 }

-- {COLUMN} 1.3.6.1.4.1.2356.11.2.2.19.1.14
lcsSetupWanDslBroadbandPeersEntryDslIfcS OBJECT-TYPE
    SYNTAX     DisplayString (SIZE(0..63))
    MAX-ACCESS read-write
    STATUS     current
    DESCRIPTION
            ""
    ::= { lcsSetupWanDslBroadbandPeersEntry 14 }

-- {COLUMN} 1.3.6.1.4.1.2356.11.2.2.19.1.15
lcsSetupWanDslBroadbandPeersEntryMacType OBJECT-TYPE
    SYNTAX     INTEGER {
                  eLocal (0),
                  eGlobal (1),
                  eUserDef (2)
            }
    MAX-ACCESS read-write
    STATUS     current
    DESCRIPTION
            ""
    ::= { lcsSetupWanDslBroadbandPeersEntry 15 }

-- {COLUMN} 1.3.6.1.4.1.2356.11.2.2.19.1.16
lcsSetupWanDslBroadbandPeersEntryVlanId OBJECT-TYPE
    SYNTAX     Integer32 (0..65535)
    MAX-ACCESS read-write
    STATUS     current
    DESCRIPTION
            ""
    ::= { lcsSetupWanDslBroadbandPeersEntry 16 }

-- {COLUMN} 1.3.6.1.4.1.2356.11.2.2.19.1.17
lcsSetupWanDslBroadbandPeersEntryPrioMapping OBJECT-TYPE
    SYNTAX     INTEGER {
                  eOff (0),
                  e1tr112 (1),
                  eDscp (2)
            }
    MAX-ACCESS read-write
    STATUS     current
    DESCRIPTION
            "-- empty --"
    ::= { lcsSetupWanDslBroadbandPeersEntry 17 }

-- {COLUMN} 1.3.6.1.4.1.2356.11.2.2.19.1.19
lcsSetupWanDslBroadbandPeersEntryIpv6 OBJECT-TYPE
    SYNTAX     DisplayString (SIZE(0..16))
    MAX-ACCESS read-write
    STATUS     current
    DESCRIPTION
            "-- empty --"
    ::= { lcsSetupWanDslBroadbandPeersEntry 19 }

-- {TABLE} 1.3.6.1.4.1.2356.11.2.2.20
lcsSetupWanIpListTable OBJECT-TYPE
    SYNTAX     SEQUENCE OF LcsSetupWanIpListEntry
    MAX-ACCESS not-accessible
    STATUS     current
    DESCRIPTION
            ""
    ::= { lcsSetupWan 20 }

-- {ROW} 1.3.6.1.4.1.2356.11.2.2.20.1
lcsSetupWanIpListEntry OBJECT-TYPE
    SYNTAX     LcsSetupWanIpListEntry
    MAX-ACCESS not-accessible
    STATUS     current
    DESCRIPTION
            ""
    INDEX {
            lcsSetupWanIpListEntryPeer
          }
    ::= { lcsSetupWanIpListTable 1 }

LcsSetupWanIpListEntry ::= SEQUENCE {
            lcsSetupWanIpListEntryPeer DisplayString,
            lcsSetupWanIpListEntryIpAddress IpAddress,
            lcsSetupWanIpListEntryIpNetmask IpAddress,
            lcsSetupWanIpListEntryGateway IpAddress,
            lcsSetupWanIpListEntryDnsDefault IpAddress,
            lcsSetupWanIpListEntryDnsBackup IpAddress,
            lcsSetupWanIpListEntryNbnsDefault IpAddress,
            lcsSetupWanIpListEntryNbnsBackup IpAddress,
            lcsSetupWanIpListEntryMasqIpAddr IpAddress
    }

-- {COLUMN} 1.3.6.1.4.1.2356.11.2.2.20.1.1
lcsSetupWanIpListEntryPeer OBJECT-TYPE
    SYNTAX     DisplayString (SIZE(0..16))
    MAX-ACCESS read-write
    STATUS     current
    DESCRIPTION
            ""
    ::= { lcsSetupWanIpListEntry 1 }

-- {COLUMN} 1.3.6.1.4.1.2356.11.2.2.20.1.2
lcsSetupWanIpListEntryIpAddress OBJECT-TYPE
    SYNTAX     IpAddress
    MAX-ACCESS read-write
    STATUS     current
    DESCRIPTION
            ""
    ::= { lcsSetupWanIpListEntry 2 }

-- {COLUMN} 1.3.6.1.4.1.2356.11.2.2.20.1.3
lcsSetupWanIpListEntryIpNetmask OBJECT-TYPE
    SYNTAX     IpAddress
    MAX-ACCESS read-write
    STATUS     current
    DESCRIPTION
            ""
    ::= { lcsSetupWanIpListEntry 3 }

-- {COLUMN} 1.3.6.1.4.1.2356.11.2.2.20.1.4
lcsSetupWanIpListEntryGateway OBJECT-TYPE
    SYNTAX     IpAddress
    MAX-ACCESS read-write
    STATUS     current
    DESCRIPTION
            ""
    ::= { lcsSetupWanIpListEntry 4 }

-- {COLUMN} 1.3.6.1.4.1.2356.11.2.2.20.1.5
lcsSetupWanIpListEntryDnsDefault OBJECT-TYPE
    SYNTAX     IpAddress
    MAX-ACCESS read-write
    STATUS     current
    DESCRIPTION
            ""
    ::= { lcsSetupWanIpListEntry 5 }

-- {COLUMN} 1.3.6.1.4.1.2356.11.2.2.20.1.6
lcsSetupWanIpListEntryDnsBackup OBJECT-TYPE
    SYNTAX     IpAddress
    MAX-ACCESS read-write
    STATUS     current
    DESCRIPTION
            ""
    ::= { lcsSetupWanIpListEntry 6 }

-- {COLUMN} 1.3.6.1.4.1.2356.11.2.2.20.1.7
lcsSetupWanIpListEntryNbnsDefault OBJECT-TYPE
    SYNTAX     IpAddress
    MAX-ACCESS read-write
    STATUS     current
    DESCRIPTION
            ""
    ::= { lcsSetupWanIpListEntry 7 }

-- {COLUMN} 1.3.6.1.4.1.2356.11.2.2.20.1.8
lcsSetupWanIpListEntryNbnsBackup OBJECT-TYPE
    SYNTAX     IpAddress
    MAX-ACCESS read-write
    STATUS     current
    DESCRIPTION
            ""
    ::= { lcsSetupWanIpListEntry 8 }

-- {COLUMN} 1.3.6.1.4.1.2356.11.2.2.20.1.9
lcsSetupWanIpListEntryMasqIpAddr OBJECT-TYPE
    SYNTAX     IpAddress
    MAX-ACCESS read-write
    STATUS     current
    DESCRIPTION
            ""
    ::= { lcsSetupWanIpListEntry 9 }

-- {TABLE} 1.3.6.1.4.1.2356.11.2.2.21
lcsSetupWanPptpPeersTable OBJECT-TYPE
    SYNTAX     SEQUENCE OF LcsSetupWanPptpPeersEntry
    MAX-ACCESS not-accessible
    STATUS     current
    DESCRIPTION
            ""
    ::= { lcsSetupWan 21 }

-- {ROW} 1.3.6.1.4.1.2356.11.2.2.21.1
lcsSetupWanPptpPeersEntry OBJECT-TYPE
    SYNTAX     LcsSetupWanPptpPeersEntry
    MAX-ACCESS not-accessible
    STATUS     current
    DESCRIPTION
            ""
    INDEX {
            lcsSetupWanPptpPeersEntryPeer
          }
    ::= { lcsSetupWanPptpPeersTable 1 }

LcsSetupWanPptpPeersEntry ::= SEQUENCE {
            lcsSetupWanPptpPeersEntryPeer DisplayString,
            lcsSetupWanPptpPeersEntryPort Integer32,
            lcsSetupWanPptpPeersEntryShTime Integer32,
            lcsSetupWanPptpPeersEntryRtgTag Integer32,
            lcsSetupWanPptpPeersEntryIpAddress DisplayString,
            lcsSetupWanPptpPeersEntryEncryption INTEGER,
            lcsSetupWanPptpPeersEntryIpv6 DisplayString
    }

-- {COLUMN} 1.3.6.1.4.1.2356.11.2.2.21.1.1
lcsSetupWanPptpPeersEntryPeer OBJECT-TYPE
    SYNTAX     DisplayString (SIZE(0..16))
    MAX-ACCESS read-write
    STATUS     current
    DESCRIPTION
            ""
    ::= { lcsSetupWanPptpPeersEntry 1 }

-- {COLUMN} 1.3.6.1.4.1.2356.11.2.2.21.1.3
lcsSetupWanPptpPeersEntryPort OBJECT-TYPE
    SYNTAX     Integer32 (0..65535)
    MAX-ACCESS read-write
    STATUS     current
    DESCRIPTION
            ""
    ::= { lcsSetupWanPptpPeersEntry 3 }

-- {COLUMN} 1.3.6.1.4.1.2356.11.2.2.21.1.4
lcsSetupWanPptpPeersEntryShTime OBJECT-TYPE
    SYNTAX     Integer32 (0..65535)
    MAX-ACCESS read-write
    STATUS     current
    DESCRIPTION
            ""
    ::= { lcsSetupWanPptpPeersEntry 4 }

-- {COLUMN} 1.3.6.1.4.1.2356.11.2.2.21.1.5
lcsSetupWanPptpPeersEntryRtgTag OBJECT-TYPE
    SYNTAX     Integer32 (0..65535)
    MAX-ACCESS read-write
    STATUS     current
    DESCRIPTION
            ""
    ::= { lcsSetupWanPptpPeersEntry 5 }

-- {COLUMN} 1.3.6.1.4.1.2356.11.2.2.21.1.6
lcsSetupWanPptpPeersEntryIpAddress OBJECT-TYPE
    SYNTAX     DisplayString (SIZE(0..63))
    MAX-ACCESS read-write
    STATUS     current
    DESCRIPTION
            ""
    ::= { lcsSetupWanPptpPeersEntry 6 }

-- {COLUMN} 1.3.6.1.4.1.2356.11.2.2.21.1.7
lcsSetupWanPptpPeersEntryEncryption OBJECT-TYPE
    SYNTAX     INTEGER {
                  eOff (0),
                  e128Bits (64),
                  e56Bits (192),
                  e40Bits (224)
            }
    MAX-ACCESS read-write
    STATUS     current
    DESCRIPTION
            "-- empty --"
    ::= { lcsSetupWanPptpPeersEntry 7 }

-- {COLUMN} 1.3.6.1.4.1.2356.11.2.2.21.1.9
lcsSetupWanPptpPeersEntryIpv6 OBJECT-TYPE
    SYNTAX     DisplayString (SIZE(0..16))
    MAX-ACCESS read-write
    STATUS     current
    DESCRIPTION
            "-- empty --"
    ::= { lcsSetupWanPptpPeersEntry 9 }

-- {NODE} 1.3.6.1.4.1.2356.11.2.2.22
lcsSetupWanRadius OBJECT IDENTIFIER ::= { lcsSetupWan 22 }

-- {SCALAR} 1.3.6.1.4.1.2356.11.2.2.22.1
lcsSetupWanRadiusOperating OBJECT-TYPE
    SYNTAX     INTEGER {
                  eNo (0),
                  eYes (1),
                  eExclusive (2)
            }
    MAX-ACCESS read-write
    STATUS     current
    DESCRIPTION
            ""
    ::= { lcsSetupWanRadius 1 }

-- {SCALAR} 1.3.6.1.4.1.2356.11.2.2.22.2
lcsSetupWanRadiusServerAddress OBJECT-TYPE
    SYNTAX     IpAddress
    MAX-ACCESS read-only
    STATUS     current
    DESCRIPTION
            ""
    ::= { lcsSetupWanRadius 2 }

-- {SCALAR} 1.3.6.1.4.1.2356.11.2.2.22.3
lcsSetupWanRadiusAuthPort OBJECT-TYPE
    SYNTAX     Integer32 (0..65535)
    MAX-ACCESS read-write
    STATUS     current
    DESCRIPTION
            ""
    ::= { lcsSetupWanRadius 3 }

-- {SCALAR} 1.3.6.1.4.1.2356.11.2.2.22.4
lcsSetupWanRadiusSecret OBJECT-TYPE
    SYNTAX     DisplayString (SIZE(0..64))
    MAX-ACCESS read-write
    STATUS     current
    DESCRIPTION
            ""
    ::= { lcsSetupWanRadius 4 }

-- {SCALAR} 1.3.6.1.4.1.2356.11.2.2.22.5
lcsSetupWanRadiusPppOperation OBJECT-TYPE
    SYNTAX     INTEGER {
                  eNo (0),
                  eYes (1),
                  eExclusive (2)
            }
    MAX-ACCESS read-write
    STATUS     current
    DESCRIPTION
            ""
    ::= { lcsSetupWanRadius 5 }

-- {SCALAR} 1.3.6.1.4.1.2356.11.2.2.22.6
lcsSetupWanRadiusClipOperation OBJECT-TYPE
    SYNTAX     INTEGER {
                  eNo (0),
                  eYes (1),
                  eExclusive (2)
            }
    MAX-ACCESS read-write
    STATUS     current
    DESCRIPTION
            ""
    ::= { lcsSetupWanRadius 6 }

-- {SCALAR} 1.3.6.1.4.1.2356.11.2.2.22.7
lcsSetupWanRadiusClipPassword OBJECT-TYPE
    SYNTAX     DisplayString (SIZE(0..64))
    MAX-ACCESS read-write
    STATUS     current
    DESCRIPTION
            ""
    ::= { lcsSetupWanRadius 7 }

-- {SCALAR} 1.3.6.1.4.1.2356.11.2.2.22.8
lcsSetupWanRadiusLoopbackAddr OBJECT-TYPE
    SYNTAX     DisplayString (SIZE(0..16))
    MAX-ACCESS read-write
    STATUS     current
    DESCRIPTION
            ""
    ::= { lcsSetupWanRadius 8 }

-- {SCALAR} 1.3.6.1.4.1.2356.11.2.2.22.9
lcsSetupWanRadiusProtocol OBJECT-TYPE
    SYNTAX     INTEGER {
                  eRadius (0),
                  eRadsec (1)
            }
    MAX-ACCESS read-write
    STATUS     current
    DESCRIPTION
            ""
    ::= { lcsSetupWanRadius 9 }

-- {SCALAR} 1.3.6.1.4.1.2356.11.2.2.22.10
lcsSetupWanRadiusAuthProtocols OBJECT-TYPE
    SYNTAX     BITS {
                  eNone (0),
                  eMsChapv2 (2),
                  eMsChap (3),
                  eChap (4),
                  ePap (5)
            }
    MAX-ACCESS read-write
    STATUS     current
    DESCRIPTION
            ""
    ::= { lcsSetupWanRadius 10 }

-- {SCALAR} 1.3.6.1.4.1.2356.11.2.2.22.11
lcsSetupWanRadiusServerHostname OBJECT-TYPE
    SYNTAX     DisplayString (SIZE(0..64))
    MAX-ACCESS read-write
    STATUS     current
    DESCRIPTION
            "-- empty --"
    ::= { lcsSetupWanRadius 11 }

-- {SCALAR} 1.3.6.1.4.1.2356.11.2.2.22.12
lcsSetupWanRadiusAttributeValues OBJECT-TYPE
    SYNTAX     DisplayString (SIZE(0..251))
    MAX-ACCESS read-write
    STATUS     current
    DESCRIPTION
            "-- empty --"
    ::= { lcsSetupWanRadius 12 }

-- {SCALAR} 1.3.6.1.4.1.2356.11.2.2.22.20
lcsSetupWanRadiusL2tpOperating OBJECT-TYPE
    SYNTAX     INTEGER {
                  eNo (0),
                  eYes (1),
                  eExclusive (2)
            }
    MAX-ACCESS read-write
    STATUS     current
    DESCRIPTION
            "-- empty --"
    ::= { lcsSetupWanRadius 20 }

-- {SCALAR} 1.3.6.1.4.1.2356.11.2.2.22.21
lcsSetupWanRadiusL2tpServerHostname OBJECT-TYPE
    SYNTAX     DisplayString (SIZE(0..64))
    MAX-ACCESS read-write
    STATUS     current
    DESCRIPTION
            "-- empty --"
    ::= { lcsSetupWanRadius 21 }

-- {SCALAR} 1.3.6.1.4.1.2356.11.2.2.22.22
lcsSetupWanRadiusL2tpAuthPort OBJECT-TYPE
    SYNTAX     Integer32 (0..65535)
    MAX-ACCESS read-write
    STATUS     current
    DESCRIPTION
            "-- empty --"
    ::= { lcsSetupWanRadius 22 }

-- {SCALAR} 1.3.6.1.4.1.2356.11.2.2.22.23
lcsSetupWanRadiusL2tpLoopbackAddress OBJECT-TYPE
    SYNTAX     DisplayString (SIZE(0..16))
    MAX-ACCESS read-write
    STATUS     current
    DESCRIPTION
            "-- empty --"
    ::= { lcsSetupWanRadius 23 }

-- {SCALAR} 1.3.6.1.4.1.2356.11.2.2.22.24
lcsSetupWanRadiusL2tpProtocol OBJECT-TYPE
    SYNTAX     INTEGER {
                  eRadius (0),
                  eRadsec (1)
            }
    MAX-ACCESS read-write
    STATUS     current
    DESCRIPTION
            "-- empty --"
    ::= { lcsSetupWanRadius 24 }

-- {SCALAR} 1.3.6.1.4.1.2356.11.2.2.22.25
lcsSetupWanRadiusL2tpSecret OBJECT-TYPE
    SYNTAX     DisplayString (SIZE(0..64))
    MAX-ACCESS read-write
    STATUS     current
    DESCRIPTION
            "-- empty --"
    ::= { lcsSetupWanRadius 25 }

-- {SCALAR} 1.3.6.1.4.1.2356.11.2.2.22.26
lcsSetupWanRadiusL2tpPassword OBJECT-TYPE
    SYNTAX     DisplayString (SIZE(0..64))
    MAX-ACCESS read-write
    STATUS     current
    DESCRIPTION
            "-- empty --"
    ::= { lcsSetupWanRadius 26 }

-- {SCALAR} 1.3.6.1.4.1.2356.11.2.2.22.27
lcsSetupWanRadiusL2tpAttributeValues OBJECT-TYPE
    SYNTAX     DisplayString (SIZE(0..251))
    MAX-ACCESS read-write
    STATUS     current
    DESCRIPTION
            "-- empty --"
    ::= { lcsSetupWanRadius 27 }

-- {TABLE} 1.3.6.1.4.1.2356.11.2.2.23
lcsSetupWanPollingTableTable OBJECT-TYPE
    SYNTAX     SEQUENCE OF LcsSetupWanPollingTableEntry
    MAX-ACCESS not-accessible
    STATUS     current
    DESCRIPTION
            ""
    ::= { lcsSetupWan 23 }

-- {ROW} 1.3.6.1.4.1.2356.11.2.2.23.1
lcsSetupWanPollingTableEntry OBJECT-TYPE
    SYNTAX     LcsSetupWanPollingTableEntry
    MAX-ACCESS not-accessible
    STATUS     current
    DESCRIPTION
            ""
    INDEX {
            lcsSetupWanPollingTableEntryPeer
          }
    ::= { lcsSetupWanPollingTableTable 1 }

LcsSetupWanPollingTableEntry ::= SEQUENCE {
            lcsSetupWanPollingTableEntryPeer DisplayString,
            lcsSetupWanPollingTableEntryIpAddress1 IpAddress,
            lcsSetupWanPollingTableEntryTime Integer32,
            lcsSetupWanPollingTableEntryTry Integer32,
            lcsSetupWanPollingTableEntryIpAddress2 IpAddress,
            lcsSetupWanPollingTableEntryIpAddress3 IpAddress,
            lcsSetupWanPollingTableEntryIpAddress4 IpAddress,
            lcsSetupWanPollingTableEntryLoopbackAddr DisplayString,
            lcsSetupWanPollingTableEntryType INTEGER
    }

-- {COLUMN} 1.3.6.1.4.1.2356.11.2.2.23.1.1
lcsSetupWanPollingTableEntryPeer OBJECT-TYPE
    SYNTAX     DisplayString (SIZE(0..16))
    MAX-ACCESS read-write
    STATUS     current
    DESCRIPTION
            ""
    ::= { lcsSetupWanPollingTableEntry 1 }

-- {COLUMN} 1.3.6.1.4.1.2356.11.2.2.23.1.2
lcsSetupWanPollingTableEntryIpAddress1 OBJECT-TYPE
    SYNTAX     IpAddress
    MAX-ACCESS read-write
    STATUS     current
    DESCRIPTION
            ""
    ::= { lcsSetupWanPollingTableEntry 2 }

-- {COLUMN} 1.3.6.1.4.1.2356.11.2.2.23.1.3
lcsSetupWanPollingTableEntryTime OBJECT-TYPE
    SYNTAX     Integer32 (0..65535)
    MAX-ACCESS read-write
    STATUS     current
    DESCRIPTION
            ""
    ::= { lcsSetupWanPollingTableEntry 3 }

-- {COLUMN} 1.3.6.1.4.1.2356.11.2.2.23.1.4
lcsSetupWanPollingTableEntryTry OBJECT-TYPE
    SYNTAX     Integer32 (0..255)
    MAX-ACCESS read-write
    STATUS     current
    DESCRIPTION
            ""
    ::= { lcsSetupWanPollingTableEntry 4 }

-- {COLUMN} 1.3.6.1.4.1.2356.11.2.2.23.1.5
lcsSetupWanPollingTableEntryIpAddress2 OBJECT-TYPE
    SYNTAX     IpAddress
    MAX-ACCESS read-write
    STATUS     current
    DESCRIPTION
            ""
    ::= { lcsSetupWanPollingTableEntry 5 }

-- {COLUMN} 1.3.6.1.4.1.2356.11.2.2.23.1.6
lcsSetupWanPollingTableEntryIpAddress3 OBJECT-TYPE
    SYNTAX     IpAddress
    MAX-ACCESS read-write
    STATUS     current
    DESCRIPTION
            ""
    ::= { lcsSetupWanPollingTableEntry 6 }

-- {COLUMN} 1.3.6.1.4.1.2356.11.2.2.23.1.7
lcsSetupWanPollingTableEntryIpAddress4 OBJECT-TYPE
    SYNTAX     IpAddress
    MAX-ACCESS read-write
    STATUS     current
    DESCRIPTION
            ""
    ::= { lcsSetupWanPollingTableEntry 7 }

-- {COLUMN} 1.3.6.1.4.1.2356.11.2.2.23.1.8
lcsSetupWanPollingTableEntryLoopbackAddr OBJECT-TYPE
    SYNTAX     DisplayString (SIZE(0..16))
    MAX-ACCESS read-write
    STATUS     current
    DESCRIPTION
            ""
    ::= { lcsSetupWanPollingTableEntry 8 }

-- {COLUMN} 1.3.6.1.4.1.2356.11.2.2.23.1.9
lcsSetupWanPollingTableEntryType OBJECT-TYPE
    SYNTAX     INTEGER {
                  eForced (0),
                  eAuto (1)
            }
    MAX-ACCESS read-write
    STATUS     current
    DESCRIPTION
            ""
    ::= { lcsSetupWanPollingTableEntry 9 }

-- {TABLE} 1.3.6.1.4.1.2356.11.2.2.24
lcsSetupWanBackupPeersTable OBJECT-TYPE
    SYNTAX     SEQUENCE OF LcsSetupWanBackupPeersEntry
    MAX-ACCESS not-accessible
    STATUS     current
    DESCRIPTION
            ""
    ::= { lcsSetupWan 24 }

-- {ROW} 1.3.6.1.4.1.2356.11.2.2.24.1
lcsSetupWanBackupPeersEntry OBJECT-TYPE
    SYNTAX     LcsSetupWanBackupPeersEntry
    MAX-ACCESS not-accessible
    STATUS     current
    DESCRIPTION
            ""
    INDEX {
            lcsSetupWanBackupPeersEntryPeer
          }
    ::= { lcsSetupWanBackupPeersTable 1 }

LcsSetupWanBackupPeersEntry ::= SEQUENCE {
            lcsSetupWanBackupPeersEntryPeer DisplayString,
            lcsSetupWanBackupPeersEntryAlternativePeers DisplayString,
            lcsSetupWanBackupPeersEntryHead INTEGER,
            lcsSetupWanBackupPeersEntryFallbackMinutes Integer32
    }

-- {COLUMN} 1.3.6.1.4.1.2356.11.2.2.24.1.1
lcsSetupWanBackupPeersEntryPeer OBJECT-TYPE
    SYNTAX     DisplayString (SIZE(0..18))
    MAX-ACCESS read-write
    STATUS     current
    DESCRIPTION
            ""
    ::= { lcsSetupWanBackupPeersEntry 1 }

-- {COLUMN} 1.3.6.1.4.1.2356.11.2.2.24.1.2
lcsSetupWanBackupPeersEntryAlternativePeers OBJECT-TYPE
    SYNTAX     DisplayString (SIZE(0..53))
    MAX-ACCESS read-write
    STATUS     current
    DESCRIPTION
            ""
    ::= { lcsSetupWanBackupPeersEntry 2 }

-- {COLUMN} 1.3.6.1.4.1.2356.11.2.2.24.1.3
lcsSetupWanBackupPeersEntryHead OBJECT-TYPE
    SYNTAX     INTEGER {
                  eLast (0),
                  eFirst (1)
            }
    MAX-ACCESS read-write
    STATUS     current
    DESCRIPTION
            ""
    ::= { lcsSetupWanBackupPeersEntry 3 }

-- {COLUMN} 1.3.6.1.4.1.2356.11.2.2.24.1.4
lcsSetupWanBackupPeersEntryFallbackMinutes OBJECT-TYPE
    SYNTAX     Integer32 (0..65535)
    MAX-ACCESS read-write
    STATUS     current
    DESCRIPTION
            "-- empty --"
    ::= { lcsSetupWanBackupPeersEntry 4 }

-- {TABLE} 1.3.6.1.4.1.2356.11.2.2.25
lcsSetupWanActionTableTable OBJECT-TYPE
    SYNTAX     SEQUENCE OF LcsSetupWanActionTableEntry
    MAX-ACCESS not-accessible
    STATUS     current
    DESCRIPTION
            ""
    ::= { lcsSetupWan 25 }

-- {ROW} 1.3.6.1.4.1.2356.11.2.2.25.1
lcsSetupWanActionTableEntry OBJECT-TYPE
    SYNTAX     LcsSetupWanActionTableEntry
    MAX-ACCESS not-accessible
    STATUS     current
    DESCRIPTION
            ""
    INDEX {
            lcsSetupWanActionTableEntryIndex
          }
    ::= { lcsSetupWanActionTableTable 1 }

LcsSetupWanActionTableEntry ::= SEQUENCE {
            lcsSetupWanActionTableEntryIndex Integer32,
            lcsSetupWanActionTableEntryHostName DisplayString,
            lcsSetupWanActionTableEntryPeer DisplayString,
            lcsSetupWanActionTableEntryLockTime Integer32,
            lcsSetupWanActionTableEntryCondition INTEGER,
            lcsSetupWanActionTableEntryAction DisplayString,
            lcsSetupWanActionTableEntryCheckFor DisplayString,
            lcsSetupWanActionTableEntryActive INTEGER,
            lcsSetupWanActionTableEntryOwner DisplayString,
            lcsSetupWanActionTableEntryRoutingTag Integer32
    }

-- {COLUMN} 1.3.6.1.4.1.2356.11.2.2.25.1.1
lcsSetupWanActionTableEntryIndex OBJECT-TYPE
    SYNTAX     Integer32 (0..65535)
    MAX-ACCESS read-write
    STATUS     current
    DESCRIPTION
            ""
    ::= { lcsSetupWanActionTableEntry 1 }

-- {COLUMN} 1.3.6.1.4.1.2356.11.2.2.25.1.2
lcsSetupWanActionTableEntryHostName OBJECT-TYPE
    SYNTAX     DisplayString (SIZE(0..64))
    MAX-ACCESS read-write
    STATUS     current
    DESCRIPTION
            ""
    ::= { lcsSetupWanActionTableEntry 2 }

-- {COLUMN} 1.3.6.1.4.1.2356.11.2.2.25.1.3
lcsSetupWanActionTableEntryPeer OBJECT-TYPE
    SYNTAX     DisplayString (SIZE(0..16))
    MAX-ACCESS read-write
    STATUS     current
    DESCRIPTION
            ""
    ::= { lcsSetupWanActionTableEntry 3 }

-- {COLUMN} 1.3.6.1.4.1.2356.11.2.2.25.1.4
lcsSetupWanActionTableEntryLockTime OBJECT-TYPE
    SYNTAX     Integer32 (0..2147483647)
    MAX-ACCESS read-write
    STATUS     current
    DESCRIPTION
            ""
    ::= { lcsSetupWanActionTableEntry 4 }

-- {COLUMN} 1.3.6.1.4.1.2356.11.2.2.25.1.5
lcsSetupWanActionTableEntryCondition OBJECT-TYPE
    SYNTAX     INTEGER {
                  eEstablish (0),
                  eDisconnect (1),
                  eEnd (2),
                  eFailure (3),
                  eEstablishFailure (4),
                  eBudgetExhausted (5),
                  eBudgetReleased (6)
            }
    MAX-ACCESS read-write
    STATUS     current
    DESCRIPTION
            ""
    ::= { lcsSetupWanActionTableEntry 5 }

-- {COLUMN} 1.3.6.1.4.1.2356.11.2.2.25.1.6
lcsSetupWanActionTableEntryAction OBJECT-TYPE
    SYNTAX     DisplayString (SIZE(0..250))
    MAX-ACCESS read-write
    STATUS     current
    DESCRIPTION
            ""
    ::= { lcsSetupWanActionTableEntry 6 }

-- {COLUMN} 1.3.6.1.4.1.2356.11.2.2.25.1.7
lcsSetupWanActionTableEntryCheckFor OBJECT-TYPE
    SYNTAX     DisplayString (SIZE(0..50))
    MAX-ACCESS read-write
    STATUS     current
    DESCRIPTION
            ""
    ::= { lcsSetupWanActionTableEntry 7 }

-- {COLUMN} 1.3.6.1.4.1.2356.11.2.2.25.1.8
lcsSetupWanActionTableEntryActive OBJECT-TYPE
    SYNTAX     INTEGER {
                  eYes (0),
                  eNo (1)
            }
    MAX-ACCESS read-write
    STATUS     current
    DESCRIPTION
            ""
    ::= { lcsSetupWanActionTableEntry 8 }

-- {COLUMN} 1.3.6.1.4.1.2356.11.2.2.25.1.9
lcsSetupWanActionTableEntryOwner OBJECT-TYPE
    SYNTAX     DisplayString (SIZE(0..16))
    MAX-ACCESS read-write
    STATUS     current
    DESCRIPTION
            ""
    ::= { lcsSetupWanActionTableEntry 9 }

-- {COLUMN} 1.3.6.1.4.1.2356.11.2.2.25.1.10
lcsSetupWanActionTableEntryRoutingTag OBJECT-TYPE
    SYNTAX     Integer32 (0..65535)
    MAX-ACCESS read-write
    STATUS     current
    DESCRIPTION
            "-- empty --"
    ::= { lcsSetupWanActionTableEntry 10 }

-- {TABLE} 1.3.6.1.4.1.2356.11.2.2.26
lcsSetupWanMtuListTable OBJECT-TYPE
    SYNTAX     SEQUENCE OF LcsSetupWanMtuListEntry
    MAX-ACCESS not-accessible
    STATUS     current
    DESCRIPTION
            ""
    ::= { lcsSetupWan 26 }

-- {ROW} 1.3.6.1.4.1.2356.11.2.2.26.1
lcsSetupWanMtuListEntry OBJECT-TYPE
    SYNTAX     LcsSetupWanMtuListEntry
    MAX-ACCESS not-accessible
    STATUS     current
    DESCRIPTION
            ""
    INDEX {
            lcsSetupWanMtuListEntryPeer
          }
    ::= { lcsSetupWanMtuListTable 1 }

LcsSetupWanMtuListEntry ::= SEQUENCE {
            lcsSetupWanMtuListEntryPeer DisplayString,
            lcsSetupWanMtuListEntryMtu Integer32
    }

-- {COLUMN} 1.3.6.1.4.1.2356.11.2.2.26.1.1
lcsSetupWanMtuListEntryPeer OBJECT-TYPE
    SYNTAX     DisplayString (SIZE(0..16))
    MAX-ACCESS read-write
    STATUS     current
    DESCRIPTION
            ""
    ::= { lcsSetupWanMtuListEntry 1 }

-- {COLUMN} 1.3.6.1.4.1.2356.11.2.2.26.1.2
lcsSetupWanMtuListEntryMtu OBJECT-TYPE
    SYNTAX     Integer32 (0..65535)
    MAX-ACCESS read-write
    STATUS     current
    DESCRIPTION
            ""
    ::= { lcsSetupWanMtuListEntry 2 }

-- {TABLE} 1.3.6.1.4.1.2356.11.2.2.30
lcsSetupWanAdditionalPptpGatewaysTable OBJECT-TYPE
    SYNTAX     SEQUENCE OF LcsSetupWanAdditionalPptpGatewaysEntry
    MAX-ACCESS not-accessible
    STATUS     current
    DESCRIPTION
            ""
    ::= { lcsSetupWan 30 }

-- {ROW} 1.3.6.1.4.1.2356.11.2.2.30.1
lcsSetupWanAdditionalPptpGatewaysEntry OBJECT-TYPE
    SYNTAX     LcsSetupWanAdditionalPptpGatewaysEntry
    MAX-ACCESS not-accessible
    STATUS     current
    DESCRIPTION
            ""
    INDEX {
            lcsSetupWanAdditionalPptpGatewaysEntryPeer
          }
    ::= { lcsSetupWanAdditionalPptpGatewaysTable 1 }

LcsSetupWanAdditionalPptpGatewaysEntry ::= SEQUENCE {
            lcsSetupWanAdditionalPptpGatewaysEntryPeer DisplayString,
            lcsSetupWanAdditionalPptpGatewaysEntryBeginWith INTEGER,
            lcsSetupWanAdditionalPptpGatewaysEntryGateway1 DisplayString,
            lcsSetupWanAdditionalPptpGatewaysEntryRtgTag1 Integer32,
            lcsSetupWanAdditionalPptpGatewaysEntryGateway2 DisplayString,
            lcsSetupWanAdditionalPptpGatewaysEntryRtgTag2 Integer32,
            lcsSetupWanAdditionalPptpGatewaysEntryGateway3 DisplayString,
            lcsSetupWanAdditionalPptpGatewaysEntryRtgTag3 Integer32,
            lcsSetupWanAdditionalPptpGatewaysEntryGateway4 DisplayString,
            lcsSetupWanAdditionalPptpGatewaysEntryRtgTag4 Integer32,
            lcsSetupWanAdditionalPptpGatewaysEntryGateway5 DisplayString,
            lcsSetupWanAdditionalPptpGatewaysEntryRtgTag5 Integer32,
            lcsSetupWanAdditionalPptpGatewaysEntryGateway6 DisplayString,
            lcsSetupWanAdditionalPptpGatewaysEntryRtgTag6 Integer32,
            lcsSetupWanAdditionalPptpGatewaysEntryGateway7 DisplayString,
            lcsSetupWanAdditionalPptpGatewaysEntryRtgTag7 Integer32,
            lcsSetupWanAdditionalPptpGatewaysEntryGateway8 DisplayString,
            lcsSetupWanAdditionalPptpGatewaysEntryRtgTag8 Integer32,
            lcsSetupWanAdditionalPptpGatewaysEntryGateway9 DisplayString,
            lcsSetupWanAdditionalPptpGatewaysEntryRtgTag9 Integer32,
            lcsSetupWanAdditionalPptpGatewaysEntryGateway10 DisplayString,
            lcsSetupWanAdditionalPptpGatewaysEntryRtgTag10 Integer32,
            lcsSetupWanAdditionalPptpGatewaysEntryGateway11 DisplayString,
            lcsSetupWanAdditionalPptpGatewaysEntryRtgTag11 Integer32,
            lcsSetupWanAdditionalPptpGatewaysEntryGateway12 DisplayString,
            lcsSetupWanAdditionalPptpGatewaysEntryRtgTag12 Integer32,
            lcsSetupWanAdditionalPptpGatewaysEntryGateway13 DisplayString,
            lcsSetupWanAdditionalPptpGatewaysEntryRtgTag13 Integer32,
            lcsSetupWanAdditionalPptpGatewaysEntryGateway14 DisplayString,
            lcsSetupWanAdditionalPptpGatewaysEntryRtgTag14 Integer32,
            lcsSetupWanAdditionalPptpGatewaysEntryGateway15 DisplayString,
            lcsSetupWanAdditionalPptpGatewaysEntryRtgTag15 Integer32,
            lcsSetupWanAdditionalPptpGatewaysEntryGateway16 DisplayString,
            lcsSetupWanAdditionalPptpGatewaysEntryRtgTag16 Integer32,
            lcsSetupWanAdditionalPptpGatewaysEntryGateway17 DisplayString,
            lcsSetupWanAdditionalPptpGatewaysEntryRtgTag17 Integer32,
            lcsSetupWanAdditionalPptpGatewaysEntryGateway18 DisplayString,
            lcsSetupWanAdditionalPptpGatewaysEntryRtgTag18 Integer32,
            lcsSetupWanAdditionalPptpGatewaysEntryGateway19 DisplayString,
            lcsSetupWanAdditionalPptpGatewaysEntryRtgTag19 Integer32,
            lcsSetupWanAdditionalPptpGatewaysEntryGateway20 DisplayString,
            lcsSetupWanAdditionalPptpGatewaysEntryRtgTag20 Integer32,
            lcsSetupWanAdditionalPptpGatewaysEntryGateway21 DisplayString,
            lcsSetupWanAdditionalPptpGatewaysEntryRtgTag21 Integer32,
            lcsSetupWanAdditionalPptpGatewaysEntryGateway22 DisplayString,
            lcsSetupWanAdditionalPptpGatewaysEntryRtgTag22 Integer32,
            lcsSetupWanAdditionalPptpGatewaysEntryGateway23 DisplayString,
            lcsSetupWanAdditionalPptpGatewaysEntryRtgTag23 Integer32,
            lcsSetupWanAdditionalPptpGatewaysEntryGateway24 DisplayString,
            lcsSetupWanAdditionalPptpGatewaysEntryRtgTag24 Integer32,
            lcsSetupWanAdditionalPptpGatewaysEntryGateway25 DisplayString,
            lcsSetupWanAdditionalPptpGatewaysEntryRtgTag25 Integer32,
            lcsSetupWanAdditionalPptpGatewaysEntryGateway26 DisplayString,
            lcsSetupWanAdditionalPptpGatewaysEntryRtgTag26 Integer32,
            lcsSetupWanAdditionalPptpGatewaysEntryGateway27 DisplayString,
            lcsSetupWanAdditionalPptpGatewaysEntryRtgTag27 Integer32,
            lcsSetupWanAdditionalPptpGatewaysEntryGateway28 DisplayString,
            lcsSetupWanAdditionalPptpGatewaysEntryRtgTag28 Integer32,
            lcsSetupWanAdditionalPptpGatewaysEntryGateway29 DisplayString,
            lcsSetupWanAdditionalPptpGatewaysEntryRtgTag29 Integer32,
            lcsSetupWanAdditionalPptpGatewaysEntryGateway30 DisplayString,
            lcsSetupWanAdditionalPptpGatewaysEntryRtgTag30 Integer32,
            lcsSetupWanAdditionalPptpGatewaysEntryGateway31 DisplayString,
            lcsSetupWanAdditionalPptpGatewaysEntryRtgTag31 Integer32,
            lcsSetupWanAdditionalPptpGatewaysEntryGateway32 DisplayString,
            lcsSetupWanAdditionalPptpGatewaysEntryRtgTag32 Integer32,
            lcsSetupWanAdditionalPptpGatewaysEntryDefaultPrio Integer32
    }

-- {COLUMN} 1.3.6.1.4.1.2356.11.2.2.30.1.1
lcsSetupWanAdditionalPptpGatewaysEntryPeer OBJECT-TYPE
    SYNTAX     DisplayString (SIZE(0..16))
    MAX-ACCESS read-write
    STATUS     current
    DESCRIPTION
            ""
    ::= { lcsSetupWanAdditionalPptpGatewaysEntry 1 }

-- {COLUMN} 1.3.6.1.4.1.2356.11.2.2.30.1.2
lcsSetupWanAdditionalPptpGatewaysEntryBeginWith OBJECT-TYPE
    SYNTAX     INTEGER {
                  eLastUsed (0),
                  eFirst (1),
                  eRandom (2)
            }
    MAX-ACCESS read-write
    STATUS     current
    DESCRIPTION
            ""
    ::= { lcsSetupWanAdditionalPptpGatewaysEntry 2 }

-- {COLUMN} 1.3.6.1.4.1.2356.11.2.2.30.1.3
lcsSetupWanAdditionalPptpGatewaysEntryGateway1 OBJECT-TYPE
    SYNTAX     DisplayString (SIZE(0..64))
    MAX-ACCESS read-write
    STATUS     current
    DESCRIPTION
            ""
    ::= { lcsSetupWanAdditionalPptpGatewaysEntry 3 }

-- {COLUMN} 1.3.6.1.4.1.2356.11.2.2.30.1.4
lcsSetupWanAdditionalPptpGatewaysEntryRtgTag1 OBJECT-TYPE
    SYNTAX     Integer32 (0..65535)
    MAX-ACCESS read-write
    STATUS     current
    DESCRIPTION
            ""
    ::= { lcsSetupWanAdditionalPptpGatewaysEntry 4 }

-- {COLUMN} 1.3.6.1.4.1.2356.11.2.2.30.1.5
lcsSetupWanAdditionalPptpGatewaysEntryGateway2 OBJECT-TYPE
    SYNTAX     DisplayString (SIZE(0..64))
    MAX-ACCESS read-write
    STATUS     current
    DESCRIPTION
            ""
    ::= { lcsSetupWanAdditionalPptpGatewaysEntry 5 }

-- {COLUMN} 1.3.6.1.4.1.2356.11.2.2.30.1.6
lcsSetupWanAdditionalPptpGatewaysEntryRtgTag2 OBJECT-TYPE
    SYNTAX     Integer32 (0..65535)
    MAX-ACCESS read-write
    STATUS     current
    DESCRIPTION
            ""
    ::= { lcsSetupWanAdditionalPptpGatewaysEntry 6 }

-- {COLUMN} 1.3.6.1.4.1.2356.11.2.2.30.1.7
lcsSetupWanAdditionalPptpGatewaysEntryGateway3 OBJECT-TYPE
    SYNTAX     DisplayString (SIZE(0..64))
    MAX-ACCESS read-write
    STATUS     current
    DESCRIPTION
            ""
    ::= { lcsSetupWanAdditionalPptpGatewaysEntry 7 }

-- {COLUMN} 1.3.6.1.4.1.2356.11.2.2.30.1.8
lcsSetupWanAdditionalPptpGatewaysEntryRtgTag3 OBJECT-TYPE
    SYNTAX     Integer32 (0..65535)
    MAX-ACCESS read-write
    STATUS     current
    DESCRIPTION
            ""
    ::= { lcsSetupWanAdditionalPptpGatewaysEntry 8 }

-- {COLUMN} 1.3.6.1.4.1.2356.11.2.2.30.1.9
lcsSetupWanAdditionalPptpGatewaysEntryGateway4 OBJECT-TYPE
    SYNTAX     DisplayString (SIZE(0..64))
    MAX-ACCESS read-write
    STATUS     current
    DESCRIPTION
            ""
    ::= { lcsSetupWanAdditionalPptpGatewaysEntry 9 }

-- {COLUMN} 1.3.6.1.4.1.2356.11.2.2.30.1.10
lcsSetupWanAdditionalPptpGatewaysEntryRtgTag4 OBJECT-TYPE
    SYNTAX     Integer32 (0..65535)
    MAX-ACCESS read-write
    STATUS     current
    DESCRIPTION
            ""
    ::= { lcsSetupWanAdditionalPptpGatewaysEntry 10 }

-- {COLUMN} 1.3.6.1.4.1.2356.11.2.2.30.1.11
lcsSetupWanAdditionalPptpGatewaysEntryGateway5 OBJECT-TYPE
    SYNTAX     DisplayString (SIZE(0..64))
    MAX-ACCESS read-write
    STATUS     current
    DESCRIPTION
            ""
    ::= { lcsSetupWanAdditionalPptpGatewaysEntry 11 }

-- {COLUMN} 1.3.6.1.4.1.2356.11.2.2.30.1.12
lcsSetupWanAdditionalPptpGatewaysEntryRtgTag5 OBJECT-TYPE
    SYNTAX     Integer32 (0..65535)
    MAX-ACCESS read-write
    STATUS     current
    DESCRIPTION
            ""
    ::= { lcsSetupWanAdditionalPptpGatewaysEntry 12 }

-- {COLUMN} 1.3.6.1.4.1.2356.11.2.2.30.1.13
lcsSetupWanAdditionalPptpGatewaysEntryGateway6 OBJECT-TYPE
    SYNTAX     DisplayString (SIZE(0..64))
    MAX-ACCESS read-write
    STATUS     current
    DESCRIPTION
            ""
    ::= { lcsSetupWanAdditionalPptpGatewaysEntry 13 }

-- {COLUMN} 1.3.6.1.4.1.2356.11.2.2.30.1.14
lcsSetupWanAdditionalPptpGatewaysEntryRtgTag6 OBJECT-TYPE
    SYNTAX     Integer32 (0..65535)
    MAX-ACCESS read-write
    STATUS     current
    DESCRIPTION
            ""
    ::= { lcsSetupWanAdditionalPptpGatewaysEntry 14 }

-- {COLUMN} 1.3.6.1.4.1.2356.11.2.2.30.1.15
lcsSetupWanAdditionalPptpGatewaysEntryGateway7 OBJECT-TYPE
    SYNTAX     DisplayString (SIZE(0..64))
    MAX-ACCESS read-write
    STATUS     current
    DESCRIPTION
            ""
    ::= { lcsSetupWanAdditionalPptpGatewaysEntry 15 }

-- {COLUMN} 1.3.6.1.4.1.2356.11.2.2.30.1.16
lcsSetupWanAdditionalPptpGatewaysEntryRtgTag7 OBJECT-TYPE
    SYNTAX     Integer32 (0..65535)
    MAX-ACCESS read-write
    STATUS     current
    DESCRIPTION
            ""
    ::= { lcsSetupWanAdditionalPptpGatewaysEntry 16 }

-- {COLUMN} 1.3.6.1.4.1.2356.11.2.2.30.1.17
lcsSetupWanAdditionalPptpGatewaysEntryGateway8 OBJECT-TYPE
    SYNTAX     DisplayString (SIZE(0..64))
    MAX-ACCESS read-write
    STATUS     current
    DESCRIPTION
            ""
    ::= { lcsSetupWanAdditionalPptpGatewaysEntry 17 }

-- {COLUMN} 1.3.6.1.4.1.2356.11.2.2.30.1.18
lcsSetupWanAdditionalPptpGatewaysEntryRtgTag8 OBJECT-TYPE
    SYNTAX     Integer32 (0..65535)
    MAX-ACCESS read-write
    STATUS     current
    DESCRIPTION
            ""
    ::= { lcsSetupWanAdditionalPptpGatewaysEntry 18 }

-- {COLUMN} 1.3.6.1.4.1.2356.11.2.2.30.1.19
lcsSetupWanAdditionalPptpGatewaysEntryGateway9 OBJECT-TYPE
    SYNTAX     DisplayString (SIZE(0..64))
    MAX-ACCESS read-write
    STATUS     current
    DESCRIPTION
            ""
    ::= { lcsSetupWanAdditionalPptpGatewaysEntry 19 }

-- {COLUMN} 1.3.6.1.4.1.2356.11.2.2.30.1.20
lcsSetupWanAdditionalPptpGatewaysEntryRtgTag9 OBJECT-TYPE
    SYNTAX     Integer32 (0..65535)
    MAX-ACCESS read-write
    STATUS     current
    DESCRIPTION
            ""
    ::= { lcsSetupWanAdditionalPptpGatewaysEntry 20 }

-- {COLUMN} 1.3.6.1.4.1.2356.11.2.2.30.1.21
lcsSetupWanAdditionalPptpGatewaysEntryGateway10 OBJECT-TYPE
    SYNTAX     DisplayString (SIZE(0..64))
    MAX-ACCESS read-write
    STATUS     current
    DESCRIPTION
            ""
    ::= { lcsSetupWanAdditionalPptpGatewaysEntry 21 }

-- {COLUMN} 1.3.6.1.4.1.2356.11.2.2.30.1.22
lcsSetupWanAdditionalPptpGatewaysEntryRtgTag10 OBJECT-TYPE
    SYNTAX     Integer32 (0..65535)
    MAX-ACCESS read-write
    STATUS     current
    DESCRIPTION
            ""
    ::= { lcsSetupWanAdditionalPptpGatewaysEntry 22 }

-- {COLUMN} 1.3.6.1.4.1.2356.11.2.2.30.1.23
lcsSetupWanAdditionalPptpGatewaysEntryGateway11 OBJECT-TYPE
    SYNTAX     DisplayString (SIZE(0..64))
    MAX-ACCESS read-write
    STATUS     current
    DESCRIPTION
            ""
    ::= { lcsSetupWanAdditionalPptpGatewaysEntry 23 }

-- {COLUMN} 1.3.6.1.4.1.2356.11.2.2.30.1.24
lcsSetupWanAdditionalPptpGatewaysEntryRtgTag11 OBJECT-TYPE
    SYNTAX     Integer32 (0..65535)
    MAX-ACCESS read-write
    STATUS     current
    DESCRIPTION
            ""
    ::= { lcsSetupWanAdditionalPptpGatewaysEntry 24 }

-- {COLUMN} 1.3.6.1.4.1.2356.11.2.2.30.1.25
lcsSetupWanAdditionalPptpGatewaysEntryGateway12 OBJECT-TYPE
    SYNTAX     DisplayString (SIZE(0..64))
    MAX-ACCESS read-write
    STATUS     current
    DESCRIPTION
            ""
    ::= { lcsSetupWanAdditionalPptpGatewaysEntry 25 }

-- {COLUMN} 1.3.6.1.4.1.2356.11.2.2.30.1.26
lcsSetupWanAdditionalPptpGatewaysEntryRtgTag12 OBJECT-TYPE
    SYNTAX     Integer32 (0..65535)
    MAX-ACCESS read-write
    STATUS     current
    DESCRIPTION
            ""
    ::= { lcsSetupWanAdditionalPptpGatewaysEntry 26 }

-- {COLUMN} 1.3.6.1.4.1.2356.11.2.2.30.1.27
lcsSetupWanAdditionalPptpGatewaysEntryGateway13 OBJECT-TYPE
    SYNTAX     DisplayString (SIZE(0..64))
    MAX-ACCESS read-write
    STATUS     current
    DESCRIPTION
            ""
    ::= { lcsSetupWanAdditionalPptpGatewaysEntry 27 }

-- {COLUMN} 1.3.6.1.4.1.2356.11.2.2.30.1.28
lcsSetupWanAdditionalPptpGatewaysEntryRtgTag13 OBJECT-TYPE
    SYNTAX     Integer32 (0..65535)
    MAX-ACCESS read-write
    STATUS     current
    DESCRIPTION
            ""
    ::= { lcsSetupWanAdditionalPptpGatewaysEntry 28 }

-- {COLUMN} 1.3.6.1.4.1.2356.11.2.2.30.1.29
lcsSetupWanAdditionalPptpGatewaysEntryGateway14 OBJECT-TYPE
    SYNTAX     DisplayString (SIZE(0..64))
    MAX-ACCESS read-write
    STATUS     current
    DESCRIPTION
            ""
    ::= { lcsSetupWanAdditionalPptpGatewaysEntry 29 }

-- {COLUMN} 1.3.6.1.4.1.2356.11.2.2.30.1.30
lcsSetupWanAdditionalPptpGatewaysEntryRtgTag14 OBJECT-TYPE
    SYNTAX     Integer32 (0..65535)
    MAX-ACCESS read-write
    STATUS     current
    DESCRIPTION
            ""
    ::= { lcsSetupWanAdditionalPptpGatewaysEntry 30 }

-- {COLUMN} 1.3.6.1.4.1.2356.11.2.2.30.1.31
lcsSetupWanAdditionalPptpGatewaysEntryGateway15 OBJECT-TYPE
    SYNTAX     DisplayString (SIZE(0..64))
    MAX-ACCESS read-write
    STATUS     current
    DESCRIPTION
            ""
    ::= { lcsSetupWanAdditionalPptpGatewaysEntry 31 }

-- {COLUMN} 1.3.6.1.4.1.2356.11.2.2.30.1.32
lcsSetupWanAdditionalPptpGatewaysEntryRtgTag15 OBJECT-TYPE
    SYNTAX     Integer32 (0..65535)
    MAX-ACCESS read-write
    STATUS     current
    DESCRIPTION
            ""
    ::= { lcsSetupWanAdditionalPptpGatewaysEntry 32 }

-- {COLUMN} 1.3.6.1.4.1.2356.11.2.2.30.1.33
lcsSetupWanAdditionalPptpGatewaysEntryGateway16 OBJECT-TYPE
    SYNTAX     DisplayString (SIZE(0..64))
    MAX-ACCESS read-write
    STATUS     current
    DESCRIPTION
            ""
    ::= { lcsSetupWanAdditionalPptpGatewaysEntry 33 }

-- {COLUMN} 1.3.6.1.4.1.2356.11.2.2.30.1.34
lcsSetupWanAdditionalPptpGatewaysEntryRtgTag16 OBJECT-TYPE
    SYNTAX     Integer32 (0..65535)
    MAX-ACCESS read-write
    STATUS     current
    DESCRIPTION
            ""
    ::= { lcsSetupWanAdditionalPptpGatewaysEntry 34 }

-- {COLUMN} 1.3.6.1.4.1.2356.11.2.2.30.1.35
lcsSetupWanAdditionalPptpGatewaysEntryGateway17 OBJECT-TYPE
    SYNTAX     DisplayString (SIZE(0..64))
    MAX-ACCESS read-write
    STATUS     current
    DESCRIPTION
            ""
    ::= { lcsSetupWanAdditionalPptpGatewaysEntry 35 }

-- {COLUMN} 1.3.6.1.4.1.2356.11.2.2.30.1.36
lcsSetupWanAdditionalPptpGatewaysEntryRtgTag17 OBJECT-TYPE
    SYNTAX     Integer32 (0..65535)
    MAX-ACCESS read-write
    STATUS     current
    DESCRIPTION
            ""
    ::= { lcsSetupWanAdditionalPptpGatewaysEntry 36 }

-- {COLUMN} 1.3.6.1.4.1.2356.11.2.2.30.1.37
lcsSetupWanAdditionalPptpGatewaysEntryGateway18 OBJECT-TYPE
    SYNTAX     DisplayString (SIZE(0..64))
    MAX-ACCESS read-write
    STATUS     current
    DESCRIPTION
            ""
    ::= { lcsSetupWanAdditionalPptpGatewaysEntry 37 }

-- {COLUMN} 1.3.6.1.4.1.2356.11.2.2.30.1.38
lcsSetupWanAdditionalPptpGatewaysEntryRtgTag18 OBJECT-TYPE
    SYNTAX     Integer32 (0..65535)
    MAX-ACCESS read-write
    STATUS     current
    DESCRIPTION
            ""
    ::= { lcsSetupWanAdditionalPptpGatewaysEntry 38 }

-- {COLUMN} 1.3.6.1.4.1.2356.11.2.2.30.1.39
lcsSetupWanAdditionalPptpGatewaysEntryGateway19 OBJECT-TYPE
    SYNTAX     DisplayString (SIZE(0..64))
    MAX-ACCESS read-write
    STATUS     current
    DESCRIPTION
            ""
    ::= { lcsSetupWanAdditionalPptpGatewaysEntry 39 }

-- {COLUMN} 1.3.6.1.4.1.2356.11.2.2.30.1.40
lcsSetupWanAdditionalPptpGatewaysEntryRtgTag19 OBJECT-TYPE
    SYNTAX     Integer32 (0..65535)
    MAX-ACCESS read-write
    STATUS     current
    DESCRIPTION
            ""
    ::= { lcsSetupWanAdditionalPptpGatewaysEntry 40 }

-- {COLUMN} 1.3.6.1.4.1.2356.11.2.2.30.1.41
lcsSetupWanAdditionalPptpGatewaysEntryGateway20 OBJECT-TYPE
    SYNTAX     DisplayString (SIZE(0..64))
    MAX-ACCESS read-write
    STATUS     current
    DESCRIPTION
            ""
    ::= { lcsSetupWanAdditionalPptpGatewaysEntry 41 }

-- {COLUMN} 1.3.6.1.4.1.2356.11.2.2.30.1.42
lcsSetupWanAdditionalPptpGatewaysEntryRtgTag20 OBJECT-TYPE
    SYNTAX     Integer32 (0..65535)
    MAX-ACCESS read-write
    STATUS     current
    DESCRIPTION
            ""
    ::= { lcsSetupWanAdditionalPptpGatewaysEntry 42 }

-- {COLUMN} 1.3.6.1.4.1.2356.11.2.2.30.1.43
lcsSetupWanAdditionalPptpGatewaysEntryGateway21 OBJECT-TYPE
    SYNTAX     DisplayString (SIZE(0..64))
    MAX-ACCESS read-write
    STATUS     current
    DESCRIPTION
            ""
    ::= { lcsSetupWanAdditionalPptpGatewaysEntry 43 }

-- {COLUMN} 1.3.6.1.4.1.2356.11.2.2.30.1.44
lcsSetupWanAdditionalPptpGatewaysEntryRtgTag21 OBJECT-TYPE
    SYNTAX     Integer32 (0..65535)
    MAX-ACCESS read-write
    STATUS     current
    DESCRIPTION
            ""
    ::= { lcsSetupWanAdditionalPptpGatewaysEntry 44 }

-- {COLUMN} 1.3.6.1.4.1.2356.11.2.2.30.1.45
lcsSetupWanAdditionalPptpGatewaysEntryGateway22 OBJECT-TYPE
    SYNTAX     DisplayString (SIZE(0..64))
    MAX-ACCESS read-write
    STATUS     current
    DESCRIPTION
            ""
    ::= { lcsSetupWanAdditionalPptpGatewaysEntry 45 }

-- {COLUMN} 1.3.6.1.4.1.2356.11.2.2.30.1.46
lcsSetupWanAdditionalPptpGatewaysEntryRtgTag22 OBJECT-TYPE
    SYNTAX     Integer32 (0..65535)
    MAX-ACCESS read-write
    STATUS     current
    DESCRIPTION
            ""
    ::= { lcsSetupWanAdditionalPptpGatewaysEntry 46 }

-- {COLUMN} 1.3.6.1.4.1.2356.11.2.2.30.1.47
lcsSetupWanAdditionalPptpGatewaysEntryGateway23 OBJECT-TYPE
    SYNTAX     DisplayString (SIZE(0..64))
    MAX-ACCESS read-write
    STATUS     current
    DESCRIPTION
            ""
    ::= { lcsSetupWanAdditionalPptpGatewaysEntry 47 }

-- {COLUMN} 1.3.6.1.4.1.2356.11.2.2.30.1.48
lcsSetupWanAdditionalPptpGatewaysEntryRtgTag23 OBJECT-TYPE
    SYNTAX     Integer32 (0..65535)
    MAX-ACCESS read-write
    STATUS     current
    DESCRIPTION
            ""
    ::= { lcsSetupWanAdditionalPptpGatewaysEntry 48 }

-- {COLUMN} 1.3.6.1.4.1.2356.11.2.2.30.1.49
lcsSetupWanAdditionalPptpGatewaysEntryGateway24 OBJECT-TYPE
    SYNTAX     DisplayString (SIZE(0..64))
    MAX-ACCESS read-write
    STATUS     current
    DESCRIPTION
            ""
    ::= { lcsSetupWanAdditionalPptpGatewaysEntry 49 }

-- {COLUMN} 1.3.6.1.4.1.2356.11.2.2.30.1.50
lcsSetupWanAdditionalPptpGatewaysEntryRtgTag24 OBJECT-TYPE
    SYNTAX     Integer32 (0..65535)
    MAX-ACCESS read-write
    STATUS     current
    DESCRIPTION
            ""
    ::= { lcsSetupWanAdditionalPptpGatewaysEntry 50 }

-- {COLUMN} 1.3.6.1.4.1.2356.11.2.2.30.1.51
lcsSetupWanAdditionalPptpGatewaysEntryGateway25 OBJECT-TYPE
    SYNTAX     DisplayString (SIZE(0..64))
    MAX-ACCESS read-write
    STATUS     current
    DESCRIPTION
            ""
    ::= { lcsSetupWanAdditionalPptpGatewaysEntry 51 }

-- {COLUMN} 1.3.6.1.4.1.2356.11.2.2.30.1.52
lcsSetupWanAdditionalPptpGatewaysEntryRtgTag25 OBJECT-TYPE
    SYNTAX     Integer32 (0..65535)
    MAX-ACCESS read-write
    STATUS     current
    DESCRIPTION
            ""
    ::= { lcsSetupWanAdditionalPptpGatewaysEntry 52 }

-- {COLUMN} 1.3.6.1.4.1.2356.11.2.2.30.1.53
lcsSetupWanAdditionalPptpGatewaysEntryGateway26 OBJECT-TYPE
    SYNTAX     DisplayString (SIZE(0..64))
    MAX-ACCESS read-write
    STATUS     current
    DESCRIPTION
            ""
    ::= { lcsSetupWanAdditionalPptpGatewaysEntry 53 }

-- {COLUMN} 1.3.6.1.4.1.2356.11.2.2.30.1.54
lcsSetupWanAdditionalPptpGatewaysEntryRtgTag26 OBJECT-TYPE
    SYNTAX     Integer32 (0..65535)
    MAX-ACCESS read-write
    STATUS     current
    DESCRIPTION
            ""
    ::= { lcsSetupWanAdditionalPptpGatewaysEntry 54 }

-- {COLUMN} 1.3.6.1.4.1.2356.11.2.2.30.1.55
lcsSetupWanAdditionalPptpGatewaysEntryGateway27 OBJECT-TYPE
    SYNTAX     DisplayString (SIZE(0..64))
    MAX-ACCESS read-write
    STATUS     current
    DESCRIPTION
            ""
    ::= { lcsSetupWanAdditionalPptpGatewaysEntry 55 }

-- {COLUMN} 1.3.6.1.4.1.2356.11.2.2.30.1.56
lcsSetupWanAdditionalPptpGatewaysEntryRtgTag27 OBJECT-TYPE
    SYNTAX     Integer32 (0..65535)
    MAX-ACCESS read-write
    STATUS     current
    DESCRIPTION
            ""
    ::= { lcsSetupWanAdditionalPptpGatewaysEntry 56 }

-- {COLUMN} 1.3.6.1.4.1.2356.11.2.2.30.1.57
lcsSetupWanAdditionalPptpGatewaysEntryGateway28 OBJECT-TYPE
    SYNTAX     DisplayString (SIZE(0..64))
    MAX-ACCESS read-write
    STATUS     current
    DESCRIPTION
            ""
    ::= { lcsSetupWanAdditionalPptpGatewaysEntry 57 }

-- {COLUMN} 1.3.6.1.4.1.2356.11.2.2.30.1.58
lcsSetupWanAdditionalPptpGatewaysEntryRtgTag28 OBJECT-TYPE
    SYNTAX     Integer32 (0..65535)
    MAX-ACCESS read-write
    STATUS     current
    DESCRIPTION
            ""
    ::= { lcsSetupWanAdditionalPptpGatewaysEntry 58 }

-- {COLUMN} 1.3.6.1.4.1.2356.11.2.2.30.1.59
lcsSetupWanAdditionalPptpGatewaysEntryGateway29 OBJECT-TYPE
    SYNTAX     DisplayString (SIZE(0..64))
    MAX-ACCESS read-write
    STATUS     current
    DESCRIPTION
            ""
    ::= { lcsSetupWanAdditionalPptpGatewaysEntry 59 }

-- {COLUMN} 1.3.6.1.4.1.2356.11.2.2.30.1.60
lcsSetupWanAdditionalPptpGatewaysEntryRtgTag29 OBJECT-TYPE
    SYNTAX     Integer32 (0..65535)
    MAX-ACCESS read-write
    STATUS     current
    DESCRIPTION
            ""
    ::= { lcsSetupWanAdditionalPptpGatewaysEntry 60 }

-- {COLUMN} 1.3.6.1.4.1.2356.11.2.2.30.1.61
lcsSetupWanAdditionalPptpGatewaysEntryGateway30 OBJECT-TYPE
    SYNTAX     DisplayString (SIZE(0..64))
    MAX-ACCESS read-write
    STATUS     current
    DESCRIPTION
            ""
    ::= { lcsSetupWanAdditionalPptpGatewaysEntry 61 }

-- {COLUMN} 1.3.6.1.4.1.2356.11.2.2.30.1.62
lcsSetupWanAdditionalPptpGatewaysEntryRtgTag30 OBJECT-TYPE
    SYNTAX     Integer32 (0..65535)
    MAX-ACCESS read-write
    STATUS     current
    DESCRIPTION
            ""
    ::= { lcsSetupWanAdditionalPptpGatewaysEntry 62 }

-- {COLUMN} 1.3.6.1.4.1.2356.11.2.2.30.1.63
lcsSetupWanAdditionalPptpGatewaysEntryGateway31 OBJECT-TYPE
    SYNTAX     DisplayString (SIZE(0..64))
    MAX-ACCESS read-write
    STATUS     current
    DESCRIPTION
            ""
    ::= { lcsSetupWanAdditionalPptpGatewaysEntry 63 }

-- {COLUMN} 1.3.6.1.4.1.2356.11.2.2.30.1.64
lcsSetupWanAdditionalPptpGatewaysEntryRtgTag31 OBJECT-TYPE
    SYNTAX     Integer32 (0..65535)
    MAX-ACCESS read-write
    STATUS     current
    DESCRIPTION
            ""
    ::= { lcsSetupWanAdditionalPptpGatewaysEntry 64 }

-- {COLUMN} 1.3.6.1.4.1.2356.11.2.2.30.1.65
lcsSetupWanAdditionalPptpGatewaysEntryGateway32 OBJECT-TYPE
    SYNTAX     DisplayString (SIZE(0..64))
    MAX-ACCESS read-write
    STATUS     current
    DESCRIPTION
            ""
    ::= { lcsSetupWanAdditionalPptpGatewaysEntry 65 }

-- {COLUMN} 1.3.6.1.4.1.2356.11.2.2.30.1.66
lcsSetupWanAdditionalPptpGatewaysEntryRtgTag32 OBJECT-TYPE
    SYNTAX     Integer32 (0..65535)
    MAX-ACCESS read-write
    STATUS     current
    DESCRIPTION
            ""
    ::= { lcsSetupWanAdditionalPptpGatewaysEntry 66 }

-- {COLUMN} 1.3.6.1.4.1.2356.11.2.2.30.1.67
lcsSetupWanAdditionalPptpGatewaysEntryDefaultPrio OBJECT-TYPE
    SYNTAX     Integer32 (0..65535)
    MAX-ACCESS read-write
    STATUS     current
    DESCRIPTION
            "-- empty --"
    ::= { lcsSetupWanAdditionalPptpGatewaysEntry 67 }

-- {SCALAR} 1.3.6.1.4.1.2356.11.2.2.31
lcsSetupWanPptpSourceCheck OBJECT-TYPE
    SYNTAX     INTEGER {
                  eAddress (0),
                  eTagPlusAddress (1)
            }
    MAX-ACCESS read-write
    STATUS     current
    DESCRIPTION
            ""
    ::= { lcsSetupWan 31 }

-- {TABLE} 1.3.6.1.4.1.2356.11.2.2.35
lcsSetupWanL2tpEndpointsTable OBJECT-TYPE
    SYNTAX     SEQUENCE OF LcsSetupWanL2tpEndpointsEntry
    MAX-ACCESS not-accessible
    STATUS     current
    DESCRIPTION
            "-- empty --"
    ::= { lcsSetupWan 35 }

-- {ROW} 1.3.6.1.4.1.2356.11.2.2.35.1
lcsSetupWanL2tpEndpointsEntry OBJECT-TYPE
    SYNTAX     LcsSetupWanL2tpEndpointsEntry
    MAX-ACCESS not-accessible
    STATUS     current
    DESCRIPTION
            ""
    INDEX {
            lcsSetupWanL2tpEndpointsEntryIdentifier
          }
    ::= { lcsSetupWanL2tpEndpointsTable 1 }

LcsSetupWanL2tpEndpointsEntry ::= SEQUENCE {
            lcsSetupWanL2tpEndpointsEntryIdentifier DisplayString,
            lcsSetupWanL2tpEndpointsEntryIpAddress DisplayString,
            lcsSetupWanL2tpEndpointsEntryRtgTag Integer32,
            lcsSetupWanL2tpEndpointsEntryPort Integer32,
            lcsSetupWanL2tpEndpointsEntryPoll Integer32,
            lcsSetupWanL2tpEndpointsEntryHostname DisplayString,
            lcsSetupWanL2tpEndpointsEntryPassword DisplayString,
            lcsSetupWanL2tpEndpointsEntryAuthPeer INTEGER,
            lcsSetupWanL2tpEndpointsEntryHide INTEGER,
            lcsSetupWanL2tpEndpointsEntryLoopbackAddress DisplayString,
            lcsSetupWanL2tpEndpointsEntryVersion INTEGER,
            lcsSetupWanL2tpEndpointsEntryOperating INTEGER
    }

-- {COLUMN} 1.3.6.1.4.1.2356.11.2.2.35.1.1
lcsSetupWanL2tpEndpointsEntryIdentifier OBJECT-TYPE
    SYNTAX     DisplayString (SIZE(0..16))
    MAX-ACCESS read-write
    STATUS     current
    DESCRIPTION
            "-- empty --"
    ::= { lcsSetupWanL2tpEndpointsEntry 1 }

-- {COLUMN} 1.3.6.1.4.1.2356.11.2.2.35.1.2
lcsSetupWanL2tpEndpointsEntryIpAddress OBJECT-TYPE
    SYNTAX     DisplayString (SIZE(0..64))
    MAX-ACCESS read-write
    STATUS     current
    DESCRIPTION
            "-- empty --"
    ::= { lcsSetupWanL2tpEndpointsEntry 2 }

-- {COLUMN} 1.3.6.1.4.1.2356.11.2.2.35.1.3
lcsSetupWanL2tpEndpointsEntryRtgTag OBJECT-TYPE
    SYNTAX     Integer32 (0..65535)
    MAX-ACCESS read-write
    STATUS     current
    DESCRIPTION
            "-- empty --"
    ::= { lcsSetupWanL2tpEndpointsEntry 3 }

-- {COLUMN} 1.3.6.1.4.1.2356.11.2.2.35.1.4
lcsSetupWanL2tpEndpointsEntryPort OBJECT-TYPE
    SYNTAX     Integer32 (0..65535)
    MAX-ACCESS read-write
    STATUS     current
    DESCRIPTION
            "-- empty --"
    ::= { lcsSetupWanL2tpEndpointsEntry 4 }

-- {COLUMN} 1.3.6.1.4.1.2356.11.2.2.35.1.5
lcsSetupWanL2tpEndpointsEntryPoll OBJECT-TYPE
    SYNTAX     Integer32 (0..65535)
    MAX-ACCESS read-write
    STATUS     current
    DESCRIPTION
            "-- empty --"
    ::= { lcsSetupWanL2tpEndpointsEntry 5 }

-- {COLUMN} 1.3.6.1.4.1.2356.11.2.2.35.1.6
lcsSetupWanL2tpEndpointsEntryHostname OBJECT-TYPE
    SYNTAX     DisplayString (SIZE(0..64))
    MAX-ACCESS read-write
    STATUS     current
    DESCRIPTION
            "-- empty --"
    ::= { lcsSetupWanL2tpEndpointsEntry 6 }

-- {COLUMN} 1.3.6.1.4.1.2356.11.2.2.35.1.7
lcsSetupWanL2tpEndpointsEntryPassword OBJECT-TYPE
    SYNTAX     DisplayString (SIZE(0..32))
    MAX-ACCESS read-write
    STATUS     current
    DESCRIPTION
            "-- empty --"
    ::= { lcsSetupWanL2tpEndpointsEntry 7 }

-- {COLUMN} 1.3.6.1.4.1.2356.11.2.2.35.1.8
lcsSetupWanL2tpEndpointsEntryAuthPeer OBJECT-TYPE
    SYNTAX     INTEGER {
                  eNo (0),
                  eYes (1)
            }
    MAX-ACCESS read-write
    STATUS     current
    DESCRIPTION
            "-- empty --"
    ::= { lcsSetupWanL2tpEndpointsEntry 8 }

-- {COLUMN} 1.3.6.1.4.1.2356.11.2.2.35.1.9
lcsSetupWanL2tpEndpointsEntryHide OBJECT-TYPE
    SYNTAX     INTEGER {
                  eNo (0),
                  eYes (1)
            }
    MAX-ACCESS read-write
    STATUS     current
    DESCRIPTION
            "-- empty --"
    ::= { lcsSetupWanL2tpEndpointsEntry 9 }

-- {COLUMN} 1.3.6.1.4.1.2356.11.2.2.35.1.10
lcsSetupWanL2tpEndpointsEntryLoopbackAddress OBJECT-TYPE
    SYNTAX     DisplayString (SIZE(0..16))
    MAX-ACCESS read-write
    STATUS     current
    DESCRIPTION
            "-- empty --"
    ::= { lcsSetupWanL2tpEndpointsEntry 10 }

-- {COLUMN} 1.3.6.1.4.1.2356.11.2.2.35.1.11
lcsSetupWanL2tpEndpointsEntryVersion OBJECT-TYPE
    SYNTAX     INTEGER {
                  eL2tpv2 (2),
                  eL2tpv3 (3)
            }
    MAX-ACCESS read-write
    STATUS     current
    DESCRIPTION
            "-- empty --"
    ::= { lcsSetupWanL2tpEndpointsEntry 11 }

-- {COLUMN} 1.3.6.1.4.1.2356.11.2.2.35.1.12
lcsSetupWanL2tpEndpointsEntryOperating OBJECT-TYPE
    SYNTAX     INTEGER {
                  eNo (0),
                  eYes (1)
            }
    MAX-ACCESS read-write
    STATUS     current
    DESCRIPTION
            "-- empty --"
    ::= { lcsSetupWanL2tpEndpointsEntry 12 }

-- {TABLE} 1.3.6.1.4.1.2356.11.2.2.36
lcsSetupWanL2tpAdditionalGatewaysTable OBJECT-TYPE
    SYNTAX     SEQUENCE OF LcsSetupWanL2tpAdditionalGatewaysEntry
    MAX-ACCESS not-accessible
    STATUS     current
    DESCRIPTION
            "-- empty --"
    ::= { lcsSetupWan 36 }

-- {ROW} 1.3.6.1.4.1.2356.11.2.2.36.1
lcsSetupWanL2tpAdditionalGatewaysEntry OBJECT-TYPE
    SYNTAX     LcsSetupWanL2tpAdditionalGatewaysEntry
    MAX-ACCESS not-accessible
    STATUS     current
    DESCRIPTION
            ""
    INDEX {
            lcsSetupWanL2tpAdditionalGatewaysEntryIdentifier
          }
    ::= { lcsSetupWanL2tpAdditionalGatewaysTable 1 }

LcsSetupWanL2tpAdditionalGatewaysEntry ::= SEQUENCE {
            lcsSetupWanL2tpAdditionalGatewaysEntryIdentifier DisplayString,
            lcsSetupWanL2tpAdditionalGatewaysEntryBeginWith INTEGER,
            lcsSetupWanL2tpAdditionalGatewaysEntryGateway1 DisplayString,
            lcsSetupWanL2tpAdditionalGatewaysEntryRtgTag1 Integer32,
            lcsSetupWanL2tpAdditionalGatewaysEntryGateway2 DisplayString,
            lcsSetupWanL2tpAdditionalGatewaysEntryRtgTag2 Integer32,
            lcsSetupWanL2tpAdditionalGatewaysEntryGateway3 DisplayString,
            lcsSetupWanL2tpAdditionalGatewaysEntryRtgTag3 Integer32,
            lcsSetupWanL2tpAdditionalGatewaysEntryGateway4 DisplayString,
            lcsSetupWanL2tpAdditionalGatewaysEntryRtgTag4 Integer32,
            lcsSetupWanL2tpAdditionalGatewaysEntryGateway5 DisplayString,
            lcsSetupWanL2tpAdditionalGatewaysEntryRtgTag5 Integer32,
            lcsSetupWanL2tpAdditionalGatewaysEntryGateway6 DisplayString,
            lcsSetupWanL2tpAdditionalGatewaysEntryRtgTag6 Integer32,
            lcsSetupWanL2tpAdditionalGatewaysEntryGateway7 DisplayString,
            lcsSetupWanL2tpAdditionalGatewaysEntryRtgTag7 Integer32,
            lcsSetupWanL2tpAdditionalGatewaysEntryGateway8 DisplayString,
            lcsSetupWanL2tpAdditionalGatewaysEntryRtgTag8 Integer32,
            lcsSetupWanL2tpAdditionalGatewaysEntryGateway9 DisplayString,
            lcsSetupWanL2tpAdditionalGatewaysEntryRtgTag9 Integer32,
            lcsSetupWanL2tpAdditionalGatewaysEntryGateway10 DisplayString,
            lcsSetupWanL2tpAdditionalGatewaysEntryRtgTag10 Integer32,
            lcsSetupWanL2tpAdditionalGatewaysEntryGateway11 DisplayString,
            lcsSetupWanL2tpAdditionalGatewaysEntryRtgTag11 Integer32,
            lcsSetupWanL2tpAdditionalGatewaysEntryGateway12 DisplayString,
            lcsSetupWanL2tpAdditionalGatewaysEntryRtgTag12 Integer32,
            lcsSetupWanL2tpAdditionalGatewaysEntryGateway13 DisplayString,
            lcsSetupWanL2tpAdditionalGatewaysEntryRtgTag13 Integer32,
            lcsSetupWanL2tpAdditionalGatewaysEntryGateway14 DisplayString,
            lcsSetupWanL2tpAdditionalGatewaysEntryRtgTag14 Integer32,
            lcsSetupWanL2tpAdditionalGatewaysEntryGateway15 DisplayString,
            lcsSetupWanL2tpAdditionalGatewaysEntryRtgTag15 Integer32,
            lcsSetupWanL2tpAdditionalGatewaysEntryGateway16 DisplayString,
            lcsSetupWanL2tpAdditionalGatewaysEntryRtgTag16 Integer32,
            lcsSetupWanL2tpAdditionalGatewaysEntryGateway17 DisplayString,
            lcsSetupWanL2tpAdditionalGatewaysEntryRtgTag17 Integer32,
            lcsSetupWanL2tpAdditionalGatewaysEntryGateway18 DisplayString,
            lcsSetupWanL2tpAdditionalGatewaysEntryRtgTag18 Integer32,
            lcsSetupWanL2tpAdditionalGatewaysEntryGateway19 DisplayString,
            lcsSetupWanL2tpAdditionalGatewaysEntryRtgTag19 Integer32,
            lcsSetupWanL2tpAdditionalGatewaysEntryGateway20 DisplayString,
            lcsSetupWanL2tpAdditionalGatewaysEntryRtgTag20 Integer32,
            lcsSetupWanL2tpAdditionalGatewaysEntryGateway21 DisplayString,
            lcsSetupWanL2tpAdditionalGatewaysEntryRtgTag21 Integer32,
            lcsSetupWanL2tpAdditionalGatewaysEntryGateway22 DisplayString,
            lcsSetupWanL2tpAdditionalGatewaysEntryRtgTag22 Integer32,
            lcsSetupWanL2tpAdditionalGatewaysEntryGateway23 DisplayString,
            lcsSetupWanL2tpAdditionalGatewaysEntryRtgTag23 Integer32,
            lcsSetupWanL2tpAdditionalGatewaysEntryGateway24 DisplayString,
            lcsSetupWanL2tpAdditionalGatewaysEntryRtgTag24 Integer32,
            lcsSetupWanL2tpAdditionalGatewaysEntryGateway25 DisplayString,
            lcsSetupWanL2tpAdditionalGatewaysEntryRtgTag25 Integer32,
            lcsSetupWanL2tpAdditionalGatewaysEntryGateway26 DisplayString,
            lcsSetupWanL2tpAdditionalGatewaysEntryRtgTag26 Integer32,
            lcsSetupWanL2tpAdditionalGatewaysEntryGateway27 DisplayString,
            lcsSetupWanL2tpAdditionalGatewaysEntryRtgTag27 Integer32,
            lcsSetupWanL2tpAdditionalGatewaysEntryGateway28 DisplayString,
            lcsSetupWanL2tpAdditionalGatewaysEntryRtgTag28 Integer32,
            lcsSetupWanL2tpAdditionalGatewaysEntryGateway29 DisplayString,
            lcsSetupWanL2tpAdditionalGatewaysEntryRtgTag29 Integer32,
            lcsSetupWanL2tpAdditionalGatewaysEntryGateway30 DisplayString,
            lcsSetupWanL2tpAdditionalGatewaysEntryRtgTag30 Integer32,
            lcsSetupWanL2tpAdditionalGatewaysEntryGateway31 DisplayString,
            lcsSetupWanL2tpAdditionalGatewaysEntryRtgTag31 Integer32,
            lcsSetupWanL2tpAdditionalGatewaysEntryGateway32 DisplayString,
            lcsSetupWanL2tpAdditionalGatewaysEntryRtgTag32 Integer32,
            lcsSetupWanL2tpAdditionalGatewaysEntryDefaultPrio Integer32
    }

-- {COLUMN} 1.3.6.1.4.1.2356.11.2.2.36.1.1
lcsSetupWanL2tpAdditionalGatewaysEntryIdentifier OBJECT-TYPE
    SYNTAX     DisplayString (SIZE(0..16))
    MAX-ACCESS read-write
    STATUS     current
    DESCRIPTION
            "-- empty --"
    ::= { lcsSetupWanL2tpAdditionalGatewaysEntry 1 }

-- {COLUMN} 1.3.6.1.4.1.2356.11.2.2.36.1.2
lcsSetupWanL2tpAdditionalGatewaysEntryBeginWith OBJECT-TYPE
    SYNTAX     INTEGER {
                  eLastUsed (0),
                  eFirst (1),
                  eRandom (2)
            }
    MAX-ACCESS read-write
    STATUS     current
    DESCRIPTION
            "-- empty --"
    ::= { lcsSetupWanL2tpAdditionalGatewaysEntry 2 }

-- {COLUMN} 1.3.6.1.4.1.2356.11.2.2.36.1.3
lcsSetupWanL2tpAdditionalGatewaysEntryGateway1 OBJECT-TYPE
    SYNTAX     DisplayString (SIZE(0..64))
    MAX-ACCESS read-write
    STATUS     current
    DESCRIPTION
            "-- empty --"
    ::= { lcsSetupWanL2tpAdditionalGatewaysEntry 3 }

-- {COLUMN} 1.3.6.1.4.1.2356.11.2.2.36.1.4
lcsSetupWanL2tpAdditionalGatewaysEntryRtgTag1 OBJECT-TYPE
    SYNTAX     Integer32 (0..65535)
    MAX-ACCESS read-write
    STATUS     current
    DESCRIPTION
            "-- empty --"
    ::= { lcsSetupWanL2tpAdditionalGatewaysEntry 4 }

-- {COLUMN} 1.3.6.1.4.1.2356.11.2.2.36.1.5
lcsSetupWanL2tpAdditionalGatewaysEntryGateway2 OBJECT-TYPE
    SYNTAX     DisplayString (SIZE(0..64))
    MAX-ACCESS read-write
    STATUS     current
    DESCRIPTION
            "-- empty --"
    ::= { lcsSetupWanL2tpAdditionalGatewaysEntry 5 }

-- {COLUMN} 1.3.6.1.4.1.2356.11.2.2.36.1.6
lcsSetupWanL2tpAdditionalGatewaysEntryRtgTag2 OBJECT-TYPE
    SYNTAX     Integer32 (0..65535)
    MAX-ACCESS read-write
    STATUS     current
    DESCRIPTION
            "-- empty --"
    ::= { lcsSetupWanL2tpAdditionalGatewaysEntry 6 }

-- {COLUMN} 1.3.6.1.4.1.2356.11.2.2.36.1.7
lcsSetupWanL2tpAdditionalGatewaysEntryGateway3 OBJECT-TYPE
    SYNTAX     DisplayString (SIZE(0..64))
    MAX-ACCESS read-write
    STATUS     current
    DESCRIPTION
            "-- empty --"
    ::= { lcsSetupWanL2tpAdditionalGatewaysEntry 7 }

-- {COLUMN} 1.3.6.1.4.1.2356.11.2.2.36.1.8
lcsSetupWanL2tpAdditionalGatewaysEntryRtgTag3 OBJECT-TYPE
    SYNTAX     Integer32 (0..65535)
    MAX-ACCESS read-write
    STATUS     current
    DESCRIPTION
            "-- empty --"
    ::= { lcsSetupWanL2tpAdditionalGatewaysEntry 8 }

-- {COLUMN} 1.3.6.1.4.1.2356.11.2.2.36.1.9
lcsSetupWanL2tpAdditionalGatewaysEntryGateway4 OBJECT-TYPE
    SYNTAX     DisplayString (SIZE(0..64))
    MAX-ACCESS read-write
    STATUS     current
    DESCRIPTION
            "-- empty --"
    ::= { lcsSetupWanL2tpAdditionalGatewaysEntry 9 }

-- {COLUMN} 1.3.6.1.4.1.2356.11.2.2.36.1.10
lcsSetupWanL2tpAdditionalGatewaysEntryRtgTag4 OBJECT-TYPE
    SYNTAX     Integer32 (0..65535)
    MAX-ACCESS read-write
    STATUS     current
    DESCRIPTION
            "-- empty --"
    ::= { lcsSetupWanL2tpAdditionalGatewaysEntry 10 }

-- {COLUMN} 1.3.6.1.4.1.2356.11.2.2.36.1.11
lcsSetupWanL2tpAdditionalGatewaysEntryGateway5 OBJECT-TYPE
    SYNTAX     DisplayString (SIZE(0..64))
    MAX-ACCESS read-write
    STATUS     current
    DESCRIPTION
            "-- empty --"
    ::= { lcsSetupWanL2tpAdditionalGatewaysEntry 11 }

-- {COLUMN} 1.3.6.1.4.1.2356.11.2.2.36.1.12
lcsSetupWanL2tpAdditionalGatewaysEntryRtgTag5 OBJECT-TYPE
    SYNTAX     Integer32 (0..65535)
    MAX-ACCESS read-write
    STATUS     current
    DESCRIPTION
            "-- empty --"
    ::= { lcsSetupWanL2tpAdditionalGatewaysEntry 12 }

-- {COLUMN} 1.3.6.1.4.1.2356.11.2.2.36.1.13
lcsSetupWanL2tpAdditionalGatewaysEntryGateway6 OBJECT-TYPE
    SYNTAX     DisplayString (SIZE(0..64))
    MAX-ACCESS read-write
    STATUS     current
    DESCRIPTION
            "-- empty --"
    ::= { lcsSetupWanL2tpAdditionalGatewaysEntry 13 }

-- {COLUMN} 1.3.6.1.4.1.2356.11.2.2.36.1.14
lcsSetupWanL2tpAdditionalGatewaysEntryRtgTag6 OBJECT-TYPE
    SYNTAX     Integer32 (0..65535)
    MAX-ACCESS read-write
    STATUS     current
    DESCRIPTION
            "-- empty --"
    ::= { lcsSetupWanL2tpAdditionalGatewaysEntry 14 }

-- {COLUMN} 1.3.6.1.4.1.2356.11.2.2.36.1.15
lcsSetupWanL2tpAdditionalGatewaysEntryGateway7 OBJECT-TYPE
    SYNTAX     DisplayString (SIZE(0..64))
    MAX-ACCESS read-write
    STATUS     current
    DESCRIPTION
            "-- empty --"
    ::= { lcsSetupWanL2tpAdditionalGatewaysEntry 15 }

-- {COLUMN} 1.3.6.1.4.1.2356.11.2.2.36.1.16
lcsSetupWanL2tpAdditionalGatewaysEntryRtgTag7 OBJECT-TYPE
    SYNTAX     Integer32 (0..65535)
    MAX-ACCESS read-write
    STATUS     current
    DESCRIPTION
            "-- empty --"
    ::= { lcsSetupWanL2tpAdditionalGatewaysEntry 16 }

-- {COLUMN} 1.3.6.1.4.1.2356.11.2.2.36.1.17
lcsSetupWanL2tpAdditionalGatewaysEntryGateway8 OBJECT-TYPE
    SYNTAX     DisplayString (SIZE(0..64))
    MAX-ACCESS read-write
    STATUS     current
    DESCRIPTION
            "-- empty --"
    ::= { lcsSetupWanL2tpAdditionalGatewaysEntry 17 }

-- {COLUMN} 1.3.6.1.4.1.2356.11.2.2.36.1.18
lcsSetupWanL2tpAdditionalGatewaysEntryRtgTag8 OBJECT-TYPE
    SYNTAX     Integer32 (0..65535)
    MAX-ACCESS read-write
    STATUS     current
    DESCRIPTION
            "-- empty --"
    ::= { lcsSetupWanL2tpAdditionalGatewaysEntry 18 }

-- {COLUMN} 1.3.6.1.4.1.2356.11.2.2.36.1.19
lcsSetupWanL2tpAdditionalGatewaysEntryGateway9 OBJECT-TYPE
    SYNTAX     DisplayString (SIZE(0..64))
    MAX-ACCESS read-write
    STATUS     current
    DESCRIPTION
            "-- empty --"
    ::= { lcsSetupWanL2tpAdditionalGatewaysEntry 19 }

-- {COLUMN} 1.3.6.1.4.1.2356.11.2.2.36.1.20
lcsSetupWanL2tpAdditionalGatewaysEntryRtgTag9 OBJECT-TYPE
    SYNTAX     Integer32 (0..65535)
    MAX-ACCESS read-write
    STATUS     current
    DESCRIPTION
            "-- empty --"
    ::= { lcsSetupWanL2tpAdditionalGatewaysEntry 20 }

-- {COLUMN} 1.3.6.1.4.1.2356.11.2.2.36.1.21
lcsSetupWanL2tpAdditionalGatewaysEntryGateway10 OBJECT-TYPE
    SYNTAX     DisplayString (SIZE(0..64))
    MAX-ACCESS read-write
    STATUS     current
    DESCRIPTION
            "-- empty --"
    ::= { lcsSetupWanL2tpAdditionalGatewaysEntry 21 }

-- {COLUMN} 1.3.6.1.4.1.2356.11.2.2.36.1.22
lcsSetupWanL2tpAdditionalGatewaysEntryRtgTag10 OBJECT-TYPE
    SYNTAX     Integer32 (0..65535)
    MAX-ACCESS read-write
    STATUS     current
    DESCRIPTION
            "-- empty --"
    ::= { lcsSetupWanL2tpAdditionalGatewaysEntry 22 }

-- {COLUMN} 1.3.6.1.4.1.2356.11.2.2.36.1.23
lcsSetupWanL2tpAdditionalGatewaysEntryGateway11 OBJECT-TYPE
    SYNTAX     DisplayString (SIZE(0..64))
    MAX-ACCESS read-write
    STATUS     current
    DESCRIPTION
            "-- empty --"
    ::= { lcsSetupWanL2tpAdditionalGatewaysEntry 23 }

-- {COLUMN} 1.3.6.1.4.1.2356.11.2.2.36.1.24
lcsSetupWanL2tpAdditionalGatewaysEntryRtgTag11 OBJECT-TYPE
    SYNTAX     Integer32 (0..65535)
    MAX-ACCESS read-write
    STATUS     current
    DESCRIPTION
            "-- empty --"
    ::= { lcsSetupWanL2tpAdditionalGatewaysEntry 24 }

-- {COLUMN} 1.3.6.1.4.1.2356.11.2.2.36.1.25
lcsSetupWanL2tpAdditionalGatewaysEntryGateway12 OBJECT-TYPE
    SYNTAX     DisplayString (SIZE(0..64))
    MAX-ACCESS read-write
    STATUS     current
    DESCRIPTION
            "-- empty --"
    ::= { lcsSetupWanL2tpAdditionalGatewaysEntry 25 }

-- {COLUMN} 1.3.6.1.4.1.2356.11.2.2.36.1.26
lcsSetupWanL2tpAdditionalGatewaysEntryRtgTag12 OBJECT-TYPE
    SYNTAX     Integer32 (0..65535)
    MAX-ACCESS read-write
    STATUS     current
    DESCRIPTION
            "-- empty --"
    ::= { lcsSetupWanL2tpAdditionalGatewaysEntry 26 }

-- {COLUMN} 1.3.6.1.4.1.2356.11.2.2.36.1.27
lcsSetupWanL2tpAdditionalGatewaysEntryGateway13 OBJECT-TYPE
    SYNTAX     DisplayString (SIZE(0..64))
    MAX-ACCESS read-write
    STATUS     current
    DESCRIPTION
            "-- empty --"
    ::= { lcsSetupWanL2tpAdditionalGatewaysEntry 27 }

-- {COLUMN} 1.3.6.1.4.1.2356.11.2.2.36.1.28
lcsSetupWanL2tpAdditionalGatewaysEntryRtgTag13 OBJECT-TYPE
    SYNTAX     Integer32 (0..65535)
    MAX-ACCESS read-write
    STATUS     current
    DESCRIPTION
            "-- empty --"
    ::= { lcsSetupWanL2tpAdditionalGatewaysEntry 28 }

-- {COLUMN} 1.3.6.1.4.1.2356.11.2.2.36.1.29
lcsSetupWanL2tpAdditionalGatewaysEntryGateway14 OBJECT-TYPE
    SYNTAX     DisplayString (SIZE(0..64))
    MAX-ACCESS read-write
    STATUS     current
    DESCRIPTION
            "-- empty --"
    ::= { lcsSetupWanL2tpAdditionalGatewaysEntry 29 }

-- {COLUMN} 1.3.6.1.4.1.2356.11.2.2.36.1.30
lcsSetupWanL2tpAdditionalGatewaysEntryRtgTag14 OBJECT-TYPE
    SYNTAX     Integer32 (0..65535)
    MAX-ACCESS read-write
    STATUS     current
    DESCRIPTION
            "-- empty --"
    ::= { lcsSetupWanL2tpAdditionalGatewaysEntry 30 }

-- {COLUMN} 1.3.6.1.4.1.2356.11.2.2.36.1.31
lcsSetupWanL2tpAdditionalGatewaysEntryGateway15 OBJECT-TYPE
    SYNTAX     DisplayString (SIZE(0..64))
    MAX-ACCESS read-write
    STATUS     current
    DESCRIPTION
            "-- empty --"
    ::= { lcsSetupWanL2tpAdditionalGatewaysEntry 31 }

-- {COLUMN} 1.3.6.1.4.1.2356.11.2.2.36.1.32
lcsSetupWanL2tpAdditionalGatewaysEntryRtgTag15 OBJECT-TYPE
    SYNTAX     Integer32 (0..65535)
    MAX-ACCESS read-write
    STATUS     current
    DESCRIPTION
            "-- empty --"
    ::= { lcsSetupWanL2tpAdditionalGatewaysEntry 32 }

-- {COLUMN} 1.3.6.1.4.1.2356.11.2.2.36.1.33
lcsSetupWanL2tpAdditionalGatewaysEntryGateway16 OBJECT-TYPE
    SYNTAX     DisplayString (SIZE(0..64))
    MAX-ACCESS read-write
    STATUS     current
    DESCRIPTION
            "-- empty --"
    ::= { lcsSetupWanL2tpAdditionalGatewaysEntry 33 }

-- {COLUMN} 1.3.6.1.4.1.2356.11.2.2.36.1.34
lcsSetupWanL2tpAdditionalGatewaysEntryRtgTag16 OBJECT-TYPE
    SYNTAX     Integer32 (0..65535)
    MAX-ACCESS read-write
    STATUS     current
    DESCRIPTION
            "-- empty --"
    ::= { lcsSetupWanL2tpAdditionalGatewaysEntry 34 }

-- {COLUMN} 1.3.6.1.4.1.2356.11.2.2.36.1.35
lcsSetupWanL2tpAdditionalGatewaysEntryGateway17 OBJECT-TYPE
    SYNTAX     DisplayString (SIZE(0..64))
    MAX-ACCESS read-write
    STATUS     current
    DESCRIPTION
            "-- empty --"
    ::= { lcsSetupWanL2tpAdditionalGatewaysEntry 35 }

-- {COLUMN} 1.3.6.1.4.1.2356.11.2.2.36.1.36
lcsSetupWanL2tpAdditionalGatewaysEntryRtgTag17 OBJECT-TYPE
    SYNTAX     Integer32 (0..65535)
    MAX-ACCESS read-write
    STATUS     current
    DESCRIPTION
            "-- empty --"
    ::= { lcsSetupWanL2tpAdditionalGatewaysEntry 36 }

-- {COLUMN} 1.3.6.1.4.1.2356.11.2.2.36.1.37
lcsSetupWanL2tpAdditionalGatewaysEntryGateway18 OBJECT-TYPE
    SYNTAX     DisplayString (SIZE(0..64))
    MAX-ACCESS read-write
    STATUS     current
    DESCRIPTION
            "-- empty --"
    ::= { lcsSetupWanL2tpAdditionalGatewaysEntry 37 }

-- {COLUMN} 1.3.6.1.4.1.2356.11.2.2.36.1.38
lcsSetupWanL2tpAdditionalGatewaysEntryRtgTag18 OBJECT-TYPE
    SYNTAX     Integer32 (0..65535)
    MAX-ACCESS read-write
    STATUS     current
    DESCRIPTION
            "-- empty --"
    ::= { lcsSetupWanL2tpAdditionalGatewaysEntry 38 }

-- {COLUMN} 1.3.6.1.4.1.2356.11.2.2.36.1.39
lcsSetupWanL2tpAdditionalGatewaysEntryGateway19 OBJECT-TYPE
    SYNTAX     DisplayString (SIZE(0..64))
    MAX-ACCESS read-write
    STATUS     current
    DESCRIPTION
            "-- empty --"
    ::= { lcsSetupWanL2tpAdditionalGatewaysEntry 39 }

-- {COLUMN} 1.3.6.1.4.1.2356.11.2.2.36.1.40
lcsSetupWanL2tpAdditionalGatewaysEntryRtgTag19 OBJECT-TYPE
    SYNTAX     Integer32 (0..65535)
    MAX-ACCESS read-write
    STATUS     current
    DESCRIPTION
            "-- empty --"
    ::= { lcsSetupWanL2tpAdditionalGatewaysEntry 40 }

-- {COLUMN} 1.3.6.1.4.1.2356.11.2.2.36.1.41
lcsSetupWanL2tpAdditionalGatewaysEntryGateway20 OBJECT-TYPE
    SYNTAX     DisplayString (SIZE(0..64))
    MAX-ACCESS read-write
    STATUS     current
    DESCRIPTION
            "-- empty --"
    ::= { lcsSetupWanL2tpAdditionalGatewaysEntry 41 }

-- {COLUMN} 1.3.6.1.4.1.2356.11.2.2.36.1.42
lcsSetupWanL2tpAdditionalGatewaysEntryRtgTag20 OBJECT-TYPE
    SYNTAX     Integer32 (0..65535)
    MAX-ACCESS read-write
    STATUS     current
    DESCRIPTION
            "-- empty --"
    ::= { lcsSetupWanL2tpAdditionalGatewaysEntry 42 }

-- {COLUMN} 1.3.6.1.4.1.2356.11.2.2.36.1.43
lcsSetupWanL2tpAdditionalGatewaysEntryGateway21 OBJECT-TYPE
    SYNTAX     DisplayString (SIZE(0..64))
    MAX-ACCESS read-write
    STATUS     current
    DESCRIPTION
            "-- empty --"
    ::= { lcsSetupWanL2tpAdditionalGatewaysEntry 43 }

-- {COLUMN} 1.3.6.1.4.1.2356.11.2.2.36.1.44
lcsSetupWanL2tpAdditionalGatewaysEntryRtgTag21 OBJECT-TYPE
    SYNTAX     Integer32 (0..65535)
    MAX-ACCESS read-write
    STATUS     current
    DESCRIPTION
            "-- empty --"
    ::= { lcsSetupWanL2tpAdditionalGatewaysEntry 44 }

-- {COLUMN} 1.3.6.1.4.1.2356.11.2.2.36.1.45
lcsSetupWanL2tpAdditionalGatewaysEntryGateway22 OBJECT-TYPE
    SYNTAX     DisplayString (SIZE(0..64))
    MAX-ACCESS read-write
    STATUS     current
    DESCRIPTION
            "-- empty --"
    ::= { lcsSetupWanL2tpAdditionalGatewaysEntry 45 }

-- {COLUMN} 1.3.6.1.4.1.2356.11.2.2.36.1.46
lcsSetupWanL2tpAdditionalGatewaysEntryRtgTag22 OBJECT-TYPE
    SYNTAX     Integer32 (0..65535)
    MAX-ACCESS read-write
    STATUS     current
    DESCRIPTION
            "-- empty --"
    ::= { lcsSetupWanL2tpAdditionalGatewaysEntry 46 }

-- {COLUMN} 1.3.6.1.4.1.2356.11.2.2.36.1.47
lcsSetupWanL2tpAdditionalGatewaysEntryGateway23 OBJECT-TYPE
    SYNTAX     DisplayString (SIZE(0..64))
    MAX-ACCESS read-write
    STATUS     current
    DESCRIPTION
            "-- empty --"
    ::= { lcsSetupWanL2tpAdditionalGatewaysEntry 47 }

-- {COLUMN} 1.3.6.1.4.1.2356.11.2.2.36.1.48
lcsSetupWanL2tpAdditionalGatewaysEntryRtgTag23 OBJECT-TYPE
    SYNTAX     Integer32 (0..65535)
    MAX-ACCESS read-write
    STATUS     current
    DESCRIPTION
            "-- empty --"
    ::= { lcsSetupWanL2tpAdditionalGatewaysEntry 48 }

-- {COLUMN} 1.3.6.1.4.1.2356.11.2.2.36.1.49
lcsSetupWanL2tpAdditionalGatewaysEntryGateway24 OBJECT-TYPE
    SYNTAX     DisplayString (SIZE(0..64))
    MAX-ACCESS read-write
    STATUS     current
    DESCRIPTION
            "-- empty --"
    ::= { lcsSetupWanL2tpAdditionalGatewaysEntry 49 }

-- {COLUMN} 1.3.6.1.4.1.2356.11.2.2.36.1.50
lcsSetupWanL2tpAdditionalGatewaysEntryRtgTag24 OBJECT-TYPE
    SYNTAX     Integer32 (0..65535)
    MAX-ACCESS read-write
    STATUS     current
    DESCRIPTION
            "-- empty --"
    ::= { lcsSetupWanL2tpAdditionalGatewaysEntry 50 }

-- {COLUMN} 1.3.6.1.4.1.2356.11.2.2.36.1.51
lcsSetupWanL2tpAdditionalGatewaysEntryGateway25 OBJECT-TYPE
    SYNTAX     DisplayString (SIZE(0..64))
    MAX-ACCESS read-write
    STATUS     current
    DESCRIPTION
            "-- empty --"
    ::= { lcsSetupWanL2tpAdditionalGatewaysEntry 51 }

-- {COLUMN} 1.3.6.1.4.1.2356.11.2.2.36.1.52
lcsSetupWanL2tpAdditionalGatewaysEntryRtgTag25 OBJECT-TYPE
    SYNTAX     Integer32 (0..65535)
    MAX-ACCESS read-write
    STATUS     current
    DESCRIPTION
            "-- empty --"
    ::= { lcsSetupWanL2tpAdditionalGatewaysEntry 52 }

-- {COLUMN} 1.3.6.1.4.1.2356.11.2.2.36.1.53
lcsSetupWanL2tpAdditionalGatewaysEntryGateway26 OBJECT-TYPE
    SYNTAX     DisplayString (SIZE(0..64))
    MAX-ACCESS read-write
    STATUS     current
    DESCRIPTION
            "-- empty --"
    ::= { lcsSetupWanL2tpAdditionalGatewaysEntry 53 }

-- {COLUMN} 1.3.6.1.4.1.2356.11.2.2.36.1.54
lcsSetupWanL2tpAdditionalGatewaysEntryRtgTag26 OBJECT-TYPE
    SYNTAX     Integer32 (0..65535)
    MAX-ACCESS read-write
    STATUS     current
    DESCRIPTION
            "-- empty --"
    ::= { lcsSetupWanL2tpAdditionalGatewaysEntry 54 }

-- {COLUMN} 1.3.6.1.4.1.2356.11.2.2.36.1.55
lcsSetupWanL2tpAdditionalGatewaysEntryGateway27 OBJECT-TYPE
    SYNTAX     DisplayString (SIZE(0..64))
    MAX-ACCESS read-write
    STATUS     current
    DESCRIPTION
            "-- empty --"
    ::= { lcsSetupWanL2tpAdditionalGatewaysEntry 55 }

-- {COLUMN} 1.3.6.1.4.1.2356.11.2.2.36.1.56
lcsSetupWanL2tpAdditionalGatewaysEntryRtgTag27 OBJECT-TYPE
    SYNTAX     Integer32 (0..65535)
    MAX-ACCESS read-write
    STATUS     current
    DESCRIPTION
            "-- empty --"
    ::= { lcsSetupWanL2tpAdditionalGatewaysEntry 56 }

-- {COLUMN} 1.3.6.1.4.1.2356.11.2.2.36.1.57
lcsSetupWanL2tpAdditionalGatewaysEntryGateway28 OBJECT-TYPE
    SYNTAX     DisplayString (SIZE(0..64))
    MAX-ACCESS read-write
    STATUS     current
    DESCRIPTION
            "-- empty --"
    ::= { lcsSetupWanL2tpAdditionalGatewaysEntry 57 }

-- {COLUMN} 1.3.6.1.4.1.2356.11.2.2.36.1.58
lcsSetupWanL2tpAdditionalGatewaysEntryRtgTag28 OBJECT-TYPE
    SYNTAX     Integer32 (0..65535)
    MAX-ACCESS read-write
    STATUS     current
    DESCRIPTION
            "-- empty --"
    ::= { lcsSetupWanL2tpAdditionalGatewaysEntry 58 }

-- {COLUMN} 1.3.6.1.4.1.2356.11.2.2.36.1.59
lcsSetupWanL2tpAdditionalGatewaysEntryGateway29 OBJECT-TYPE
    SYNTAX     DisplayString (SIZE(0..64))
    MAX-ACCESS read-write
    STATUS     current
    DESCRIPTION
            "-- empty --"
    ::= { lcsSetupWanL2tpAdditionalGatewaysEntry 59 }

-- {COLUMN} 1.3.6.1.4.1.2356.11.2.2.36.1.60
lcsSetupWanL2tpAdditionalGatewaysEntryRtgTag29 OBJECT-TYPE
    SYNTAX     Integer32 (0..65535)
    MAX-ACCESS read-write
    STATUS     current
    DESCRIPTION
            "-- empty --"
    ::= { lcsSetupWanL2tpAdditionalGatewaysEntry 60 }

-- {COLUMN} 1.3.6.1.4.1.2356.11.2.2.36.1.61
lcsSetupWanL2tpAdditionalGatewaysEntryGateway30 OBJECT-TYPE
    SYNTAX     DisplayString (SIZE(0..64))
    MAX-ACCESS read-write
    STATUS     current
    DESCRIPTION
            "-- empty --"
    ::= { lcsSetupWanL2tpAdditionalGatewaysEntry 61 }

-- {COLUMN} 1.3.6.1.4.1.2356.11.2.2.36.1.62
lcsSetupWanL2tpAdditionalGatewaysEntryRtgTag30 OBJECT-TYPE
    SYNTAX     Integer32 (0..65535)
    MAX-ACCESS read-write
    STATUS     current
    DESCRIPTION
            "-- empty --"
    ::= { lcsSetupWanL2tpAdditionalGatewaysEntry 62 }

-- {COLUMN} 1.3.6.1.4.1.2356.11.2.2.36.1.63
lcsSetupWanL2tpAdditionalGatewaysEntryGateway31 OBJECT-TYPE
    SYNTAX     DisplayString (SIZE(0..64))
    MAX-ACCESS read-write
    STATUS     current
    DESCRIPTION
            "-- empty --"
    ::= { lcsSetupWanL2tpAdditionalGatewaysEntry 63 }

-- {COLUMN} 1.3.6.1.4.1.2356.11.2.2.36.1.64
lcsSetupWanL2tpAdditionalGatewaysEntryRtgTag31 OBJECT-TYPE
    SYNTAX     Integer32 (0..65535)
    MAX-ACCESS read-write
    STATUS     current
    DESCRIPTION
            "-- empty --"
    ::= { lcsSetupWanL2tpAdditionalGatewaysEntry 64 }

-- {COLUMN} 1.3.6.1.4.1.2356.11.2.2.36.1.65
lcsSetupWanL2tpAdditionalGatewaysEntryGateway32 OBJECT-TYPE
    SYNTAX     DisplayString (SIZE(0..64))
    MAX-ACCESS read-write
    STATUS     current
    DESCRIPTION
            "-- empty --"
    ::= { lcsSetupWanL2tpAdditionalGatewaysEntry 65 }

-- {COLUMN} 1.3.6.1.4.1.2356.11.2.2.36.1.66
lcsSetupWanL2tpAdditionalGatewaysEntryRtgTag32 OBJECT-TYPE
    SYNTAX     Integer32 (0..65535)
    MAX-ACCESS read-write
    STATUS     current
    DESCRIPTION
            "-- empty --"
    ::= { lcsSetupWanL2tpAdditionalGatewaysEntry 66 }

-- {COLUMN} 1.3.6.1.4.1.2356.11.2.2.36.1.67
lcsSetupWanL2tpAdditionalGatewaysEntryDefaultPrio OBJECT-TYPE
    SYNTAX     Integer32 (0..65535)
    MAX-ACCESS read-write
    STATUS     current
    DESCRIPTION
            "-- empty --"
    ::= { lcsSetupWanL2tpAdditionalGatewaysEntry 67 }

-- {TABLE} 1.3.6.1.4.1.2356.11.2.2.37
lcsSetupWanL2tpPeersTable OBJECT-TYPE
    SYNTAX     SEQUENCE OF LcsSetupWanL2tpPeersEntry
    MAX-ACCESS not-accessible
    STATUS     current
    DESCRIPTION
            "-- empty --"
    ::= { lcsSetupWan 37 }

-- {ROW} 1.3.6.1.4.1.2356.11.2.2.37.1
lcsSetupWanL2tpPeersEntry OBJECT-TYPE
    SYNTAX     LcsSetupWanL2tpPeersEntry
    MAX-ACCESS not-accessible
    STATUS     current
    DESCRIPTION
            ""
    INDEX {
            lcsSetupWanL2tpPeersEntryPeer
          }
    ::= { lcsSetupWanL2tpPeersTable 1 }

LcsSetupWanL2tpPeersEntry ::= SEQUENCE {
            lcsSetupWanL2tpPeersEntryPeer DisplayString,
            lcsSetupWanL2tpPeersEntryL2tpEndpoint DisplayString,
            lcsSetupWanL2tpPeersEntryShTime Integer32,
            lcsSetupWanL2tpPeersEntryIpv4 DisplayString,
            lcsSetupWanL2tpPeersEntryIpv6 DisplayString
    }

-- {COLUMN} 1.3.6.1.4.1.2356.11.2.2.37.1.1
lcsSetupWanL2tpPeersEntryPeer OBJECT-TYPE
    SYNTAX     DisplayString (SIZE(0..16))
    MAX-ACCESS read-write
    STATUS     current
    DESCRIPTION
            "-- empty --"
    ::= { lcsSetupWanL2tpPeersEntry 1 }

-- {COLUMN} 1.3.6.1.4.1.2356.11.2.2.37.1.2
lcsSetupWanL2tpPeersEntryL2tpEndpoint OBJECT-TYPE
    SYNTAX     DisplayString (SIZE(0..16))
    MAX-ACCESS read-write
    STATUS     current
    DESCRIPTION
            "-- empty --"
    ::= { lcsSetupWanL2tpPeersEntry 2 }

-- {COLUMN} 1.3.6.1.4.1.2356.11.2.2.37.1.3
lcsSetupWanL2tpPeersEntryShTime OBJECT-TYPE
    SYNTAX     Integer32 (0..65535)
    MAX-ACCESS read-write
    STATUS     current
    DESCRIPTION
            "-- empty --"
    ::= { lcsSetupWanL2tpPeersEntry 3 }

-- {COLUMN} 1.3.6.1.4.1.2356.11.2.2.37.1.4
lcsSetupWanL2tpPeersEntryIpv4 OBJECT-TYPE
    SYNTAX     DisplayString (SIZE(0..16))
    MAX-ACCESS read-write
    STATUS     current
    DESCRIPTION
            "-- empty --"
    ::= { lcsSetupWanL2tpPeersEntry 4 }

-- {COLUMN} 1.3.6.1.4.1.2356.11.2.2.37.1.5
lcsSetupWanL2tpPeersEntryIpv6 OBJECT-TYPE
    SYNTAX     DisplayString (SIZE(0..16))
    MAX-ACCESS read-write
    STATUS     current
    DESCRIPTION
            "-- empty --"
    ::= { lcsSetupWanL2tpPeersEntry 5 }

-- {SCALAR} 1.3.6.1.4.1.2356.11.2.2.38
lcsSetupWanL2tpSourceCheck OBJECT-TYPE
    SYNTAX     INTEGER {
                  eAddress (0),
                  eTagPlusAddress (1)
            }
    MAX-ACCESS read-write
    STATUS     current
    DESCRIPTION
            "-- empty --"
    ::= { lcsSetupWan 38 }

-- {TABLE} 1.3.6.1.4.1.2356.11.2.2.39
lcsSetupWanL2tpEthernetTable OBJECT-TYPE
    SYNTAX     SEQUENCE OF LcsSetupWanL2tpEthernetEntry
    MAX-ACCESS not-accessible
    STATUS     current
    DESCRIPTION
            "-- empty --"
    ::= { lcsSetupWan 39 }

-- {ROW} 1.3.6.1.4.1.2356.11.2.2.39.1
lcsSetupWanL2tpEthernetEntry OBJECT-TYPE
    SYNTAX     LcsSetupWanL2tpEthernetEntry
    MAX-ACCESS not-accessible
    STATUS     current
    DESCRIPTION
            ""
    INDEX {
            lcsSetupWanL2tpEthernetEntryRemoteEnd,
            lcsSetupWanL2tpEthernetEntryL2tpEndpoint
          }
    ::= { lcsSetupWanL2tpEthernetTable 1 }

LcsSetupWanL2tpEthernetEntry ::= SEQUENCE {
            lcsSetupWanL2tpEthernetEntryRemoteEnd DisplayString,
            lcsSetupWanL2tpEthernetEntryL2tpEndpoint DisplayString,
            lcsSetupWanL2tpEthernetEntryInterface INTEGER
    }

-- {COLUMN} 1.3.6.1.4.1.2356.11.2.2.39.1.1
lcsSetupWanL2tpEthernetEntryRemoteEnd OBJECT-TYPE
    SYNTAX     DisplayString (SIZE(0..32))
    MAX-ACCESS read-write
    STATUS     current
    DESCRIPTION
            "-- empty --"
    ::= { lcsSetupWanL2tpEthernetEntry 1 }

-- {COLUMN} 1.3.6.1.4.1.2356.11.2.2.39.1.2
lcsSetupWanL2tpEthernetEntryL2tpEndpoint OBJECT-TYPE
    SYNTAX     DisplayString (SIZE(0..16))
    MAX-ACCESS read-write
    STATUS     current
    DESCRIPTION
            "-- empty --"
    ::= { lcsSetupWanL2tpEthernetEntry 2 }

-- {COLUMN} 1.3.6.1.4.1.2356.11.2.2.39.1.3
lcsSetupWanL2tpEthernetEntryInterface OBJECT-TYPE
    SYNTAX     INTEGER {
                  eL2tpEthernet1 (0),
                  eL2tpEthernet2 (1),
                  eL2tpEthernet3 (2),
                  eL2tpEthernet4 (3),
                  eL2tpEthernet5 (4),
                  eL2tpEthernet6 (5),
                  eL2tpEthernet7 (6),
                  eL2tpEthernet8 (7),
                  eL2tpEthernet9 (8),
                  eL2tpEthernet10 (9),
                  eL2tpEthernet11 (10),
                  eL2tpEthernet12 (11),
                  eL2tpEthernet13 (12),
                  eL2tpEthernet14 (13),
                  eL2tpEthernet15 (14),
                  eL2tpEthernet16 (15)
            }
    MAX-ACCESS read-write
    STATUS     current
    DESCRIPTION
            "-- empty --"
    ::= { lcsSetupWanL2tpEthernetEntry 3 }

-- {TABLE} 1.3.6.1.4.1.2356.11.2.2.40
lcsSetupWanDsLiteTunnelTable OBJECT-TYPE
    SYNTAX     SEQUENCE OF LcsSetupWanDsLiteTunnelEntry
    MAX-ACCESS not-accessible
    STATUS     current
    DESCRIPTION
            "-- empty --"
    ::= { lcsSetupWan 40 }

-- {ROW} 1.3.6.1.4.1.2356.11.2.2.40.1
lcsSetupWanDsLiteTunnelEntry OBJECT-TYPE
    SYNTAX     LcsSetupWanDsLiteTunnelEntry
    MAX-ACCESS not-accessible
    STATUS     current
    DESCRIPTION
            ""
    INDEX {
            lcsSetupWanDsLiteTunnelEntryName
          }
    ::= { lcsSetupWanDsLiteTunnelTable 1 }

LcsSetupWanDsLiteTunnelEntry ::= SEQUENCE {
            lcsSetupWanDsLiteTunnelEntryName DisplayString,
            lcsSetupWanDsLiteTunnelEntryGatewayAddress DisplayString,
            lcsSetupWanDsLiteTunnelEntryRtgTag Integer32,
            lcsSetupWanDsLiteTunnelEntryIpv4 DisplayString
    }

-- {COLUMN} 1.3.6.1.4.1.2356.11.2.2.40.1.1
lcsSetupWanDsLiteTunnelEntryName OBJECT-TYPE
    SYNTAX     DisplayString (SIZE(0..16))
    MAX-ACCESS read-write
    STATUS     current
    DESCRIPTION
            "-- empty --"
    ::= { lcsSetupWanDsLiteTunnelEntry 1 }

-- {COLUMN} 1.3.6.1.4.1.2356.11.2.2.40.1.2
lcsSetupWanDsLiteTunnelEntryGatewayAddress OBJECT-TYPE
    SYNTAX     DisplayString (SIZE(0..64))
    MAX-ACCESS read-write
    STATUS     current
    DESCRIPTION
            "-- empty --"
    ::= { lcsSetupWanDsLiteTunnelEntry 2 }

-- {COLUMN} 1.3.6.1.4.1.2356.11.2.2.40.1.3
lcsSetupWanDsLiteTunnelEntryRtgTag OBJECT-TYPE
    SYNTAX     Integer32 (0..65535)
    MAX-ACCESS read-write
    STATUS     current
    DESCRIPTION
            "-- empty --"
    ::= { lcsSetupWanDsLiteTunnelEntry 3 }

-- {COLUMN} 1.3.6.1.4.1.2356.11.2.2.40.1.4
lcsSetupWanDsLiteTunnelEntryIpv4 OBJECT-TYPE
    SYNTAX     DisplayString (SIZE(0..16))
    MAX-ACCESS read-write
    STATUS     current
    DESCRIPTION
            "-- empty --"
    ::= { lcsSetupWanDsLiteTunnelEntry 4 }

-- {NODE} 1.3.6.1.4.1.2356.11.2.2.45
lcsSetupWanX25Bridge OBJECT IDENTIFIER ::= { lcsSetupWan 45 }

-- {TABLE} 1.3.6.1.4.1.2356.11.2.2.45.2
lcsSetupWanX25BridgeOutgoingCallsTable OBJECT-TYPE
    SYNTAX     SEQUENCE OF LcsSetupWanX25BridgeOutgoingCallsEntry
    MAX-ACCESS not-accessible
    STATUS     current
    DESCRIPTION
            "-- empty --"
    ::= { lcsSetupWanX25Bridge 2 }

-- {ROW} 1.3.6.1.4.1.2356.11.2.2.45.2.1
lcsSetupWanX25BridgeOutgoingCallsEntry OBJECT-TYPE
    SYNTAX     LcsSetupWanX25BridgeOutgoingCallsEntry
    MAX-ACCESS not-accessible
    STATUS     current
    DESCRIPTION
            ""
    INDEX {
            lcsSetupWanX25BridgeOutgoingCallsEntryName
          }
    ::= { lcsSetupWanX25BridgeOutgoingCallsTable 1 }

LcsSetupWanX25BridgeOutgoingCallsEntry ::= SEQUENCE {
            lcsSetupWanX25BridgeOutgoingCallsEntryName DisplayString,
            lcsSetupWanX25BridgeOutgoingCallsEntryPrio Integer32,
            lcsSetupWanX25BridgeOutgoingCallsEntryTerminalIp IpAddress,
            lcsSetupWanX25BridgeOutgoingCallsEntryTerminalPort Integer32,
            lcsSetupWanX25BridgeOutgoingCallsEntryLoopbackAddress DisplayString,
            lcsSetupWanX25BridgeOutgoingCallsEntryLocalPort Integer32,
            lcsSetupWanX25BridgeOutgoingCallsEntryIsdnRemote DisplayString,
            lcsSetupWanX25BridgeOutgoingCallsEntryIsdnLocal DisplayString,
            lcsSetupWanX25BridgeOutgoingCallsEntryX25Remote DisplayString,
            lcsSetupWanX25BridgeOutgoingCallsEntryX25Local DisplayString,
            lcsSetupWanX25BridgeOutgoingCallsEntryProtocolId Integer32,
            lcsSetupWanX25BridgeOutgoingCallsEntryUserdata DisplayString,
            lcsSetupWanX25BridgeOutgoingCallsEntryPayloadSize Integer32
    }

-- {COLUMN} 1.3.6.1.4.1.2356.11.2.2.45.2.1.1
lcsSetupWanX25BridgeOutgoingCallsEntryName OBJECT-TYPE
    SYNTAX     DisplayString (SIZE(0..16))
    MAX-ACCESS read-write
    STATUS     current
    DESCRIPTION
            "-- empty --"
    ::= { lcsSetupWanX25BridgeOutgoingCallsEntry 1 }

-- {COLUMN} 1.3.6.1.4.1.2356.11.2.2.45.2.1.2
lcsSetupWanX25BridgeOutgoingCallsEntryPrio OBJECT-TYPE
    SYNTAX     Integer32 (0..65535)
    MAX-ACCESS read-write
    STATUS     current
    DESCRIPTION
            "-- empty --"
    ::= { lcsSetupWanX25BridgeOutgoingCallsEntry 2 }

-- {COLUMN} 1.3.6.1.4.1.2356.11.2.2.45.2.1.3
lcsSetupWanX25BridgeOutgoingCallsEntryTerminalIp OBJECT-TYPE
    SYNTAX     IpAddress
    MAX-ACCESS read-write
    STATUS     current
    DESCRIPTION
            "-- empty --"
    ::= { lcsSetupWanX25BridgeOutgoingCallsEntry 3 }

-- {COLUMN} 1.3.6.1.4.1.2356.11.2.2.45.2.1.4
lcsSetupWanX25BridgeOutgoingCallsEntryTerminalPort OBJECT-TYPE
    SYNTAX     Integer32 (0..65535)
    MAX-ACCESS read-write
    STATUS     current
    DESCRIPTION
            "-- empty --"
    ::= { lcsSetupWanX25BridgeOutgoingCallsEntry 4 }

-- {COLUMN} 1.3.6.1.4.1.2356.11.2.2.45.2.1.5
lcsSetupWanX25BridgeOutgoingCallsEntryLoopbackAddress OBJECT-TYPE
    SYNTAX     DisplayString (SIZE(0..39))
    MAX-ACCESS read-write
    STATUS     current
    DESCRIPTION
            "-- empty --"
    ::= { lcsSetupWanX25BridgeOutgoingCallsEntry 5 }

-- {COLUMN} 1.3.6.1.4.1.2356.11.2.2.45.2.1.6
lcsSetupWanX25BridgeOutgoingCallsEntryLocalPort OBJECT-TYPE
    SYNTAX     Integer32 (0..65535)
    MAX-ACCESS read-write
    STATUS     current
    DESCRIPTION
            "-- empty --"
    ::= { lcsSetupWanX25BridgeOutgoingCallsEntry 6 }

-- {COLUMN} 1.3.6.1.4.1.2356.11.2.2.45.2.1.7
lcsSetupWanX25BridgeOutgoingCallsEntryIsdnRemote OBJECT-TYPE
    SYNTAX     DisplayString (SIZE(0..21))
    MAX-ACCESS read-write
    STATUS     current
    DESCRIPTION
            "-- empty --"
    ::= { lcsSetupWanX25BridgeOutgoingCallsEntry 7 }

-- {COLUMN} 1.3.6.1.4.1.2356.11.2.2.45.2.1.8
lcsSetupWanX25BridgeOutgoingCallsEntryIsdnLocal OBJECT-TYPE
    SYNTAX     DisplayString (SIZE(0..21))
    MAX-ACCESS read-write
    STATUS     current
    DESCRIPTION
            "-- empty --"
    ::= { lcsSetupWanX25BridgeOutgoingCallsEntry 8 }

-- {COLUMN} 1.3.6.1.4.1.2356.11.2.2.45.2.1.9
lcsSetupWanX25BridgeOutgoingCallsEntryX25Remote OBJECT-TYPE
    SYNTAX     DisplayString (SIZE(0..14))
    MAX-ACCESS read-write
    STATUS     current
    DESCRIPTION
            "-- empty --"
    ::= { lcsSetupWanX25BridgeOutgoingCallsEntry 9 }

-- {COLUMN} 1.3.6.1.4.1.2356.11.2.2.45.2.1.10
lcsSetupWanX25BridgeOutgoingCallsEntryX25Local OBJECT-TYPE
    SYNTAX     DisplayString (SIZE(0..14))
    MAX-ACCESS read-write
    STATUS     current
    DESCRIPTION
            "-- empty --"
    ::= { lcsSetupWanX25BridgeOutgoingCallsEntry 10 }

-- {COLUMN} 1.3.6.1.4.1.2356.11.2.2.45.2.1.11
lcsSetupWanX25BridgeOutgoingCallsEntryProtocolId OBJECT-TYPE
    SYNTAX     Integer32 (0..2147483647)
    MAX-ACCESS read-write
    STATUS     current
    DESCRIPTION
            "-- empty --"
    ::= { lcsSetupWanX25BridgeOutgoingCallsEntry 11 }

-- {COLUMN} 1.3.6.1.4.1.2356.11.2.2.45.2.1.12
lcsSetupWanX25BridgeOutgoingCallsEntryUserdata OBJECT-TYPE
    SYNTAX     DisplayString (SIZE(0..8))
    MAX-ACCESS read-write
    STATUS     current
    DESCRIPTION
            "-- empty --"
    ::= { lcsSetupWanX25BridgeOutgoingCallsEntry 12 }

-- {COLUMN} 1.3.6.1.4.1.2356.11.2.2.45.2.1.13
lcsSetupWanX25BridgeOutgoingCallsEntryPayloadSize OBJECT-TYPE
    SYNTAX     Integer32 (0..2147483647)
    MAX-ACCESS read-write
    STATUS     current
    DESCRIPTION
            "-- empty --"
    ::= { lcsSetupWanX25BridgeOutgoingCallsEntry 13 }

-- {SCALAR} 1.3.6.1.4.1.2356.11.2.2.45.4
lcsSetupWanX25BridgeDisconnectDelay OBJECT-TYPE
    SYNTAX     Integer32 (0..2147483647)
    MAX-ACCESS read-write
    STATUS     current
    DESCRIPTION
            "-- empty --"
    ::= { lcsSetupWanX25Bridge 4 }

-- {SCALAR} 1.3.6.1.4.1.2356.11.2.2.45.5
lcsSetupWanX25BridgeDataTrace OBJECT-TYPE
    SYNTAX     INTEGER {
                  eOff (0),
                  eOn (1),
                  eExtended (2)
            }
    MAX-ACCESS read-write
    STATUS     current
    DESCRIPTION
            "-- empty --"
    ::= { lcsSetupWanX25Bridge 5 }

-- {TABLE} 1.3.6.1.4.1.2356.11.2.2.50
lcsSetupWanEogreTunnelTable OBJECT-TYPE
    SYNTAX     SEQUENCE OF LcsSetupWanEogreTunnelEntry
    MAX-ACCESS not-accessible
    STATUS     current
    DESCRIPTION
            "-- empty --"
    ::= { lcsSetupWan 50 }

-- {ROW} 1.3.6.1.4.1.2356.11.2.2.50.1
lcsSetupWanEogreTunnelEntry OBJECT-TYPE
    SYNTAX     LcsSetupWanEogreTunnelEntry
    MAX-ACCESS not-accessible
    STATUS     current
    DESCRIPTION
            ""
    INDEX {
            lcsSetupWanEogreTunnelEntryPort
          }
    ::= { lcsSetupWanEogreTunnelTable 1 }

LcsSetupWanEogreTunnelEntry ::= SEQUENCE {
            lcsSetupWanEogreTunnelEntryPort DisplayString,
            lcsSetupWanEogreTunnelEntryActive INTEGER,
            lcsSetupWanEogreTunnelEntryRemoteEndpointAddress DisplayString,
            lcsSetupWanEogreTunnelEntryRtgTag Integer32,
            lcsSetupWanEogreTunnelEntryKeyPresent INTEGER,
            lcsSetupWanEogreTunnelEntryKeyValue Integer32,
            lcsSetupWanEogreTunnelEntryChecksum INTEGER,
            lcsSetupWanEogreTunnelEntrySequencing INTEGER,
            lcsSetupWanEogreTunnelEntryLoopbackAddress DisplayString
    }

-- {COLUMN} 1.3.6.1.4.1.2356.11.2.2.50.1.1
lcsSetupWanEogreTunnelEntryPort OBJECT-TYPE
    SYNTAX     DisplayString (SIZE(0..15))
    MAX-ACCESS read-only
    STATUS     current
    DESCRIPTION
            "-- empty --"
    ::= { lcsSetupWanEogreTunnelEntry 1 }

-- {COLUMN} 1.3.6.1.4.1.2356.11.2.2.50.1.2
lcsSetupWanEogreTunnelEntryActive OBJECT-TYPE
    SYNTAX     INTEGER {
                  eNo (0),
                  eYes (1)
            }
    MAX-ACCESS read-write
    STATUS     current
    DESCRIPTION
            "-- empty --"
    ::= { lcsSetupWanEogreTunnelEntry 2 }

-- {COLUMN} 1.3.6.1.4.1.2356.11.2.2.50.1.3
lcsSetupWanEogreTunnelEntryRemoteEndpointAddress OBJECT-TYPE
    SYNTAX     DisplayString (SIZE(0..64))
    MAX-ACCESS read-write
    STATUS     current
    DESCRIPTION
            "-- empty --"
    ::= { lcsSetupWanEogreTunnelEntry 3 }

-- {COLUMN} 1.3.6.1.4.1.2356.11.2.2.50.1.4
lcsSetupWanEogreTunnelEntryRtgTag OBJECT-TYPE
    SYNTAX     Integer32 (0..2147483647)
    MAX-ACCESS read-write
    STATUS     current
    DESCRIPTION
            "-- empty --"
    ::= { lcsSetupWanEogreTunnelEntry 4 }

-- {COLUMN} 1.3.6.1.4.1.2356.11.2.2.50.1.5
lcsSetupWanEogreTunnelEntryKeyPresent OBJECT-TYPE
    SYNTAX     INTEGER {
                  eNo (0),
                  eYes (1)
            }
    MAX-ACCESS read-write
    STATUS     current
    DESCRIPTION
            "-- empty --"
    ::= { lcsSetupWanEogreTunnelEntry 5 }

-- {COLUMN} 1.3.6.1.4.1.2356.11.2.2.50.1.6
lcsSetupWanEogreTunnelEntryKeyValue OBJECT-TYPE
    SYNTAX     Integer32 (0..2147483647)
    MAX-ACCESS read-write
    STATUS     current
    DESCRIPTION
            "-- empty --"
    ::= { lcsSetupWanEogreTunnelEntry 6 }

-- {COLUMN} 1.3.6.1.4.1.2356.11.2.2.50.1.7
lcsSetupWanEogreTunnelEntryChecksum OBJECT-TYPE
    SYNTAX     INTEGER {
                  eNo (0),
                  eYes (1)
            }
    MAX-ACCESS read-write
    STATUS     current
    DESCRIPTION
            "-- empty --"
    ::= { lcsSetupWanEogreTunnelEntry 7 }

-- {COLUMN} 1.3.6.1.4.1.2356.11.2.2.50.1.8
lcsSetupWanEogreTunnelEntrySequencing OBJECT-TYPE
    SYNTAX     INTEGER {
                  eNo (0),
                  eYes (1)
            }
    MAX-ACCESS read-write
    STATUS     current
    DESCRIPTION
            "-- empty --"
    ::= { lcsSetupWanEogreTunnelEntry 8 }

-- {COLUMN} 1.3.6.1.4.1.2356.11.2.2.50.1.9
lcsSetupWanEogreTunnelEntryLoopbackAddress OBJECT-TYPE
    SYNTAX     DisplayString (SIZE(0..16))
    MAX-ACCESS read-write
    STATUS     current
    DESCRIPTION
            "-- empty --"
    ::= { lcsSetupWanEogreTunnelEntry 9 }

-- {TABLE} 1.3.6.1.4.1.2356.11.2.2.51
lcsSetupWanGreTunnelTable OBJECT-TYPE
    SYNTAX     SEQUENCE OF LcsSetupWanGreTunnelEntry
    MAX-ACCESS not-accessible
    STATUS     current
    DESCRIPTION
            "-- empty --"
    ::= { lcsSetupWan 51 }

-- {ROW} 1.3.6.1.4.1.2356.11.2.2.51.1
lcsSetupWanGreTunnelEntry OBJECT-TYPE
    SYNTAX     LcsSetupWanGreTunnelEntry
    MAX-ACCESS not-accessible
    STATUS     current
    DESCRIPTION
            ""
    INDEX {
            lcsSetupWanGreTunnelEntryPeer
          }
    ::= { lcsSetupWanGreTunnelTable 1 }

LcsSetupWanGreTunnelEntry ::= SEQUENCE {
            lcsSetupWanGreTunnelEntryPeer DisplayString,
            lcsSetupWanGreTunnelEntryIpAddress DisplayString,
            lcsSetupWanGreTunnelEntryRtgTag Integer32,
            lcsSetupWanGreTunnelEntryKeyPresent INTEGER,
            lcsSetupWanGreTunnelEntryKeyValue Integer32,
            lcsSetupWanGreTunnelEntryChecksum INTEGER,
            lcsSetupWanGreTunnelEntrySequencing INTEGER,
            lcsSetupWanGreTunnelEntryLoopbackAddress DisplayString,
            lcsSetupWanGreTunnelEntryIpv4 DisplayString,
            lcsSetupWanGreTunnelEntryIpv6 DisplayString
    }

-- {COLUMN} 1.3.6.1.4.1.2356.11.2.2.51.1.1
lcsSetupWanGreTunnelEntryPeer OBJECT-TYPE
    SYNTAX     DisplayString (SIZE(0..16))
    MAX-ACCESS read-write
    STATUS     current
    DESCRIPTION
            "-- empty --"
    ::= { lcsSetupWanGreTunnelEntry 1 }

-- {COLUMN} 1.3.6.1.4.1.2356.11.2.2.51.1.3
lcsSetupWanGreTunnelEntryIpAddress OBJECT-TYPE
    SYNTAX     DisplayString (SIZE(0..64))
    MAX-ACCESS read-write
    STATUS     current
    DESCRIPTION
            "-- empty --"
    ::= { lcsSetupWanGreTunnelEntry 3 }

-- {COLUMN} 1.3.6.1.4.1.2356.11.2.2.51.1.4
lcsSetupWanGreTunnelEntryRtgTag OBJECT-TYPE
    SYNTAX     Integer32 (0..2147483647)
    MAX-ACCESS read-write
    STATUS     current
    DESCRIPTION
            "-- empty --"
    ::= { lcsSetupWanGreTunnelEntry 4 }

-- {COLUMN} 1.3.6.1.4.1.2356.11.2.2.51.1.5
lcsSetupWanGreTunnelEntryKeyPresent OBJECT-TYPE
    SYNTAX     INTEGER {
                  eNo (0),
                  eYes (1)
            }
    MAX-ACCESS read-write
    STATUS     current
    DESCRIPTION
            "-- empty --"
    ::= { lcsSetupWanGreTunnelEntry 5 }

-- {COLUMN} 1.3.6.1.4.1.2356.11.2.2.51.1.6
lcsSetupWanGreTunnelEntryKeyValue OBJECT-TYPE
    SYNTAX     Integer32 (0..2147483647)
    MAX-ACCESS read-write
    STATUS     current
    DESCRIPTION
            "-- empty --"
    ::= { lcsSetupWanGreTunnelEntry 6 }

-- {COLUMN} 1.3.6.1.4.1.2356.11.2.2.51.1.7
lcsSetupWanGreTunnelEntryChecksum OBJECT-TYPE
    SYNTAX     INTEGER {
                  eNo (0),
                  eYes (1)
            }
    MAX-ACCESS read-write
    STATUS     current
    DESCRIPTION
            "-- empty --"
    ::= { lcsSetupWanGreTunnelEntry 7 }

-- {COLUMN} 1.3.6.1.4.1.2356.11.2.2.51.1.8
lcsSetupWanGreTunnelEntrySequencing OBJECT-TYPE
    SYNTAX     INTEGER {
                  eNo (0),
                  eYes (1)
            }
    MAX-ACCESS read-write
    STATUS     current
    DESCRIPTION
            "-- empty --"
    ::= { lcsSetupWanGreTunnelEntry 8 }

-- {COLUMN} 1.3.6.1.4.1.2356.11.2.2.51.1.9
lcsSetupWanGreTunnelEntryLoopbackAddress OBJECT-TYPE
    SYNTAX     DisplayString (SIZE(0..16))
    MAX-ACCESS read-write
    STATUS     current
    DESCRIPTION
            "-- empty --"
    ::= { lcsSetupWanGreTunnelEntry 9 }

-- {COLUMN} 1.3.6.1.4.1.2356.11.2.2.51.1.10
lcsSetupWanGreTunnelEntryIpv4 OBJECT-TYPE
    SYNTAX     DisplayString (SIZE(0..16))
    MAX-ACCESS read-write
    STATUS     current
    DESCRIPTION
            "-- empty --"
    ::= { lcsSetupWanGreTunnelEntry 10 }

-- {COLUMN} 1.3.6.1.4.1.2356.11.2.2.51.1.11
lcsSetupWanGreTunnelEntryIpv6 OBJECT-TYPE
    SYNTAX     DisplayString (SIZE(0..16))
    MAX-ACCESS read-write
    STATUS     current
    DESCRIPTION
            "-- empty --"
    ::= { lcsSetupWanGreTunnelEntry 11 }

-- {NODE} 1.3.6.1.4.1.2356.11.2.2.53
lcsSetupWanSslForActionTable OBJECT IDENTIFIER ::= { lcsSetupWan 53 }

-- {SCALAR} 1.3.6.1.4.1.2356.11.2.2.53.1
lcsSetupWanSslForActionTableVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupWanSslForActionTable 1 }

-- {SCALAR} 1.3.6.1.4.1.2356.11.2.2.53.2
lcsSetupWanSslForActionTableKeyexAlgorithms OBJECT-TYPE
    SYNTAX     BITS {
                  eEcdhe (27),
                  eDhe (29),
                  eRsa (31)
            }
    MAX-ACCESS read-write
    STATUS     current
    DESCRIPTION
            "-- empty --"
    ::= { lcsSetupWanSslForActionTable 2 }

-- {SCALAR} 1.3.6.1.4.1.2356.11.2.2.53.3
lcsSetupWanSslForActionTableCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupWanSslForActionTable 3 }

-- {SCALAR} 1.3.6.1.4.1.2356.11.2.2.53.4
lcsSetupWanSslForActionTableHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupWanSslForActionTable 4 }

-- {SCALAR} 1.3.6.1.4.1.2356.11.2.2.53.5
lcsSetupWanSslForActionTablePreferPfs OBJECT-TYPE
    SYNTAX     BITS {
                  eNo (0),
                  eYes (7)
            }
    MAX-ACCESS read-write
    STATUS     current
    DESCRIPTION
            "-- empty --"
    ::= { lcsSetupWanSslForActionTable 5 }

-- {SCALAR} 1.3.6.1.4.1.2356.11.2.2.53.6
lcsSetupWanSslForActionTableRenegotiations OBJECT-TYPE
    SYNTAX     INTEGER {
                  eForbidden (0),
                  eAllowed (1),
                  eIgnored (2)
            }
    MAX-ACCESS read-write
    STATUS     current
    DESCRIPTION
            "-- empty --"
    ::= { lcsSetupWanSslForActionTable 6 }

-- {SCALAR} 1.3.6.1.4.1.2356.11.2.2.53.7
lcsSetupWanSslForActionTableEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupWanSslForActionTable 7 }

-- {SCALAR} 1.3.6.1.4.1.2356.11.2.2.53.21
lcsSetupWanSslForActionTableSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupWanSslForActionTable 21 }

-- {NODE} 1.3.6.1.4.1.2356.11.2.2.60
lcsSetupWanVlans OBJECT IDENTIFIER ::= { lcsSetupWan 60 }

-- {TABLE} 1.3.6.1.4.1.2356.11.2.2.60.1
lcsSetupWanVlansProviderListTable OBJECT-TYPE
    SYNTAX     SEQUENCE OF LcsSetupWanVlansProviderListEntry
    MAX-ACCESS not-accessible
    STATUS     current
    DESCRIPTION
            "-- empty --"
    ::= { lcsSetupWanVlans 1 }

-- {ROW} 1.3.6.1.4.1.2356.11.2.2.60.1.1
lcsSetupWanVlansProviderListEntry OBJECT-TYPE
    SYNTAX     LcsSetupWanVlansProviderListEntry
    MAX-ACCESS not-accessible
    STATUS     current
    DESCRIPTION
            ""
    INDEX {
            lcsSetupWanVlansProviderListEntryProvider
          }
    ::= { lcsSetupWanVlansProviderListTable 1 }

LcsSetupWanVlansProviderListEntry ::= SEQUENCE {
            lcsSetupWanVlansProviderListEntryProvider DisplayString,
            lcsSetupWanVlansProviderListEntryVlanIds DisplayString
    }

-- {COLUMN} 1.3.6.1.4.1.2356.11.2.2.60.1.1.1
lcsSetupWanVlansProviderListEntryProvider OBJECT-TYPE
    SYNTAX     DisplayString (SIZE(0..64))
    MAX-ACCESS read-write
    STATUS     current
    DESCRIPTION
            "-- empty --"
    ::= { lcsSetupWanVlansProviderListEntry 1 }

-- {COLUMN} 1.3.6.1.4.1.2356.11.2.2.60.1.1.2
lcsSetupWanVlansProviderListEntryVlanIds OBJECT-TYPE
    SYNTAX     DisplayString (SIZE(0..32))
    MAX-ACCESS read-write
    STATUS     current
    DESCRIPTION
            "-- empty --"
    ::= { lcsSetupWanVlansProviderListEntry 2 }

-- {TABLE} 1.3.6.1.4.1.2356.11.2.2.62
lcsSetupWanProviderSpecificsTable OBJECT-TYPE
    SYNTAX     SEQUENCE OF LcsSetupWanProviderSpecificsEntry
    MAX-ACCESS not-accessible
    STATUS     current
    DESCRIPTION
            "-- empty --"
    ::= { lcsSetupWan 62 }

-- {ROW} 1.3.6.1.4.1.2356.11.2.2.62.1
lcsSetupWanProviderSpecificsEntry OBJECT-TYPE
    SYNTAX     LcsSetupWanProviderSpecificsEntry
    MAX-ACCESS not-accessible
    STATUS     current
    DESCRIPTION
            ""
    INDEX {
            lcsSetupWanProviderSpecificsEntryProvider
          }
    ::= { lcsSetupWanProviderSpecificsTable 1 }

LcsSetupWanProviderSpecificsEntry ::= SEQUENCE {
            lcsSetupWanProviderSpecificsEntryProvider DisplayString,
            lcsSetupWanProviderSpecificsEntryParameterFormat DisplayString
    }

-- {COLUMN} 1.3.6.1.4.1.2356.11.2.2.62.1.1
lcsSetupWanProviderSpecificsEntryProvider OBJECT-TYPE
    SYNTAX     DisplayString (SIZE(0..64))
    MAX-ACCESS read-write
    STATUS     current
    DESCRIPTION
            "-- empty --"
    ::= { lcsSetupWanProviderSpecificsEntry 1 }

-- {COLUMN} 1.3.6.1.4.1.2356.11.2.2.62.1.2
lcsSetupWanProviderSpecificsEntryParameterFormat OBJECT-TYPE
    SYNTAX     DisplayString (SIZE(0..250))
    MAX-ACCESS read-write
    STATUS     current
    DESCRIPTION
            "-- empty --"
    ::= { lcsSetupWanProviderSpecificsEntry 2 }

-- {SCALAR} 1.3.6.1.4.1.2356.11.2.2.70
lcsSetupWanMaxWanQueueLength OBJECT-TYPE
    SYNTAX     Integer32 (0..2147483647)
    MAX-ACCESS read-write
    STATUS     current
    DESCRIPTION
            "-- empty --"
    ::= { lcsSetupWan 70 }

-- {NODE} 1.3.6.1.4.1.2356.11.2.3
lcsSetupCharges OBJECT IDENTIFIER ::= { lcsSetup 3 }

-- {SCALAR} 1.3.6.1.4.1.2356.11.2.3.1
lcsSetupChargesBudgetUnits OBJECT-TYPE
    SYNTAX     Integer32 (0..65535)
    MAX-ACCESS read-write
    STATUS     current
    DESCRIPTION
            ""
    ::= { lcsSetupCharges 1 }

-- {SCALAR} 1.3.6.1.4.1.2356.11.2.3.2
lcsSetupChargesDaysPerPeriod OBJECT-TYPE
    SYNTAX     Integer32 (0..65535)
    MAX-ACCESS read-write
    STATUS     current
    DESCRIPTION
            ""
    ::= { lcsSetupCharges 2 }

-- {SCALAR} 1.3.6.1.4.1.2356.11.2.3.3
lcsSetupChargesSpareUnits OBJECT-TYPE
    SYNTAX     Integer32 (0..65535)
    MAX-ACCESS read-only
    STATUS     current
    DESCRIPTION
            ""
    ::= { lcsSetupCharges 3 }

-- {SCALAR} 1.3.6.1.4.1.2356.11.2.3.4
lcsSetupChargesRouterUnits OBJECT-TYPE
    SYNTAX     Integer32 (0..2147483647)
    MAX-ACCESS read-only
    STATUS     current
    DESCRIPTION
            ""
    ::= { lcsSetupCharges 4 }

-- {TABLE} 1.3.6.1.4.1.2356.11.2.3.5
lcsSetupChargesTableBudgetTable OBJECT-TYPE
    SYNTAX     SEQUENCE OF LcsSetupChargesTableBudgetEntry
    MAX-ACCESS not-accessible
    STATUS     current
    DESCRIPTION
            ""
    ::= { lcsSetupCharges 5 }

-- {ROW} 1.3.6.1.4.1.2356.11.2.3.5.1
lcsSetupChargesTableBudgetEntry OBJECT-TYPE
    SYNTAX     LcsSetupChargesTableBudgetEntry
    MAX-ACCESS not-accessible
    STATUS     current
    DESCRIPTION
            ""
    INDEX {
            lcsSetupChargesTableBudgetEntryIfc
          }
    ::= { lcsSetupChargesTableBudgetTable 1 }

LcsSetupChargesTableBudgetEntry ::= SEQUENCE {
            lcsSetupChargesTableBudgetEntryIfc INTEGER,
            lcsSetupChargesTableBudgetEntryBudgetUnits Integer32,
            lcsSetupChargesTableBudgetEntrySpareBudget Integer32,
            lcsSetupChargesTableBudgetEntryTotalUnits Integer32
    }

-- {COLUMN} 1.3.6.1.4.1.2356.11.2.3.5.1.1
lcsSetupChargesTableBudgetEntryIfc OBJECT-TYPE
    SYNTAX     INTEGER {
                  eRouterSerial (1),
                  eLancapi (2),
                  eAb1 (3),
                  eAb2 (4),
                  eAb3 (5),
                  eAb4 (6),
                  eTimeModul (255)
            }
    MAX-ACCESS read-only
    STATUS     current
    DESCRIPTION
            ""
    ::= { lcsSetupChargesTableBudgetEntry 1 }

-- {COLUMN} 1.3.6.1.4.1.2356.11.2.3.5.1.2
lcsSetupChargesTableBudgetEntryBudgetUnits OBJECT-TYPE
    SYNTAX     Integer32 (0..65535)
    MAX-ACCESS read-only
    STATUS     current
    DESCRIPTION
            ""
    ::= { lcsSetupChargesTableBudgetEntry 2 }

-- {COLUMN} 1.3.6.1.4.1.2356.11.2.3.5.1.3
lcsSetupChargesTableBudgetEntrySpareBudget OBJECT-TYPE
    SYNTAX     Integer32 (0..65535)
    MAX-ACCESS read-only
    STATUS     current
    DESCRIPTION
            ""
    ::= { lcsSetupChargesTableBudgetEntry 3 }

-- {COLUMN} 1.3.6.1.4.1.2356.11.2.3.5.1.4
lcsSetupChargesTableBudgetEntryTotalUnits OBJECT-TYPE
    SYNTAX     Integer32 (0..2147483647)
    MAX-ACCESS read-only
    STATUS     current
    DESCRIPTION
            ""
    ::= { lcsSetupChargesTableBudgetEntry 4 }

-- {SCALAR} 1.3.6.1.4.1.2356.11.2.3.6
lcsSetupChargesTotalUnits OBJECT-TYPE
    SYNTAX     Integer32 (0..2147483647)
    MAX-ACCESS read-only
    STATUS     current
    DESCRIPTION
            ""
    ::= { lcsSetupCharges 6 }

-- {TABLE} 1.3.6.1.4.1.2356.11.2.3.7
lcsSetupChargesTimeTableTable OBJECT-TYPE
    SYNTAX     SEQUENCE OF LcsSetupChargesTimeTableEntry
    MAX-ACCESS not-accessible
    STATUS     current
    DESCRIPTION
            ""
    ::= { lcsSetupCharges 7 }

-- {ROW} 1.3.6.1.4.1.2356.11.2.3.7.1
lcsSetupChargesTimeTableEntry OBJECT-TYPE
    SYNTAX     LcsSetupChargesTimeTableEntry
    MAX-ACCESS not-accessible
    STATUS     current
    DESCRIPTION
            ""
    INDEX {
            lcsSetupChargesTimeTableEntryIfc
          }
    ::= { lcsSetupChargesTimeTableTable 1 }

LcsSetupChargesTimeTableEntry ::= SEQUENCE {
            lcsSetupChargesTimeTableEntryIfc INTEGER,
            lcsSetupChargesTimeTableEntryBudgetMinutes Integer32,
            lcsSetupChargesTimeTableEntrySpareMinutes Integer32,
            lcsSetupChargesTimeTableEntryMinutesActive Integer32,
            lcsSetupChargesTimeTableEntryMinutesPassive Integer32
    }

-- {COLUMN} 1.3.6.1.4.1.2356.11.2.3.7.1.1
lcsSetupChargesTimeTableEntryIfc OBJECT-TYPE
    SYNTAX     INTEGER {
                  eRouterDslBroadband (1),
                  eRouterSerial (2),
                  eLancapi (3),
                  eAb1 (4),
                  eAb2 (5),
                  eAb3 (6),
                  eAb4 (7),
                  eTimeModul (255)
            }
    MAX-ACCESS read-only
    STATUS     current
    DESCRIPTION
            ""
    ::= { lcsSetupChargesTimeTableEntry 1 }

-- {COLUMN} 1.3.6.1.4.1.2356.11.2.3.7.1.2
lcsSetupChargesTimeTableEntryBudgetMinutes OBJECT-TYPE
    SYNTAX     Integer32 (0..2147483647)
    MAX-ACCESS read-only
    STATUS     current
    DESCRIPTION
            ""
    ::= { lcsSetupChargesTimeTableEntry 2 }

-- {COLUMN} 1.3.6.1.4.1.2356.11.2.3.7.1.3
lcsSetupChargesTimeTableEntrySpareMinutes OBJECT-TYPE
    SYNTAX     Integer32 (0..2147483647)
    MAX-ACCESS read-only
    STATUS     current
    DESCRIPTION
            ""
    ::= { lcsSetupChargesTimeTableEntry 3 }

-- {COLUMN} 1.3.6.1.4.1.2356.11.2.3.7.1.4
lcsSetupChargesTimeTableEntryMinutesActive OBJECT-TYPE
    SYNTAX     Integer32 (0..2147483647)
    MAX-ACCESS read-only
    STATUS     current
    DESCRIPTION
            ""
    ::= { lcsSetupChargesTimeTableEntry 4 }

-- {COLUMN} 1.3.6.1.4.1.2356.11.2.3.7.1.5
lcsSetupChargesTimeTableEntryMinutesPassive OBJECT-TYPE
    SYNTAX     Integer32 (0..2147483647)
    MAX-ACCESS read-only
    STATUS     current
    DESCRIPTION
            ""
    ::= { lcsSetupChargesTimeTableEntry 5 }

-- {SCALAR} 1.3.6.1.4.1.2356.11.2.3.8
lcsSetupChargesDslBroadbandMinutesBudget OBJECT-TYPE
    SYNTAX     Integer32 (0..2147483647)
    MAX-ACCESS read-write
    STATUS     current
    DESCRIPTION
            ""
    ::= { lcsSetupCharges 8 }

-- {SCALAR} 1.3.6.1.4.1.2356.11.2.3.9
lcsSetupChargesSpareDslBroadbandMinutes OBJECT-TYPE
    SYNTAX     Integer32 (0..2147483647)
    MAX-ACCESS read-only
    STATUS     current
    DESCRIPTION
            ""
    ::= { lcsSetupCharges 9 }

-- {SCALAR} 1.3.6.1.4.1.2356.11.2.3.10
lcsSetupChargesRouterDslBroadbandMinutesActive OBJECT-TYPE
    SYNTAX     Integer32 (0..2147483647)
    MAX-ACCESS read-only
    STATUS     current
    DESCRIPTION
            ""
    ::= { lcsSetupCharges 10 }

-- {SCALAR} 1.3.6.1.4.1.2356.11.2.3.11
lcsSetupChargesAdditionalDslBroadbandBudget OBJECT-TYPE
    SYNTAX     Integer32 (0..2147483647)
    MAX-ACCESS read-write
    STATUS     current
    DESCRIPTION
            ""
    ::= { lcsSetupCharges 11 }

-- {SCALAR} 1.3.6.1.4.1.2356.11.2.3.12
lcsSetupChargesActivateAdditionalBudget OBJECT-TYPE
    SYNTAX     DisplayString
    MAX-ACCESS read-write
    STATUS     current
    DESCRIPTION
            ""
    ::= { lcsSetupCharges 12 }

-- {SCALAR} 1.3.6.1.4.1.2356.11.2.3.13
lcsSetupChargesDialupMinutesBudget OBJECT-TYPE
    SYNTAX     Integer32 (0..2147483647)
    MAX-ACCESS read-write
    STATUS     current
    DESCRIPTION
            ""
    ::= { lcsSetupCharges 13 }

-- {SCALAR} 1.3.6.1.4.1.2356.11.2.3.14
lcsSetupChargesSpareDialupMinutes OBJECT-TYPE
    SYNTAX     Integer32 (0..2147483647)
    MAX-ACCESS read-only
    STATUS     current
    DESCRIPTION
            ""
    ::= { lcsSetupCharges 14 }

-- {SCALAR} 1.3.6.1.4.1.2356.11.2.3.15
lcsSetupChargesDialupMinutesActive OBJECT-TYPE
    SYNTAX     Integer32 (0..2147483647)
    MAX-ACCESS read-only
    STATUS     current
    DESCRIPTION
            ""
    ::= { lcsSetupCharges 15 }

-- {SCALAR} 1.3.6.1.4.1.2356.11.2.3.16
lcsSetupChargesResetBudgets OBJECT-TYPE
    SYNTAX     DisplayString
    MAX-ACCESS read-write
    STATUS     current
    DESCRIPTION
            ""
    ::= { lcsSetupCharges 16 }

-- {TABLE} 1.3.6.1.4.1.2356.11.2.3.17
lcsSetupChargesVolumeBudgetsTable OBJECT-TYPE
    SYNTAX     SEQUENCE OF LcsSetupChargesVolumeBudgetsEntry
    MAX-ACCESS not-accessible
    STATUS     current
    DESCRIPTION
            "-- empty --"
    ::= { lcsSetupCharges 17 }

-- {ROW} 1.3.6.1.4.1.2356.11.2.3.17.1
lcsSetupChargesVolumeBudgetsEntry OBJECT-TYPE
    SYNTAX     LcsSetupChargesVolumeBudgetsEntry
    MAX-ACCESS not-accessible
    STATUS     current
    DESCRIPTION
            ""
    INDEX {
            lcsSetupChargesVolumeBudgetsEntryPeer
          }
    ::= { lcsSetupChargesVolumeBudgetsTable 1 }

LcsSetupChargesVolumeBudgetsEntry ::= SEQUENCE {
            lcsSetupChargesVolumeBudgetsEntryPeer DisplayString,
            lcsSetupChargesVolumeBudgetsEntryLimitMb Integer32,
            lcsSetupChargesVolumeBudgetsEntryAction BITS
    }

-- {COLUMN} 1.3.6.1.4.1.2356.11.2.3.17.1.1
lcsSetupChargesVolumeBudgetsEntryPeer OBJECT-TYPE
    SYNTAX     DisplayString (SIZE(0..16))
    MAX-ACCESS read-write
    STATUS     current
    DESCRIPTION
            "-- empty --"
    ::= { lcsSetupChargesVolumeBudgetsEntry 1 }

-- {COLUMN} 1.3.6.1.4.1.2356.11.2.3.17.1.2
lcsSetupChargesVolumeBudgetsEntryLimitMb OBJECT-TYPE
    SYNTAX     Integer32 (0..2147483647)
    MAX-ACCESS read-write
    STATUS     current
    DESCRIPTION
            "-- empty --"
    ::= { lcsSetupChargesVolumeBudgetsEntry 2 }

-- {COLUMN} 1.3.6.1.4.1.2356.11.2.3.17.1.3
lcsSetupChargesVolumeBudgetsEntryAction OBJECT-TYPE
    SYNTAX     BITS {
                  eDisconnect (4),
                  eMail (5),
                  eSyslog (7)
            }
    MAX-ACCESS read-write
    STATUS     current
    DESCRIPTION
            "-- empty --"
    ::= { lcsSetupChargesVolumeBudgetsEntry 3 }

-- {TABLE} 1.3.6.1.4.1.2356.11.2.3.18
lcsSetupChargesFreeNetworksTable OBJECT-TYPE
    SYNTAX     SEQUENCE OF LcsSetupChargesFreeNetworksEntry
    MAX-ACCESS not-accessible
    STATUS     current
    DESCRIPTION
            "-- empty --"
    ::= { lcsSetupCharges 18 }

-- {ROW} 1.3.6.1.4.1.2356.11.2.3.18.1
lcsSetupChargesFreeNetworksEntry OBJECT-TYPE
    SYNTAX     LcsSetupChargesFreeNetworksEntry
    MAX-ACCESS not-accessible
    STATUS     current
    DESCRIPTION
            ""
    INDEX {
            lcsSetupChargesFreeNetworksEntryPeer
          }
    ::= { lcsSetupChargesFreeNetworksTable 1 }

LcsSetupChargesFreeNetworksEntry ::= SEQUENCE {
            lcsSetupChargesFreeNetworksEntryPeer DisplayString,
            lcsSetupChargesFreeNetworksEntryFreeNetworks DisplayString
    }

-- {COLUMN} 1.3.6.1.4.1.2356.11.2.3.18.1.1
lcsSetupChargesFreeNetworksEntryPeer OBJECT-TYPE
    SYNTAX     DisplayString (SIZE(0..20))
    MAX-ACCESS read-write
    STATUS     current
    DESCRIPTION
            "-- empty --"
    ::= { lcsSetupChargesFreeNetworksEntry 1 }

-- {COLUMN} 1.3.6.1.4.1.2356.11.2.3.18.1.2
lcsSetupChargesFreeNetworksEntryFreeNetworks OBJECT-TYPE
    SYNTAX     DisplayString (SIZE(0..100))
    MAX-ACCESS read-write
    STATUS     current
    DESCRIPTION
            "-- empty --"
    ::= { lcsSetupChargesFreeNetworksEntry 2 }

-- {TABLE} 1.3.6.1.4.1.2356.11.2.3.19
lcsSetupChargesBudgetControlTable OBJECT-TYPE
    SYNTAX     SEQUENCE OF LcsSetupChargesBudgetControlEntry
    MAX-ACCESS not-accessible
    STATUS     current
    DESCRIPTION
            "-- empty --"
    ::= { lcsSetupCharges 19 }

-- {ROW} 1.3.6.1.4.1.2356.11.2.3.19.1
lcsSetupChargesBudgetControlEntry OBJECT-TYPE
    SYNTAX     LcsSetupChargesBudgetControlEntry
    MAX-ACCESS not-accessible
    STATUS     current
    DESCRIPTION
            ""
    INDEX {
            lcsSetupChargesBudgetControlEntryPeer
          }
    ::= { lcsSetupChargesBudgetControlTable 1 }

LcsSetupChargesBudgetControlEntry ::= SEQUENCE {
            lcsSetupChargesBudgetControlEntryPeer DisplayString,
            lcsSetupChargesBudgetControlEntryDay Integer32,
            lcsSetupChargesBudgetControlEntryHour Integer32,
            lcsSetupChargesBudgetControlEntryMinute Integer32
    }

-- {COLUMN} 1.3.6.1.4.1.2356.11.2.3.19.1.1
lcsSetupChargesBudgetControlEntryPeer OBJECT-TYPE
    SYNTAX     DisplayString (SIZE(0..16))
    MAX-ACCESS read-write
    STATUS     current
    DESCRIPTION
            "-- empty --"
    ::= { lcsSetupChargesBudgetControlEntry 1 }

-- {COLUMN} 1.3.6.1.4.1.2356.11.2.3.19.1.2
lcsSetupChargesBudgetControlEntryDay OBJECT-TYPE
    SYNTAX     Integer32 (0..255)
    MAX-ACCESS read-write
    STATUS     current
    DESCRIPTION
            "-- empty --"
    ::= { lcsSetupChargesBudgetControlEntry 2 }

-- {COLUMN} 1.3.6.1.4.1.2356.11.2.3.19.1.3
lcsSetupChargesBudgetControlEntryHour OBJECT-TYPE
    SYNTAX     Integer32 (0..255)
    MAX-ACCESS read-write
    STATUS     current
    DESCRIPTION
            "-- empty --"
    ::= { lcsSetupChargesBudgetControlEntry 3 }

-- {COLUMN} 1.3.6.1.4.1.2356.11.2.3.19.1.4
lcsSetupChargesBudgetControlEntryMinute OBJECT-TYPE
    SYNTAX     Integer32 (0..255)
    MAX-ACCESS read-write
    STATUS     current
    DESCRIPTION
            "-- empty --"
    ::= { lcsSetupChargesBudgetControlEntry 4 }

-- {SCALAR} 1.3.6.1.4.1.2356.11.2.3.20
lcsSetupChargesChargingEmail OBJECT-TYPE
    SYNTAX     DisplayString (SIZE(0..255))
    MAX-ACCESS read-write
    STATUS     current
    DESCRIPTION
            "-- empty --"
    ::= { lcsSetupCharges 20 }

-- {SCALAR} 1.3.6.1.4.1.2356.11.2.3.21
lcsSetupChargesFlashInterval OBJECT-TYPE
    SYNTAX     Integer32 (0..255)
    MAX-ACCESS read-write
    STATUS     current
    DESCRIPTION
            "-- empty --"
    ::= { lcsSetupCharges 21 }

-- {NODE} 1.3.6.1.4.1.2356.11.2.4
lcsSetupLan OBJECT IDENTIFIER ::= { lcsSetup 4 }

-- {SCALAR} 1.3.6.1.4.1.2356.11.2.4.2
lcsSetupLanMacAddress OBJECT-TYPE
    SYNTAX     MacAddress
    MAX-ACCESS read-only
    STATUS     current
    DESCRIPTION
            ""
    ::= { lcsSetupLan 2 }

-- {SCALAR} 1.3.6.1.4.1.2356.11.2.4.3
lcsSetupLanSpareHeap OBJECT-TYPE
    SYNTAX     Integer32 (0..65535)
    MAX-ACCESS read-write
    STATUS     current
    DESCRIPTION
            ""
    ::= { lcsSetupLan 3 }

-- {SCALAR} 1.3.6.1.4.1.2356.11.2.4.8
lcsSetupLanTraceMac OBJECT-TYPE
    SYNTAX     MacAddress
    MAX-ACCESS read-write
    STATUS     current
    DESCRIPTION
            ""
    ::= { lcsSetupLan 8 }

-- {SCALAR} 1.3.6.1.4.1.2356.11.2.4.9
lcsSetupLanTraceLevel OBJECT-TYPE
    SYNTAX     Integer32 (0..255)
    MAX-ACCESS read-write
    STATUS     current
    DESCRIPTION
            ""
    ::= { lcsSetupLan 9 }

-- {NODE} 1.3.6.1.4.1.2356.11.2.4.10
lcsSetupLanIeee8021x OBJECT IDENTIFIER ::= { lcsSetupLan 10 }

-- {TABLE} 1.3.6.1.4.1.2356.11.2.4.10.1
lcsSetupLanIeee8021xSupplicantIfcSetupTable OBJECT-TYPE
    SYNTAX     SEQUENCE OF LcsSetupLanIeee8021xSupplicantIfcSetupEntry
    MAX-ACCESS not-accessible
    STATUS     current
    DESCRIPTION
            ""
    ::= { lcsSetupLanIeee8021x 1 }

-- {ROW} 1.3.6.1.4.1.2356.11.2.4.10.1.1
lcsSetupLanIeee8021xSupplicantIfcSetupEntry OBJECT-TYPE
    SYNTAX     LcsSetupLanIeee8021xSupplicantIfcSetupEntry
    MAX-ACCESS not-accessible
    STATUS     current
    DESCRIPTION
            ""
    INDEX {
            lcsSetupLanIeee8021xSupplicantIfcSetupEntryIfc
          }
    ::= { lcsSetupLanIeee8021xSupplicantIfcSetupTable 1 }

LcsSetupLanIeee8021xSupplicantIfcSetupEntry ::= SEQUENCE {
            lcsSetupLanIeee8021xSupplicantIfcSetupEntryIfc INTEGER,
            lcsSetupLanIeee8021xSupplicantIfcSetupEntryMethod INTEGER,
            lcsSetupLanIeee8021xSupplicantIfcSetupEntryCredentials DisplayString
    }

-- {COLUMN} 1.3.6.1.4.1.2356.11.2.4.10.1.1.1
lcsSetupLanIeee8021xSupplicantIfcSetupEntryIfc OBJECT-TYPE
    SYNTAX     INTEGER {
                  eLan1 (1),
                  eLan2 (2),
                  eLan3 (3),
                  eLan4 (4)
            }
    MAX-ACCESS read-only
    STATUS     current
    DESCRIPTION
            ""
    ::= { lcsSetupLanIeee8021xSupplicantIfcSetupEntry 1 }

-- {COLUMN} 1.3.6.1.4.1.2356.11.2.4.10.1.1.2
lcsSetupLanIeee8021xSupplicantIfcSetupEntryMethod OBJECT-TYPE
    SYNTAX     INTEGER {
                  eNone (0),
                  eMd5 (1024),
                  eTls (3328),
                  eTtlsMd5 (5380),
                  eTtlsPap (5383),
                  eTtlsChap (5384),
                  eTtlsMschapv2 (5402),
                  eTtlsMschap (5567),
                  ePeapGtc (6406),
                  ePeapMschapv2 (6426)
            }
    MAX-ACCESS read-write
    STATUS     current
    DESCRIPTION
            ""
    ::= { lcsSetupLanIeee8021xSupplicantIfcSetupEntry 2 }

-- {COLUMN} 1.3.6.1.4.1.2356.11.2.4.10.1.1.3
lcsSetupLanIeee8021xSupplicantIfcSetupEntryCredentials OBJECT-TYPE
    SYNTAX     DisplayString (SIZE(0..64))
    MAX-ACCESS read-write
    STATUS     current
    DESCRIPTION
            ""
    ::= { lcsSetupLanIeee8021xSupplicantIfcSetupEntry 3 }

-- {TABLE} 1.3.6.1.4.1.2356.11.2.4.10.2
lcsSetupLanIeee8021xAuthenticatorIfcSetupTable OBJECT-TYPE
    SYNTAX     SEQUENCE OF LcsSetupLanIeee8021xAuthenticatorIfcSetupEntry
    MAX-ACCESS not-accessible
    STATUS     current
    DESCRIPTION
            "-- empty --"
    ::= { lcsSetupLanIeee8021x 2 }

-- {ROW} 1.3.6.1.4.1.2356.11.2.4.10.2.1
lcsSetupLanIeee8021xAuthenticatorIfcSetupEntry OBJECT-TYPE
    SYNTAX     LcsSetupLanIeee8021xAuthenticatorIfcSetupEntry
    MAX-ACCESS not-accessible
    STATUS     current
    DESCRIPTION
            ""
    INDEX {
            lcsSetupLanIeee8021xAuthenticatorIfcSetupEntryIfc
          }
    ::= { lcsSetupLanIeee8021xAuthenticatorIfcSetupTable 1 }

LcsSetupLanIeee8021xAuthenticatorIfcSetupEntry ::= SEQUENCE {
            lcsSetupLanIeee8021xAuthenticatorIfcSetupEntryIfc INTEGER,
            lcsSetupLanIeee8021xAuthenticatorIfcSetupEntryOperating INTEGER,
            lcsSetupLanIeee8021xAuthenticatorIfcSetupEntryMode INTEGER,
            lcsSetupLanIeee8021xAuthenticatorIfcSetupEntryRadiusServer DisplayString,
            lcsSetupLanIeee8021xAuthenticatorIfcSetupEntryMacAuthBypass INTEGER
    }

-- {COLUMN} 1.3.6.1.4.1.2356.11.2.4.10.2.1.1
lcsSetupLanIeee8021xAuthenticatorIfcSetupEntryIfc OBJECT-TYPE
    SYNTAX     INTEGER {
                  eLan1 (1),
                  eLan2 (2),
                  eLan3 (3),
                  eLan4 (4)
            }
    MAX-ACCESS read-only
    STATUS     current
    DESCRIPTION
            "-- empty --"
    ::= { lcsSetupLanIeee8021xAuthenticatorIfcSetupEntry 1 }

-- {COLUMN} 1.3.6.1.4.1.2356.11.2.4.10.2.1.2
lcsSetupLanIeee8021xAuthenticatorIfcSetupEntryOperating OBJECT-TYPE
    SYNTAX     INTEGER {
                  eNo (0),
                  eYes (1)
            }
    MAX-ACCESS read-write
    STATUS     current
    DESCRIPTION
            "-- empty --"
    ::= { lcsSetupLanIeee8021xAuthenticatorIfcSetupEntry 2 }

-- {COLUMN} 1.3.6.1.4.1.2356.11.2.4.10.2.1.3
lcsSetupLanIeee8021xAuthenticatorIfcSetupEntryMode OBJECT-TYPE
    SYNTAX     INTEGER {
                  eSingleHost (0),
                  eMultipleHost (1),
                  eMultipleAuth (2)
            }
    MAX-ACCESS read-write
    STATUS     current
    DESCRIPTION
            "-- empty --"
    ::= { lcsSetupLanIeee8021xAuthenticatorIfcSetupEntry 3 }

-- {COLUMN} 1.3.6.1.4.1.2356.11.2.4.10.2.1.4
lcsSetupLanIeee8021xAuthenticatorIfcSetupEntryRadiusServer OBJECT-TYPE
    SYNTAX     DisplayString (SIZE(0..16))
    MAX-ACCESS read-write
    STATUS     current
    DESCRIPTION
            "-- empty --"
    ::= { lcsSetupLanIeee8021xAuthenticatorIfcSetupEntry 4 }

-- {COLUMN} 1.3.6.1.4.1.2356.11.2.4.10.2.1.5
lcsSetupLanIeee8021xAuthenticatorIfcSetupEntryMacAuthBypass OBJECT-TYPE
    SYNTAX     INTEGER {
                  eNo (0),
                  eYes (1)
            }
    MAX-ACCESS read-write
    STATUS     current
    DESCRIPTION
            "-- empty --"
    ::= { lcsSetupLanIeee8021xAuthenticatorIfcSetupEntry 5 }

-- {SCALAR} 1.3.6.1.4.1.2356.11.2.4.11
lcsSetupLanLinkupReportDelayMs OBJECT-TYPE
    SYNTAX     Integer32 (0..2147483647)
    MAX-ACCESS read-write
    STATUS     current
    DESCRIPTION
            "-- empty --"
    ::= { lcsSetupLan 11 }

-- {SCALAR} 1.3.6.1.4.1.2356.11.2.4.12
lcsSetupLanHnat OBJECT-TYPE
    SYNTAX     INTEGER {
                  eNo (0),
                  eYes (1)
            }
    MAX-ACCESS read-write
    STATUS     current
    DESCRIPTION
            "-- empty --"
    ::= { lcsSetupLan 12 }

-- {NODE} 1.3.6.1.4.1.2356.11.2.4.13
lcsSetupLanIfcBundl OBJECT IDENTIFIER ::= { lcsSetupLan 13 }

-- {TABLE} 1.3.6.1.4.1.2356.11.2.4.13.1
lcsSetupLanIfcBundlInterfacesTable OBJECT-TYPE
    SYNTAX     SEQUENCE OF LcsSetupLanIfcBundlInterfacesEntry
    MAX-ACCESS not-accessible
    STATUS     current
    DESCRIPTION
            "-- empty --"
    ::= { lcsSetupLanIfcBundl 1 }

-- {ROW} 1.3.6.1.4.1.2356.11.2.4.13.1.1
lcsSetupLanIfcBundlInterfacesEntry OBJECT-TYPE
    SYNTAX     LcsSetupLanIfcBundlInterfacesEntry
    MAX-ACCESS not-accessible
    STATUS     current
    DESCRIPTION
            ""
    INDEX {
            lcsSetupLanIfcBundlInterfacesEntryInterface
          }
    ::= { lcsSetupLanIfcBundlInterfacesTable 1 }

LcsSetupLanIfcBundlInterfacesEntry ::= SEQUENCE {
            lcsSetupLanIfcBundlInterfacesEntryInterface DisplayString,
            lcsSetupLanIfcBundlInterfacesEntryOperating INTEGER,
            lcsSetupLanIfcBundlInterfacesEntryProtocol INTEGER,
            lcsSetupLanIfcBundlInterfacesEntryMacAddress MacAddress,
            lcsSetupLanIfcBundlInterfacesEntryInterfaceA INTEGER,
            lcsSetupLanIfcBundlInterfacesEntryInterfaceB INTEGER
    }

-- {COLUMN} 1.3.6.1.4.1.2356.11.2.4.13.1.1.1
lcsSetupLanIfcBundlInterfacesEntryInterface OBJECT-TYPE
    SYNTAX     DisplayString (SIZE(0..18))
    MAX-ACCESS read-write
    STATUS     current
    DESCRIPTION
            "-- empty --"
    ::= { lcsSetupLanIfcBundlInterfacesEntry 1 }

-- {COLUMN} 1.3.6.1.4.1.2356.11.2.4.13.1.1.2
lcsSetupLanIfcBundlInterfacesEntryOperating OBJECT-TYPE
    SYNTAX     INTEGER {
                  eNo (0),
                  eYes (1)
            }
    MAX-ACCESS read-write
    STATUS     current
    DESCRIPTION
            "-- empty --"
    ::= { lcsSetupLanIfcBundlInterfacesEntry 2 }

-- {COLUMN} 1.3.6.1.4.1.2356.11.2.4.13.1.1.3
lcsSetupLanIfcBundlInterfacesEntryProtocol OBJECT-TYPE
    SYNTAX     INTEGER {
                  ePrp (1),
                  eLacp (2)
            }
    MAX-ACCESS read-write
    STATUS     current
    DESCRIPTION
            "-- empty --"
    ::= { lcsSetupLanIfcBundlInterfacesEntry 3 }

-- {COLUMN} 1.3.6.1.4.1.2356.11.2.4.13.1.1.4
lcsSetupLanIfcBundlInterfacesEntryMacAddress OBJECT-TYPE
    SYNTAX     MacAddress
    MAX-ACCESS read-write
    STATUS     current
    DESCRIPTION
            "-- empty --"
    ::= { lcsSetupLanIfcBundlInterfacesEntry 4 }

-- {COLUMN} 1.3.6.1.4.1.2356.11.2.4.13.1.1.5
lcsSetupLanIfcBundlInterfacesEntryInterfaceA OBJECT-TYPE
    SYNTAX     INTEGER {
                  eNone (0),
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eXdsl1 (2816),
                  eXdsl2 (2817)
            }
    MAX-ACCESS read-write
    STATUS     current
    DESCRIPTION
            "-- empty --"
    ::= { lcsSetupLanIfcBundlInterfacesEntry 5 }

-- {COLUMN} 1.3.6.1.4.1.2356.11.2.4.13.1.1.6
lcsSetupLanIfcBundlInterfacesEntryInterfaceB OBJECT-TYPE
    SYNTAX     INTEGER {
                  eNone (0),
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eXdsl1 (2816),
                  eXdsl2 (2817)
            }
    MAX-ACCESS read-write
    STATUS     current
    DESCRIPTION
            "-- empty --"
    ::= { lcsSetupLanIfcBundlInterfacesEntry 6 }

-- {NODE} 1.3.6.1.4.1.2356.11.2.4.13.11
lcsSetupLanIfcBundlPrp OBJECT IDENTIFIER ::= { lcsSetupLanIfcBundl 11 }

-- {TABLE} 1.3.6.1.4.1.2356.11.2.4.13.11.1
lcsSetupLanIfcBundlPrpInterfacesTable OBJECT-TYPE
    SYNTAX     SEQUENCE OF LcsSetupLanIfcBundlPrpInterfacesEntry
    MAX-ACCESS not-accessible
    STATUS     current
    DESCRIPTION
            "-- empty --"
    ::= { lcsSetupLanIfcBundlPrp 1 }

-- {ROW} 1.3.6.1.4.1.2356.11.2.4.13.11.1.1
lcsSetupLanIfcBundlPrpInterfacesEntry OBJECT-TYPE
    SYNTAX     LcsSetupLanIfcBundlPrpInterfacesEntry
    MAX-ACCESS not-accessible
    STATUS     current
    DESCRIPTION
            ""
    INDEX {
            lcsSetupLanIfcBundlPrpInterfacesEntryInterface
          }
    ::= { lcsSetupLanIfcBundlPrpInterfacesTable 1 }

LcsSetupLanIfcBundlPrpInterfacesEntry ::= SEQUENCE {
            lcsSetupLanIfcBundlPrpInterfacesEntryInterface DisplayString,
            lcsSetupLanIfcBundlPrpInterfacesEntryDuplicateAccept INTEGER,
            lcsSetupLanIfcBundlPrpInterfacesEntryTransparentMode INTEGER,
            lcsSetupLanIfcBundlPrpInterfacesEntryLifeCheckInterval Integer32,
            lcsSetupLanIfcBundlPrpInterfacesEntryNodeForgetTime Integer32,
            lcsSetupLanIfcBundlPrpInterfacesEntryEntryForgetTime Integer32,
            lcsSetupLanIfcBundlPrpInterfacesEntryNodeRebootInterval Integer32,
            lcsSetupLanIfcBundlPrpInterfacesEntryDupEliminationBufferSize Integer32,
            lcsSetupLanIfcBundlPrpInterfacesEntrySendSupervisionFrames INTEGER,
            lcsSetupLanIfcBundlPrpInterfacesEntryNodeName DisplayString,
            lcsSetupLanIfcBundlPrpInterfacesEntryEvaluateSupFrames INTEGER,
            lcsSetupLanIfcBundlPrpInterfacesEntryBufferedPrpEnable INTEGER,
            lcsSetupLanIfcBundlPrpInterfacesEntryBufferMaxTime Integer32
    }

-- {COLUMN} 1.3.6.1.4.1.2356.11.2.4.13.11.1.1.1
lcsSetupLanIfcBundlPrpInterfacesEntryInterface OBJECT-TYPE
    SYNTAX     DisplayString (SIZE(0..18))
    MAX-ACCESS read-write
    STATUS     current
    DESCRIPTION
            "-- empty --"
    ::= { lcsSetupLanIfcBundlPrpInterfacesEntry 1 }

-- {COLUMN} 1.3.6.1.4.1.2356.11.2.4.13.11.1.1.2
lcsSetupLanIfcBundlPrpInterfacesEntryDuplicateAccept OBJECT-TYPE
    SYNTAX     INTEGER {
                  eNo (0),
                  eYes (1)
            }
    MAX-ACCESS read-write
    STATUS     current
    DESCRIPTION
            "-- empty --"
    ::= { lcsSetupLanIfcBundlPrpInterfacesEntry 2 }

-- {COLUMN} 1.3.6.1.4.1.2356.11.2.4.13.11.1.1.3
lcsSetupLanIfcBundlPrpInterfacesEntryTransparentMode OBJECT-TYPE
    SYNTAX     INTEGER {
                  eNo (0),
                  eYes (1)
            }
    MAX-ACCESS read-write
    STATUS     current
    DESCRIPTION
            "-- empty --"
    ::= { lcsSetupLanIfcBundlPrpInterfacesEntry 3 }

-- {COLUMN} 1.3.6.1.4.1.2356.11.2.4.13.11.1.1.4
lcsSetupLanIfcBundlPrpInterfacesEntryLifeCheckInterval OBJECT-TYPE
    SYNTAX     Integer32 (0..2147483647)
    MAX-ACCESS read-write
    STATUS     current
    DESCRIPTION
            "-- empty --"
    ::= { lcsSetupLanIfcBundlPrpInterfacesEntry 4 }

-- {COLUMN} 1.3.6.1.4.1.2356.11.2.4.13.11.1.1.5
lcsSetupLanIfcBundlPrpInterfacesEntryNodeForgetTime OBJECT-TYPE
    SYNTAX     Integer32 (0..2147483647)
    MAX-ACCESS read-write
    STATUS     current
    DESCRIPTION
            "-- empty --"
    ::= { lcsSetupLanIfcBundlPrpInterfacesEntry 5 }

-- {COLUMN} 1.3.6.1.4.1.2356.11.2.4.13.11.1.1.6
lcsSetupLanIfcBundlPrpInterfacesEntryEntryForgetTime OBJECT-TYPE
    SYNTAX     Integer32 (0..2147483647)
    MAX-ACCESS read-write
    STATUS     current
    DESCRIPTION
            "-- empty --"
    ::= { lcsSetupLanIfcBundlPrpInterfacesEntry 6 }

-- {COLUMN} 1.3.6.1.4.1.2356.11.2.4.13.11.1.1.7
lcsSetupLanIfcBundlPrpInterfacesEntryNodeRebootInterval OBJECT-TYPE
    SYNTAX     Integer32 (0..2147483647)
    MAX-ACCESS read-write
    STATUS     current
    DESCRIPTION
            "-- empty --"
    ::= { lcsSetupLanIfcBundlPrpInterfacesEntry 7 }

-- {COLUMN} 1.3.6.1.4.1.2356.11.2.4.13.11.1.1.8
lcsSetupLanIfcBundlPrpInterfacesEntryDupEliminationBufferSize OBJECT-TYPE
    SYNTAX     Integer32 (0..2147483647)
    MAX-ACCESS read-write
    STATUS     current
    DESCRIPTION
            "-- empty --"
    ::= { lcsSetupLanIfcBundlPrpInterfacesEntry 8 }

-- {COLUMN} 1.3.6.1.4.1.2356.11.2.4.13.11.1.1.9
lcsSetupLanIfcBundlPrpInterfacesEntrySendSupervisionFrames OBJECT-TYPE
    SYNTAX     INTEGER {
                  eNone (0),
                  eOwnMacOnly (1),
                  eAllNodes (2)
            }
    MAX-ACCESS read-write
    STATUS     current
    DESCRIPTION
            "-- empty --"
    ::= { lcsSetupLanIfcBundlPrpInterfacesEntry 9 }

-- {COLUMN} 1.3.6.1.4.1.2356.11.2.4.13.11.1.1.10
lcsSetupLanIfcBundlPrpInterfacesEntryNodeName OBJECT-TYPE
    SYNTAX     DisplayString (SIZE(0..32))
    MAX-ACCESS read-write
    STATUS     current
    DESCRIPTION
            "-- empty --"
    ::= { lcsSetupLanIfcBundlPrpInterfacesEntry 10 }

-- {COLUMN} 1.3.6.1.4.1.2356.11.2.4.13.11.1.1.11
lcsSetupLanIfcBundlPrpInterfacesEntryEvaluateSupFrames OBJECT-TYPE
    SYNTAX     INTEGER {
                  eNo (0),
                  eYes (1)
            }
    MAX-ACCESS read-write
    STATUS     current
    DESCRIPTION
            "-- empty --"
    ::= { lcsSetupLanIfcBundlPrpInterfacesEntry 11 }

-- {COLUMN} 1.3.6.1.4.1.2356.11.2.4.13.11.1.1.248
lcsSetupLanIfcBundlPrpInterfacesEntryBufferedPrpEnable OBJECT-TYPE
    SYNTAX     INTEGER {
                  eNo (0),
                  eYes (1)
            }
    MAX-ACCESS read-write
    STATUS     current
    DESCRIPTION
            "-- empty --"
    ::= { lcsSetupLanIfcBundlPrpInterfacesEntry 248 }

-- {COLUMN} 1.3.6.1.4.1.2356.11.2.4.13.11.1.1.249
lcsSetupLanIfcBundlPrpInterfacesEntryBufferMaxTime OBJECT-TYPE
    SYNTAX     Integer32 (0..2147483647)
    MAX-ACCESS read-write
    STATUS     current
    DESCRIPTION
            "-- empty --"
    ::= { lcsSetupLanIfcBundlPrpInterfacesEntry 249 }

-- {NODE} 1.3.6.1.4.1.2356.11.2.4.13.12
lcsSetupLanIfcBundlLacp OBJECT IDENTIFIER ::= { lcsSetupLanIfcBundl 12 }

-- {TABLE} 1.3.6.1.4.1.2356.11.2.4.13.12.1
lcsSetupLanIfcBundlLacpInterfacesTable OBJECT-TYPE
    SYNTAX     SEQUENCE OF LcsSetupLanIfcBundlLacpInterfacesEntry
    MAX-ACCESS not-accessible
    STATUS     current
    DESCRIPTION
            "-- empty --"
    ::= { lcsSetupLanIfcBundlLacp 1 }

-- {ROW} 1.3.6.1.4.1.2356.11.2.4.13.12.1.1
lcsSetupLanIfcBundlLacpInterfacesEntry OBJECT-TYPE
    SYNTAX     LcsSetupLanIfcBundlLacpInterfacesEntry
    MAX-ACCESS not-accessible
    STATUS     current
    DESCRIPTION
            ""
    INDEX {
            lcsSetupLanIfcBundlLacpInterfacesEntryInterface
          }
    ::= { lcsSetupLanIfcBundlLacpInterfacesTable 1 }

LcsSetupLanIfcBundlLacpInterfacesEntry ::= SEQUENCE {
            lcsSetupLanIfcBundlLacpInterfacesEntryInterface DisplayString,
            lcsSetupLanIfcBundlLacpInterfacesEntrySystemPriority Integer32,
            lcsSetupLanIfcBundlLacpInterfacesEntryKey Integer32,
            lcsSetupLanIfcBundlLacpInterfacesEntryFrameDistributionPolicy INTEGER,
            lcsSetupLanIfcBundlLacpInterfacesEntryPortPriorityA Integer32,
            lcsSetupLanIfcBundlLacpInterfacesEntryPortPriorityB Integer32
    }

-- {COLUMN} 1.3.6.1.4.1.2356.11.2.4.13.12.1.1.1
lcsSetupLanIfcBundlLacpInterfacesEntryInterface OBJECT-TYPE
    SYNTAX     DisplayString (SIZE(0..18))
    MAX-ACCESS read-write
    STATUS     current
    DESCRIPTION
            "-- empty --"
    ::= { lcsSetupLanIfcBundlLacpInterfacesEntry 1 }

-- {COLUMN} 1.3.6.1.4.1.2356.11.2.4.13.12.1.1.2
lcsSetupLanIfcBundlLacpInterfacesEntrySystemPriority OBJECT-TYPE
    SYNTAX     Integer32 (0..65535)
    MAX-ACCESS read-write
    STATUS     current
    DESCRIPTION
            "-- empty --"
    ::= { lcsSetupLanIfcBundlLacpInterfacesEntry 2 }

-- {COLUMN} 1.3.6.1.4.1.2356.11.2.4.13.12.1.1.3
lcsSetupLanIfcBundlLacpInterfacesEntryKey OBJECT-TYPE
    SYNTAX     Integer32 (0..255)
    MAX-ACCESS read-write
    STATUS     current
    DESCRIPTION
            "-- empty --"
    ::= { lcsSetupLanIfcBundlLacpInterfacesEntry 3 }

-- {COLUMN} 1.3.6.1.4.1.2356.11.2.4.13.12.1.1.4
lcsSetupLanIfcBundlLacpInterfacesEntryFrameDistributionPolicy OBJECT-TYPE
    SYNTAX     INTEGER {
                  eVlan (0),
                  eFlowHash (1),
                  eSourceMac (2),
                  eDestMac (3),
                  eSourceDestMac (4)
            }
    MAX-ACCESS read-write
    STATUS     current
    DESCRIPTION
            "-- empty --"
    ::= { lcsSetupLanIfcBundlLacpInterfacesEntry 4 }

-- {COLUMN} 1.3.6.1.4.1.2356.11.2.4.13.12.1.1.5
lcsSetupLanIfcBundlLacpInterfacesEntryPortPriorityA OBJECT-TYPE
    SYNTAX     Integer32 (0..65535)
    MAX-ACCESS read-write
    STATUS     current
    DESCRIPTION
            "-- empty --"
    ::= { lcsSetupLanIfcBundlLacpInterfacesEntry 5 }

-- {COLUMN} 1.3.6.1.4.1.2356.11.2.4.13.12.1.1.6
lcsSetupLanIfcBundlLacpInterfacesEntryPortPriorityB OBJECT-TYPE
    SYNTAX     Integer32 (0..65535)
    MAX-ACCESS read-write
    STATUS     current
    DESCRIPTION
            "-- empty --"
    ::= { lcsSetupLanIfcBundlLacpInterfacesEntry 6 }

-- {NODE} 1.3.6.1.4.1.2356.11.2.7
lcsSetupTcpIp OBJECT IDENTIFIER ::= { lcsSetup 7 }

-- {SCALAR} 1.3.6.1.4.1.2356.11.2.7.1
lcsSetupTcpIpOperating OBJECT-TYPE
    SYNTAX     INTEGER {
                  eNo (0),
                  eYes (1)
            }
    MAX-ACCESS read-write
    STATUS     current
    DESCRIPTION
            ""
    ::= { lcsSetupTcpIp 1 }

-- {TABLE} 1.3.6.1.4.1.2356.11.2.7.6
lcsSetupTcpIpAccessListTable OBJECT-TYPE
    SYNTAX     SEQUENCE OF LcsSetupTcpIpAccessListEntry
    MAX-ACCESS not-accessible
    STATUS     current
    DESCRIPTION
            ""
    ::= { lcsSetupTcpIp 6 }

-- {ROW} 1.3.6.1.4.1.2356.11.2.7.6.1
lcsSetupTcpIpAccessListEntry OBJECT-TYPE
    SYNTAX     LcsSetupTcpIpAccessListEntry
    MAX-ACCESS not-accessible
    STATUS     current
    DESCRIPTION
            ""
    INDEX {
            lcsSetupTcpIpAccessListEntryIpAddress,
            lcsSetupTcpIpAccessListEntryIpNetmask,
            lcsSetupTcpIpAccessListEntryRtgTag
          }
    ::= { lcsSetupTcpIpAccessListTable 1 }

LcsSetupTcpIpAccessListEntry ::= SEQUENCE {
            lcsSetupTcpIpAccessListEntryIpAddress IpAddress,
            lcsSetupTcpIpAccessListEntryIpNetmask IpAddress,
            lcsSetupTcpIpAccessListEntryRtgTag Integer32,
            lcsSetupTcpIpAccessListEntryComment DisplayString
    }

-- {COLUMN} 1.3.6.1.4.1.2356.11.2.7.6.1.1
lcsSetupTcpIpAccessListEntryIpAddress OBJECT-TYPE
    SYNTAX     IpAddress
    MAX-ACCESS read-write
    STATUS     current
    DESCRIPTION
            ""
    ::= { lcsSetupTcpIpAccessListEntry 1 }

-- {COLUMN} 1.3.6.1.4.1.2356.11.2.7.6.1.2
lcsSetupTcpIpAccessListEntryIpNetmask OBJECT-TYPE
    SYNTAX     IpAddress
    MAX-ACCESS read-write
    STATUS     current
    DESCRIPTION
            ""
    ::= { lcsSetupTcpIpAccessListEntry 2 }

-- {COLUMN} 1.3.6.1.4.1.2356.11.2.7.6.1.3
lcsSetupTcpIpAccessListEntryRtgTag OBJECT-TYPE
    SYNTAX     Integer32 (0..65535)
    MAX-ACCESS read-write
    STATUS     current
    DESCRIPTION
            ""
    ::= { lcsSetupTcpIpAccessListEntry 3 }

-- {COLUMN} 1.3.6.1.4.1.2356.11.2.7.6.1.4
lcsSetupTcpIpAccessListEntryComment OBJECT-TYPE
    SYNTAX     DisplayString (SIZE(0..63))
    MAX-ACCESS read-write
    STATUS     current
    DESCRIPTION
            "-- empty --"
    ::= { lcsSetupTcpIpAccessListEntry 4 }

-- {SCALAR} 1.3.6.1.4.1.2356.11.2.7.7
lcsSetupTcpIpDnsDefault OBJECT-TYPE
    SYNTAX     IpAddress
    MAX-ACCESS read-write
    STATUS     current
    DESCRIPTION
            ""
    ::= { lcsSetupTcpIp 7 }

-- {SCALAR} 1.3.6.1.4.1.2356.11.2.7.8
lcsSetupTcpIpDnsBackup OBJECT-TYPE
    SYNTAX     IpAddress
    MAX-ACCESS read-write
    STATUS     current
    DESCRIPTION
            ""
    ::= { lcsSetupTcpIp 8 }

-- {SCALAR} 1.3.6.1.4.1.2356.11.2.7.9
lcsSetupTcpIpNbnsDefault OBJECT-TYPE
    SYNTAX     IpAddress
    MAX-ACCESS read-write
    STATUS     current
    DESCRIPTION
            ""
    ::= { lcsSetupTcpIp 9 }

-- {SCALAR} 1.3.6.1.4.1.2356.11.2.7.10
lcsSetupTcpIpNbnsBackup OBJECT-TYPE
    SYNTAX     IpAddress
    MAX-ACCESS read-write
    STATUS     current
    DESCRIPTION
            ""
    ::= { lcsSetupTcpIp 10 }

-- {SCALAR} 1.3.6.1.4.1.2356.11.2.7.11
lcsSetupTcpIpArpAgingMinutes OBJECT-TYPE
    SYNTAX     Integer32 (0..255)
    MAX-ACCESS read-write
    STATUS     current
    DESCRIPTION
            ""
    ::= { lcsSetupTcpIp 11 }

-- {SCALAR} 1.3.6.1.4.1.2356.11.2.7.12
lcsSetupTcpIpTcpAgingMinutes OBJECT-TYPE
    SYNTAX     Integer32 (0..255)
    MAX-ACCESS read-write
    STATUS     current
    DESCRIPTION
            "-- empty --"
    ::= { lcsSetupTcpIp 12 }

-- {SCALAR} 1.3.6.1.4.1.2356.11.2.7.13
lcsSetupTcpIpTcpMaxConn OBJECT-TYPE
    SYNTAX     Integer32 (0..255)
    MAX-ACCESS read-write
    STATUS     current
    DESCRIPTION
            "-- empty --"
    ::= { lcsSetupTcpIp 13 }

-- {TABLE} 1.3.6.1.4.1.2356.11.2.7.16
lcsSetupTcpIpArpTableTable OBJECT-TYPE
    SYNTAX     SEQUENCE OF LcsSetupTcpIpArpTableEntry
    MAX-ACCESS not-accessible
    STATUS     current
    DESCRIPTION
            ""
    ::= { lcsSetupTcpIp 16 }

-- {ROW} 1.3.6.1.4.1.2356.11.2.7.16.1
lcsSetupTcpIpArpTableEntry OBJECT-TYPE
    SYNTAX     LcsSetupTcpIpArpTableEntry
    MAX-ACCESS not-accessible
    STATUS     current
    DESCRIPTION
            ""
    INDEX {
            lcsSetupTcpIpArpTableEntryIpAddress
          }
    ::= { lcsSetupTcpIpArpTableTable 1 }

LcsSetupTcpIpArpTableEntry ::= SEQUENCE {
            lcsSetupTcpIpArpTableEntryIpAddress IpAddress,
            lcsSetupTcpIpArpTableEntryMacAddress MacAddress,
            lcsSetupTcpIpArpTableEntryLastAccess Integer32,
            lcsSetupTcpIpArpTableEntryEthernetPort INTEGER,
            lcsSetupTcpIpArpTableEntryPeer DisplayString,
            lcsSetupTcpIpArpTableEntryVlanId Integer32,
            lcsSetupTcpIpArpTableEntryConnect INTEGER
    }

-- {COLUMN} 1.3.6.1.4.1.2356.11.2.7.16.1.1
lcsSetupTcpIpArpTableEntryIpAddress OBJECT-TYPE
    SYNTAX     IpAddress
    MAX-ACCESS read-only
    STATUS     current
    DESCRIPTION
            ""
    ::= { lcsSetupTcpIpArpTableEntry 1 }

-- {COLUMN} 1.3.6.1.4.1.2356.11.2.7.16.1.2
lcsSetupTcpIpArpTableEntryMacAddress OBJECT-TYPE
    SYNTAX     MacAddress
    MAX-ACCESS read-only
    STATUS     current
    DESCRIPTION
            ""
    ::= { lcsSetupTcpIpArpTableEntry 2 }

-- {COLUMN} 1.3.6.1.4.1.2356.11.2.7.16.1.3
lcsSetupTcpIpArpTableEntryLastAccess OBJECT-TYPE
    SYNTAX     Integer32 (0..2147483647)
    MAX-ACCESS read-only
    STATUS     current
    DESCRIPTION
            ""
    ::= { lcsSetupTcpIpArpTableEntry 3 }

-- {COLUMN} 1.3.6.1.4.1.2356.11.2.7.16.1.5
lcsSetupTcpIpArpTableEntryEthernetPort OBJECT-TYPE
    SYNTAX     INTEGER {
                  eUnknown (0),
                  eUplink (1),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            ""
    ::= { lcsSetupTcpIpArpTableEntry 5 }

-- {COLUMN} 1.3.6.1.4.1.2356.11.2.7.16.1.6
lcsSetupTcpIpArpTableEntryPeer OBJECT-TYPE
    SYNTAX     DisplayString (SIZE(0..255))
    MAX-ACCESS read-only
    STATUS     current
    DESCRIPTION
            ""
    ::= { lcsSetupTcpIpArpTableEntry 6 }

-- {COLUMN} 1.3.6.1.4.1.2356.11.2.7.16.1.7
lcsSetupTcpIpArpTableEntryVlanId OBJECT-TYPE
    SYNTAX     Integer32 (0..65535)
    MAX-ACCESS read-only
    STATUS     current
    DESCRIPTION
            ""
    ::= { lcsSetupTcpIpArpTableEntry 7 }

-- {COLUMN} 1.3.6.1.4.1.2356.11.2.7.16.1.8
lcsSetupTcpIpArpTableEntryConnect OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eWan (32768)
            }
    MAX-ACCESS read-only
    STATUS     current
    DESCRIPTION
            ""
    ::= { lcsSetupTcpIpArpTableEntry 8 }

-- {TABLE} 1.3.6.1.4.1.2356.11.2.7.17
lcsSetupTcpIpLoopbackListTable OBJECT-TYPE
    SYNTAX     SEQUENCE OF LcsSetupTcpIpLoopbackListEntry
    MAX-ACCESS not-accessible
    STATUS     current
    DESCRIPTION
            ""
    ::= { lcsSetupTcpIp 17 }

-- {ROW} 1.3.6.1.4.1.2356.11.2.7.17.1
lcsSetupTcpIpLoopbackListEntry OBJECT-TYPE
    SYNTAX     LcsSetupTcpIpLoopbackListEntry
    MAX-ACCESS not-accessible
    STATUS     current
    DESCRIPTION
            ""
    INDEX {
            lcsSetupTcpIpLoopbackListEntryName
          }
    ::= { lcsSetupTcpIpLoopbackListTable 1 }

LcsSetupTcpIpLoopbackListEntry ::= SEQUENCE {
            lcsSetupTcpIpLoopbackListEntryLoopbackAddr IpAddress,
            lcsSetupTcpIpLoopbackListEntryName DisplayString,
            lcsSetupTcpIpLoopbackListEntryRtgTag Integer32
    }

-- {COLUMN} 1.3.6.1.4.1.2356.11.2.7.17.1.1
lcsSetupTcpIpLoopbackListEntryLoopbackAddr OBJECT-TYPE
    SYNTAX     IpAddress
    MAX-ACCESS read-write
    STATUS     current
    DESCRIPTION
            ""
    ::= { lcsSetupTcpIpLoopbackListEntry 1 }

-- {COLUMN} 1.3.6.1.4.1.2356.11.2.7.17.1.2
lcsSetupTcpIpLoopbackListEntryName OBJECT-TYPE
    SYNTAX     DisplayString (SIZE(0..16))
    MAX-ACCESS read-write
    STATUS     current
    DESCRIPTION
            ""
    ::= { lcsSetupTcpIpLoopbackListEntry 2 }

-- {COLUMN} 1.3.6.1.4.1.2356.11.2.7.17.1.3
lcsSetupTcpIpLoopbackListEntryRtgTag OBJECT-TYPE
    SYNTAX     Integer32 (0..65535)
    MAX-ACCESS read-write
    STATUS     current
    DESCRIPTION
            ""
    ::= { lcsSetupTcpIpLoopbackListEntry 3 }

-- {SCALAR} 1.3.6.1.4.1.2356.11.2.7.20
lcsSetupTcpIpNonLocArpReplies OBJECT-TYPE
    SYNTAX     INTEGER {
                  eNo (0),
                  eYes (1)
            }
    MAX-ACCESS read-write
    STATUS     current
    DESCRIPTION
            ""
    ::= { lcsSetupTcpIp 20 }

-- {NODE} 1.3.6.1.4.1.2356.11.2.7.21
lcsSetupTcpIpAliveTest OBJECT IDENTIFIER ::= { lcsSetupTcpIp 21 }

-- {SCALAR} 1.3.6.1.4.1.2356.11.2.7.21.1
lcsSetupTcpIpAliveTestTargetAddress OBJECT-TYPE
    SYNTAX     IpAddress
    MAX-ACCESS read-write
    STATUS     current
    DESCRIPTION
            ""
    ::= { lcsSetupTcpIpAliveTest 1 }

-- {SCALAR} 1.3.6.1.4.1.2356.11.2.7.21.2
lcsSetupTcpIpAliveTestTestInterval OBJECT-TYPE
    SYNTAX     Integer32 (0..2147483647)
    MAX-ACCESS read-write
    STATUS     current
    DESCRIPTION
            ""
    ::= { lcsSetupTcpIpAliveTest 2 }

-- {SCALAR} 1.3.6.1.4.1.2356.11.2.7.21.3
lcsSetupTcpIpAliveTestRetryCount OBJECT-TYPE
    SYNTAX     Integer32 (0..2147483647)
    MAX-ACCESS read-write
    STATUS     current
    DESCRIPTION
            ""
    ::= { lcsSetupTcpIpAliveTest 3 }

-- {SCALAR} 1.3.6.1.4.1.2356.11.2.7.21.4
lcsSetupTcpIpAliveTestRetryInterval OBJECT-TYPE
    SYNTAX     Integer32 (0..2147483647)
    MAX-ACCESS read-write
    STATUS     current
    DESCRIPTION
            ""
    ::= { lcsSetupTcpIpAliveTest 4 }

-- {SCALAR} 1.3.6.1.4.1.2356.11.2.7.21.5
lcsSetupTcpIpAliveTestFailLimit OBJECT-TYPE
    SYNTAX     Integer32 (0..2147483647)
    MAX-ACCESS read-write
    STATUS     current
    DESCRIPTION
            ""
    ::= { lcsSetupTcpIpAliveTest 5 }

-- {SCALAR} 1.3.6.1.4.1.2356.11.2.7.21.6
lcsSetupTcpIpAliveTestBootType OBJECT-TYPE
    SYNTAX     INTEGER {
                  eWarmBoot (0),
                  eColdBoot (1),
                  eAction (2)
            }
    MAX-ACCESS read-write
    STATUS     current
    DESCRIPTION
            ""
    ::= { lcsSetupTcpIpAliveTest 6 }

-- {SCALAR} 1.3.6.1.4.1.2356.11.2.7.21.7
lcsSetupTcpIpAliveTestAction OBJECT-TYPE
    SYNTAX     DisplayString (SIZE(0..251))
    MAX-ACCESS read-write
    STATUS     current
    DESCRIPTION
            "-- empty --"
    ::= { lcsSetupTcpIpAliveTest 7 }

-- {SCALAR} 1.3.6.1.4.1.2356.11.2.7.21.8
lcsSetupTcpIpAliveTestLoopbackAddress OBJECT-TYPE
    SYNTAX     DisplayString (SIZE(0..16))
    MAX-ACCESS read-write
    STATUS     current
    DESCRIPTION
            "-- empty --"
    ::= { lcsSetupTcpIpAliveTest 8 }

-- {SCALAR} 1.3.6.1.4.1.2356.11.2.7.22
lcsSetupTcpIpIcmpOnArpTimeout OBJECT-TYPE
    SYNTAX     INTEGER {
                  eNo (0),
                  eYes (1)
            }
    MAX-ACCESS read-write
    STATUS     current
    DESCRIPTION
            ""
    ::= { lcsSetupTcpIp 22 }

-- {TABLE} 1.3.6.1.4.1.2356.11.2.7.30
lcsSetupTcpIpNetworkListTable OBJECT-TYPE
    SYNTAX     SEQUENCE OF LcsSetupTcpIpNetworkListEntry
    MAX-ACCESS not-accessible
    STATUS     current
    DESCRIPTION
            ""
    ::= { lcsSetupTcpIp 30 }

-- {ROW} 1.3.6.1.4.1.2356.11.2.7.30.1
lcsSetupTcpIpNetworkListEntry OBJECT-TYPE
    SYNTAX     LcsSetupTcpIpNetworkListEntry
    MAX-ACCESS not-accessible
    STATUS     current
    DESCRIPTION
            ""
    INDEX {
            lcsSetupTcpIpNetworkListEntryNetworkName
          }
    ::= { lcsSetupTcpIpNetworkListTable 1 }

LcsSetupTcpIpNetworkListEntry ::= SEQUENCE {
            lcsSetupTcpIpNetworkListEntryNetworkName DisplayString,
            lcsSetupTcpIpNetworkListEntryIpAddress IpAddress,
            lcsSetupTcpIpNetworkListEntryIpNetmask IpAddress,
            lcsSetupTcpIpNetworkListEntryVlanId Integer32,
            lcsSetupTcpIpNetworkListEntryInterface INTEGER,
            lcsSetupTcpIpNetworkListEntrySrcCheck INTEGER,
            lcsSetupTcpIpNetworkListEntryType INTEGER,
            lcsSetupTcpIpNetworkListEntryRtgTag Integer32,
            lcsSetupTcpIpNetworkListEntryComment DisplayString,
            lcsSetupTcpIpNetworkListEntryProxyArp INTEGER,
            lcsSetupTcpIpNetworkListEntryForwarding INTEGER,
            lcsSetupTcpIpNetworkListEntryMtu Integer32
    }

-- {COLUMN} 1.3.6.1.4.1.2356.11.2.7.30.1.1
lcsSetupTcpIpNetworkListEntryNetworkName OBJECT-TYPE
    SYNTAX     DisplayString (SIZE(0..16))
    MAX-ACCESS read-write
    STATUS     current
    DESCRIPTION
            ""
    ::= { lcsSetupTcpIpNetworkListEntry 1 }

-- {COLUMN} 1.3.6.1.4.1.2356.11.2.7.30.1.2
lcsSetupTcpIpNetworkListEntryIpAddress OBJECT-TYPE
    SYNTAX     IpAddress
    MAX-ACCESS read-write
    STATUS     current
    DESCRIPTION
            ""
    ::= { lcsSetupTcpIpNetworkListEntry 2 }

-- {COLUMN} 1.3.6.1.4.1.2356.11.2.7.30.1.3
lcsSetupTcpIpNetworkListEntryIpNetmask OBJECT-TYPE
    SYNTAX     IpAddress
    MAX-ACCESS read-write
    STATUS     current
    DESCRIPTION
            ""
    ::= { lcsSetupTcpIpNetworkListEntry 3 }

-- {COLUMN} 1.3.6.1.4.1.2356.11.2.7.30.1.4
lcsSetupTcpIpNetworkListEntryVlanId OBJECT-TYPE
    SYNTAX     Integer32 (0..65535)
    MAX-ACCESS read-write
    STATUS     current
    DESCRIPTION
            ""
    ::= { lcsSetupTcpIpNetworkListEntry 4 }

-- {COLUMN} 1.3.6.1.4.1.2356.11.2.7.30.1.5
lcsSetupTcpIpNetworkListEntryInterface OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-write
    STATUS     current
    DESCRIPTION
            ""
    ::= { lcsSetupTcpIpNetworkListEntry 5 }

-- {COLUMN} 1.3.6.1.4.1.2356.11.2.7.30.1.6
lcsSetupTcpIpNetworkListEntrySrcCheck OBJECT-TYPE
    SYNTAX     INTEGER {
                  eLoose (0),
                  eStrict (1)
            }
    MAX-ACCESS read-write
    STATUS     current
    DESCRIPTION
            ""
    ::= { lcsSetupTcpIpNetworkListEntry 6 }

-- {COLUMN} 1.3.6.1.4.1.2356.11.2.7.30.1.7
lcsSetupTcpIpNetworkListEntryType OBJECT-TYPE
    SYNTAX     INTEGER {
                  eDisabled (0),
                  eIntranet (1),
                  eDmz (2)
            }
    MAX-ACCESS read-write
    STATUS     current
    DESCRIPTION
            ""
    ::= { lcsSetupTcpIpNetworkListEntry 7 }

-- {COLUMN} 1.3.6.1.4.1.2356.11.2.7.30.1.8
lcsSetupTcpIpNetworkListEntryRtgTag OBJECT-TYPE
    SYNTAX     Integer32 (0..65535)
    MAX-ACCESS read-write
    STATUS     current
    DESCRIPTION
            ""
    ::= { lcsSetupTcpIpNetworkListEntry 8 }

-- {COLUMN} 1.3.6.1.4.1.2356.11.2.7.30.1.9
lcsSetupTcpIpNetworkListEntryComment OBJECT-TYPE
    SYNTAX     DisplayString (SIZE(0..64))
    MAX-ACCESS read-write
    STATUS     current
    DESCRIPTION
            ""
    ::= { lcsSetupTcpIpNetworkListEntry 9 }

-- {COLUMN} 1.3.6.1.4.1.2356.11.2.7.30.1.10
lcsSetupTcpIpNetworkListEntryProxyArp OBJECT-TYPE
    SYNTAX     INTEGER {
                  eNo (0),
                  eYes (1)
            }
    MAX-ACCESS read-write
    STATUS     current
    DESCRIPTION
            "-- empty --"
    ::= { lcsSetupTcpIpNetworkListEntry 10 }

-- {COLUMN} 1.3.6.1.4.1.2356.11.2.7.30.1.11
lcsSetupTcpIpNetworkListEntryForwarding OBJECT-TYPE
    SYNTAX     INTEGER {
                  eNo (0),
                  eYes (1)
            }
    MAX-ACCESS read-write
    STATUS     current
    DESCRIPTION
            "-- empty --"
    ::= { lcsSetupTcpIpNetworkListEntry 11 }

-- {COLUMN} 1.3.6.1.4.1.2356.11.2.7.30.1.12
lcsSetupTcpIpNetworkListEntryMtu OBJECT-TYPE
    SYNTAX     Integer32 (0..65535)
    MAX-ACCESS read-write
    STATUS     current
    DESCRIPTION
            "-- empty --"
    ::= { lcsSetupTcpIpNetworkListEntry 12 }

-- {SCALAR} 1.3.6.1.4.1.2356.11.2.7.32
lcsSetupTcpIpDropGratuitousArp OBJECT-TYPE
    SYNTAX     INTEGER {
                  eNo (0),
                  eYes (1)
            }
    MAX-ACCESS read-write
    STATUS     current
    DESCRIPTION
            "-- empty --"
    ::= { lcsSetupTcpIp 32 }

-- {NODE} 1.3.6.1.4.1.2356.11.2.8
lcsSetupIpRouter OBJECT IDENTIFIER ::= { lcsSetup 8 }

-- {SCALAR} 1.3.6.1.4.1.2356.11.2.8.1
lcsSetupIpRouterOperating OBJECT-TYPE
    SYNTAX     INTEGER {
                  eNo (0),
                  eYes (1)
            }
    MAX-ACCESS read-write
    STATUS     current
    DESCRIPTION
            ""
    ::= { lcsSetupIpRouter 1 }

-- {TABLE} 1.3.6.1.4.1.2356.11.2.8.2
lcsSetupIpRouterIpRoutingTableTable OBJECT-TYPE
    SYNTAX     SEQUENCE OF LcsSetupIpRouterIpRoutingTableEntry
    MAX-ACCESS not-accessible
    STATUS     current
    DESCRIPTION
            ""
    ::= { lcsSetupIpRouter 2 }

-- {ROW} 1.3.6.1.4.1.2356.11.2.8.2.1
lcsSetupIpRouterIpRoutingTableEntry OBJECT-TYPE
    SYNTAX     LcsSetupIpRouterIpRoutingTableEntry
    MAX-ACCESS not-accessible
    STATUS     current
    DESCRIPTION
            ""
    INDEX {
            lcsSetupIpRouterIpRoutingTableEntryIpAddress,
            lcsSetupIpRouterIpRoutingTableEntryIpNetmask,
            lcsSetupIpRouterIpRoutingTableEntryRtgTag,
            lcsSetupIpRouterIpRoutingTableEntryAdminDistance
          }
    ::= { lcsSetupIpRouterIpRoutingTableTable 1 }

LcsSetupIpRouterIpRoutingTableEntry ::= SEQUENCE {
            lcsSetupIpRouterIpRoutingTableEntryIpAddress IpAddress,
            lcsSetupIpRouterIpRoutingTableEntryIpNetmask IpAddress,
            lcsSetupIpRouterIpRoutingTableEntryPeerOrIp DisplayString,
            lcsSetupIpRouterIpRoutingTableEntryDistance Integer32,
            lcsSetupIpRouterIpRoutingTableEntryMasquerade INTEGER,
            lcsSetupIpRouterIpRoutingTableEntryActive INTEGER,
            lcsSetupIpRouterIpRoutingTableEntryComment DisplayString,
            lcsSetupIpRouterIpRoutingTableEntryRtgTag Integer32,
            lcsSetupIpRouterIpRoutingTableEntryAdminDistance Integer32
    }

-- {COLUMN} 1.3.6.1.4.1.2356.11.2.8.2.1.1
lcsSetupIpRouterIpRoutingTableEntryIpAddress OBJECT-TYPE
    SYNTAX     IpAddress
    MAX-ACCESS read-write
    STATUS     current
    DESCRIPTION
            ""
    ::= { lcsSetupIpRouterIpRoutingTableEntry 1 }

-- {COLUMN} 1.3.6.1.4.1.2356.11.2.8.2.1.2
lcsSetupIpRouterIpRoutingTableEntryIpNetmask OBJECT-TYPE
    SYNTAX     IpAddress
    MAX-ACCESS read-write
    STATUS     current
    DESCRIPTION
            ""
    ::= { lcsSetupIpRouterIpRoutingTableEntry 2 }

-- {COLUMN} 1.3.6.1.4.1.2356.11.2.8.2.1.3
lcsSetupIpRouterIpRoutingTableEntryPeerOrIp OBJECT-TYPE
    SYNTAX     DisplayString (SIZE(0..21))
    MAX-ACCESS read-write
    STATUS     current
    DESCRIPTION
            ""
    ::= { lcsSetupIpRouterIpRoutingTableEntry 3 }

-- {COLUMN} 1.3.6.1.4.1.2356.11.2.8.2.1.4
lcsSetupIpRouterIpRoutingTableEntryDistance OBJECT-TYPE
    SYNTAX     Integer32 (0..255)
    MAX-ACCESS read-write
    STATUS     current
    DESCRIPTION
            ""
    ::= { lcsSetupIpRouterIpRoutingTableEntry 4 }

-- {COLUMN} 1.3.6.1.4.1.2356.11.2.8.2.1.5
lcsSetupIpRouterIpRoutingTableEntryMasquerade OBJECT-TYPE
    SYNTAX     INTEGER {
                  eNo (0),
                  eOn (1),
                  eIntranet (2)
            }
    MAX-ACCESS read-write
    STATUS     current
    DESCRIPTION
            ""
    ::= { lcsSetupIpRouterIpRoutingTableEntry 5 }

-- {COLUMN} 1.3.6.1.4.1.2356.11.2.8.2.1.6
lcsSetupIpRouterIpRoutingTableEntryActive OBJECT-TYPE
    SYNTAX     INTEGER {
                  eYes (0),
                  eNo (1),
                  eSemi (2)
            }
    MAX-ACCESS read-write
    STATUS     current
    DESCRIPTION
            ""
    ::= { lcsSetupIpRouterIpRoutingTableEntry 6 }

-- {COLUMN} 1.3.6.1.4.1.2356.11.2.8.2.1.7
lcsSetupIpRouterIpRoutingTableEntryComment OBJECT-TYPE
    SYNTAX     DisplayString (SIZE(0..64))
    MAX-ACCESS read-write
    STATUS     current
    DESCRIPTION
            ""
    ::= { lcsSetupIpRouterIpRoutingTableEntry 7 }

-- {COLUMN} 1.3.6.1.4.1.2356.11.2.8.2.1.8
lcsSetupIpRouterIpRoutingTableEntryRtgTag OBJECT-TYPE
    SYNTAX     Integer32 (0..65535)
    MAX-ACCESS read-write
    STATUS     current
    DESCRIPTION
            ""
    ::= { lcsSetupIpRouterIpRoutingTableEntry 8 }

-- {COLUMN} 1.3.6.1.4.1.2356.11.2.8.2.1.9
lcsSetupIpRouterIpRoutingTableEntryAdminDistance OBJECT-TYPE
    SYNTAX     Integer32 (0..255)
    MAX-ACCESS read-write
    STATUS     current
    DESCRIPTION
            "-- empty --"
    ::= { lcsSetupIpRouterIpRoutingTableEntry 9 }

-- {SCALAR} 1.3.6.1.4.1.2356.11.2.8.5
lcsSetupIpRouterProxyArp OBJECT-TYPE
    SYNTAX     INTEGER {
                  eNo (0),
                  eYes (1)
            }
    MAX-ACCESS read-write
    STATUS     current
    DESCRIPTION
            ""
    ::= { lcsSetupIpRouter 5 }

-- {SCALAR} 1.3.6.1.4.1.2356.11.2.8.6
lcsSetupIpRouterSendIcmpRedirect OBJECT-TYPE
    SYNTAX     INTEGER {
                  eYes (0),
                  eNo (1)
            }
    MAX-ACCESS read-write
    STATUS     current
    DESCRIPTION
            ""
    ::= { lcsSetupIpRouter 6 }

-- {NODE} 1.3.6.1.4.1.2356.11.2.8.7
lcsSetupIpRouterRoutingMethod OBJECT IDENTIFIER ::= { lcsSetupIpRouter 7 }

-- {SCALAR} 1.3.6.1.4.1.2356.11.2.8.7.1
lcsSetupIpRouterRoutingMethodRoutingMethod OBJECT-TYPE
    SYNTAX     INTEGER {
                  eNormal (0),
                  eTypeOfService (1),
                  eDiffserv (2)
            }
    MAX-ACCESS read-write
    STATUS     current
    DESCRIPTION
            ""
    ::= { lcsSetupIpRouterRoutingMethod 1 }

-- {SCALAR} 1.3.6.1.4.1.2356.11.2.8.7.2
lcsSetupIpRouterRoutingMethodIcmpRoutingMethod OBJECT-TYPE
    SYNTAX     INTEGER {
                  eNormal (0),
                  eReliable (1)
            }
    MAX-ACCESS read-write
    STATUS     current
    DESCRIPTION
            ""
    ::= { lcsSetupIpRouterRoutingMethod 2 }

-- {SCALAR} 1.3.6.1.4.1.2356.11.2.8.7.3
lcsSetupIpRouterRoutingMethodSynAckSpeedup OBJECT-TYPE
    SYNTAX     INTEGER {
                  eNo (0),
                  eYes (1)
            }
    MAX-ACCESS read-write
    STATUS     current
    DESCRIPTION
            ""
    ::= { lcsSetupIpRouterRoutingMethod 3 }

-- {SCALAR} 1.3.6.1.4.1.2356.11.2.8.7.4
lcsSetupIpRouterRoutingMethodL2L3Tagging OBJECT-TYPE
    SYNTAX     INTEGER {
                  eNo (0),
                  eYes (1),
                  eAuto (2)
            }
    MAX-ACCESS read-write
    STATUS     current
    DESCRIPTION
            ""
    ::= { lcsSetupIpRouterRoutingMethod 4 }

-- {SCALAR} 1.3.6.1.4.1.2356.11.2.8.7.5
lcsSetupIpRouterRoutingMethodL3L2Tagging OBJECT-TYPE
    SYNTAX     INTEGER {
                  eNo (0),
                  eYes (1)
            }
    MAX-ACCESS read-write
    STATUS     current
    DESCRIPTION
            ""
    ::= { lcsSetupIpRouterRoutingMethod 5 }

-- {SCALAR} 1.3.6.1.4.1.2356.11.2.8.7.6
lcsSetupIpRouterRoutingMethodRouteInternalServices OBJECT-TYPE
    SYNTAX     INTEGER {
                  eNo (0),
                  eYes (1)
            }
    MAX-ACCESS read-write
    STATUS     current
    DESCRIPTION
            ""
    ::= { lcsSetupIpRouterRoutingMethod 6 }

-- {NODE} 1.3.6.1.4.1.2356.11.2.8.8
lcsSetupIpRouterRip OBJECT IDENTIFIER ::= { lcsSetupIpRouter 8 }

-- {SCALAR} 1.3.6.1.4.1.2356.11.2.8.8.2
lcsSetupIpRouterRipR1Mask OBJECT-TYPE
    SYNTAX     INTEGER {
                  eClass (0),
                  eAddress (1),
                  eClPlusAddr (2)
            }
    MAX-ACCESS read-write
    STATUS     current
    DESCRIPTION
            ""
    ::= { lcsSetupIpRouterRip 2 }

-- {TABLE} 1.3.6.1.4.1.2356.11.2.8.8.4
lcsSetupIpRouterRipWanSitesTable OBJECT-TYPE
    SYNTAX     SEQUENCE OF LcsSetupIpRouterRipWanSitesEntry
    MAX-ACCESS not-accessible
    STATUS     current
    DESCRIPTION
            ""
    ::= { lcsSetupIpRouterRip 4 }

-- {ROW} 1.3.6.1.4.1.2356.11.2.8.8.4.1
lcsSetupIpRouterRipWanSitesEntry OBJECT-TYPE
    SYNTAX     LcsSetupIpRouterRipWanSitesEntry
    MAX-ACCESS not-accessible
    STATUS     current
    DESCRIPTION
            ""
    INDEX {
            lcsSetupIpRouterRipWanSitesEntryPeer
          }
    ::= { lcsSetupIpRouterRipWanSitesTable 1 }

LcsSetupIpRouterRipWanSitesEntry ::= SEQUENCE {
            lcsSetupIpRouterRipWanSitesEntryPeer DisplayString,
            lcsSetupIpRouterRipWanSitesEntryRipType INTEGER,
            lcsSetupIpRouterRipWanSitesEntryRipAccept INTEGER,
            lcsSetupIpRouterRipWanSitesEntryMasquerade INTEGER,
            lcsSetupIpRouterRipWanSitesEntryDftRtgTag Integer32,
            lcsSetupIpRouterRipWanSitesEntryRtgTagList DisplayString,
            lcsSetupIpRouterRipWanSitesEntryPoisonedReverse INTEGER,
            lcsSetupIpRouterRipWanSitesEntryRfc2091 INTEGER,
            lcsSetupIpRouterRipWanSitesEntryGateway IpAddress,
            lcsSetupIpRouterRipWanSitesEntryRxFilter DisplayString,
            lcsSetupIpRouterRipWanSitesEntryTxFilter DisplayString,
            lcsSetupIpRouterRipWanSitesEntryRipSend INTEGER,
            lcsSetupIpRouterRipWanSitesEntryLoopbackAddress DisplayString,
            lcsSetupIpRouterRipWanSitesEntryIgnoreTags INTEGER
    }

-- {COLUMN} 1.3.6.1.4.1.2356.11.2.8.8.4.1.1
lcsSetupIpRouterRipWanSitesEntryPeer OBJECT-TYPE
    SYNTAX     DisplayString (SIZE(0..16))
    MAX-ACCESS read-write
    STATUS     current
    DESCRIPTION
            ""
    ::= { lcsSetupIpRouterRipWanSitesEntry 1 }

-- {COLUMN} 1.3.6.1.4.1.2356.11.2.8.8.4.1.2
lcsSetupIpRouterRipWanSitesEntryRipType OBJECT-TYPE
    SYNTAX     INTEGER {
                  eOff (0),
                  eRip1 (1),
                  eR1Comp (2),
                  eRip2 (3)
            }
    MAX-ACCESS read-write
    STATUS     current
    DESCRIPTION
            ""
    ::= { lcsSetupIpRouterRipWanSitesEntry 2 }

-- {COLUMN} 1.3.6.1.4.1.2356.11.2.8.8.4.1.3
lcsSetupIpRouterRipWanSitesEntryRipAccept OBJECT-TYPE
    SYNTAX     INTEGER {
                  eNo (0),
                  eYes (1)
            }
    MAX-ACCESS read-write
    STATUS     current
    DESCRIPTION
            ""
    ::= { lcsSetupIpRouterRipWanSitesEntry 3 }

-- {COLUMN} 1.3.6.1.4.1.2356.11.2.8.8.4.1.4
lcsSetupIpRouterRipWanSitesEntryMasquerade OBJECT-TYPE
    SYNTAX     INTEGER {
                  eAuto (0),
                  eOn (1),
                  eIntranet (2)
            }
    MAX-ACCESS read-write
    STATUS     current
    DESCRIPTION
            ""
    ::= { lcsSetupIpRouterRipWanSitesEntry 4 }

-- {COLUMN} 1.3.6.1.4.1.2356.11.2.8.8.4.1.5
lcsSetupIpRouterRipWanSitesEntryDftRtgTag OBJECT-TYPE
    SYNTAX     Integer32 (0..65535)
    MAX-ACCESS read-write
    STATUS     current
    DESCRIPTION
            ""
    ::= { lcsSetupIpRouterRipWanSitesEntry 5 }

-- {COLUMN} 1.3.6.1.4.1.2356.11.2.8.8.4.1.6
lcsSetupIpRouterRipWanSitesEntryRtgTagList OBJECT-TYPE
    SYNTAX     DisplayString (SIZE(0..33))
    MAX-ACCESS read-write
    STATUS     current
    DESCRIPTION
            ""
    ::= { lcsSetupIpRouterRipWanSitesEntry 6 }

-- {COLUMN} 1.3.6.1.4.1.2356.11.2.8.8.4.1.7
lcsSetupIpRouterRipWanSitesEntryPoisonedReverse OBJECT-TYPE
    SYNTAX     INTEGER {
                  eNo (0),
                  eYes (1)
            }
    MAX-ACCESS read-write
    STATUS     current
    DESCRIPTION
            ""
    ::= { lcsSetupIpRouterRipWanSitesEntry 7 }

-- {COLUMN} 1.3.6.1.4.1.2356.11.2.8.8.4.1.8
lcsSetupIpRouterRipWanSitesEntryRfc2091 OBJECT-TYPE
    SYNTAX     INTEGER {
                  eNo (0),
                  eYes (1)
            }
    MAX-ACCESS read-write
    STATUS     current
    DESCRIPTION
            ""
    ::= { lcsSetupIpRouterRipWanSitesEntry 8 }

-- {COLUMN} 1.3.6.1.4.1.2356.11.2.8.8.4.1.9
lcsSetupIpRouterRipWanSitesEntryGateway OBJECT-TYPE
    SYNTAX     IpAddress
    MAX-ACCESS read-write
    STATUS     current
    DESCRIPTION
            ""
    ::= { lcsSetupIpRouterRipWanSitesEntry 9 }

-- {COLUMN} 1.3.6.1.4.1.2356.11.2.8.8.4.1.10
lcsSetupIpRouterRipWanSitesEntryRxFilter OBJECT-TYPE
    SYNTAX     DisplayString (SIZE(0..16))
    MAX-ACCESS read-write
    STATUS     current
    DESCRIPTION
            ""
    ::= { lcsSetupIpRouterRipWanSitesEntry 10 }

-- {COLUMN} 1.3.6.1.4.1.2356.11.2.8.8.4.1.11
lcsSetupIpRouterRipWanSitesEntryTxFilter OBJECT-TYPE
    SYNTAX     DisplayString (SIZE(0..16))
    MAX-ACCESS read-write
    STATUS     current
    DESCRIPTION
            ""
    ::= { lcsSetupIpRouterRipWanSitesEntry 11 }

-- {COLUMN} 1.3.6.1.4.1.2356.11.2.8.8.4.1.12
lcsSetupIpRouterRipWanSitesEntryRipSend OBJECT-TYPE
    SYNTAX     INTEGER {
                  eNo (0),
                  eYes (1)
            }
    MAX-ACCESS read-write
    STATUS     current
    DESCRIPTION
            ""
    ::= { lcsSetupIpRouterRipWanSitesEntry 12 }

-- {COLUMN} 1.3.6.1.4.1.2356.11.2.8.8.4.1.13
lcsSetupIpRouterRipWanSitesEntryLoopbackAddress OBJECT-TYPE
    SYNTAX     DisplayString (SIZE(0..16))
    MAX-ACCESS read-write
    STATUS     current
    DESCRIPTION
            "-- empty --"
    ::= { lcsSetupIpRouterRipWanSitesEntry 13 }

-- {COLUMN} 1.3.6.1.4.1.2356.11.2.8.8.4.1.14
lcsSetupIpRouterRipWanSitesEntryIgnoreTags OBJECT-TYPE
    SYNTAX     INTEGER {
                  eNo (0),
                  eYes (1)
            }
    MAX-ACCESS read-write
    STATUS     current
    DESCRIPTION
            "-- empty --"
    ::= { lcsSetupIpRouterRipWanSitesEntry 14 }

-- {TABLE} 1.3.6.1.4.1.2356.11.2.8.8.5
lcsSetupIpRouterRipLanSitesTable OBJECT-TYPE
    SYNTAX     SEQUENCE OF LcsSetupIpRouterRipLanSitesEntry
    MAX-ACCESS not-accessible
    STATUS     current
    DESCRIPTION
            ""
    ::= { lcsSetupIpRouterRip 5 }

-- {ROW} 1.3.6.1.4.1.2356.11.2.8.8.5.1
lcsSetupIpRouterRipLanSitesEntry OBJECT-TYPE
    SYNTAX     LcsSetupIpRouterRipLanSitesEntry
    MAX-ACCESS not-accessible
    STATUS     current
    DESCRIPTION
            ""
    INDEX {
            lcsSetupIpRouterRipLanSitesEntryNetworkName
          }
    ::= { lcsSetupIpRouterRipLanSitesTable 1 }

LcsSetupIpRouterRipLanSitesEntry ::= SEQUENCE {
            lcsSetupIpRouterRipLanSitesEntryNetworkName DisplayString,
            lcsSetupIpRouterRipLanSitesEntryRipType INTEGER,
            lcsSetupIpRouterRipLanSitesEntryRipAccept INTEGER,
            lcsSetupIpRouterRipLanSitesEntryPropagate INTEGER,
            lcsSetupIpRouterRipLanSitesEntryDftRtgTag Integer32,
            lcsSetupIpRouterRipLanSitesEntryRtgTagList DisplayString,
            lcsSetupIpRouterRipLanSitesEntryPoisonedReverse INTEGER,
            lcsSetupIpRouterRipLanSitesEntryRxFilter DisplayString,
            lcsSetupIpRouterRipLanSitesEntryTxFilter DisplayString,
            lcsSetupIpRouterRipLanSitesEntryRipSend INTEGER,
            lcsSetupIpRouterRipLanSitesEntryIgnoreTags INTEGER
    }

-- {COLUMN} 1.3.6.1.4.1.2356.11.2.8.8.5.1.1
lcsSetupIpRouterRipLanSitesEntryNetworkName OBJECT-TYPE
    SYNTAX     DisplayString (SIZE(0..16))
    MAX-ACCESS read-write
    STATUS     current
    DESCRIPTION
            ""
    ::= { lcsSetupIpRouterRipLanSitesEntry 1 }

-- {COLUMN} 1.3.6.1.4.1.2356.11.2.8.8.5.1.2
lcsSetupIpRouterRipLanSitesEntryRipType OBJECT-TYPE
    SYNTAX     INTEGER {
                  eOff (0),
                  eRip1 (1),
                  eR1Comp (2),
                  eRip2 (3)
            }
    MAX-ACCESS read-write
    STATUS     current
    DESCRIPTION
            ""
    ::= { lcsSetupIpRouterRipLanSitesEntry 2 }

-- {COLUMN} 1.3.6.1.4.1.2356.11.2.8.8.5.1.3
lcsSetupIpRouterRipLanSitesEntryRipAccept OBJECT-TYPE
    SYNTAX     INTEGER {
                  eNo (0),
                  eYes (1)
            }
    MAX-ACCESS read-write
    STATUS     current
    DESCRIPTION
            ""
    ::= { lcsSetupIpRouterRipLanSitesEntry 3 }

-- {COLUMN} 1.3.6.1.4.1.2356.11.2.8.8.5.1.4
lcsSetupIpRouterRipLanSitesEntryPropagate OBJECT-TYPE
    SYNTAX     INTEGER {
                  eNo (0),
                  eYes (1)
            }
    MAX-ACCESS read-write
    STATUS     current
    DESCRIPTION
            ""
    ::= { lcsSetupIpRouterRipLanSitesEntry 4 }

-- {COLUMN} 1.3.6.1.4.1.2356.11.2.8.8.5.1.5
lcsSetupIpRouterRipLanSitesEntryDftRtgTag OBJECT-TYPE
    SYNTAX     Integer32 (0..65535)
    MAX-ACCESS read-write
    STATUS     current
    DESCRIPTION
            ""
    ::= { lcsSetupIpRouterRipLanSitesEntry 5 }

-- {COLUMN} 1.3.6.1.4.1.2356.11.2.8.8.5.1.6
lcsSetupIpRouterRipLanSitesEntryRtgTagList OBJECT-TYPE
    SYNTAX     DisplayString (SIZE(0..33))
    MAX-ACCESS read-write
    STATUS     current
    DESCRIPTION
            ""
    ::= { lcsSetupIpRouterRipLanSitesEntry 6 }

-- {COLUMN} 1.3.6.1.4.1.2356.11.2.8.8.5.1.7
lcsSetupIpRouterRipLanSitesEntryPoisonedReverse OBJECT-TYPE
    SYNTAX     INTEGER {
                  eNo (0),
                  eYes (1)
            }
    MAX-ACCESS read-write
    STATUS     current
    DESCRIPTION
            ""
    ::= { lcsSetupIpRouterRipLanSitesEntry 7 }

-- {COLUMN} 1.3.6.1.4.1.2356.11.2.8.8.5.1.10
lcsSetupIpRouterRipLanSitesEntryRxFilter OBJECT-TYPE
    SYNTAX     DisplayString (SIZE(0..16))
    MAX-ACCESS read-write
    STATUS     current
    DESCRIPTION
            ""
    ::= { lcsSetupIpRouterRipLanSitesEntry 10 }

-- {COLUMN} 1.3.6.1.4.1.2356.11.2.8.8.5.1.11
lcsSetupIpRouterRipLanSitesEntryTxFilter OBJECT-TYPE
    SYNTAX     DisplayString (SIZE(0..16))
    MAX-ACCESS read-write
    STATUS     current
    DESCRIPTION
            ""
    ::= { lcsSetupIpRouterRipLanSitesEntry 11 }

-- {COLUMN} 1.3.6.1.4.1.2356.11.2.8.8.5.1.12
lcsSetupIpRouterRipLanSitesEntryRipSend OBJECT-TYPE
    SYNTAX     INTEGER {
                  eNo (0),
                  eYes (1)
            }
    MAX-ACCESS read-write
    STATUS     current
    DESCRIPTION
            ""
    ::= { lcsSetupIpRouterRipLanSitesEntry 12 }

-- {COLUMN} 1.3.6.1.4.1.2356.11.2.8.8.5.1.14
lcsSetupIpRouterRipLanSitesEntryIgnoreTags OBJECT-TYPE
    SYNTAX     INTEGER {
                  eNo (0),
                  eYes (1)
            }
    MAX-ACCESS read-write
    STATUS     current
    DESCRIPTION
            "-- empty --"
    ::= { lcsSetupIpRouterRipLanSitesEntry 14 }

-- {NODE} 1.3.6.1.4.1.2356.11.2.8.8.6
lcsSetupIpRouterRipParameter OBJECT IDENTIFIER ::= { lcsSetupIpRouterRip 6 }

-- {SCALAR} 1.3.6.1.4.1.2356.11.2.8.8.6.1
lcsSetupIpRouterRipParameterUpdate OBJECT-TYPE
    SYNTAX     Integer32 (0..255)
    MAX-ACCESS read-write
    STATUS     current
    DESCRIPTION
            ""
    ::= { lcsSetupIpRouterRipParameter 1 }

-- {SCALAR} 1.3.6.1.4.1.2356.11.2.8.8.6.2
lcsSetupIpRouterRipParameterHolddown OBJECT-TYPE
    SYNTAX     Integer32 (0..255)
    MAX-ACCESS read-write
    STATUS     current
    DESCRIPTION
            ""
    ::= { lcsSetupIpRouterRipParameter 2 }

-- {SCALAR} 1.3.6.1.4.1.2356.11.2.8.8.6.3
lcsSetupIpRouterRipParameterInvalidate OBJECT-TYPE
    SYNTAX     Integer32 (0..255)
    MAX-ACCESS read-write
    STATUS     current
    DESCRIPTION
            ""
    ::= { lcsSetupIpRouterRipParameter 3 }

-- {SCALAR} 1.3.6.1.4.1.2356.11.2.8.8.6.4
lcsSetupIpRouterRipParameterFlush OBJECT-TYPE
    SYNTAX     Integer32 (0..255)
    MAX-ACCESS read-write
    STATUS     current
    DESCRIPTION
            ""
    ::= { lcsSetupIpRouterRipParameter 4 }

-- {SCALAR} 1.3.6.1.4.1.2356.11.2.8.8.6.5
lcsSetupIpRouterRipParameterUpdDelay OBJECT-TYPE
    SYNTAX     Integer32 (0..255)
    MAX-ACCESS read-write
    STATUS     current
    DESCRIPTION
            ""
    ::= { lcsSetupIpRouterRipParameter 5 }

-- {SCALAR} 1.3.6.1.4.1.2356.11.2.8.8.6.6
lcsSetupIpRouterRipParameterMaxHopcount OBJECT-TYPE
    SYNTAX     Integer32 (0..255)
    MAX-ACCESS read-write
    STATUS     current
    DESCRIPTION
            ""
    ::= { lcsSetupIpRouterRipParameter 6 }

-- {SCALAR} 1.3.6.1.4.1.2356.11.2.8.8.6.7
lcsSetupIpRouterRipParameterRoutesPerFrame OBJECT-TYPE
    SYNTAX     Integer32 (0..255)
    MAX-ACCESS read-write
    STATUS     current
    DESCRIPTION
            ""
    ::= { lcsSetupIpRouterRipParameter 7 }

-- {SCALAR} 1.3.6.1.4.1.2356.11.2.8.8.6.8
lcsSetupIpRouterRipParameterInterPacketDelay OBJECT-TYPE
    SYNTAX     Integer32 (0..255)
    MAX-ACCESS read-write
    STATUS     current
    DESCRIPTION
            "-- empty --"
    ::= { lcsSetupIpRouterRipParameter 8 }

-- {TABLE} 1.3.6.1.4.1.2356.11.2.8.8.7
lcsSetupIpRouterRipFilterTable OBJECT-TYPE
    SYNTAX     SEQUENCE OF LcsSetupIpRouterRipFilterEntry
    MAX-ACCESS not-accessible
    STATUS     current
    DESCRIPTION
            ""
    ::= { lcsSetupIpRouterRip 7 }

-- {ROW} 1.3.6.1.4.1.2356.11.2.8.8.7.1
lcsSetupIpRouterRipFilterEntry OBJECT-TYPE
    SYNTAX     LcsSetupIpRouterRipFilterEntry
    MAX-ACCESS not-accessible
    STATUS     current
    DESCRIPTION
            ""
    INDEX {
            lcsSetupIpRouterRipFilterEntryName
          }
    ::= { lcsSetupIpRouterRipFilterTable 1 }

LcsSetupIpRouterRipFilterEntry ::= SEQUENCE {
            lcsSetupIpRouterRipFilterEntryName DisplayString,
            lcsSetupIpRouterRipFilterEntryFilter DisplayString
    }

-- {COLUMN} 1.3.6.1.4.1.2356.11.2.8.8.7.1.1
lcsSetupIpRouterRipFilterEntryName OBJECT-TYPE
    SYNTAX     DisplayString (SIZE(0..18))
    MAX-ACCESS read-write
    STATUS     current
    DESCRIPTION
            ""
    ::= { lcsSetupIpRouterRipFilterEntry 1 }

-- {COLUMN} 1.3.6.1.4.1.2356.11.2.8.8.7.1.2
lcsSetupIpRouterRipFilterEntryFilter OBJECT-TYPE
    SYNTAX     DisplayString (SIZE(0..64))
    MAX-ACCESS read-write
    STATUS     current
    DESCRIPTION
            ""
    ::= { lcsSetupIpRouterRipFilterEntry 2 }

-- {TABLE} 1.3.6.1.4.1.2356.11.2.8.8.8
lcsSetupIpRouterRipBestRoutesTable OBJECT-TYPE
    SYNTAX     SEQUENCE OF LcsSetupIpRouterRipBestRoutesEntry
    MAX-ACCESS not-accessible
    STATUS     current
    DESCRIPTION
            ""
    ::= { lcsSetupIpRouterRip 8 }

-- {ROW} 1.3.6.1.4.1.2356.11.2.8.8.8.1
lcsSetupIpRouterRipBestRoutesEntry OBJECT-TYPE
    SYNTAX     LcsSetupIpRouterRipBestRoutesEntry
    MAX-ACCESS not-accessible
    STATUS     current
    DESCRIPTION
            ""
    INDEX {
            lcsSetupIpRouterRipBestRoutesEntryIpAddress,
            lcsSetupIpRouterRipBestRoutesEntryIpNetmask,
            lcsSetupIpRouterRipBestRoutesEntryRtgTag,
            lcsSetupIpRouterRipBestRoutesEntryGateway
          }
    ::= { lcsSetupIpRouterRipBestRoutesTable 1 }

LcsSetupIpRouterRipBestRoutesEntry ::= SEQUENCE {
            lcsSetupIpRouterRipBestRoutesEntryIpAddress IpAddress,
            lcsSetupIpRouterRipBestRoutesEntryIpNetmask IpAddress,
            lcsSetupIpRouterRipBestRoutesEntryTime Integer32,
            lcsSetupIpRouterRipBestRoutesEntryDistance Integer32,
            lcsSetupIpRouterRipBestRoutesEntryGateway IpAddress,
            lcsSetupIpRouterRipBestRoutesEntryRtgTag Integer32,
            lcsSetupIpRouterRipBestRoutesEntryPeer DisplayString,
            lcsSetupIpRouterRipBestRoutesEntryVlanId Integer32,
            lcsSetupIpRouterRipBestRoutesEntryNetworkName DisplayString,
            lcsSetupIpRouterRipBestRoutesEntryPort INTEGER
    }

-- {COLUMN} 1.3.6.1.4.1.2356.11.2.8.8.8.1.1
lcsSetupIpRouterRipBestRoutesEntryIpAddress OBJECT-TYPE
    SYNTAX     IpAddress
    MAX-ACCESS read-only
    STATUS     current
    DESCRIPTION
            ""
    ::= { lcsSetupIpRouterRipBestRoutesEntry 1 }

-- {COLUMN} 1.3.6.1.4.1.2356.11.2.8.8.8.1.2
lcsSetupIpRouterRipBestRoutesEntryIpNetmask OBJECT-TYPE
    SYNTAX     IpAddress
    MAX-ACCESS read-only
    STATUS     current
    DESCRIPTION
            ""
    ::= { lcsSetupIpRouterRipBestRoutesEntry 2 }

-- {COLUMN} 1.3.6.1.4.1.2356.11.2.8.8.8.1.3
lcsSetupIpRouterRipBestRoutesEntryTime OBJECT-TYPE
    SYNTAX     Integer32 (0..65535)
    MAX-ACCESS read-only
    STATUS     current
    DESCRIPTION
            ""
    ::= { lcsSetupIpRouterRipBestRoutesEntry 3 }

-- {COLUMN} 1.3.6.1.4.1.2356.11.2.8.8.8.1.4
lcsSetupIpRouterRipBestRoutesEntryDistance OBJECT-TYPE
    SYNTAX     Integer32 (0..65535)
    MAX-ACCESS read-only
    STATUS     current
    DESCRIPTION
            ""
    ::= { lcsSetupIpRouterRipBestRoutesEntry 4 }

-- {COLUMN} 1.3.6.1.4.1.2356.11.2.8.8.8.1.5
lcsSetupIpRouterRipBestRoutesEntryGateway OBJECT-TYPE
    SYNTAX     IpAddress
    MAX-ACCESS read-only
    STATUS     current
    DESCRIPTION
            ""
    ::= { lcsSetupIpRouterRipBestRoutesEntry 5 }

-- {COLUMN} 1.3.6.1.4.1.2356.11.2.8.8.8.1.6
lcsSetupIpRouterRipBestRoutesEntryRtgTag OBJECT-TYPE
    SYNTAX     Integer32 (0..65535)
    MAX-ACCESS read-only
    STATUS     current
    DESCRIPTION
            ""
    ::= { lcsSetupIpRouterRipBestRoutesEntry 6 }

-- {COLUMN} 1.3.6.1.4.1.2356.11.2.8.8.8.1.8
lcsSetupIpRouterRipBestRoutesEntryPeer OBJECT-TYPE
    SYNTAX     DisplayString (SIZE(0..255))
    MAX-ACCESS read-only
    STATUS     current
    DESCRIPTION
            ""
    ::= { lcsSetupIpRouterRipBestRoutesEntry 8 }

-- {COLUMN} 1.3.6.1.4.1.2356.11.2.8.8.8.1.10
lcsSetupIpRouterRipBestRoutesEntryVlanId OBJECT-TYPE
    SYNTAX     Integer32 (0..65535)
    MAX-ACCESS read-only
    STATUS     current
    DESCRIPTION
            ""
    ::= { lcsSetupIpRouterRipBestRoutesEntry 10 }

-- {COLUMN} 1.3.6.1.4.1.2356.11.2.8.8.8.1.11
lcsSetupIpRouterRipBestRoutesEntryNetworkName OBJECT-TYPE
    SYNTAX     DisplayString (SIZE(0..255))
    MAX-ACCESS read-only
    STATUS     current
    DESCRIPTION
            ""
    ::= { lcsSetupIpRouterRipBestRoutesEntry 11 }

-- {COLUMN} 1.3.6.1.4.1.2356.11.2.8.8.8.1.12
lcsSetupIpRouterRipBestRoutesEntryPort OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsSetupIpRouterRipBestRoutesEntry 12 }

-- {TABLE} 1.3.6.1.4.1.2356.11.2.8.8.9
lcsSetupIpRouterRipAllRoutesTable OBJECT-TYPE
    SYNTAX     SEQUENCE OF LcsSetupIpRouterRipAllRoutesEntry
    MAX-ACCESS not-accessible
    STATUS     current
    DESCRIPTION
            ""
    ::= { lcsSetupIpRouterRip 9 }

-- {ROW} 1.3.6.1.4.1.2356.11.2.8.8.9.1
lcsSetupIpRouterRipAllRoutesEntry OBJECT-TYPE
    SYNTAX     LcsSetupIpRouterRipAllRoutesEntry
    MAX-ACCESS not-accessible
    STATUS     current
    DESCRIPTION
            ""
    INDEX {
            lcsSetupIpRouterRipAllRoutesEntryIpAddress,
            lcsSetupIpRouterRipAllRoutesEntryIpNetmask,
            lcsSetupIpRouterRipAllRoutesEntryRtgTag,
            lcsSetupIpRouterRipAllRoutesEntryGateway
          }
    ::= { lcsSetupIpRouterRipAllRoutesTable 1 }

LcsSetupIpRouterRipAllRoutesEntry ::= SEQUENCE {
            lcsSetupIpRouterRipAllRoutesEntryIpAddress IpAddress,
            lcsSetupIpRouterRipAllRoutesEntryIpNetmask IpAddress,
            lcsSetupIpRouterRipAllRoutesEntryTime Integer32,
            lcsSetupIpRouterRipAllRoutesEntryDistance Integer32,
            lcsSetupIpRouterRipAllRoutesEntryGateway IpAddress,
            lcsSetupIpRouterRipAllRoutesEntryRtgTag Integer32,
            lcsSetupIpRouterRipAllRoutesEntryPeer DisplayString,
            lcsSetupIpRouterRipAllRoutesEntryVlanId Integer32,
            lcsSetupIpRouterRipAllRoutesEntryNetworkName DisplayString,
            lcsSetupIpRouterRipAllRoutesEntryPort INTEGER
    }

-- {COLUMN} 1.3.6.1.4.1.2356.11.2.8.8.9.1.1
lcsSetupIpRouterRipAllRoutesEntryIpAddress OBJECT-TYPE
    SYNTAX     IpAddress
    MAX-ACCESS read-only
    STATUS     current
    DESCRIPTION
            ""
    ::= { lcsSetupIpRouterRipAllRoutesEntry 1 }

-- {COLUMN} 1.3.6.1.4.1.2356.11.2.8.8.9.1.2
lcsSetupIpRouterRipAllRoutesEntryIpNetmask OBJECT-TYPE
    SYNTAX     IpAddress
    MAX-ACCESS read-only
    STATUS     current
    DESCRIPTION
            ""
    ::= { lcsSetupIpRouterRipAllRoutesEntry 2 }

-- {COLUMN} 1.3.6.1.4.1.2356.11.2.8.8.9.1.3
lcsSetupIpRouterRipAllRoutesEntryTime OBJECT-TYPE
    SYNTAX     Integer32 (0..65535)
    MAX-ACCESS read-only
    STATUS     current
    DESCRIPTION
            ""
    ::= { lcsSetupIpRouterRipAllRoutesEntry 3 }

-- {COLUMN} 1.3.6.1.4.1.2356.11.2.8.8.9.1.4
lcsSetupIpRouterRipAllRoutesEntryDistance OBJECT-TYPE
    SYNTAX     Integer32 (0..65535)
    MAX-ACCESS read-only
    STATUS     current
    DESCRIPTION
            ""
    ::= { lcsSetupIpRouterRipAllRoutesEntry 4 }

-- {COLUMN} 1.3.6.1.4.1.2356.11.2.8.8.9.1.5
lcsSetupIpRouterRipAllRoutesEntryGateway OBJECT-TYPE
    SYNTAX     IpAddress
    MAX-ACCESS read-only
    STATUS     current
    DESCRIPTION
            ""
    ::= { lcsSetupIpRouterRipAllRoutesEntry 5 }

-- {COLUMN} 1.3.6.1.4.1.2356.11.2.8.8.9.1.6
lcsSetupIpRouterRipAllRoutesEntryRtgTag OBJECT-TYPE
    SYNTAX     Integer32 (0..65535)
    MAX-ACCESS read-only
    STATUS     current
    DESCRIPTION
            ""
    ::= { lcsSetupIpRouterRipAllRoutesEntry 6 }

-- {COLUMN} 1.3.6.1.4.1.2356.11.2.8.8.9.1.8
lcsSetupIpRouterRipAllRoutesEntryPeer OBJECT-TYPE
    SYNTAX     DisplayString (SIZE(0..255))
    MAX-ACCESS read-only
    STATUS     current
    DESCRIPTION
            ""
    ::= { lcsSetupIpRouterRipAllRoutesEntry 8 }

-- {COLUMN} 1.3.6.1.4.1.2356.11.2.8.8.9.1.10
lcsSetupIpRouterRipAllRoutesEntryVlanId OBJECT-TYPE
    SYNTAX     Integer32 (0..65535)
    MAX-ACCESS read-only
    STATUS     current
    DESCRIPTION
            ""
    ::= { lcsSetupIpRouterRipAllRoutesEntry 10 }

-- {COLUMN} 1.3.6.1.4.1.2356.11.2.8.8.9.1.11
lcsSetupIpRouterRipAllRoutesEntryNetworkName OBJECT-TYPE
    SYNTAX     DisplayString (SIZE(0..255))
    MAX-ACCESS read-only
    STATUS     current
    DESCRIPTION
            ""
    ::= { lcsSetupIpRouterRipAllRoutesEntry 11 }

-- {COLUMN} 1.3.6.1.4.1.2356.11.2.8.8.9.1.12
lcsSetupIpRouterRipAllRoutesEntryPort OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsSetupIpRouterRipAllRoutesEntry 12 }

-- {NODE} 1.3.6.1.4.1.2356.11.2.8.9
lcsSetupIpRouter1NNat OBJECT IDENTIFIER ::= { lcsSetupIpRouter 9 }

-- {SCALAR} 1.3.6.1.4.1.2356.11.2.8.9.1
lcsSetupIpRouter1NNatTcpAgingSeconds OBJECT-TYPE
    SYNTAX     Integer32 (0..65535)
    MAX-ACCESS read-write
    STATUS     current
    DESCRIPTION
            ""
    ::= { lcsSetupIpRouter1NNat 1 }

-- {SCALAR} 1.3.6.1.4.1.2356.11.2.8.9.2
lcsSetupIpRouter1NNatUdpAgingSeconds OBJECT-TYPE
    SYNTAX     Integer32 (0..65535)
    MAX-ACCESS read-write
    STATUS     current
    DESCRIPTION
            ""
    ::= { lcsSetupIpRouter1NNat 2 }

-- {SCALAR} 1.3.6.1.4.1.2356.11.2.8.9.3
lcsSetupIpRouter1NNatIcmpAgingSeconds OBJECT-TYPE
    SYNTAX     Integer32 (0..65535)
    MAX-ACCESS read-write
    STATUS     current
    DESCRIPTION
            ""
    ::= { lcsSetupIpRouter1NNat 3 }

-- {TABLE} 1.3.6.1.4.1.2356.11.2.8.9.4
lcsSetupIpRouter1NNatServiceTableTable OBJECT-TYPE
    SYNTAX     SEQUENCE OF LcsSetupIpRouter1NNatServiceTableEntry
    MAX-ACCESS not-accessible
    STATUS     current
    DESCRIPTION
            ""
    ::= { lcsSetupIpRouter1NNat 4 }

-- {ROW} 1.3.6.1.4.1.2356.11.2.8.9.4.1
lcsSetupIpRouter1NNatServiceTableEntry OBJECT-TYPE
    SYNTAX     LcsSetupIpRouter1NNatServiceTableEntry
    MAX-ACCESS not-accessible
    STATUS     current
    DESCRIPTION
            ""
    INDEX {
            lcsSetupIpRouter1NNatServiceTableEntryDPortFrom,
            lcsSetupIpRouter1NNatServiceTableEntryDPortTo,
            lcsSetupIpRouter1NNatServiceTableEntryProtocol,
            lcsSetupIpRouter1NNatServiceTableEntryPeer,
            lcsSetupIpRouter1NNatServiceTableEntryWanAddress
          }
    ::= { lcsSetupIpRouter1NNatServiceTableTable 1 }

LcsSetupIpRouter1NNatServiceTableEntry ::= SEQUENCE {
            lcsSetupIpRouter1NNatServiceTableEntryDPortFrom Integer32,
            lcsSetupIpRouter1NNatServiceTableEntryIntranetAddress IpAddress,
            lcsSetupIpRouter1NNatServiceTableEntryDPortTo Integer32,
            lcsSetupIpRouter1NNatServiceTableEntryMapPort Integer32,
            lcsSetupIpRouter1NNatServiceTableEntryActive INTEGER,
            lcsSetupIpRouter1NNatServiceTableEntryComment DisplayString,
            lcsSetupIpRouter1NNatServiceTableEntryPeer DisplayString,
            lcsSetupIpRouter1NNatServiceTableEntryProtocol INTEGER,
            lcsSetupIpRouter1NNatServiceTableEntryWanAddress IpAddress
    }

-- {COLUMN} 1.3.6.1.4.1.2356.11.2.8.9.4.1.1
lcsSetupIpRouter1NNatServiceTableEntryDPortFrom OBJECT-TYPE
    SYNTAX     Integer32 (0..65535)
    MAX-ACCESS read-write
    STATUS     current
    DESCRIPTION
            ""
    ::= { lcsSetupIpRouter1NNatServiceTableEntry 1 }

-- {COLUMN} 1.3.6.1.4.1.2356.11.2.8.9.4.1.2
lcsSetupIpRouter1NNatServiceTableEntryIntranetAddress OBJECT-TYPE
    SYNTAX     IpAddress
    MAX-ACCESS read-write
    STATUS     current
    DESCRIPTION
            ""
    ::= { lcsSetupIpRouter1NNatServiceTableEntry 2 }

-- {COLUMN} 1.3.6.1.4.1.2356.11.2.8.9.4.1.3
lcsSetupIpRouter1NNatServiceTableEntryDPortTo OBJECT-TYPE
    SYNTAX     Integer32 (0..65535)
    MAX-ACCESS read-write
    STATUS     current
    DESCRIPTION
            ""
    ::= { lcsSetupIpRouter1NNatServiceTableEntry 3 }

-- {COLUMN} 1.3.6.1.4.1.2356.11.2.8.9.4.1.4
lcsSetupIpRouter1NNatServiceTableEntryMapPort OBJECT-TYPE
    SYNTAX     Integer32 (0..65535)
    MAX-ACCESS read-write
    STATUS     current
    DESCRIPTION
            ""
    ::= { lcsSetupIpRouter1NNatServiceTableEntry 4 }

-- {COLUMN} 1.3.6.1.4.1.2356.11.2.8.9.4.1.5
lcsSetupIpRouter1NNatServiceTableEntryActive OBJECT-TYPE
    SYNTAX     INTEGER {
                  eYes (0),
                  eNo (1)
            }
    MAX-ACCESS read-write
    STATUS     current
    DESCRIPTION
            ""
    ::= { lcsSetupIpRouter1NNatServiceTableEntry 5 }

-- {COLUMN} 1.3.6.1.4.1.2356.11.2.8.9.4.1.6
lcsSetupIpRouter1NNatServiceTableEntryComment OBJECT-TYPE
    SYNTAX     DisplayString (SIZE(0..64))
    MAX-ACCESS read-write
    STATUS     current
    DESCRIPTION
            ""
    ::= { lcsSetupIpRouter1NNatServiceTableEntry 6 }

-- {COLUMN} 1.3.6.1.4.1.2356.11.2.8.9.4.1.7
lcsSetupIpRouter1NNatServiceTableEntryPeer OBJECT-TYPE
    SYNTAX     DisplayString (SIZE(0..16))
    MAX-ACCESS read-write
    STATUS     current
    DESCRIPTION
            ""
    ::= { lcsSetupIpRouter1NNatServiceTableEntry 7 }

-- {COLUMN} 1.3.6.1.4.1.2356.11.2.8.9.4.1.8
lcsSetupIpRouter1NNatServiceTableEntryProtocol OBJECT-TYPE
    SYNTAX     INTEGER {
                  eTcpPlusUdp (0),
                  eTcp (1),
                  eUdp (2)
            }
    MAX-ACCESS read-write
    STATUS     current
    DESCRIPTION
            ""
    ::= { lcsSetupIpRouter1NNatServiceTableEntry 8 }

-- {COLUMN} 1.3.6.1.4.1.2356.11.2.8.9.4.1.9
lcsSetupIpRouter1NNatServiceTableEntryWanAddress OBJECT-TYPE
    SYNTAX     IpAddress
    MAX-ACCESS read-write
    STATUS     current
    DESCRIPTION
            ""
    ::= { lcsSetupIpRouter1NNatServiceTableEntry 9 }

-- {TABLE} 1.3.6.1.4.1.2356.11.2.8.9.5
lcsSetupIpRouter1NNatTable1NNatTable OBJECT-TYPE
    SYNTAX     SEQUENCE OF LcsSetupIpRouter1NNatTable1NNatEntry
    MAX-ACCESS not-accessible
    STATUS     current
    DESCRIPTION
            ""
    ::= { lcsSetupIpRouter1NNat 5 }

-- {ROW} 1.3.6.1.4.1.2356.11.2.8.9.5.1
lcsSetupIpRouter1NNatTable1NNatEntry OBJECT-TYPE
    SYNTAX     LcsSetupIpRouter1NNatTable1NNatEntry
    MAX-ACCESS not-accessible
    STATUS     current
    DESCRIPTION
            ""
    INDEX {
            lcsSetupIpRouter1NNatTable1NNatEntryIntranetAddress
          }
    ::= { lcsSetupIpRouter1NNatTable1NNatTable 1 }

LcsSetupIpRouter1NNatTable1NNatEntry ::= SEQUENCE {
            lcsSetupIpRouter1NNatTable1NNatEntryIntranetAddress IpAddress,
            lcsSetupIpRouter1NNatTable1NNatEntrySourcePort Integer32,
            lcsSetupIpRouter1NNatTable1NNatEntryProtocol INTEGER,
            lcsSetupIpRouter1NNatTable1NNatEntryTimeout Integer32,
            lcsSetupIpRouter1NNatTable1NNatEntryHandler DisplayString,
            lcsSetupIpRouter1NNatTable1NNatEntryRemoteAddress IpAddress,
            lcsSetupIpRouter1NNatTable1NNatEntryWanAddress IpAddress
    }

-- {COLUMN} 1.3.6.1.4.1.2356.11.2.8.9.5.1.1
lcsSetupIpRouter1NNatTable1NNatEntryIntranetAddress OBJECT-TYPE
    SYNTAX     IpAddress
    MAX-ACCESS read-only
    STATUS     current
    DESCRIPTION
            ""
    ::= { lcsSetupIpRouter1NNatTable1NNatEntry 1 }

-- {COLUMN} 1.3.6.1.4.1.2356.11.2.8.9.5.1.2
lcsSetupIpRouter1NNatTable1NNatEntrySourcePort OBJECT-TYPE
    SYNTAX     Integer32 (0..65535)
    MAX-ACCESS read-only
    STATUS     current
    DESCRIPTION
            ""
    ::= { lcsSetupIpRouter1NNatTable1NNatEntry 2 }

-- {COLUMN} 1.3.6.1.4.1.2356.11.2.8.9.5.1.3
lcsSetupIpRouter1NNatTable1NNatEntryProtocol OBJECT-TYPE
    SYNTAX     INTEGER {
                  eIcmp (1),
                  eTcp (6),
                  eUdp (17)
            }
    MAX-ACCESS read-only
    STATUS     current
    DESCRIPTION
            ""
    ::= { lcsSetupIpRouter1NNatTable1NNatEntry 3 }

-- {COLUMN} 1.3.6.1.4.1.2356.11.2.8.9.5.1.4
lcsSetupIpRouter1NNatTable1NNatEntryTimeout OBJECT-TYPE
    SYNTAX     Integer32 (0..65535)
    MAX-ACCESS read-only
    STATUS     current
    DESCRIPTION
            ""
    ::= { lcsSetupIpRouter1NNatTable1NNatEntry 4 }

-- {COLUMN} 1.3.6.1.4.1.2356.11.2.8.9.5.1.5
lcsSetupIpRouter1NNatTable1NNatEntryHandler OBJECT-TYPE
    SYNTAX     DisplayString (SIZE(0..255))
    MAX-ACCESS read-only
    STATUS     current
    DESCRIPTION
            ""
    ::= { lcsSetupIpRouter1NNatTable1NNatEntry 5 }

-- {COLUMN} 1.3.6.1.4.1.2356.11.2.8.9.5.1.6
lcsSetupIpRouter1NNatTable1NNatEntryRemoteAddress OBJECT-TYPE
    SYNTAX     IpAddress
    MAX-ACCESS read-only
    STATUS     current
    DESCRIPTION
            ""
    ::= { lcsSetupIpRouter1NNatTable1NNatEntry 6 }

-- {COLUMN} 1.3.6.1.4.1.2356.11.2.8.9.5.1.7
lcsSetupIpRouter1NNatTable1NNatEntryWanAddress OBJECT-TYPE
    SYNTAX     IpAddress
    MAX-ACCESS read-only
    STATUS     current
    DESCRIPTION
            "-- empty --"
    ::= { lcsSetupIpRouter1NNatTable1NNatEntry 7 }

-- {SCALAR} 1.3.6.1.4.1.2356.11.2.8.9.6
lcsSetupIpRouter1NNatFragments OBJECT-TYPE
    SYNTAX     INTEGER {
                  eFilter (0),
                  eRoute (1),
                  eReassemble (2)
            }
    MAX-ACCESS read-write
    STATUS     current
    DESCRIPTION
            ""
    ::= { lcsSetupIpRouter1NNat 6 }

-- {SCALAR} 1.3.6.1.4.1.2356.11.2.8.9.7
lcsSetupIpRouter1NNatFragmentAgingSeconds OBJECT-TYPE
    SYNTAX     Integer32 (0..255)
    MAX-ACCESS read-write
    STATUS     current
    DESCRIPTION
            ""
    ::= { lcsSetupIpRouter1NNat 7 }

-- {SCALAR} 1.3.6.1.4.1.2356.11.2.8.9.8
lcsSetupIpRouter1NNatIpsecAgingSeconds OBJECT-TYPE
    SYNTAX     Integer32 (0..65535)
    MAX-ACCESS read-write
    STATUS     current
    DESCRIPTION
            ""
    ::= { lcsSetupIpRouter1NNat 8 }

-- {TABLE} 1.3.6.1.4.1.2356.11.2.8.9.9
lcsSetupIpRouter1NNatIpsecTableTable OBJECT-TYPE
    SYNTAX     SEQUENCE OF LcsSetupIpRouter1NNatIpsecTableEntry
    MAX-ACCESS not-accessible
    STATUS     current
    DESCRIPTION
            ""
    ::= { lcsSetupIpRouter1NNat 9 }

-- {ROW} 1.3.6.1.4.1.2356.11.2.8.9.9.1
lcsSetupIpRouter1NNatIpsecTableEntry OBJECT-TYPE
    SYNTAX     LcsSetupIpRouter1NNatIpsecTableEntry
    MAX-ACCESS not-accessible
    STATUS     current
    DESCRIPTION
            ""
    INDEX {
            lcsSetupIpRouter1NNatIpsecTableEntryRemoteAddress
          }
    ::= { lcsSetupIpRouter1NNatIpsecTableTable 1 }

LcsSetupIpRouter1NNatIpsecTableEntry ::= SEQUENCE {
            lcsSetupIpRouter1NNatIpsecTableEntryRemoteAddress IpAddress,
            lcsSetupIpRouter1NNatIpsecTableEntryLocalAddress IpAddress,
            lcsSetupIpRouter1NNatIpsecTableEntryRcHi DisplayString,
            lcsSetupIpRouter1NNatIpsecTableEntryRcLo DisplayString,
            lcsSetupIpRouter1NNatIpsecTableEntryLcHi DisplayString,
            lcsSetupIpRouter1NNatIpsecTableEntryLcLo DisplayString,
            lcsSetupIpRouter1NNatIpsecTableEntryRemoteSpi DisplayString,
            lcsSetupIpRouter1NNatIpsecTableEntryLocalSpi DisplayString,
            lcsSetupIpRouter1NNatIpsecTableEntryTimeout Integer32,
            lcsSetupIpRouter1NNatIpsecTableEntryFlags DisplayString,
            lcsSetupIpRouter1NNatIpsecTableEntryCo Integer32,
            lcsSetupIpRouter1NNatIpsecTableEntryNl Integer32,
            lcsSetupIpRouter1NNatIpsecTableEntryNr Integer32,
            lcsSetupIpRouter1NNatIpsecTableEntryDp Integer32,
            lcsSetupIpRouter1NNatIpsecTableEntryWanAddress IpAddress
    }

-- {COLUMN} 1.3.6.1.4.1.2356.11.2.8.9.9.1.1
lcsSetupIpRouter1NNatIpsecTableEntryRemoteAddress OBJECT-TYPE
    SYNTAX     IpAddress
    MAX-ACCESS read-only
    STATUS     current
    DESCRIPTION
            ""
    ::= { lcsSetupIpRouter1NNatIpsecTableEntry 1 }

-- {COLUMN} 1.3.6.1.4.1.2356.11.2.8.9.9.1.2
lcsSetupIpRouter1NNatIpsecTableEntryLocalAddress OBJECT-TYPE
    SYNTAX     IpAddress
    MAX-ACCESS read-only
    STATUS     current
    DESCRIPTION
            ""
    ::= { lcsSetupIpRouter1NNatIpsecTableEntry 2 }

-- {COLUMN} 1.3.6.1.4.1.2356.11.2.8.9.9.1.3
lcsSetupIpRouter1NNatIpsecTableEntryRcHi OBJECT-TYPE
    SYNTAX     DisplayString (SIZE(0..8))
    MAX-ACCESS read-only
    STATUS     current
    DESCRIPTION
            ""
    ::= { lcsSetupIpRouter1NNatIpsecTableEntry 3 }

-- {COLUMN} 1.3.6.1.4.1.2356.11.2.8.9.9.1.4
lcsSetupIpRouter1NNatIpsecTableEntryRcLo OBJECT-TYPE
    SYNTAX     DisplayString (SIZE(0..8))
    MAX-ACCESS read-only
    STATUS     current
    DESCRIPTION
            ""
    ::= { lcsSetupIpRouter1NNatIpsecTableEntry 4 }

-- {COLUMN} 1.3.6.1.4.1.2356.11.2.8.9.9.1.5
lcsSetupIpRouter1NNatIpsecTableEntryLcHi OBJECT-TYPE
    SYNTAX     DisplayString (SIZE(0..8))
    MAX-ACCESS read-only
    STATUS     current
    DESCRIPTION
            ""
    ::= { lcsSetupIpRouter1NNatIpsecTableEntry 5 }

-- {COLUMN} 1.3.6.1.4.1.2356.11.2.8.9.9.1.6
lcsSetupIpRouter1NNatIpsecTableEntryLcLo OBJECT-TYPE
    SYNTAX     DisplayString (SIZE(0..8))
    MAX-ACCESS read-only
    STATUS     current
    DESCRIPTION
            ""
    ::= { lcsSetupIpRouter1NNatIpsecTableEntry 6 }

-- {COLUMN} 1.3.6.1.4.1.2356.11.2.8.9.9.1.7
lcsSetupIpRouter1NNatIpsecTableEntryRemoteSpi OBJECT-TYPE
    SYNTAX     DisplayString (SIZE(0..8))
    MAX-ACCESS read-only
    STATUS     current
    DESCRIPTION
            ""
    ::= { lcsSetupIpRouter1NNatIpsecTableEntry 7 }

-- {COLUMN} 1.3.6.1.4.1.2356.11.2.8.9.9.1.8
lcsSetupIpRouter1NNatIpsecTableEntryLocalSpi OBJECT-TYPE
    SYNTAX     DisplayString (SIZE(0..8))
    MAX-ACCESS read-only
    STATUS     current
    DESCRIPTION
            ""
    ::= { lcsSetupIpRouter1NNatIpsecTableEntry 8 }

-- {COLUMN} 1.3.6.1.4.1.2356.11.2.8.9.9.1.9
lcsSetupIpRouter1NNatIpsecTableEntryTimeout OBJECT-TYPE
    SYNTAX     Integer32 (0..2147483647)
    MAX-ACCESS read-only
    STATUS     current
    DESCRIPTION
            ""
    ::= { lcsSetupIpRouter1NNatIpsecTableEntry 9 }

-- {COLUMN} 1.3.6.1.4.1.2356.11.2.8.9.9.1.10
lcsSetupIpRouter1NNatIpsecTableEntryFlags OBJECT-TYPE
    SYNTAX     DisplayString (SIZE(0..4))
    MAX-ACCESS read-only
    STATUS     current
    DESCRIPTION
            ""
    ::= { lcsSetupIpRouter1NNatIpsecTableEntry 10 }

-- {COLUMN} 1.3.6.1.4.1.2356.11.2.8.9.9.1.11
lcsSetupIpRouter1NNatIpsecTableEntryCo OBJECT-TYPE
    SYNTAX     Integer32 (0..255)
    MAX-ACCESS read-only
    STATUS     current
    DESCRIPTION
            ""
    ::= { lcsSetupIpRouter1NNatIpsecTableEntry 11 }

-- {COLUMN} 1.3.6.1.4.1.2356.11.2.8.9.9.1.12
lcsSetupIpRouter1NNatIpsecTableEntryNl OBJECT-TYPE
    SYNTAX     Integer32 (0..255)
    MAX-ACCESS read-only
    STATUS     current
    DESCRIPTION
            ""
    ::= { lcsSetupIpRouter1NNatIpsecTableEntry 12 }

-- {COLUMN} 1.3.6.1.4.1.2356.11.2.8.9.9.1.13
lcsSetupIpRouter1NNatIpsecTableEntryNr OBJECT-TYPE
    SYNTAX     Integer32 (0..255)
    MAX-ACCESS read-only
    STATUS     current
    DESCRIPTION
            ""
    ::= { lcsSetupIpRouter1NNatIpsecTableEntry 13 }

-- {COLUMN} 1.3.6.1.4.1.2356.11.2.8.9.9.1.14
lcsSetupIpRouter1NNatIpsecTableEntryDp OBJECT-TYPE
    SYNTAX     Integer32 (0..255)
    MAX-ACCESS read-only
    STATUS     current
    DESCRIPTION
            ""
    ::= { lcsSetupIpRouter1NNatIpsecTableEntry 14 }

-- {COLUMN} 1.3.6.1.4.1.2356.11.2.8.9.9.1.15
lcsSetupIpRouter1NNatIpsecTableEntryWanAddress OBJECT-TYPE
    SYNTAX     IpAddress
    MAX-ACCESS read-only
    STATUS     current
    DESCRIPTION
            "-- empty --"
    ::= { lcsSetupIpRouter1NNatIpsecTableEntry 15 }

-- {SCALAR} 1.3.6.1.4.1.2356.11.2.8.9.10
lcsSetupIpRouter1NNatIdSpoofing OBJECT-TYPE
    SYNTAX     INTEGER {
                  eNo (0),
                  eYes (1)
            }
    MAX-ACCESS read-write
    STATUS     current
    DESCRIPTION
            ""
    ::= { lcsSetupIpRouter1NNat 10 }

-- {NODE} 1.3.6.1.4.1.2356.11.2.8.10
lcsSetupIpRouterFirewall OBJECT IDENTIFIER ::= { lcsSetupIpRouter 10 }

-- {TABLE} 1.3.6.1.4.1.2356.11.2.8.10.1
lcsSetupIpRouterFirewallObjectsTable OBJECT-TYPE
    SYNTAX     SEQUENCE OF LcsSetupIpRouterFirewallObjectsEntry
    MAX-ACCESS not-accessible
    STATUS     current
    DESCRIPTION
            ""
    ::= { lcsSetupIpRouterFirewall 1 }

-- {ROW} 1.3.6.1.4.1.2356.11.2.8.10.1.1
lcsSetupIpRouterFirewallObjectsEntry OBJECT-TYPE
    SYNTAX     LcsSetupIpRouterFirewallObjectsEntry
    MAX-ACCESS not-accessible
    STATUS     current
    DESCRIPTION
            ""
    INDEX {
            lcsSetupIpRouterFirewallObjectsEntryName
          }
    ::= { lcsSetupIpRouterFirewallObjectsTable 1 }

LcsSetupIpRouterFirewallObjectsEntry ::= SEQUENCE {
            lcsSetupIpRouterFirewallObjectsEntryName DisplayString,
            lcsSetupIpRouterFirewallObjectsEntryDescription DisplayString
    }

-- {COLUMN} 1.3.6.1.4.1.2356.11.2.8.10.1.1.1
lcsSetupIpRouterFirewallObjectsEntryName OBJECT-TYPE
    SYNTAX     DisplayString (SIZE(0..32))
    MAX-ACCESS read-write
    STATUS     current
    DESCRIPTION
            ""
    ::= { lcsSetupIpRouterFirewallObjectsEntry 1 }

-- {COLUMN} 1.3.6.1.4.1.2356.11.2.8.10.1.1.2
lcsSetupIpRouterFirewallObjectsEntryDescription OBJECT-TYPE
    SYNTAX     DisplayString (SIZE(0..64))
    MAX-ACCESS read-write
    STATUS     current
    DESCRIPTION
            ""
    ::= { lcsSetupIpRouterFirewallObjectsEntry 2 }

-- {TABLE} 1.3.6.1.4.1.2356.11.2.8.10.2
lcsSetupIpRouterFirewallRulesTable OBJECT-TYPE
    SYNTAX     SEQUENCE OF LcsSetupIpRouterFirewallRulesEntry
    MAX-ACCESS not-accessible
    STATUS     current
    DESCRIPTION
            ""
    ::= { lcsSetupIpRouterFirewall 2 }

-- {ROW} 1.3.6.1.4.1.2356.11.2.8.10.2.1
lcsSetupIpRouterFirewallRulesEntry OBJECT-TYPE
    SYNTAX     LcsSetupIpRouterFirewallRulesEntry
    MAX-ACCESS not-accessible
    STATUS     current
    DESCRIPTION
            ""
    INDEX {
            lcsSetupIpRouterFirewallRulesEntryName
          }
    ::= { lcsSetupIpRouterFirewallRulesTable 1 }

LcsSetupIpRouterFirewallRulesEntry ::= SEQUENCE {
            lcsSetupIpRouterFirewallRulesEntryName DisplayString,
            lcsSetupIpRouterFirewallRulesEntryProt DisplayString,
            lcsSetupIpRouterFirewallRulesEntrySource DisplayString,
            lcsSetupIpRouterFirewallRulesEntryDestination DisplayString,
            lcsSetupIpRouterFirewallRulesEntryAction DisplayString,
            lcsSetupIpRouterFirewallRulesEntryLinked INTEGER,
            lcsSetupIpRouterFirewallRulesEntryPrio Integer32,
            lcsSetupIpRouterFirewallRulesEntryFirewallRule INTEGER,
            lcsSetupIpRouterFirewallRulesEntryVpnRule INTEGER,
            lcsSetupIpRouterFirewallRulesEntryStateful INTEGER,
            lcsSetupIpRouterFirewallRulesEntryComment DisplayString,
            lcsSetupIpRouterFirewallRulesEntryRtgTag Integer32,
            lcsSetupIpRouterFirewallRulesEntrySrcTag Integer32
    }

-- {COLUMN} 1.3.6.1.4.1.2356.11.2.8.10.2.1.1
lcsSetupIpRouterFirewallRulesEntryName OBJECT-TYPE
    SYNTAX     DisplayString (SIZE(0..32))
    MAX-ACCESS read-write
    STATUS     current
    DESCRIPTION
            ""
    ::= { lcsSetupIpRouterFirewallRulesEntry 1 }

-- {COLUMN} 1.3.6.1.4.1.2356.11.2.8.10.2.1.2
lcsSetupIpRouterFirewallRulesEntryProt OBJECT-TYPE
    SYNTAX     DisplayString (SIZE(0..10))
    MAX-ACCESS read-write
    STATUS     current
    DESCRIPTION
            ""
    ::= { lcsSetupIpRouterFirewallRulesEntry 2 }

-- {COLUMN} 1.3.6.1.4.1.2356.11.2.8.10.2.1.3
lcsSetupIpRouterFirewallRulesEntrySource OBJECT-TYPE
    SYNTAX     DisplayString (SIZE(0..40))
    MAX-ACCESS read-write
    STATUS     current
    DESCRIPTION
            ""
    ::= { lcsSetupIpRouterFirewallRulesEntry 3 }

-- {COLUMN} 1.3.6.1.4.1.2356.11.2.8.10.2.1.4
lcsSetupIpRouterFirewallRulesEntryDestination OBJECT-TYPE
    SYNTAX     DisplayString (SIZE(0..40))
    MAX-ACCESS read-write
    STATUS     current
    DESCRIPTION
            ""
    ::= { lcsSetupIpRouterFirewallRulesEntry 4 }

-- {COLUMN} 1.3.6.1.4.1.2356.11.2.8.10.2.1.7
lcsSetupIpRouterFirewallRulesEntryAction OBJECT-TYPE
    SYNTAX     DisplayString (SIZE(0..40))
    MAX-ACCESS read-write
    STATUS     current
    DESCRIPTION
            ""
    ::= { lcsSetupIpRouterFirewallRulesEntry 7 }

-- {COLUMN} 1.3.6.1.4.1.2356.11.2.8.10.2.1.8
lcsSetupIpRouterFirewallRulesEntryLinked OBJECT-TYPE
    SYNTAX     INTEGER {
                  eNo (0),
                  eYes (1)
            }
    MAX-ACCESS read-write
    STATUS     current
    DESCRIPTION
            ""
    ::= { lcsSetupIpRouterFirewallRulesEntry 8 }

-- {COLUMN} 1.3.6.1.4.1.2356.11.2.8.10.2.1.9
lcsSetupIpRouterFirewallRulesEntryPrio OBJECT-TYPE
    SYNTAX     Integer32 (0..65535)
    MAX-ACCESS read-write
    STATUS     current
    DESCRIPTION
            ""
    ::= { lcsSetupIpRouterFirewallRulesEntry 9 }

-- {COLUMN} 1.3.6.1.4.1.2356.11.2.8.10.2.1.10
lcsSetupIpRouterFirewallRulesEntryFirewallRule OBJECT-TYPE
    SYNTAX     INTEGER {
                  eYes (0),
                  eNo (1)
            }
    MAX-ACCESS read-write
    STATUS     current
    DESCRIPTION
            ""
    ::= { lcsSetupIpRouterFirewallRulesEntry 10 }

-- {COLUMN} 1.3.6.1.4.1.2356.11.2.8.10.2.1.11
lcsSetupIpRouterFirewallRulesEntryVpnRule OBJECT-TYPE
    SYNTAX     INTEGER {
                  eNo (0),
                  eYes (1)
            }
    MAX-ACCESS read-write
    STATUS     current
    DESCRIPTION
            ""
    ::= { lcsSetupIpRouterFirewallRulesEntry 11 }

-- {COLUMN} 1.3.6.1.4.1.2356.11.2.8.10.2.1.12
lcsSetupIpRouterFirewallRulesEntryStateful OBJECT-TYPE
    SYNTAX     INTEGER {
                  eYes (0),
                  eNo (1)
            }
    MAX-ACCESS read-write
    STATUS     current
    DESCRIPTION
            ""
    ::= { lcsSetupIpRouterFirewallRulesEntry 12 }

-- {COLUMN} 1.3.6.1.4.1.2356.11.2.8.10.2.1.13
lcsSetupIpRouterFirewallRulesEntryComment OBJECT-TYPE
    SYNTAX     DisplayString (SIZE(0..64))
    MAX-ACCESS read-write
    STATUS     current
    DESCRIPTION
            ""
    ::= { lcsSetupIpRouterFirewallRulesEntry 13 }

-- {COLUMN} 1.3.6.1.4.1.2356.11.2.8.10.2.1.14
lcsSetupIpRouterFirewallRulesEntryRtgTag OBJECT-TYPE
    SYNTAX     Integer32 (0..65535)
    MAX-ACCESS read-write
    STATUS     current
    DESCRIPTION
            ""
    ::= { lcsSetupIpRouterFirewallRulesEntry 14 }

-- {COLUMN} 1.3.6.1.4.1.2356.11.2.8.10.2.1.15
lcsSetupIpRouterFirewallRulesEntrySrcTag OBJECT-TYPE
    SYNTAX     Integer32 (0..65535)
    MAX-ACCESS read-write
    STATUS     current
    DESCRIPTION
            "-- empty --"
    ::= { lcsSetupIpRouterFirewallRulesEntry 15 }

-- {TABLE} 1.3.6.1.4.1.2356.11.2.8.10.3
lcsSetupIpRouterFirewallFilterListTable OBJECT-TYPE
    SYNTAX     SEQUENCE OF LcsSetupIpRouterFirewallFilterListEntry
    MAX-ACCESS not-accessible
    STATUS     current
    DESCRIPTION
            ""
    ::= { lcsSetupIpRouterFirewall 3 }

-- {ROW} 1.3.6.1.4.1.2356.11.2.8.10.3.1
lcsSetupIpRouterFirewallFilterListEntry OBJECT-TYPE
    SYNTAX     LcsSetupIpRouterFirewallFilterListEntry
    MAX-ACCESS not-accessible
    STATUS     current
    DESCRIPTION
            ""
    INDEX {
            lcsSetupIpRouterFirewallFilterListEntryIdx
          }
    ::= { lcsSetupIpRouterFirewallFilterListTable 1 }

LcsSetupIpRouterFirewallFilterListEntry ::= SEQUENCE {
            lcsSetupIpRouterFirewallFilterListEntryIdx Integer32,
            lcsSetupIpRouterFirewallFilterListEntryProt Integer32,
            lcsSetupIpRouterFirewallFilterListEntrySrcAddress IpAddress,
            lcsSetupIpRouterFirewallFilterListEntrySrcNetmask IpAddress,
            lcsSetupIpRouterFirewallFilterListEntrySSt Integer32,
            lcsSetupIpRouterFirewallFilterListEntrySEnd Integer32,
            lcsSetupIpRouterFirewallFilterListEntryDstAddress IpAddress,
            lcsSetupIpRouterFirewallFilterListEntryDstNetmask IpAddress,
            lcsSetupIpRouterFirewallFilterListEntryDSt Integer32,
            lcsSetupIpRouterFirewallFilterListEntryDEnd Integer32,
            lcsSetupIpRouterFirewallFilterListEntryAction DisplayString,
            lcsSetupIpRouterFirewallFilterListEntrySrcMac DisplayString,
            lcsSetupIpRouterFirewallFilterListEntryDstMac DisplayString,
            lcsSetupIpRouterFirewallFilterListEntryLinked INTEGER,
            lcsSetupIpRouterFirewallFilterListEntryPrio Integer32,
            lcsSetupIpRouterFirewallFilterListEntryRtgTag Integer32,
            lcsSetupIpRouterFirewallFilterListEntrySrcTag Integer32,
            lcsSetupIpRouterFirewallFilterListEntrySource DisplayString,
            lcsSetupIpRouterFirewallFilterListEntryDestination DisplayString
    }

-- {COLUMN} 1.3.6.1.4.1.2356.11.2.8.10.3.1.1
lcsSetupIpRouterFirewallFilterListEntryIdx OBJECT-TYPE
    SYNTAX     Integer32 (0..2147483647)
    MAX-ACCESS read-only
    STATUS     current
    DESCRIPTION
            ""
    ::= { lcsSetupIpRouterFirewallFilterListEntry 1 }

-- {COLUMN} 1.3.6.1.4.1.2356.11.2.8.10.3.1.2
lcsSetupIpRouterFirewallFilterListEntryProt OBJECT-TYPE
    SYNTAX     Integer32 (0..255)
    MAX-ACCESS read-only
    STATUS     current
    DESCRIPTION
            ""
    ::= { lcsSetupIpRouterFirewallFilterListEntry 2 }

-- {COLUMN} 1.3.6.1.4.1.2356.11.2.8.10.3.1.3
lcsSetupIpRouterFirewallFilterListEntrySrcAddress OBJECT-TYPE
    SYNTAX     IpAddress
    MAX-ACCESS read-only
    STATUS     current
    DESCRIPTION
            ""
    ::= { lcsSetupIpRouterFirewallFilterListEntry 3 }

-- {COLUMN} 1.3.6.1.4.1.2356.11.2.8.10.3.1.4
lcsSetupIpRouterFirewallFilterListEntrySrcNetmask OBJECT-TYPE
    SYNTAX     IpAddress
    MAX-ACCESS read-only
    STATUS     current
    DESCRIPTION
            ""
    ::= { lcsSetupIpRouterFirewallFilterListEntry 4 }

-- {COLUMN} 1.3.6.1.4.1.2356.11.2.8.10.3.1.5
lcsSetupIpRouterFirewallFilterListEntrySSt OBJECT-TYPE
    SYNTAX     Integer32 (0..65535)
    MAX-ACCESS read-only
    STATUS     current
    DESCRIPTION
            ""
    ::= { lcsSetupIpRouterFirewallFilterListEntry 5 }

-- {COLUMN} 1.3.6.1.4.1.2356.11.2.8.10.3.1.6
lcsSetupIpRouterFirewallFilterListEntrySEnd OBJECT-TYPE
    SYNTAX     Integer32 (0..65535)
    MAX-ACCESS read-only
    STATUS     current
    DESCRIPTION
            ""
    ::= { lcsSetupIpRouterFirewallFilterListEntry 6 }

-- {COLUMN} 1.3.6.1.4.1.2356.11.2.8.10.3.1.7
lcsSetupIpRouterFirewallFilterListEntryDstAddress OBJECT-TYPE
    SYNTAX     IpAddress
    MAX-ACCESS read-only
    STATUS     current
    DESCRIPTION
            ""
    ::= { lcsSetupIpRouterFirewallFilterListEntry 7 }

-- {COLUMN} 1.3.6.1.4.1.2356.11.2.8.10.3.1.8
lcsSetupIpRouterFirewallFilterListEntryDstNetmask OBJECT-TYPE
    SYNTAX     IpAddress
    MAX-ACCESS read-only
    STATUS     current
    DESCRIPTION
            ""
    ::= { lcsSetupIpRouterFirewallFilterListEntry 8 }

-- {COLUMN} 1.3.6.1.4.1.2356.11.2.8.10.3.1.9
lcsSetupIpRouterFirewallFilterListEntryDSt OBJECT-TYPE
    SYNTAX     Integer32 (0..65535)
    MAX-ACCESS read-only
    STATUS     current
    DESCRIPTION
            ""
    ::= { lcsSetupIpRouterFirewallFilterListEntry 9 }

-- {COLUMN} 1.3.6.1.4.1.2356.11.2.8.10.3.1.10
lcsSetupIpRouterFirewallFilterListEntryDEnd OBJECT-TYPE
    SYNTAX     Integer32 (0..65535)
    MAX-ACCESS read-only
    STATUS     current
    DESCRIPTION
            ""
    ::= { lcsSetupIpRouterFirewallFilterListEntry 10 }

-- {COLUMN} 1.3.6.1.4.1.2356.11.2.8.10.3.1.11
lcsSetupIpRouterFirewallFilterListEntryAction OBJECT-TYPE
    SYNTAX     DisplayString (SIZE(0..255))
    MAX-ACCESS read-only
    STATUS     current
    DESCRIPTION
            ""
    ::= { lcsSetupIpRouterFirewallFilterListEntry 11 }

-- {COLUMN} 1.3.6.1.4.1.2356.11.2.8.10.3.1.13
lcsSetupIpRouterFirewallFilterListEntrySrcMac OBJECT-TYPE
    SYNTAX     DisplayString (SIZE(0..255))
    MAX-ACCESS read-only
    STATUS     current
    DESCRIPTION
            ""
    ::= { lcsSetupIpRouterFirewallFilterListEntry 13 }

-- {COLUMN} 1.3.6.1.4.1.2356.11.2.8.10.3.1.14
lcsSetupIpRouterFirewallFilterListEntryDstMac OBJECT-TYPE
    SYNTAX     DisplayString (SIZE(0..255))
    MAX-ACCESS read-only
    STATUS     current
    DESCRIPTION
            ""
    ::= { lcsSetupIpRouterFirewallFilterListEntry 14 }

-- {COLUMN} 1.3.6.1.4.1.2356.11.2.8.10.3.1.15
lcsSetupIpRouterFirewallFilterListEntryLinked OBJECT-TYPE
    SYNTAX     INTEGER {
                  eNo (0),
                  eYes (1)
            }
    MAX-ACCESS read-only
    STATUS     current
    DESCRIPTION
            ""
    ::= { lcsSetupIpRouterFirewallFilterListEntry 15 }

-- {COLUMN} 1.3.6.1.4.1.2356.11.2.8.10.3.1.16
lcsSetupIpRouterFirewallFilterListEntryPrio OBJECT-TYPE
    SYNTAX     Integer32 (0..65535)
    MAX-ACCESS read-only
    STATUS     current
    DESCRIPTION
            ""
    ::= { lcsSetupIpRouterFirewallFilterListEntry 16 }

-- {COLUMN} 1.3.6.1.4.1.2356.11.2.8.10.3.1.17
lcsSetupIpRouterFirewallFilterListEntryRtgTag OBJECT-TYPE
    SYNTAX     Integer32 (0..65535)
    MAX-ACCESS read-only
    STATUS     current
    DESCRIPTION
            ""
    ::= { lcsSetupIpRouterFirewallFilterListEntry 17 }

-- {COLUMN} 1.3.6.1.4.1.2356.11.2.8.10.3.1.18
lcsSetupIpRouterFirewallFilterListEntrySrcTag OBJECT-TYPE
    SYNTAX     Integer32 (0..65535)
    MAX-ACCESS read-only
    STATUS     current
    DESCRIPTION
            "-- empty --"
    ::= { lcsSetupIpRouterFirewallFilterListEntry 18 }

-- {COLUMN} 1.3.6.1.4.1.2356.11.2.8.10.3.1.19
lcsSetupIpRouterFirewallFilterListEntrySource OBJECT-TYPE
    SYNTAX     DisplayString (SIZE(0..255))
    MAX-ACCESS read-only
    STATUS     current
    DESCRIPTION
            "-- empty --"
    ::= { lcsSetupIpRouterFirewallFilterListEntry 19 }

-- {COLUMN} 1.3.6.1.4.1.2356.11.2.8.10.3.1.20
lcsSetupIpRouterFirewallFilterListEntryDestination OBJECT-TYPE
    SYNTAX     DisplayString (SIZE(0..255))
    MAX-ACCESS read-only
    STATUS     current
    DESCRIPTION
            "-- empty --"
    ::= { lcsSetupIpRouterFirewallFilterListEntry 20 }

-- {TABLE} 1.3.6.1.4.1.2356.11.2.8.10.4
lcsSetupIpRouterFirewallActionsTable OBJECT-TYPE
    SYNTAX     SEQUENCE OF LcsSetupIpRouterFirewallActionsEntry
    MAX-ACCESS not-accessible
    STATUS     current
    DESCRIPTION
            ""
    ::= { lcsSetupIpRouterFirewall 4 }

-- {ROW} 1.3.6.1.4.1.2356.11.2.8.10.4.1
lcsSetupIpRouterFirewallActionsEntry OBJECT-TYPE
    SYNTAX     LcsSetupIpRouterFirewallActionsEntry
    MAX-ACCESS not-accessible
    STATUS     current
    DESCRIPTION
            ""
    INDEX {
            lcsSetupIpRouterFirewallActionsEntryName
          }
    ::= { lcsSetupIpRouterFirewallActionsTable 1 }

LcsSetupIpRouterFirewallActionsEntry ::= SEQUENCE {
            lcsSetupIpRouterFirewallActionsEntryName DisplayString,
            lcsSetupIpRouterFirewallActionsEntryDescription DisplayString
    }

-- {COLUMN} 1.3.6.1.4.1.2356.11.2.8.10.4.1.1
lcsSetupIpRouterFirewallActionsEntryName OBJECT-TYPE
    SYNTAX     DisplayString (SIZE(0..32))
    MAX-ACCESS read-write
    STATUS     current
    DESCRIPTION
            ""
    ::= { lcsSetupIpRouterFirewallActionsEntry 1 }

-- {COLUMN} 1.3.6.1.4.1.2356.11.2.8.10.4.1.2
lcsSetupIpRouterFirewallActionsEntryDescription OBJECT-TYPE
    SYNTAX     DisplayString (SIZE(0..64))
    MAX-ACCESS read-write
    STATUS     current
    DESCRIPTION
            ""
    ::= { lcsSetupIpRouterFirewallActionsEntry 2 }

-- {TABLE} 1.3.6.1.4.1.2356.11.2.8.10.5
lcsSetupIpRouterFirewallConnectionListTable OBJECT-TYPE
    SYNTAX     SEQUENCE OF LcsSetupIpRouterFirewallConnectionListEntry
    MAX-ACCESS not-accessible
    STATUS     current
    DESCRIPTION
            ""
    ::= { lcsSetupIpRouterFirewall 5 }

-- {ROW} 1.3.6.1.4.1.2356.11.2.8.10.5.1
lcsSetupIpRouterFirewallConnectionListEntry OBJECT-TYPE
    SYNTAX     LcsSetupIpRouterFirewallConnectionListEntry
    MAX-ACCESS not-accessible
    STATUS     current
    DESCRIPTION
            ""
    INDEX {
            lcsSetupIpRouterFirewallConnectionListEntrySrcAddress,
            lcsSetupIpRouterFirewallConnectionListEntryDstAddress,
            lcsSetupIpRouterFirewallConnectionListEntryProt,
            lcsSetupIpRouterFirewallConnectionListEntrySrcPort,
            lcsSetupIpRouterFirewallConnectionListEntryDstPort
          }
    ::= { lcsSetupIpRouterFirewallConnectionListTable 1 }

LcsSetupIpRouterFirewallConnectionListEntry ::= SEQUENCE {
            lcsSetupIpRouterFirewallConnectionListEntrySrcAddress IpAddress,
            lcsSetupIpRouterFirewallConnectionListEntryDstAddress IpAddress,
            lcsSetupIpRouterFirewallConnectionListEntryProt Integer32,
            lcsSetupIpRouterFirewallConnectionListEntrySrcPort Integer32,
            lcsSetupIpRouterFirewallConnectionListEntryDstPort Integer32,
            lcsSetupIpRouterFirewallConnectionListEntryTimeout Integer32,
            lcsSetupIpRouterFirewallConnectionListEntryFlags Integer32,
            lcsSetupIpRouterFirewallConnectionListEntryFilterRule DisplayString,
            lcsSetupIpRouterFirewallConnectionListEntrySrcRoute DisplayString,
            lcsSetupIpRouterFirewallConnectionListEntryDestRoute DisplayString,
            lcsSetupIpRouterFirewallConnectionListEntryRtgTag Integer32
    }

-- {COLUMN} 1.3.6.1.4.1.2356.11.2.8.10.5.1.1
lcsSetupIpRouterFirewallConnectionListEntrySrcAddress OBJECT-TYPE
    SYNTAX     IpAddress
    MAX-ACCESS read-only
    STATUS     current
    DESCRIPTION
            ""
    ::= { lcsSetupIpRouterFirewallConnectionListEntry 1 }

-- {COLUMN} 1.3.6.1.4.1.2356.11.2.8.10.5.1.2
lcsSetupIpRouterFirewallConnectionListEntryDstAddress OBJECT-TYPE
    SYNTAX     IpAddress
    MAX-ACCESS read-only
    STATUS     current
    DESCRIPTION
            ""
    ::= { lcsSetupIpRouterFirewallConnectionListEntry 2 }

-- {COLUMN} 1.3.6.1.4.1.2356.11.2.8.10.5.1.3
lcsSetupIpRouterFirewallConnectionListEntryProt OBJECT-TYPE
    SYNTAX     Integer32 (0..255)
    MAX-ACCESS read-only
    STATUS     current
    DESCRIPTION
            ""
    ::= { lcsSetupIpRouterFirewallConnectionListEntry 3 }

-- {COLUMN} 1.3.6.1.4.1.2356.11.2.8.10.5.1.4
lcsSetupIpRouterFirewallConnectionListEntrySrcPort OBJECT-TYPE
    SYNTAX     Integer32 (0..65535)
    MAX-ACCESS read-only
    STATUS     current
    DESCRIPTION
            ""
    ::= { lcsSetupIpRouterFirewallConnectionListEntry 4 }

-- {COLUMN} 1.3.6.1.4.1.2356.11.2.8.10.5.1.5
lcsSetupIpRouterFirewallConnectionListEntryDstPort OBJECT-TYPE
    SYNTAX     Integer32 (0..65535)
    MAX-ACCESS read-only
    STATUS     current
    DESCRIPTION
            ""
    ::= { lcsSetupIpRouterFirewallConnectionListEntry 5 }

-- {COLUMN} 1.3.6.1.4.1.2356.11.2.8.10.5.1.6
lcsSetupIpRouterFirewallConnectionListEntryTimeout OBJECT-TYPE
    SYNTAX     Integer32 (0..65535)
    MAX-ACCESS read-only
    STATUS     current
    DESCRIPTION
            ""
    ::= { lcsSetupIpRouterFirewallConnectionListEntry 6 }

-- {COLUMN} 1.3.6.1.4.1.2356.11.2.8.10.5.1.7
lcsSetupIpRouterFirewallConnectionListEntryFlags OBJECT-TYPE
    SYNTAX     Integer32 (0..2147483647)
    MAX-ACCESS read-only
    STATUS     current
    DESCRIPTION
            ""
    ::= { lcsSetupIpRouterFirewallConnectionListEntry 7 }

-- {COLUMN} 1.3.6.1.4.1.2356.11.2.8.10.5.1.8
lcsSetupIpRouterFirewallConnectionListEntryFilterRule OBJECT-TYPE
    SYNTAX     DisplayString (SIZE(0..255))
    MAX-ACCESS read-only
    STATUS     current
    DESCRIPTION
            ""
    ::= { lcsSetupIpRouterFirewallConnectionListEntry 8 }

-- {COLUMN} 1.3.6.1.4.1.2356.11.2.8.10.5.1.9
lcsSetupIpRouterFirewallConnectionListEntrySrcRoute OBJECT-TYPE
    SYNTAX     DisplayString (SIZE(0..255))
    MAX-ACCESS read-only
    STATUS     current
    DESCRIPTION
            ""
    ::= { lcsSetupIpRouterFirewallConnectionListEntry 9 }

-- {COLUMN} 1.3.6.1.4.1.2356.11.2.8.10.5.1.10
lcsSetupIpRouterFirewallConnectionListEntryDestRoute OBJECT-TYPE
    SYNTAX     DisplayString (SIZE(0..255))
    MAX-ACCESS read-only
    STATUS     current
    DESCRIPTION
            ""
    ::= { lcsSetupIpRouterFirewallConnectionListEntry 10 }

-- {COLUMN} 1.3.6.1.4.1.2356.11.2.8.10.5.1.11
lcsSetupIpRouterFirewallConnectionListEntryRtgTag OBJECT-TYPE
    SYNTAX     Integer32 (0..65535)
    MAX-ACCESS read-only
    STATUS     current
    DESCRIPTION
            ""
    ::= { lcsSetupIpRouterFirewallConnectionListEntry 11 }

-- {TABLE} 1.3.6.1.4.1.2356.11.2.8.10.6
lcsSetupIpRouterFirewallHostBlockListTable OBJECT-TYPE
    SYNTAX     SEQUENCE OF LcsSetupIpRouterFirewallHostBlockListEntry
    MAX-ACCESS not-accessible
    STATUS     current
    DESCRIPTION
            ""
    ::= { lcsSetupIpRouterFirewall 6 }

-- {ROW} 1.3.6.1.4.1.2356.11.2.8.10.6.1
lcsSetupIpRouterFirewallHostBlockListEntry OBJECT-TYPE
    SYNTAX     LcsSetupIpRouterFirewallHostBlockListEntry
    MAX-ACCESS not-accessible
    STATUS     current
    DESCRIPTION
            ""
    INDEX {
            lcsSetupIpRouterFirewallHostBlockListEntrySrcAddress
          }
    ::= { lcsSetupIpRouterFirewallHostBlockListTable 1 }

LcsSetupIpRouterFirewallHostBlockListEntry ::= SEQUENCE {
            lcsSetupIpRouterFirewallHostBlockListEntrySrcAddress IpAddress,
            lcsSetupIpRouterFirewallHostBlockListEntryTimeout Integer32,
            lcsSetupIpRouterFirewallHostBlockListEntryFilterRule DisplayString
    }

-- {COLUMN} 1.3.6.1.4.1.2356.11.2.8.10.6.1.1
lcsSetupIpRouterFirewallHostBlockListEntrySrcAddress OBJECT-TYPE
    SYNTAX     IpAddress
    MAX-ACCESS read-only
    STATUS     current
    DESCRIPTION
            ""
    ::= { lcsSetupIpRouterFirewallHostBlockListEntry 1 }

-- {COLUMN} 1.3.6.1.4.1.2356.11.2.8.10.6.1.2
lcsSetupIpRouterFirewallHostBlockListEntryTimeout OBJECT-TYPE
    SYNTAX     Integer32 (0..2147483647)
    MAX-ACCESS read-only
    STATUS     current
    DESCRIPTION
            ""
    ::= { lcsSetupIpRouterFirewallHostBlockListEntry 2 }

-- {COLUMN} 1.3.6.1.4.1.2356.11.2.8.10.6.1.3
lcsSetupIpRouterFirewallHostBlockListEntryFilterRule OBJECT-TYPE
    SYNTAX     DisplayString (SIZE(0..255))
    MAX-ACCESS read-only
    STATUS     current
    DESCRIPTION
            ""
    ::= { lcsSetupIpRouterFirewallHostBlockListEntry 3 }

-- {TABLE} 1.3.6.1.4.1.2356.11.2.8.10.7
lcsSetupIpRouterFirewallPortBlockListTable OBJECT-TYPE
    SYNTAX     SEQUENCE OF LcsSetupIpRouterFirewallPortBlockListEntry
    MAX-ACCESS not-accessible
    STATUS     current
    DESCRIPTION
            ""
    ::= { lcsSetupIpRouterFirewall 7 }

-- {ROW} 1.3.6.1.4.1.2356.11.2.8.10.7.1
lcsSetupIpRouterFirewallPortBlockListEntry OBJECT-TYPE
    SYNTAX     LcsSetupIpRouterFirewallPortBlockListEntry
    MAX-ACCESS not-accessible
    STATUS     current
    DESCRIPTION
            ""
    INDEX {
            lcsSetupIpRouterFirewallPortBlockListEntryDstAddress
          }
    ::= { lcsSetupIpRouterFirewallPortBlockListTable 1 }

LcsSetupIpRouterFirewallPortBlockListEntry ::= SEQUENCE {
            lcsSetupIpRouterFirewallPortBlockListEntryDstAddress IpAddress,
            lcsSetupIpRouterFirewallPortBlockListEntryProt Integer32,
            lcsSetupIpRouterFirewallPortBlockListEntryDstPort Integer32,
            lcsSetupIpRouterFirewallPortBlockListEntryTimeout Integer32,
            lcsSetupIpRouterFirewallPortBlockListEntryFilterRule DisplayString
    }

-- {COLUMN} 1.3.6.1.4.1.2356.11.2.8.10.7.1.1
lcsSetupIpRouterFirewallPortBlockListEntryDstAddress OBJECT-TYPE
    SYNTAX     IpAddress
    MAX-ACCESS read-only
    STATUS     current
    DESCRIPTION
            ""
    ::= { lcsSetupIpRouterFirewallPortBlockListEntry 1 }

-- {COLUMN} 1.3.6.1.4.1.2356.11.2.8.10.7.1.2
lcsSetupIpRouterFirewallPortBlockListEntryProt OBJECT-TYPE
    SYNTAX     Integer32 (0..65535)
    MAX-ACCESS read-only
    STATUS     current
    DESCRIPTION
            ""
    ::= { lcsSetupIpRouterFirewallPortBlockListEntry 2 }

-- {COLUMN} 1.3.6.1.4.1.2356.11.2.8.10.7.1.3
lcsSetupIpRouterFirewallPortBlockListEntryDstPort OBJECT-TYPE
    SYNTAX     Integer32 (0..65535)
    MAX-ACCESS read-only
    STATUS     current
    DESCRIPTION
            ""
    ::= { lcsSetupIpRouterFirewallPortBlockListEntry 3 }

-- {COLUMN} 1.3.6.1.4.1.2356.11.2.8.10.7.1.4
lcsSetupIpRouterFirewallPortBlockListEntryTimeout OBJECT-TYPE
    SYNTAX     Integer32 (0..2147483647)
    MAX-ACCESS read-only
    STATUS     current
    DESCRIPTION
            ""
    ::= { lcsSetupIpRouterFirewallPortBlockListEntry 4 }

-- {COLUMN} 1.3.6.1.4.1.2356.11.2.8.10.7.1.5
lcsSetupIpRouterFirewallPortBlockListEntryFilterRule OBJECT-TYPE
    SYNTAX     DisplayString (SIZE(0..255))
    MAX-ACCESS read-only
    STATUS     current
    DESCRIPTION
            ""
    ::= { lcsSetupIpRouterFirewallPortBlockListEntry 5 }

-- {SCALAR} 1.3.6.1.4.1.2356.11.2.8.10.8
lcsSetupIpRouterFirewallMaxHalfOpenConns OBJECT-TYPE
    SYNTAX     Integer32 (0..2147483647)
    MAX-ACCESS read-write
    STATUS     current
    DESCRIPTION
            ""
    ::= { lcsSetupIpRouterFirewall 8 }

-- {SCALAR} 1.3.6.1.4.1.2356.11.2.8.10.9
lcsSetupIpRouterFirewallDosAction OBJECT-TYPE
    SYNTAX     DisplayString (SIZE(0..29))
    MAX-ACCESS read-write
    STATUS     current
    DESCRIPTION
            ""
    ::= { lcsSetupIpRouterFirewall 9 }

-- {SCALAR} 1.3.6.1.4.1.2356.11.2.8.10.10
lcsSetupIpRouterFirewallAdminEmail OBJECT-TYPE
    SYNTAX     DisplayString (SIZE(0..255))
    MAX-ACCESS read-write
    STATUS     current
    DESCRIPTION
            ""
    ::= { lcsSetupIpRouterFirewall 10 }

-- {SCALAR} 1.3.6.1.4.1.2356.11.2.8.10.11
lcsSetupIpRouterFirewallOperating OBJECT-TYPE
    SYNTAX     INTEGER {
                  eNo (0),
                  eYes (1)
            }
    MAX-ACCESS read-write
    STATUS     current
    DESCRIPTION
            ""
    ::= { lcsSetupIpRouterFirewall 11 }

-- {SCALAR} 1.3.6.1.4.1.2356.11.2.8.10.12
lcsSetupIpRouterFirewallPortScanThreshold OBJECT-TYPE
    SYNTAX     Integer32 (0..2147483647)
    MAX-ACCESS read-write
    STATUS     current
    DESCRIPTION
            ""
    ::= { lcsSetupIpRouterFirewall 12 }

-- {SCALAR} 1.3.6.1.4.1.2356.11.2.8.10.13
lcsSetupIpRouterFirewallIdsAction OBJECT-TYPE
    SYNTAX     DisplayString (SIZE(0..29))
    MAX-ACCESS read-write
    STATUS     current
    DESCRIPTION
            ""
    ::= { lcsSetupIpRouterFirewall 13 }

-- {SCALAR} 1.3.6.1.4.1.2356.11.2.8.10.14
lcsSetupIpRouterFirewallPingBlock OBJECT-TYPE
    SYNTAX     INTEGER {
                  eOff (0),
                  eAlways (1),
                  eWan (2),
                  eDefaultRoute (3)
            }
    MAX-ACCESS read-write
    STATUS     current
    DESCRIPTION
            ""
    ::= { lcsSetupIpRouterFirewall 14 }

-- {SCALAR} 1.3.6.1.4.1.2356.11.2.8.10.15
lcsSetupIpRouterFirewallStealthMode OBJECT-TYPE
    SYNTAX     INTEGER {
                  eOff (0),
                  eAlways (1),
                  eWan (2),
                  eDefaultRoute (3)
            }
    MAX-ACCESS read-write
    STATUS     current
    DESCRIPTION
            ""
    ::= { lcsSetupIpRouterFirewall 15 }

-- {SCALAR} 1.3.6.1.4.1.2356.11.2.8.10.16
lcsSetupIpRouterFirewallAuthPort OBJECT-TYPE
    SYNTAX     INTEGER {
                  eClosed (0),
                  eStealth (1)
            }
    MAX-ACCESS read-write
    STATUS     current
    DESCRIPTION
            ""
    ::= { lcsSetupIpRouterFirewall 16 }

-- {SCALAR} 1.3.6.1.4.1.2356.11.2.8.10.17
lcsSetupIpRouterFirewallDenySessionRecover OBJECT-TYPE
    SYNTAX     INTEGER {
                  eOff (0),
                  eAlways (1),
                  eWan (2),
                  eDefaultRoute (3)
            }
    MAX-ACCESS read-write
    STATUS     current
    DESCRIPTION
            ""
    ::= { lcsSetupIpRouterFirewall 17 }

-- {TABLE} 1.3.6.1.4.1.2356.11.2.8.10.19
lcsSetupIpRouterFirewallOpenPortListTable OBJECT-TYPE
    SYNTAX     SEQUENCE OF LcsSetupIpRouterFirewallOpenPortListEntry
    MAX-ACCESS not-accessible
    STATUS     current
    DESCRIPTION
            ""
    ::= { lcsSetupIpRouterFirewall 19 }

-- {ROW} 1.3.6.1.4.1.2356.11.2.8.10.19.1
lcsSetupIpRouterFirewallOpenPortListEntry OBJECT-TYPE
    SYNTAX     LcsSetupIpRouterFirewallOpenPortListEntry
    MAX-ACCESS not-accessible
    STATUS     current
    DESCRIPTION
            ""
    INDEX {
            lcsSetupIpRouterFirewallOpenPortListEntrySrcAddress,
            lcsSetupIpRouterFirewallOpenPortListEntryDstAddress,
            lcsSetupIpRouterFirewallOpenPortListEntryProt,
            lcsSetupIpRouterFirewallOpenPortListEntryDstPort
          }
    ::= { lcsSetupIpRouterFirewallOpenPortListTable 1 }

LcsSetupIpRouterFirewallOpenPortListEntry ::= SEQUENCE {
            lcsSetupIpRouterFirewallOpenPortListEntrySrcAddress IpAddress,
            lcsSetupIpRouterFirewallOpenPortListEntryDstAddress IpAddress,
            lcsSetupIpRouterFirewallOpenPortListEntryProt Integer32,
            lcsSetupIpRouterFirewallOpenPortListEntryDstPort Integer32,
            lcsSetupIpRouterFirewallOpenPortListEntryTimeout Integer32,
            lcsSetupIpRouterFirewallOpenPortListEntryFilterRule DisplayString,
            lcsSetupIpRouterFirewallOpenPortListEntrySrcRoute DisplayString
    }

-- {COLUMN} 1.3.6.1.4.1.2356.11.2.8.10.19.1.1
lcsSetupIpRouterFirewallOpenPortListEntrySrcAddress OBJECT-TYPE
    SYNTAX     IpAddress
    MAX-ACCESS read-only
    STATUS     current
    DESCRIPTION
            ""
    ::= { lcsSetupIpRouterFirewallOpenPortListEntry 1 }

-- {COLUMN} 1.3.6.1.4.1.2356.11.2.8.10.19.1.2
lcsSetupIpRouterFirewallOpenPortListEntryDstAddress OBJECT-TYPE
    SYNTAX     IpAddress
    MAX-ACCESS read-only
    STATUS     current
    DESCRIPTION
            ""
    ::= { lcsSetupIpRouterFirewallOpenPortListEntry 2 }

-- {COLUMN} 1.3.6.1.4.1.2356.11.2.8.10.19.1.3
lcsSetupIpRouterFirewallOpenPortListEntryProt OBJECT-TYPE
    SYNTAX     Integer32 (0..255)
    MAX-ACCESS read-only
    STATUS     current
    DESCRIPTION
            ""
    ::= { lcsSetupIpRouterFirewallOpenPortListEntry 3 }

-- {COLUMN} 1.3.6.1.4.1.2356.11.2.8.10.19.1.5
lcsSetupIpRouterFirewallOpenPortListEntryDstPort OBJECT-TYPE
    SYNTAX     Integer32 (0..65535)
    MAX-ACCESS read-only
    STATUS     current
    DESCRIPTION
            ""
    ::= { lcsSetupIpRouterFirewallOpenPortListEntry 5 }

-- {COLUMN} 1.3.6.1.4.1.2356.11.2.8.10.19.1.6
lcsSetupIpRouterFirewallOpenPortListEntryTimeout OBJECT-TYPE
    SYNTAX     Integer32 (0..65535)
    MAX-ACCESS read-only
    STATUS     current
    DESCRIPTION
            ""
    ::= { lcsSetupIpRouterFirewallOpenPortListEntry 6 }

-- {COLUMN} 1.3.6.1.4.1.2356.11.2.8.10.19.1.8
lcsSetupIpRouterFirewallOpenPortListEntryFilterRule OBJECT-TYPE
    SYNTAX     DisplayString (SIZE(0..255))
    MAX-ACCESS read-only
    STATUS     current
    DESCRIPTION
            ""
    ::= { lcsSetupIpRouterFirewallOpenPortListEntry 8 }

-- {COLUMN} 1.3.6.1.4.1.2356.11.2.8.10.19.1.9
lcsSetupIpRouterFirewallOpenPortListEntrySrcRoute OBJECT-TYPE
    SYNTAX     DisplayString (SIZE(0..255))
    MAX-ACCESS read-only
    STATUS     current
    DESCRIPTION
            ""
    ::= { lcsSetupIpRouterFirewallOpenPortListEntry 9 }

-- {NODE} 1.3.6.1.4.1.2356.11.2.8.10.20
lcsSetupIpRouterFirewallApplications OBJECT IDENTIFIER ::= { lcsSetupIpRouterFirewall 20 }

-- {NODE} 1.3.6.1.4.1.2356.11.2.8.10.20.1
lcsSetupIpRouterFirewallApplicationsFtp OBJECT IDENTIFIER ::= { lcsSetupIpRouterFirewallApplications 1 }

-- {SCALAR} 1.3.6.1.4.1.2356.11.2.8.10.20.1.1
lcsSetupIpRouterFirewallApplicationsFtpFtpBlock OBJECT-TYPE
    SYNTAX     INTEGER {
                  eOff (0),
                  eAlways (1),
                  eWan (2),
                  eDefaultRoute (3)
            }
    MAX-ACCESS read-write
    STATUS     current
    DESCRIPTION
            ""
    ::= { lcsSetupIpRouterFirewallApplicationsFtp 1 }

-- {SCALAR} 1.3.6.1.4.1.2356.11.2.8.10.20.1.2
lcsSetupIpRouterFirewallApplicationsFtpActiveFtpBlock OBJECT-TYPE
    SYNTAX     INTEGER {
                  eOff (0),
                  eAlways (1),
                  eWan (2),
                  eDefaultRoute (3)
            }
    MAX-ACCESS read-write
    STATUS     current
    DESCRIPTION
            ""
    ::= { lcsSetupIpRouterFirewallApplicationsFtp 2 }

-- {SCALAR} 1.3.6.1.4.1.2356.11.2.8.10.20.1.3
lcsSetupIpRouterFirewallApplicationsFtpMinPort OBJECT-TYPE
    SYNTAX     Integer32 (0..65535)
    MAX-ACCESS read-write
    STATUS     current
    DESCRIPTION
            ""
    ::= { lcsSetupIpRouterFirewallApplicationsFtp 3 }

-- {SCALAR} 1.3.6.1.4.1.2356.11.2.8.10.20.1.4
lcsSetupIpRouterFirewallApplicationsFtpCheckHostIp OBJECT-TYPE
    SYNTAX     INTEGER {
                  eOff (0),
                  eAlways (1),
                  eWan (2),
                  eDefaultRoute (3)
            }
    MAX-ACCESS read-write
    STATUS     current
    DESCRIPTION
            ""
    ::= { lcsSetupIpRouterFirewallApplicationsFtp 4 }

-- {SCALAR} 1.3.6.1.4.1.2356.11.2.8.10.20.1.5
lcsSetupIpRouterFirewallApplicationsFtpFxpBlock OBJECT-TYPE
    SYNTAX     INTEGER {
                  eOff (0),
                  eAlways (1),
                  eWan (2),
                  eDefaultRoute (3)
            }
    MAX-ACCESS read-write
    STATUS     current
    DESCRIPTION
            ""
    ::= { lcsSetupIpRouterFirewallApplicationsFtp 5 }

-- {NODE} 1.3.6.1.4.1.2356.11.2.8.10.20.2
lcsSetupIpRouterFirewallApplicationsIrc OBJECT IDENTIFIER ::= { lcsSetupIpRouterFirewallApplications 2 }

-- {SCALAR} 1.3.6.1.4.1.2356.11.2.8.10.20.2.1
lcsSetupIpRouterFirewallApplicationsIrcIrcBlock OBJECT-TYPE
    SYNTAX     INTEGER {
                  eOff (0),
                  eAlways (1),
                  eWan (2),
                  eDefaultRoute (3)
            }
    MAX-ACCESS read-write
    STATUS     current
    DESCRIPTION
            ""
    ::= { lcsSetupIpRouterFirewallApplicationsIrc 1 }

-- {SCALAR} 1.3.6.1.4.1.2356.11.2.8.10.20.2.2
lcsSetupIpRouterFirewallApplicationsIrcDdcBlock OBJECT-TYPE
    SYNTAX     INTEGER {
                  eOff (0),
                  eAlways (1),
                  eWan (2),
                  eDefaultRoute (3)
            }
    MAX-ACCESS read-write
    STATUS     current
    DESCRIPTION
            ""
    ::= { lcsSetupIpRouterFirewallApplicationsIrc 2 }

-- {SCALAR} 1.3.6.1.4.1.2356.11.2.8.10.20.2.3
lcsSetupIpRouterFirewallApplicationsIrcMinPort OBJECT-TYPE
    SYNTAX     Integer32 (0..65535)
    MAX-ACCESS read-write
    STATUS     current
    DESCRIPTION
            ""
    ::= { lcsSetupIpRouterFirewallApplicationsIrc 3 }

-- {SCALAR} 1.3.6.1.4.1.2356.11.2.8.10.20.2.4
lcsSetupIpRouterFirewallApplicationsIrcCheckHostIp OBJECT-TYPE
    SYNTAX     INTEGER {
                  eOff (0),
                  eAlways (1),
                  eWan (2),
                  eDefaultRoute (3)
            }
    MAX-ACCESS read-write
    STATUS     current
    DESCRIPTION
            ""
    ::= { lcsSetupIpRouterFirewallApplicationsIrc 4 }

-- {NODE} 1.3.6.1.4.1.2356.11.2.8.10.20.3
lcsSetupIpRouterFirewallApplicationsH323 OBJECT IDENTIFIER ::= { lcsSetupIpRouterFirewallApplications 3 }

-- {SCALAR} 1.3.6.1.4.1.2356.11.2.8.10.20.3.1
lcsSetupIpRouterFirewallApplicationsH323H323Support OBJECT-TYPE
    SYNTAX     INTEGER {
                  eNo (0),
                  eYes (1)
            }
    MAX-ACCESS read-write
    STATUS     current
    DESCRIPTION
            "-- empty --"
    ::= { lcsSetupIpRouterFirewallApplicationsH323 1 }

-- {SCALAR} 1.3.6.1.4.1.2356.11.2.8.10.20.10
lcsSetupIpRouterFirewallApplicationsApplAction OBJECT-TYPE
    SYNTAX     DisplayString (SIZE(0..29))
    MAX-ACCESS read-write
    STATUS     current
    DESCRIPTION
            ""
    ::= { lcsSetupIpRouterFirewallApplications 10 }

-- {SCALAR} 1.3.6.1.4.1.2356.11.2.8.11
lcsSetupIpRouterStartWanPool OBJECT-TYPE
    SYNTAX     IpAddress
    MAX-ACCESS read-write
    STATUS     current
    DESCRIPTION
            ""
    ::= { lcsSetupIpRouter 11 }

-- {SCALAR} 1.3.6.1.4.1.2356.11.2.8.12
lcsSetupIpRouterEndWanPool OBJECT-TYPE
    SYNTAX     IpAddress
    MAX-ACCESS read-write
    STATUS     current
    DESCRIPTION
            ""
    ::= { lcsSetupIpRouter 12 }

-- {TABLE} 1.3.6.1.4.1.2356.11.2.8.13
lcsSetupIpRouterDefaultTimeListTable OBJECT-TYPE
    SYNTAX     SEQUENCE OF LcsSetupIpRouterDefaultTimeListEntry
    MAX-ACCESS not-accessible
    STATUS     current
    DESCRIPTION
            ""
    ::= { lcsSetupIpRouter 13 }

-- {ROW} 1.3.6.1.4.1.2356.11.2.8.13.1
lcsSetupIpRouterDefaultTimeListEntry OBJECT-TYPE
    SYNTAX     LcsSetupIpRouterDefaultTimeListEntry
    MAX-ACCESS not-accessible
    STATUS     current
    DESCRIPTION
            ""
    INDEX {
            lcsSetupIpRouterDefaultTimeListEntryIndex
          }
    ::= { lcsSetupIpRouterDefaultTimeListTable 1 }

LcsSetupIpRouterDefaultTimeListEntry ::= SEQUENCE {
            lcsSetupIpRouterDefaultTimeListEntryIndex Integer32,
            lcsSetupIpRouterDefaultTimeListEntryDays BITS,
            lcsSetupIpRouterDefaultTimeListEntryStart DisplayString,
            lcsSetupIpRouterDefaultTimeListEntryStop DisplayString,
            lcsSetupIpRouterDefaultTimeListEntryPeer DisplayString
    }

-- {COLUMN} 1.3.6.1.4.1.2356.11.2.8.13.1.1
lcsSetupIpRouterDefaultTimeListEntryIndex OBJECT-TYPE
    SYNTAX     Integer32 (0..65535)
    MAX-ACCESS read-write
    STATUS     current
    DESCRIPTION
            ""
    ::= { lcsSetupIpRouterDefaultTimeListEntry 1 }

-- {COLUMN} 1.3.6.1.4.1.2356.11.2.8.13.1.2
lcsSetupIpRouterDefaultTimeListEntryDays OBJECT-TYPE
    SYNTAX     BITS {
                  eHoliday (0),
                  eSunday (1),
                  eSaturday (2),
                  eFriday (3),
                  eThursday (4),
                  eWednesday (5),
                  eTuesday (6),
                  eMonday (7)
            }
    MAX-ACCESS read-write
    STATUS     current
    DESCRIPTION
            ""
    ::= { lcsSetupIpRouterDefaultTimeListEntry 2 }

-- {COLUMN} 1.3.6.1.4.1.2356.11.2.8.13.1.3
lcsSetupIpRouterDefaultTimeListEntryStart OBJECT-TYPE
    SYNTAX     DisplayString (SIZE(0..5))
    MAX-ACCESS read-write
    STATUS     current
    DESCRIPTION
            ""
    ::= { lcsSetupIpRouterDefaultTimeListEntry 3 }

-- {COLUMN} 1.3.6.1.4.1.2356.11.2.8.13.1.4
lcsSetupIpRouterDefaultTimeListEntryStop OBJECT-TYPE
    SYNTAX     DisplayString (SIZE(0..5))
    MAX-ACCESS read-write
    STATUS     current
    DESCRIPTION
            ""
    ::= { lcsSetupIpRouterDefaultTimeListEntry 4 }

-- {COLUMN} 1.3.6.1.4.1.2356.11.2.8.13.1.5
lcsSetupIpRouterDefaultTimeListEntryPeer OBJECT-TYPE
    SYNTAX     DisplayString (SIZE(0..16))
    MAX-ACCESS read-write
    STATUS     current
    DESCRIPTION
            ""
    ::= { lcsSetupIpRouterDefaultTimeListEntry 5 }

-- {SCALAR} 1.3.6.1.4.1.2356.11.2.8.14
lcsSetupIpRouterUsageDefaultTimetable OBJECT-TYPE
    SYNTAX     INTEGER {
                  eNo (0),
                  eYes (1)
            }
    MAX-ACCESS read-write
    STATUS     current
    DESCRIPTION
            ""
    ::= { lcsSetupIpRouter 14 }

-- {TABLE} 1.3.6.1.4.1.2356.11.2.8.19
lcsSetupIpRouterNNNatTable OBJECT-TYPE
    SYNTAX     SEQUENCE OF LcsSetupIpRouterNNNatEntry
    MAX-ACCESS not-accessible
    STATUS     current
    DESCRIPTION
            ""
    ::= { lcsSetupIpRouter 19 }

-- {ROW} 1.3.6.1.4.1.2356.11.2.8.19.1
lcsSetupIpRouterNNNatEntry OBJECT-TYPE
    SYNTAX     LcsSetupIpRouterNNNatEntry
    MAX-ACCESS not-accessible
    STATUS     current
    DESCRIPTION
            ""
    INDEX {
            lcsSetupIpRouterNNNatEntryIdx
          }
    ::= { lcsSetupIpRouterNNNatTable 1 }

LcsSetupIpRouterNNNatEntry ::= SEQUENCE {
            lcsSetupIpRouterNNNatEntryIdx DisplayString,
            lcsSetupIpRouterNNNatEntrySrcAddress IpAddress,
            lcsSetupIpRouterNNNatEntrySrcMask IpAddress,
            lcsSetupIpRouterNNNatEntryDstStation DisplayString,
            lcsSetupIpRouterNNNatEntryMappedNetwork IpAddress
    }

-- {COLUMN} 1.3.6.1.4.1.2356.11.2.8.19.1.1
lcsSetupIpRouterNNNatEntryIdx OBJECT-TYPE
    SYNTAX     DisplayString (SIZE(0..4))
    MAX-ACCESS read-write
    STATUS     current
    DESCRIPTION
            ""
    ::= { lcsSetupIpRouterNNNatEntry 1 }

-- {COLUMN} 1.3.6.1.4.1.2356.11.2.8.19.1.2
lcsSetupIpRouterNNNatEntrySrcAddress OBJECT-TYPE
    SYNTAX     IpAddress
    MAX-ACCESS read-write
    STATUS     current
    DESCRIPTION
            ""
    ::= { lcsSetupIpRouterNNNatEntry 2 }

-- {COLUMN} 1.3.6.1.4.1.2356.11.2.8.19.1.3
lcsSetupIpRouterNNNatEntrySrcMask OBJECT-TYPE
    SYNTAX     IpAddress
    MAX-ACCESS read-write
    STATUS     current
    DESCRIPTION
            ""
    ::= { lcsSetupIpRouterNNNatEntry 3 }

-- {COLUMN} 1.3.6.1.4.1.2356.11.2.8.19.1.4
lcsSetupIpRouterNNNatEntryDstStation OBJECT-TYPE
    SYNTAX     DisplayString (SIZE(0..16))
    MAX-ACCESS read-write
    STATUS     current
    DESCRIPTION
            ""
    ::= { lcsSetupIpRouterNNNatEntry 4 }

-- {COLUMN} 1.3.6.1.4.1.2356.11.2.8.19.1.5
lcsSetupIpRouterNNNatEntryMappedNetwork OBJECT-TYPE
    SYNTAX     IpAddress
    MAX-ACCESS read-write
    STATUS     current
    DESCRIPTION
            ""
    ::= { lcsSetupIpRouterNNNatEntry 5 }

-- {NODE} 1.3.6.1.4.1.2356.11.2.8.20
lcsSetupIpRouterLoadBalancer OBJECT IDENTIFIER ::= { lcsSetupIpRouter 20 }

-- {SCALAR} 1.3.6.1.4.1.2356.11.2.8.20.1
lcsSetupIpRouterLoadBalancerOperating OBJECT-TYPE
    SYNTAX     INTEGER {
                  eNo (0),
                  eYes (1)
            }
    MAX-ACCESS read-write
    STATUS     current
    DESCRIPTION
            ""
    ::= { lcsSetupIpRouterLoadBalancer 1 }

-- {TABLE} 1.3.6.1.4.1.2356.11.2.8.20.2
lcsSetupIpRouterLoadBalancerBundlePeersTable OBJECT-TYPE
    SYNTAX     SEQUENCE OF LcsSetupIpRouterLoadBalancerBundlePeersEntry
    MAX-ACCESS not-accessible
    STATUS     current
    DESCRIPTION
            ""
    ::= { lcsSetupIpRouterLoadBalancer 2 }

-- {ROW} 1.3.6.1.4.1.2356.11.2.8.20.2.1
lcsSetupIpRouterLoadBalancerBundlePeersEntry OBJECT-TYPE
    SYNTAX     LcsSetupIpRouterLoadBalancerBundlePeersEntry
    MAX-ACCESS not-accessible
    STATUS     current
    DESCRIPTION
            ""
    INDEX {
            lcsSetupIpRouterLoadBalancerBundlePeersEntryPeer
          }
    ::= { lcsSetupIpRouterLoadBalancerBundlePeersTable 1 }

LcsSetupIpRouterLoadBalancerBundlePeersEntry ::= SEQUENCE {
            lcsSetupIpRouterLoadBalancerBundlePeersEntryPeer DisplayString,
            lcsSetupIpRouterLoadBalancerBundlePeersEntryBundlePeer1 DisplayString,
            lcsSetupIpRouterLoadBalancerBundlePeersEntryBundlePeer2 DisplayString,
            lcsSetupIpRouterLoadBalancerBundlePeersEntryBundlePeer3 DisplayString,
            lcsSetupIpRouterLoadBalancerBundlePeersEntryBundlePeer4 DisplayString,
            lcsSetupIpRouterLoadBalancerBundlePeersEntryClientBinding INTEGER,
            lcsSetupIpRouterLoadBalancerBundlePeersEntryIpv4Masq INTEGER
    }

-- {COLUMN} 1.3.6.1.4.1.2356.11.2.8.20.2.1.1
lcsSetupIpRouterLoadBalancerBundlePeersEntryPeer OBJECT-TYPE
    SYNTAX     DisplayString (SIZE(0..16))
    MAX-ACCESS read-write
    STATUS     current
    DESCRIPTION
            ""
    ::= { lcsSetupIpRouterLoadBalancerBundlePeersEntry 1 }

-- {COLUMN} 1.3.6.1.4.1.2356.11.2.8.20.2.1.2
lcsSetupIpRouterLoadBalancerBundlePeersEntryBundlePeer1 OBJECT-TYPE
    SYNTAX     DisplayString (SIZE(0..16))
    MAX-ACCESS read-write
    STATUS     current
    DESCRIPTION
            ""
    ::= { lcsSetupIpRouterLoadBalancerBundlePeersEntry 2 }

-- {COLUMN} 1.3.6.1.4.1.2356.11.2.8.20.2.1.3
lcsSetupIpRouterLoadBalancerBundlePeersEntryBundlePeer2 OBJECT-TYPE
    SYNTAX     DisplayString (SIZE(0..16))
    MAX-ACCESS read-write
    STATUS     current
    DESCRIPTION
            ""
    ::= { lcsSetupIpRouterLoadBalancerBundlePeersEntry 3 }

-- {COLUMN} 1.3.6.1.4.1.2356.11.2.8.20.2.1.4
lcsSetupIpRouterLoadBalancerBundlePeersEntryBundlePeer3 OBJECT-TYPE
    SYNTAX     DisplayString (SIZE(0..16))
    MAX-ACCESS read-write
    STATUS     current
    DESCRIPTION
            ""
    ::= { lcsSetupIpRouterLoadBalancerBundlePeersEntry 4 }

-- {COLUMN} 1.3.6.1.4.1.2356.11.2.8.20.2.1.5
lcsSetupIpRouterLoadBalancerBundlePeersEntryBundlePeer4 OBJECT-TYPE
    SYNTAX     DisplayString (SIZE(0..16))
    MAX-ACCESS read-write
    STATUS     current
    DESCRIPTION
            ""
    ::= { lcsSetupIpRouterLoadBalancerBundlePeersEntry 5 }

-- {COLUMN} 1.3.6.1.4.1.2356.11.2.8.20.2.1.10
lcsSetupIpRouterLoadBalancerBundlePeersEntryClientBinding OBJECT-TYPE
    SYNTAX     INTEGER {
                  eNo (0),
                  eYes (1)
            }
    MAX-ACCESS read-write
    STATUS     current
    DESCRIPTION
            "-- empty --"
    ::= { lcsSetupIpRouterLoadBalancerBundlePeersEntry 10 }

-- {COLUMN} 1.3.6.1.4.1.2356.11.2.8.20.2.1.11
lcsSetupIpRouterLoadBalancerBundlePeersEntryIpv4Masq OBJECT-TYPE
    SYNTAX     INTEGER {
                  eAuto (0),
                  eNo (1),
                  eOn (2),
                  eIntranet (3)
            }
    MAX-ACCESS read-write
    STATUS     current
    DESCRIPTION
            "-- empty --"
    ::= { lcsSetupIpRouterLoadBalancerBundlePeersEntry 11 }

-- {NODE} 1.3.6.1.4.1.2356.11.2.8.20.3
lcsSetupIpRouterLoadBalancerClientBinding OBJECT IDENTIFIER ::= { lcsSetupIpRouterLoadBalancer 3 }

-- {TABLE} 1.3.6.1.4.1.2356.11.2.8.20.3.1
lcsSetupIpRouterLoadBalancerClientBindingProtocolsTable OBJECT-TYPE
    SYNTAX     SEQUENCE OF LcsSetupIpRouterLoadBalancerClientBindingProtocolsEntry
    MAX-ACCESS not-accessible
    STATUS     current
    DESCRIPTION
            "-- empty --"
    ::= { lcsSetupIpRouterLoadBalancerClientBinding 1 }

-- {ROW} 1.3.6.1.4.1.2356.11.2.8.20.3.1.1
lcsSetupIpRouterLoadBalancerClientBindingProtocolsEntry OBJECT-TYPE
    SYNTAX     LcsSetupIpRouterLoadBalancerClientBindingProtocolsEntry
    MAX-ACCESS not-accessible
    STATUS     current
    DESCRIPTION
            ""
    INDEX {
            lcsSetupIpRouterLoadBalancerClientBindingProtocolsEntryName
          }
    ::= { lcsSetupIpRouterLoadBalancerClientBindingProtocolsTable 1 }

LcsSetupIpRouterLoadBalancerClientBindingProtocolsEntry ::= SEQUENCE {
            lcsSetupIpRouterLoadBalancerClientBindingProtocolsEntryName DisplayString,
            lcsSetupIpRouterLoadBalancerClientBindingProtocolsEntryProtocol Integer32,
            lcsSetupIpRouterLoadBalancerClientBindingProtocolsEntryPort Integer32,
            lcsSetupIpRouterLoadBalancerClientBindingProtocolsEntryActive INTEGER
    }

-- {COLUMN} 1.3.6.1.4.1.2356.11.2.8.20.3.1.1.1
lcsSetupIpRouterLoadBalancerClientBindingProtocolsEntryName OBJECT-TYPE
    SYNTAX     DisplayString (SIZE(0..16))
    MAX-ACCESS read-write
    STATUS     current
    DESCRIPTION
            "-- empty --"
    ::= { lcsSetupIpRouterLoadBalancerClientBindingProtocolsEntry 1 }

-- {COLUMN} 1.3.6.1.4.1.2356.11.2.8.20.3.1.1.2
lcsSetupIpRouterLoadBalancerClientBindingProtocolsEntryProtocol OBJECT-TYPE
    SYNTAX     Integer32 (0..255)
    MAX-ACCESS read-write
    STATUS     current
    DESCRIPTION
            "-- empty --"
    ::= { lcsSetupIpRouterLoadBalancerClientBindingProtocolsEntry 2 }

-- {COLUMN} 1.3.6.1.4.1.2356.11.2.8.20.3.1.1.3
lcsSetupIpRouterLoadBalancerClientBindingProtocolsEntryPort OBJECT-TYPE
    SYNTAX     Integer32 (0..65535)
    MAX-ACCESS read-write
    STATUS     current
    DESCRIPTION
            "-- empty --"
    ::= { lcsSetupIpRouterLoadBalancerClientBindingProtocolsEntry 3 }

-- {COLUMN} 1.3.6.1.4.1.2356.11.2.8.20.3.1.1.4
lcsSetupIpRouterLoadBalancerClientBindingProtocolsEntryActive OBJECT-TYPE
    SYNTAX     INTEGER {
                  eNo (0),
                  eYes (1)
            }
    MAX-ACCESS read-write
    STATUS     current
    DESCRIPTION
            "-- empty --"
    ::= { lcsSetupIpRouterLoadBalancerClientBindingProtocolsEntry 4 }

-- {SCALAR} 1.3.6.1.4.1.2356.11.2.8.20.3.2
lcsSetupIpRouterLoadBalancerClientBindingBalanceSeconds OBJECT-TYPE
    SYNTAX     Integer32 (0..2147483647)
    MAX-ACCESS read-write
    STATUS     current
    DESCRIPTION
            "-- empty --"
    ::= { lcsSetupIpRouterLoadBalancerClientBinding 2 }

-- {SCALAR} 1.3.6.1.4.1.2356.11.2.8.20.3.3
lcsSetupIpRouterLoadBalancerClientBindingBindingMinutes OBJECT-TYPE
    SYNTAX     Integer32 (0..2147483647)
    MAX-ACCESS read-write
    STATUS     current
    DESCRIPTION
            "-- empty --"
    ::= { lcsSetupIpRouterLoadBalancerClientBinding 3 }

-- {NODE} 1.3.6.1.4.1.2356.11.2.8.21
lcsSetupIpRouterVrrp OBJECT IDENTIFIER ::= { lcsSetupIpRouter 21 }

-- {SCALAR} 1.3.6.1.4.1.2356.11.2.8.21.1
lcsSetupIpRouterVrrpOperating OBJECT-TYPE
    SYNTAX     INTEGER {
                  eNo (0),
                  eYes (1)
            }
    MAX-ACCESS read-write
    STATUS     current
    DESCRIPTION
            ""
    ::= { lcsSetupIpRouterVrrp 1 }

-- {TABLE} 1.3.6.1.4.1.2356.11.2.8.21.2
lcsSetupIpRouterVrrpVrrpListTable OBJECT-TYPE
    SYNTAX     SEQUENCE OF LcsSetupIpRouterVrrpVrrpListEntry
    MAX-ACCESS not-accessible
    STATUS     current
    DESCRIPTION
            ""
    ::= { lcsSetupIpRouterVrrp 2 }

-- {ROW} 1.3.6.1.4.1.2356.11.2.8.21.2.1
lcsSetupIpRouterVrrpVrrpListEntry OBJECT-TYPE
    SYNTAX     LcsSetupIpRouterVrrpVrrpListEntry
    MAX-ACCESS not-accessible
    STATUS     current
    DESCRIPTION
            ""
    INDEX {
            lcsSetupIpRouterVrrpVrrpListEntryRouterId
          }
    ::= { lcsSetupIpRouterVrrpVrrpListTable 1 }

LcsSetupIpRouterVrrpVrrpListEntry ::= SEQUENCE {
            lcsSetupIpRouterVrrpVrrpListEntryRouterId Integer32,
            lcsSetupIpRouterVrrpVrrpListEntryVirtAddress IpAddress,
            lcsSetupIpRouterVrrpVrrpListEntryPrio Integer32,
            lcsSetupIpRouterVrrpVrrpListEntryBPrio Integer32,
            lcsSetupIpRouterVrrpVrrpListEntryPeer DisplayString,
            lcsSetupIpRouterVrrpVrrpListEntryComment DisplayString
    }

-- {COLUMN} 1.3.6.1.4.1.2356.11.2.8.21.2.1.1
lcsSetupIpRouterVrrpVrrpListEntryRouterId OBJECT-TYPE
    SYNTAX     Integer32 (0..255)
    MAX-ACCESS read-write
    STATUS     current
    DESCRIPTION
            ""
    ::= { lcsSetupIpRouterVrrpVrrpListEntry 1 }

-- {COLUMN} 1.3.6.1.4.1.2356.11.2.8.21.2.1.2
lcsSetupIpRouterVrrpVrrpListEntryVirtAddress OBJECT-TYPE
    SYNTAX     IpAddress
    MAX-ACCESS read-write
    STATUS     current
    DESCRIPTION
            ""
    ::= { lcsSetupIpRouterVrrpVrrpListEntry 2 }

-- {COLUMN} 1.3.6.1.4.1.2356.11.2.8.21.2.1.3
lcsSetupIpRouterVrrpVrrpListEntryPrio OBJECT-TYPE
    SYNTAX     Integer32 (0..255)
    MAX-ACCESS read-write
    STATUS     current
    DESCRIPTION
            ""
    ::= { lcsSetupIpRouterVrrpVrrpListEntry 3 }

-- {COLUMN} 1.3.6.1.4.1.2356.11.2.8.21.2.1.4
lcsSetupIpRouterVrrpVrrpListEntryBPrio OBJECT-TYPE
    SYNTAX     Integer32 (0..255)
    MAX-ACCESS read-write
    STATUS     current
    DESCRIPTION
            ""
    ::= { lcsSetupIpRouterVrrpVrrpListEntry 4 }

-- {COLUMN} 1.3.6.1.4.1.2356.11.2.8.21.2.1.5
lcsSetupIpRouterVrrpVrrpListEntryPeer OBJECT-TYPE
    SYNTAX     DisplayString (SIZE(0..16))
    MAX-ACCESS read-write
    STATUS     current
    DESCRIPTION
            ""
    ::= { lcsSetupIpRouterVrrpVrrpListEntry 5 }

-- {COLUMN} 1.3.6.1.4.1.2356.11.2.8.21.2.1.6
lcsSetupIpRouterVrrpVrrpListEntryComment OBJECT-TYPE
    SYNTAX     DisplayString (SIZE(0..64))
    MAX-ACCESS read-write
    STATUS     current
    DESCRIPTION
            ""
    ::= { lcsSetupIpRouterVrrpVrrpListEntry 6 }

-- {SCALAR} 1.3.6.1.4.1.2356.11.2.8.21.3
lcsSetupIpRouterVrrpReconnectDelay OBJECT-TYPE
    SYNTAX     Integer32 (0..65535)
    MAX-ACCESS read-write
    STATUS     current
    DESCRIPTION
            ""
    ::= { lcsSetupIpRouterVrrp 3 }

-- {SCALAR} 1.3.6.1.4.1.2356.11.2.8.21.4
lcsSetupIpRouterVrrpAdvertIntervall OBJECT-TYPE
    SYNTAX     Integer32 (0..255)
    MAX-ACCESS read-write
    STATUS     current
    DESCRIPTION
            ""
    ::= { lcsSetupIpRouterVrrp 4 }

-- {SCALAR} 1.3.6.1.4.1.2356.11.2.8.21.5
lcsSetupIpRouterVrrpInternalServices OBJECT-TYPE
    SYNTAX     INTEGER {
                  eNo (0),
                  eYes (1)
            }
    MAX-ACCESS read-write
    STATUS     current
    DESCRIPTION
            ""
    ::= { lcsSetupIpRouterVrrp 5 }

-- {SCALAR} 1.3.6.1.4.1.2356.11.2.8.22
lcsSetupIpRouterWanTagCreation OBJECT-TYPE
    SYNTAX     INTEGER {
                  eManual (0),
                  eAuto (1)
            }
    MAX-ACCESS read-write
    STATUS     current
    DESCRIPTION
            ""
    ::= { lcsSetupIpRouter 22 }

-- {TABLE} 1.3.6.1.4.1.2356.11.2.8.23
lcsSetupIpRouterTagTableTable OBJECT-TYPE
    SYNTAX     SEQUENCE OF LcsSetupIpRouterTagTableEntry
    MAX-ACCESS not-accessible
    STATUS     current
    DESCRIPTION
            ""
    ::= { lcsSetupIpRouter 23 }

-- {ROW} 1.3.6.1.4.1.2356.11.2.8.23.1
lcsSetupIpRouterTagTableEntry OBJECT-TYPE
    SYNTAX     LcsSetupIpRouterTagTableEntry
    MAX-ACCESS not-accessible
    STATUS     current
    DESCRIPTION
            ""
    INDEX {
            lcsSetupIpRouterTagTableEntryPeer
          }
    ::= { lcsSetupIpRouterTagTableTable 1 }

LcsSetupIpRouterTagTableEntry ::= SEQUENCE {
            lcsSetupIpRouterTagTableEntryPeer DisplayString,
            lcsSetupIpRouterTagTableEntryRtgTag Integer32,
            lcsSetupIpRouterTagTableEntryStartWanPool IpAddress,
            lcsSetupIpRouterTagTableEntryEndWanPool IpAddress,
            lcsSetupIpRouterTagTableEntryDnsDefault IpAddress,
            lcsSetupIpRouterTagTableEntryDnsBackup IpAddress,
            lcsSetupIpRouterTagTableEntryNbnsDefault IpAddress,
            lcsSetupIpRouterTagTableEntryNbnsBackup IpAddress
    }

-- {COLUMN} 1.3.6.1.4.1.2356.11.2.8.23.1.1
lcsSetupIpRouterTagTableEntryPeer OBJECT-TYPE
    SYNTAX     DisplayString (SIZE(0..16))
    MAX-ACCESS read-write
    STATUS     current
    DESCRIPTION
            ""
    ::= { lcsSetupIpRouterTagTableEntry 1 }

-- {COLUMN} 1.3.6.1.4.1.2356.11.2.8.23.1.2
lcsSetupIpRouterTagTableEntryRtgTag OBJECT-TYPE
    SYNTAX     Integer32 (0..65535)
    MAX-ACCESS read-write
    STATUS     current
    DESCRIPTION
            ""
    ::= { lcsSetupIpRouterTagTableEntry 2 }

-- {COLUMN} 1.3.6.1.4.1.2356.11.2.8.23.1.3
lcsSetupIpRouterTagTableEntryStartWanPool OBJECT-TYPE
    SYNTAX     IpAddress
    MAX-ACCESS read-write
    STATUS     current
    DESCRIPTION
            ""
    ::= { lcsSetupIpRouterTagTableEntry 3 }

-- {COLUMN} 1.3.6.1.4.1.2356.11.2.8.23.1.4
lcsSetupIpRouterTagTableEntryEndWanPool OBJECT-TYPE
    SYNTAX     IpAddress
    MAX-ACCESS read-write
    STATUS     current
    DESCRIPTION
            ""
    ::= { lcsSetupIpRouterTagTableEntry 4 }

-- {COLUMN} 1.3.6.1.4.1.2356.11.2.8.23.1.5
lcsSetupIpRouterTagTableEntryDnsDefault OBJECT-TYPE
    SYNTAX     IpAddress
    MAX-ACCESS read-write
    STATUS     current
    DESCRIPTION
            "-- empty --"
    ::= { lcsSetupIpRouterTagTableEntry 5 }

-- {COLUMN} 1.3.6.1.4.1.2356.11.2.8.23.1.6
lcsSetupIpRouterTagTableEntryDnsBackup OBJECT-TYPE
    SYNTAX     IpAddress
    MAX-ACCESS read-write
    STATUS     current
    DESCRIPTION
            "-- empty --"
    ::= { lcsSetupIpRouterTagTableEntry 6 }

-- {COLUMN} 1.3.6.1.4.1.2356.11.2.8.23.1.7
lcsSetupIpRouterTagTableEntryNbnsDefault OBJECT-TYPE
    SYNTAX     IpAddress
    MAX-ACCESS read-write
    STATUS     current
    DESCRIPTION
            "-- empty --"
    ::= { lcsSetupIpRouterTagTableEntry 7 }

-- {COLUMN} 1.3.6.1.4.1.2356.11.2.8.23.1.8
lcsSetupIpRouterTagTableEntryNbnsBackup OBJECT-TYPE
    SYNTAX     IpAddress
    MAX-ACCESS read-write
    STATUS     current
    DESCRIPTION
            "-- empty --"
    ::= { lcsSetupIpRouterTagTableEntry 8 }

-- {TABLE} 1.3.6.1.4.1.2356.11.2.8.24
lcsSetupIpRouterIcmpTable OBJECT-TYPE
    SYNTAX     SEQUENCE OF LcsSetupIpRouterIcmpEntry
    MAX-ACCESS not-accessible
    STATUS     current
    DESCRIPTION
            "-- empty --"
    ::= { lcsSetupIpRouter 24 }

-- {ROW} 1.3.6.1.4.1.2356.11.2.8.24.1
lcsSetupIpRouterIcmpEntry OBJECT-TYPE
    SYNTAX     LcsSetupIpRouterIcmpEntry
    MAX-ACCESS not-accessible
    STATUS     current
    DESCRIPTION
            ""
    INDEX {
            lcsSetupIpRouterIcmpEntryInterfaceName
          }
    ::= { lcsSetupIpRouterIcmpTable 1 }

LcsSetupIpRouterIcmpEntry ::= SEQUENCE {
            lcsSetupIpRouterIcmpEntryInterfaceName DisplayString,
            lcsSetupIpRouterIcmpEntryMaxSize Integer32,
            lcsSetupIpRouterIcmpEntryRefreshAmount Integer32,
            lcsSetupIpRouterIcmpEntryInterval Integer32,
            lcsSetupIpRouterIcmpEntryMode INTEGER,
            lcsSetupIpRouterIcmpEntryRedirects INTEGER
    }

-- {COLUMN} 1.3.6.1.4.1.2356.11.2.8.24.1.1
lcsSetupIpRouterIcmpEntryInterfaceName OBJECT-TYPE
    SYNTAX     DisplayString (SIZE(0..16))
    MAX-ACCESS read-only
    STATUS     current
    DESCRIPTION
            "-- empty --"
    ::= { lcsSetupIpRouterIcmpEntry 1 }

-- {COLUMN} 1.3.6.1.4.1.2356.11.2.8.24.1.2
lcsSetupIpRouterIcmpEntryMaxSize OBJECT-TYPE
    SYNTAX     Integer32 (0..2147483647)
    MAX-ACCESS read-write
    STATUS     current
    DESCRIPTION
            "-- empty --"
    ::= { lcsSetupIpRouterIcmpEntry 2 }

-- {COLUMN} 1.3.6.1.4.1.2356.11.2.8.24.1.3
lcsSetupIpRouterIcmpEntryRefreshAmount OBJECT-TYPE
    SYNTAX     Integer32 (0..2147483647)
    MAX-ACCESS read-write
    STATUS     current
    DESCRIPTION
            "-- empty --"
    ::= { lcsSetupIpRouterIcmpEntry 3 }

-- {COLUMN} 1.3.6.1.4.1.2356.11.2.8.24.1.4
lcsSetupIpRouterIcmpEntryInterval OBJECT-TYPE
    SYNTAX     Integer32 (0..2147483647)
    MAX-ACCESS read-write
    STATUS     current
    DESCRIPTION
            "-- empty --"
    ::= { lcsSetupIpRouterIcmpEntry 4 }

-- {COLUMN} 1.3.6.1.4.1.2356.11.2.8.24.1.5
lcsSetupIpRouterIcmpEntryMode OBJECT-TYPE
    SYNTAX     INTEGER {
                  eBandwidth (0),
                  ePackets (1),
                  eDisabled (2)
            }
    MAX-ACCESS read-write
    STATUS     current
    DESCRIPTION
            "-- empty --"
    ::= { lcsSetupIpRouterIcmpEntry 5 }

-- {COLUMN} 1.3.6.1.4.1.2356.11.2.8.24.1.6
lcsSetupIpRouterIcmpEntryRedirects OBJECT-TYPE
    SYNTAX     INTEGER {
                  eYes (0),
                  eNo (1)
            }
    MAX-ACCESS read-write
    STATUS     current
    DESCRIPTION
            "-- empty --"
    ::= { lcsSetupIpRouterIcmpEntry 6 }

-- {NODE} 1.3.6.1.4.1.2356.11.2.9
lcsSetupSnmp OBJECT IDENTIFIER ::= { lcsSetup 9 }

-- {SCALAR} 1.3.6.1.4.1.2356.11.2.9.1
lcsSetupSnmpSendTraps OBJECT-TYPE
    SYNTAX     INTEGER {
                  eNo (0),
                  eYes (1)
            }
    MAX-ACCESS read-write
    STATUS     current
    DESCRIPTION
            ""
    ::= { lcsSetupSnmp 1 }

-- {TABLE} 1.3.6.1.4.1.2356.11.2.9.2
lcsSetupSnmpIpTrapsTable OBJECT-TYPE
    SYNTAX     SEQUENCE OF LcsSetupSnmpIpTrapsEntry
    MAX-ACCESS not-accessible
    STATUS     current
    DESCRIPTION
            ""
    ::= { lcsSetupSnmp 2 }

-- {ROW} 1.3.6.1.4.1.2356.11.2.9.2.1
lcsSetupSnmpIpTrapsEntry OBJECT-TYPE
    SYNTAX     LcsSetupSnmpIpTrapsEntry
    MAX-ACCESS not-accessible
    STATUS     current
    DESCRIPTION
            ""
    INDEX {
            lcsSetupSnmpIpTrapsEntryTrapIp
          }
    ::= { lcsSetupSnmpIpTrapsTable 1 }

LcsSetupSnmpIpTrapsEntry ::= SEQUENCE {
            lcsSetupSnmpIpTrapsEntryTrapIp IpAddress,
            lcsSetupSnmpIpTrapsEntryLoopbackAddr DisplayString,
            lcsSetupSnmpIpTrapsEntryVersion INTEGER,
            lcsSetupSnmpIpTrapsEntryPort Integer32
    }

-- {COLUMN} 1.3.6.1.4.1.2356.11.2.9.2.1.1
lcsSetupSnmpIpTrapsEntryTrapIp OBJECT-TYPE
    SYNTAX     IpAddress
    MAX-ACCESS read-write
    STATUS     current
    DESCRIPTION
            ""
    ::= { lcsSetupSnmpIpTrapsEntry 1 }

-- {COLUMN} 1.3.6.1.4.1.2356.11.2.9.2.1.3
lcsSetupSnmpIpTrapsEntryLoopbackAddr OBJECT-TYPE
    SYNTAX     DisplayString (SIZE(0..16))
    MAX-ACCESS read-write
    STATUS     current
    DESCRIPTION
            ""
    ::= { lcsSetupSnmpIpTrapsEntry 3 }

-- {COLUMN} 1.3.6.1.4.1.2356.11.2.9.2.1.4
lcsSetupSnmpIpTrapsEntryVersion OBJECT-TYPE
    SYNTAX     INTEGER {
                  eSnmpv2 (0),
                  eSnmpv1 (1)
            }
    MAX-ACCESS read-write
    STATUS     current
    DESCRIPTION
            ""
    ::= { lcsSetupSnmpIpTrapsEntry 4 }

-- {COLUMN} 1.3.6.1.4.1.2356.11.2.9.2.1.5
lcsSetupSnmpIpTrapsEntryPort OBJECT-TYPE
    SYNTAX     Integer32 (0..65535)
    MAX-ACCESS read-write
    STATUS     current
    DESCRIPTION
            "-- empty --"
    ::= { lcsSetupSnmpIpTrapsEntry 5 }

-- {SCALAR} 1.3.6.1.4.1.2356.11.2.9.3
lcsSetupSnmpAdministrator OBJECT-TYPE
    SYNTAX     DisplayString (SIZE(0..255))
    MAX-ACCESS read-write
    STATUS     current
    DESCRIPTION
            ""
    ::= { lcsSetupSnmp 3 }

-- {SCALAR} 1.3.6.1.4.1.2356.11.2.9.4
lcsSetupSnmpLocation OBJECT-TYPE
    SYNTAX     DisplayString (SIZE(0..255))
    MAX-ACCESS read-write
    STATUS     current
    DESCRIPTION
            ""
    ::= { lcsSetupSnmp 4 }

-- {SCALAR} 1.3.6.1.4.1.2356.11.2.9.5
lcsSetupSnmpRegisterMonitor OBJECT-TYPE
    SYNTAX     DisplayString
    MAX-ACCESS read-write
    STATUS     current
    DESCRIPTION
            ""
    ::= { lcsSetupSnmp 5 }

-- {SCALAR} 1.3.6.1.4.1.2356.11.2.9.6
lcsSetupSnmpDeleteMonitor OBJECT-TYPE
    SYNTAX     DisplayString
    MAX-ACCESS read-write
    STATUS     current
    DESCRIPTION
            ""
    ::= { lcsSetupSnmp 6 }

-- {TABLE} 1.3.6.1.4.1.2356.11.2.9.7
lcsSetupSnmpMonitorTableTable OBJECT-TYPE
    SYNTAX     SEQUENCE OF LcsSetupSnmpMonitorTableEntry
    MAX-ACCESS not-accessible
    STATUS     current
    DESCRIPTION
            ""
    ::= { lcsSetupSnmp 7 }

-- {ROW} 1.3.6.1.4.1.2356.11.2.9.7.1
lcsSetupSnmpMonitorTableEntry OBJECT-TYPE
    SYNTAX     LcsSetupSnmpMonitorTableEntry
    MAX-ACCESS not-accessible
    STATUS     current
    DESCRIPTION
            ""
    INDEX {
            lcsSetupSnmpMonitorTableEntryIpAddress,
            lcsSetupSnmpMonitorTableEntryPort
          }
    ::= { lcsSetupSnmpMonitorTableTable 1 }

LcsSetupSnmpMonitorTableEntry ::= SEQUENCE {
            lcsSetupSnmpMonitorTableEntryIpAddress IpAddress,
            lcsSetupSnmpMonitorTableEntryPort Integer32,
            lcsSetupSnmpMonitorTableEntryTimeout Integer32,
            lcsSetupSnmpMonitorTableEntryMacAddress DisplayString,
            lcsSetupSnmpMonitorTableEntryPeer DisplayString,
            lcsSetupSnmpMonitorTableEntryLoopbackAddr IpAddress,
            lcsSetupSnmpMonitorTableEntryVlanId Integer32,
            lcsSetupSnmpMonitorTableEntryLanIfc DisplayString,
            lcsSetupSnmpMonitorTableEntryEthernetPort Integer32
    }

-- {COLUMN} 1.3.6.1.4.1.2356.11.2.9.7.1.1
lcsSetupSnmpMonitorTableEntryIpAddress OBJECT-TYPE
    SYNTAX     IpAddress
    MAX-ACCESS read-only
    STATUS     current
    DESCRIPTION
            ""
    ::= { lcsSetupSnmpMonitorTableEntry 1 }

-- {COLUMN} 1.3.6.1.4.1.2356.11.2.9.7.1.2
lcsSetupSnmpMonitorTableEntryPort OBJECT-TYPE
    SYNTAX     Integer32 (0..65535)
    MAX-ACCESS read-only
    STATUS     current
    DESCRIPTION
            ""
    ::= { lcsSetupSnmpMonitorTableEntry 2 }

-- {COLUMN} 1.3.6.1.4.1.2356.11.2.9.7.1.3
lcsSetupSnmpMonitorTableEntryTimeout OBJECT-TYPE
    SYNTAX     Integer32 (0..65535)
    MAX-ACCESS read-only
    STATUS     current
    DESCRIPTION
            ""
    ::= { lcsSetupSnmpMonitorTableEntry 3 }

-- {COLUMN} 1.3.6.1.4.1.2356.11.2.9.7.1.4
lcsSetupSnmpMonitorTableEntryMacAddress OBJECT-TYPE
    SYNTAX     DisplayString (SIZE(0..12))
    MAX-ACCESS read-only
    STATUS     current
    DESCRIPTION
            ""
    ::= { lcsSetupSnmpMonitorTableEntry 4 }

-- {COLUMN} 1.3.6.1.4.1.2356.11.2.9.7.1.5
lcsSetupSnmpMonitorTableEntryPeer OBJECT-TYPE
    SYNTAX     DisplayString (SIZE(0..16))
    MAX-ACCESS read-only
    STATUS     current
    DESCRIPTION
            ""
    ::= { lcsSetupSnmpMonitorTableEntry 5 }

-- {COLUMN} 1.3.6.1.4.1.2356.11.2.9.7.1.6
lcsSetupSnmpMonitorTableEntryLoopbackAddr OBJECT-TYPE
    SYNTAX     IpAddress
    MAX-ACCESS read-only
    STATUS     current
    DESCRIPTION
            ""
    ::= { lcsSetupSnmpMonitorTableEntry 6 }

-- {COLUMN} 1.3.6.1.4.1.2356.11.2.9.7.1.7
lcsSetupSnmpMonitorTableEntryVlanId OBJECT-TYPE
    SYNTAX     Integer32 (0..65535)
    MAX-ACCESS read-only
    STATUS     current
    DESCRIPTION
            ""
    ::= { lcsSetupSnmpMonitorTableEntry 7 }

-- {COLUMN} 1.3.6.1.4.1.2356.11.2.9.7.1.8
lcsSetupSnmpMonitorTableEntryLanIfc OBJECT-TYPE
    SYNTAX     DisplayString (SIZE(0..255))
    MAX-ACCESS read-only
    STATUS     current
    DESCRIPTION
            ""
    ::= { lcsSetupSnmpMonitorTableEntry 8 }

-- {COLUMN} 1.3.6.1.4.1.2356.11.2.9.7.1.9
lcsSetupSnmpMonitorTableEntryEthernetPort OBJECT-TYPE
    SYNTAX     Integer32 (0..255)
    MAX-ACCESS read-only
    STATUS     current
    DESCRIPTION
            ""
    ::= { lcsSetupSnmpMonitorTableEntry 9 }

-- {SCALAR} 1.3.6.1.4.1.2356.11.2.9.10
lcsSetupSnmpPasswordRequiredForSnmpReadAccess OBJECT-TYPE
    SYNTAX     INTEGER {
                  eNo (0),
                  eYes (1)
            }
    MAX-ACCESS read-write
    STATUS     current
    DESCRIPTION
            ""
    ::= { lcsSetupSnmp 10 }

-- {SCALAR} 1.3.6.1.4.1.2356.11.2.9.11
lcsSetupSnmpComment1 OBJECT-TYPE
    SYNTAX     DisplayString (SIZE(0..255))
    MAX-ACCESS read-write
    STATUS     current
    DESCRIPTION
            ""
    ::= { lcsSetupSnmp 11 }

-- {SCALAR} 1.3.6.1.4.1.2356.11.2.9.12
lcsSetupSnmpComment2 OBJECT-TYPE
    SYNTAX     DisplayString (SIZE(0..255))
    MAX-ACCESS read-write
    STATUS     current
    DESCRIPTION
            ""
    ::= { lcsSetupSnmp 12 }

-- {SCALAR} 1.3.6.1.4.1.2356.11.2.9.13
lcsSetupSnmpComment3 OBJECT-TYPE
    SYNTAX     DisplayString (SIZE(0..255))
    MAX-ACCESS read-write
    STATUS     current
    DESCRIPTION
            ""
    ::= { lcsSetupSnmp 13 }

-- {SCALAR} 1.3.6.1.4.1.2356.11.2.9.14
lcsSetupSnmpComment4 OBJECT-TYPE
    SYNTAX     DisplayString (SIZE(0..255))
    MAX-ACCESS read-write
    STATUS     current
    DESCRIPTION
            ""
    ::= { lcsSetupSnmp 14 }

-- {SCALAR} 1.3.6.1.4.1.2356.11.2.9.15
lcsSetupSnmpReadOnlyCommunity OBJECT-TYPE
    SYNTAX     DisplayString (SIZE(0..31))
    MAX-ACCESS read-write
    STATUS     current
    DESCRIPTION
            ""
    ::= { lcsSetupSnmp 15 }

-- {SCALAR} 1.3.6.1.4.1.2356.11.2.9.16
lcsSetupSnmpComment5 OBJECT-TYPE
    SYNTAX     DisplayString (SIZE(0..255))
    MAX-ACCESS read-write
    STATUS     current
    DESCRIPTION
            ""
    ::= { lcsSetupSnmp 16 }

-- {SCALAR} 1.3.6.1.4.1.2356.11.2.9.17
lcsSetupSnmpComment6 OBJECT-TYPE
    SYNTAX     DisplayString (SIZE(0..255))
    MAX-ACCESS read-write
    STATUS     current
    DESCRIPTION
            ""
    ::= { lcsSetupSnmp 17 }

-- {SCALAR} 1.3.6.1.4.1.2356.11.2.9.18
lcsSetupSnmpComment7 OBJECT-TYPE
    SYNTAX     DisplayString (SIZE(0..255))
    MAX-ACCESS read-write
    STATUS     current
    DESCRIPTION
            ""
    ::= { lcsSetupSnmp 18 }

-- {SCALAR} 1.3.6.1.4.1.2356.11.2.9.19
lcsSetupSnmpComment8 OBJECT-TYPE
    SYNTAX     DisplayString (SIZE(0..255))
    MAX-ACCESS read-write
    STATUS     current
    DESCRIPTION
            ""
    ::= { lcsSetupSnmp 19 }

-- {SCALAR} 1.3.6.1.4.1.2356.11.2.9.20
lcsSetupSnmpFullHostMib OBJECT-TYPE
    SYNTAX     INTEGER {
                  eNo (0),
                  eYes (1)
            }
    MAX-ACCESS read-write
    STATUS     current
    DESCRIPTION
            ""
    ::= { lcsSetupSnmp 20 }

-- {SCALAR} 1.3.6.1.4.1.2356.11.2.9.21
lcsSetupSnmpPort OBJECT-TYPE
    SYNTAX     Integer32 (0..65535)
    MAX-ACCESS read-write
    STATUS     current
    DESCRIPTION
            "-- empty --"
    ::= { lcsSetupSnmp 21 }

-- {TABLE} 1.3.6.1.4.1.2356.11.2.9.22
lcsSetupSnmpReadOnlyCommunitiesTable OBJECT-TYPE
    SYNTAX     SEQUENCE OF LcsSetupSnmpReadOnlyCommunitiesEntry
    MAX-ACCESS not-accessible
    STATUS     current
    DESCRIPTION
            "-- empty --"
    ::= { lcsSetupSnmp 22 }

-- {ROW} 1.3.6.1.4.1.2356.11.2.9.22.1
lcsSetupSnmpReadOnlyCommunitiesEntry OBJECT-TYPE
    SYNTAX     LcsSetupSnmpReadOnlyCommunitiesEntry
    MAX-ACCESS not-accessible
    STATUS     current
    DESCRIPTION
            ""
    INDEX {
            lcsSetupSnmpReadOnlyCommunitiesEntryReadOnlyCommunity
          }
    ::= { lcsSetupSnmpReadOnlyCommunitiesTable 1 }

LcsSetupSnmpReadOnlyCommunitiesEntry ::= SEQUENCE {
            lcsSetupSnmpReadOnlyCommunitiesEntryReadOnlyCommunity DisplayString
    }

-- {COLUMN} 1.3.6.1.4.1.2356.11.2.9.22.1.1
lcsSetupSnmpReadOnlyCommunitiesEntryReadOnlyCommunity OBJECT-TYPE
    SYNTAX     DisplayString (SIZE(0..31))
    MAX-ACCESS read-write
    STATUS     current
    DESCRIPTION
            "-- empty --"
    ::= { lcsSetupSnmpReadOnlyCommunitiesEntry 1 }

-- {SCALAR} 1.3.6.1.4.1.2356.11.2.9.23
lcsSetupSnmpPublicComment1 OBJECT-TYPE
    SYNTAX     DisplayString (SIZE(0..255))
    MAX-ACCESS read-write
    STATUS     current
    DESCRIPTION
            "-- empty --"
    ::= { lcsSetupSnmp 23 }

-- {SCALAR} 1.3.6.1.4.1.2356.11.2.9.24
lcsSetupSnmpPublicComment2 OBJECT-TYPE
    SYNTAX     DisplayString (SIZE(0..255))
    MAX-ACCESS read-write
    STATUS     current
    DESCRIPTION
            "-- empty --"
    ::= { lcsSetupSnmp 24 }

-- {SCALAR} 1.3.6.1.4.1.2356.11.2.9.25
lcsSetupSnmpPublicComment3 OBJECT-TYPE
    SYNTAX     DisplayString (SIZE(0..255))
    MAX-ACCESS read-write
    STATUS     current
    DESCRIPTION
            "-- empty --"
    ::= { lcsSetupSnmp 25 }

-- {SCALAR} 1.3.6.1.4.1.2356.11.2.9.26
lcsSetupSnmpPublicComment4 OBJECT-TYPE
    SYNTAX     DisplayString (SIZE(0..255))
    MAX-ACCESS read-write
    STATUS     current
    DESCRIPTION
            "-- empty --"
    ::= { lcsSetupSnmp 26 }

-- {SCALAR} 1.3.6.1.4.1.2356.11.2.9.37
lcsSetupSnmpAdmittedProtocols OBJECT-TYPE
    SYNTAX     BITS {
                  eSnmpv3 (29),
                  eSnmpv2 (30),
                  eSnmpv1 (31)
            }
    MAX-ACCESS read-write
    STATUS     current
    DESCRIPTION
            "-- empty --"
    ::= { lcsSetupSnmp 37 }

-- {SCALAR} 1.3.6.1.4.1.2356.11.2.9.38
lcsSetupSnmpAllowAdmins OBJECT-TYPE
    SYNTAX     INTEGER {
                  eNo (0),
                  eYes (1)
            }
    MAX-ACCESS read-write
    STATUS     current
    DESCRIPTION
            "-- empty --"
    ::= { lcsSetupSnmp 38 }

-- {SCALAR} 1.3.6.1.4.1.2356.11.2.9.39
lcsSetupSnmpSnmpv3AdminAuthentication OBJECT-TYPE
    SYNTAX     INTEGER {
                  eHmacMd5 (2),
                  eHmacSha (3),
                  eHmacSha224 (4),
                  eHmacSha256 (5),
                  eHmacSha384 (6),
                  eHmacSha512 (7)
            }
    MAX-ACCESS read-only
    STATUS     current
    DESCRIPTION
            "-- empty --"
    ::= { lcsSetupSnmp 39 }

-- {SCALAR} 1.3.6.1.4.1.2356.11.2.9.40
lcsSetupSnmpSnmpv3AdminPrivacy OBJECT-TYPE
    SYNTAX     INTEGER {
                  eDes (2),
                  eAes128 (4),
                  eAes192 (20),
                  eAes256 (21)
            }
    MAX-ACCESS read-only
    STATUS     current
    DESCRIPTION
            "-- empty --"
    ::= { lcsSetupSnmp 40 }

-- {SCALAR} 1.3.6.1.4.1.2356.11.2.9.41
lcsSetupSnmpOperating OBJECT-TYPE
    SYNTAX     BITS {
                  eNo (0),
                  eYes (7)
            }
    MAX-ACCESS read-write
    STATUS     current
    DESCRIPTION
            "-- empty --"
    ::= { lcsSetupSnmp 41 }

-- {TABLE} 1.3.6.1.4.1.2356.11.2.9.42
lcsSetupSnmpFiltersTable OBJECT-TYPE
    SYNTAX     SEQUENCE OF LcsSetupSnmpFiltersEntry
    MAX-ACCESS not-accessible
    STATUS     current
    DESCRIPTION
            "-- empty --"
    ::= { lcsSetupSnmp 42 }

-- {ROW} 1.3.6.1.4.1.2356.11.2.9.42.1
lcsSetupSnmpFiltersEntry OBJECT-TYPE
    SYNTAX     LcsSetupSnmpFiltersEntry
    MAX-ACCESS not-accessible
    STATUS     current
    DESCRIPTION
            ""
    INDEX {
            lcsSetupSnmpFiltersEntryIndex
          }
    ::= { lcsSetupSnmpFiltersTable 1 }

LcsSetupSnmpFiltersEntry ::= SEQUENCE {
            lcsSetupSnmpFiltersEntryIndex DisplayString,
            lcsSetupSnmpFiltersEntryViewName DisplayString,
            lcsSetupSnmpFiltersEntrySpecTrapid DisplayString,
            lcsSetupSnmpFiltersEntryVarBindingid DisplayString,
            lcsSetupSnmpFiltersEntryFilterAction INTEGER
    }

-- {COLUMN} 1.3.6.1.4.1.2356.11.2.9.42.1.1
lcsSetupSnmpFiltersEntryIndex OBJECT-TYPE
    SYNTAX     DisplayString (SIZE(0..4))
    MAX-ACCESS read-write
    STATUS     current
    DESCRIPTION
            "-- empty --"
    ::= { lcsSetupSnmpFiltersEntry 1 }

-- {COLUMN} 1.3.6.1.4.1.2356.11.2.9.42.1.2
lcsSetupSnmpFiltersEntryViewName OBJECT-TYPE
    SYNTAX     DisplayString (SIZE(0..32))
    MAX-ACCESS read-write
    STATUS     current
    DESCRIPTION
            "-- empty --"
    ::= { lcsSetupSnmpFiltersEntry 2 }

-- {COLUMN} 1.3.6.1.4.1.2356.11.2.9.42.1.3
lcsSetupSnmpFiltersEntrySpecTrapid OBJECT-TYPE
    SYNTAX     DisplayString (SIZE(0..128))
    MAX-ACCESS read-write
    STATUS     current
    DESCRIPTION
            "-- empty --"
    ::= { lcsSetupSnmpFiltersEntry 3 }

-- {COLUMN} 1.3.6.1.4.1.2356.11.2.9.42.1.4
lcsSetupSnmpFiltersEntryVarBindingid OBJECT-TYPE
    SYNTAX     DisplayString (SIZE(0..128))
    MAX-ACCESS read-write
    STATUS     current
    DESCRIPTION
            "-- empty --"
    ::= { lcsSetupSnmpFiltersEntry 4 }

-- {COLUMN} 1.3.6.1.4.1.2356.11.2.9.42.1.5
lcsSetupSnmpFiltersEntryFilterAction OBJECT-TYPE
    SYNTAX     INTEGER {
                  eAllow (0),
                  eDeny (1)
            }
    MAX-ACCESS read-write
    STATUS     current
    DESCRIPTION
            "-- empty --"
    ::= { lcsSetupSnmpFiltersEntry 5 }

-- {SCALAR} 1.3.6.1.4.1.2356.11.2.9.43
lcsSetupSnmpEnforcePasswordRules OBJECT-TYPE
    SYNTAX     INTEGER {
                  eNo (0),
                  eYes (1)
            }
    MAX-ACCESS read-write
    STATUS     current
    DESCRIPTION
            "-- empty --"
    ::= { lcsSetupSnmp 43 }

-- {NODE} 1.3.6.1.4.1.2356.11.2.10
lcsSetupDhcp OBJECT IDENTIFIER ::= { lcsSetup 10 }

-- {SCALAR} 1.3.6.1.4.1.2356.11.2.10.6
lcsSetupDhcpMaxLeaseTimeMinutes OBJECT-TYPE
    SYNTAX     Integer32 (0..2147483647)
    MAX-ACCESS read-write
    STATUS     current
    DESCRIPTION
            ""
    ::= { lcsSetupDhcp 6 }

-- {SCALAR} 1.3.6.1.4.1.2356.11.2.10.7
lcsSetupDhcpDefaultLeaseTimeMinutes OBJECT-TYPE
    SYNTAX     Integer32 (0..2147483647)
    MAX-ACCESS read-write
    STATUS     current
    DESCRIPTION
            ""
    ::= { lcsSetupDhcp 7 }

-- {TABLE} 1.3.6.1.4.1.2356.11.2.10.8
lcsSetupDhcpDhcpTableTable OBJECT-TYPE
    SYNTAX     SEQUENCE OF LcsSetupDhcpDhcpTableEntry
    MAX-ACCESS not-accessible
    STATUS     current
    DESCRIPTION
            ""
    ::= { lcsSetupDhcp 8 }

-- {ROW} 1.3.6.1.4.1.2356.11.2.10.8.1
lcsSetupDhcpDhcpTableEntry OBJECT-TYPE
    SYNTAX     LcsSetupDhcpDhcpTableEntry
    MAX-ACCESS not-accessible
    STATUS     current
    DESCRIPTION
            ""
    INDEX {
            lcsSetupDhcpDhcpTableEntryIpAddress,
            lcsSetupDhcpDhcpTableEntryNetworkName
          }
    ::= { lcsSetupDhcpDhcpTableTable 1 }

LcsSetupDhcpDhcpTableEntry ::= SEQUENCE {
            lcsSetupDhcpDhcpTableEntryIpAddress IpAddress,
            lcsSetupDhcpDhcpTableEntryMacAddress DisplayString,
            lcsSetupDhcpDhcpTableEntryTimeout Integer32,
            lcsSetupDhcpDhcpTableEntryHostname DisplayString,
            lcsSetupDhcpDhcpTableEntryType BITS,
            lcsSetupDhcpDhcpTableEntryEthernetPort INTEGER,
            lcsSetupDhcpDhcpTableEntryVlanId Integer32,
            lcsSetupDhcpDhcpTableEntryNetworkName DisplayString,
            lcsSetupDhcpDhcpTableEntryLanIfc INTEGER,
            lcsSetupDhcpDhcpTableEntryAssignment DisplayString,
            lcsSetupDhcpDhcpTableEntryAssignmentNumeric Gauge32
    }

-- {COLUMN} 1.3.6.1.4.1.2356.11.2.10.8.1.1
lcsSetupDhcpDhcpTableEntryIpAddress OBJECT-TYPE
    SYNTAX     IpAddress
    MAX-ACCESS read-only
    STATUS     current
    DESCRIPTION
            ""
    ::= { lcsSetupDhcpDhcpTableEntry 1 }

-- {COLUMN} 1.3.6.1.4.1.2356.11.2.10.8.1.2
lcsSetupDhcpDhcpTableEntryMacAddress OBJECT-TYPE
    SYNTAX     DisplayString (SIZE(0..12))
    MAX-ACCESS read-only
    STATUS     current
    DESCRIPTION
            ""
    ::= { lcsSetupDhcpDhcpTableEntry 2 }

-- {COLUMN} 1.3.6.1.4.1.2356.11.2.10.8.1.3
lcsSetupDhcpDhcpTableEntryTimeout OBJECT-TYPE
    SYNTAX     Integer32 (0..2147483647)
    MAX-ACCESS read-only
    STATUS     current
    DESCRIPTION
            ""
    ::= { lcsSetupDhcpDhcpTableEntry 3 }

-- {COLUMN} 1.3.6.1.4.1.2356.11.2.10.8.1.4
lcsSetupDhcpDhcpTableEntryHostname OBJECT-TYPE
    SYNTAX     DisplayString (SIZE(0..65))
    MAX-ACCESS read-only
    STATUS     current
    DESCRIPTION
            ""
    ::= { lcsSetupDhcpDhcpTableEntry 4 }

-- {COLUMN} 1.3.6.1.4.1.2356.11.2.10.8.1.5
lcsSetupDhcpDhcpTableEntryType OBJECT-TYPE
    SYNTAX     BITS {
                  eRelay (4),
                  eCache (8),
                  eBootp (10),
                  eDyn (11),
                  eStat (12),
                  eUnkn (13),
                  enewreq (14),
                  enew (15)
            }
    MAX-ACCESS read-only
    STATUS     current
    DESCRIPTION
            ""
    ::= { lcsSetupDhcpDhcpTableEntry 5 }

-- {COLUMN} 1.3.6.1.4.1.2356.11.2.10.8.1.7
lcsSetupDhcpDhcpTableEntryEthernetPort OBJECT-TYPE
    SYNTAX     INTEGER {
                  eUnknown (0),
                  eUplink (1),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            ""
    ::= { lcsSetupDhcpDhcpTableEntry 7 }

-- {COLUMN} 1.3.6.1.4.1.2356.11.2.10.8.1.8
lcsSetupDhcpDhcpTableEntryVlanId OBJECT-TYPE
    SYNTAX     Integer32 (0..65535)
    MAX-ACCESS read-only
    STATUS     current
    DESCRIPTION
            ""
    ::= { lcsSetupDhcpDhcpTableEntry 8 }

-- {COLUMN} 1.3.6.1.4.1.2356.11.2.10.8.1.9
lcsSetupDhcpDhcpTableEntryNetworkName OBJECT-TYPE
    SYNTAX     DisplayString (SIZE(0..17))
    MAX-ACCESS read-only
    STATUS     current
    DESCRIPTION
            ""
    ::= { lcsSetupDhcpDhcpTableEntry 9 }

-- {COLUMN} 1.3.6.1.4.1.2356.11.2.10.8.1.10
lcsSetupDhcpDhcpTableEntryLanIfc OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817),
                  eAny (65535)
            }
    MAX-ACCESS read-only
    STATUS     current
    DESCRIPTION
            ""
    ::= { lcsSetupDhcpDhcpTableEntry 10 }

-- {COLUMN} 1.3.6.1.4.1.2356.11.2.10.8.1.11
lcsSetupDhcpDhcpTableEntryAssignment OBJECT-TYPE
    SYNTAX     DisplayString (SIZE(0..21))
    MAX-ACCESS read-only
    STATUS     current
    DESCRIPTION
            "-- empty --"
    ::= { lcsSetupDhcpDhcpTableEntry 11 }

-- {COLUMN} 1.3.6.1.4.1.2356.11.2.10.8.1.12
lcsSetupDhcpDhcpTableEntryAssignmentNumeric OBJECT-TYPE
    SYNTAX     Gauge32
    MAX-ACCESS read-only
    STATUS     current
    DESCRIPTION
            "-- empty --"
    ::= { lcsSetupDhcpDhcpTableEntry 12 }

-- {TABLE} 1.3.6.1.4.1.2356.11.2.10.9
lcsSetupDhcpHostsTable OBJECT-TYPE
    SYNTAX     SEQUENCE OF LcsSetupDhcpHostsEntry
    MAX-ACCESS not-accessible
    STATUS     current
    DESCRIPTION
            ""
    ::= { lcsSetupDhcp 9 }

-- {ROW} 1.3.6.1.4.1.2356.11.2.10.9.1
lcsSetupDhcpHostsEntry OBJECT-TYPE
    SYNTAX     LcsSetupDhcpHostsEntry
    MAX-ACCESS not-accessible
    STATUS     current
    DESCRIPTION
            ""
    INDEX {
            lcsSetupDhcpHostsEntryMacAddress,
            lcsSetupDhcpHostsEntryNetworkName
          }
    ::= { lcsSetupDhcpHostsTable 1 }

LcsSetupDhcpHostsEntry ::= SEQUENCE {
            lcsSetupDhcpHostsEntryMacAddress DisplayString,
            lcsSetupDhcpHostsEntryIpAddress IpAddress,
            lcsSetupDhcpHostsEntryHostname DisplayString,
            lcsSetupDhcpHostsEntryImageAlias DisplayString,
            lcsSetupDhcpHostsEntryNetworkName DisplayString
    }

-- {COLUMN} 1.3.6.1.4.1.2356.11.2.10.9.1.1
lcsSetupDhcpHostsEntryMacAddress OBJECT-TYPE
    SYNTAX     DisplayString (SIZE(0..12))
    MAX-ACCESS read-write
    STATUS     current
    DESCRIPTION
            ""
    ::= { lcsSetupDhcpHostsEntry 1 }

-- {COLUMN} 1.3.6.1.4.1.2356.11.2.10.9.1.2
lcsSetupDhcpHostsEntryIpAddress OBJECT-TYPE
    SYNTAX     IpAddress
    MAX-ACCESS read-write
    STATUS     current
    DESCRIPTION
            ""
    ::= { lcsSetupDhcpHostsEntry 2 }

-- {COLUMN} 1.3.6.1.4.1.2356.11.2.10.9.1.3
lcsSetupDhcpHostsEntryHostname OBJECT-TYPE
    SYNTAX     DisplayString (SIZE(0..64))
    MAX-ACCESS read-write
    STATUS     current
    DESCRIPTION
            ""
    ::= { lcsSetupDhcpHostsEntry 3 }

-- {COLUMN} 1.3.6.1.4.1.2356.11.2.10.9.1.4
lcsSetupDhcpHostsEntryImageAlias OBJECT-TYPE
    SYNTAX     DisplayString (SIZE(0..16))
    MAX-ACCESS read-write
    STATUS     current
    DESCRIPTION
            ""
    ::= { lcsSetupDhcpHostsEntry 4 }

-- {COLUMN} 1.3.6.1.4.1.2356.11.2.10.9.1.5
lcsSetupDhcpHostsEntryNetworkName OBJECT-TYPE
    SYNTAX     DisplayString (SIZE(0..16))
    MAX-ACCESS read-write
    STATUS     current
    DESCRIPTION
            ""
    ::= { lcsSetupDhcpHostsEntry 5 }

-- {TABLE} 1.3.6.1.4.1.2356.11.2.10.10
lcsSetupDhcpAliasListTable OBJECT-TYPE
    SYNTAX     SEQUENCE OF LcsSetupDhcpAliasListEntry
    MAX-ACCESS not-accessible
    STATUS     current
    DESCRIPTION
            ""
    ::= { lcsSetupDhcp 10 }

-- {ROW} 1.3.6.1.4.1.2356.11.2.10.10.1
lcsSetupDhcpAliasListEntry OBJECT-TYPE
    SYNTAX     LcsSetupDhcpAliasListEntry
    MAX-ACCESS not-accessible
    STATUS     current
    DESCRIPTION
            ""
    INDEX {
            lcsSetupDhcpAliasListEntryImageAlias
          }
    ::= { lcsSetupDhcpAliasListTable 1 }

LcsSetupDhcpAliasListEntry ::= SEQUENCE {
            lcsSetupDhcpAliasListEntryImageAlias DisplayString,
            lcsSetupDhcpAliasListEntryImageFile DisplayString,
            lcsSetupDhcpAliasListEntryImageServer IpAddress
    }

-- {COLUMN} 1.3.6.1.4.1.2356.11.2.10.10.1.1
lcsSetupDhcpAliasListEntryImageAlias OBJECT-TYPE
    SYNTAX     DisplayString (SIZE(0..16))
    MAX-ACCESS read-write
    STATUS     current
    DESCRIPTION
            ""
    ::= { lcsSetupDhcpAliasListEntry 1 }

-- {COLUMN} 1.3.6.1.4.1.2356.11.2.10.10.1.2
lcsSetupDhcpAliasListEntryImageFile OBJECT-TYPE
    SYNTAX     DisplayString (SIZE(0..60))
    MAX-ACCESS read-write
    STATUS     current
    DESCRIPTION
            ""
    ::= { lcsSetupDhcpAliasListEntry 2 }

-- {COLUMN} 1.3.6.1.4.1.2356.11.2.10.10.1.3
lcsSetupDhcpAliasListEntryImageServer OBJECT-TYPE
    SYNTAX     IpAddress
    MAX-ACCESS read-write
    STATUS     current
    DESCRIPTION
            ""
    ::= { lcsSetupDhcpAliasListEntry 3 }

-- {TABLE} 1.3.6.1.4.1.2356.11.2.10.18
lcsSetupDhcpPortsTable OBJECT-TYPE
    SYNTAX     SEQUENCE OF LcsSetupDhcpPortsEntry
    MAX-ACCESS not-accessible
    STATUS     current
    DESCRIPTION
            ""
    ::= { lcsSetupDhcp 18 }

-- {ROW} 1.3.6.1.4.1.2356.11.2.10.18.1
lcsSetupDhcpPortsEntry OBJECT-TYPE
    SYNTAX     LcsSetupDhcpPortsEntry
    MAX-ACCESS not-accessible
    STATUS     current
    DESCRIPTION
            ""
    INDEX {
            lcsSetupDhcpPortsEntryPort
          }
    ::= { lcsSetupDhcpPortsTable 1 }

LcsSetupDhcpPortsEntry ::= SEQUENCE {
            lcsSetupDhcpPortsEntryPort DisplayString,
            lcsSetupDhcpPortsEntryEnableDhcp INTEGER
    }

-- {COLUMN} 1.3.6.1.4.1.2356.11.2.10.18.1.2
lcsSetupDhcpPortsEntryPort OBJECT-TYPE
    SYNTAX     DisplayString (SIZE(0..18))
    MAX-ACCESS read-only
    STATUS     current
    DESCRIPTION
            ""
    ::= { lcsSetupDhcpPortsEntry 2 }

-- {COLUMN} 1.3.6.1.4.1.2356.11.2.10.18.1.3
lcsSetupDhcpPortsEntryEnableDhcp OBJECT-TYPE
    SYNTAX     INTEGER {
                  eNo (0),
                  eYes (1)
            }
    MAX-ACCESS read-write
    STATUS     current
    DESCRIPTION
            ""
    ::= { lcsSetupDhcpPortsEntry 3 }

-- {SCALAR} 1.3.6.1.4.1.2356.11.2.10.19
lcsSetupDhcpUserClassIdentifer OBJECT-TYPE
    SYNTAX     DisplayString (SIZE(0..63))
    MAX-ACCESS read-write
    STATUS     current
    DESCRIPTION
            ""
    ::= { lcsSetupDhcp 19 }

-- {TABLE} 1.3.6.1.4.1.2356.11.2.10.20
lcsSetupDhcpNetworkListTable OBJECT-TYPE
    SYNTAX     SEQUENCE OF LcsSetupDhcpNetworkListEntry
    MAX-ACCESS not-accessible
    STATUS     current
    DESCRIPTION
            ""
    ::= { lcsSetupDhcp 20 }

-- {ROW} 1.3.6.1.4.1.2356.11.2.10.20.1
lcsSetupDhcpNetworkListEntry OBJECT-TYPE
    SYNTAX     LcsSetupDhcpNetworkListEntry
    MAX-ACCESS not-accessible
    STATUS     current
    DESCRIPTION
            ""
    INDEX {
            lcsSetupDhcpNetworkListEntryNetworkName
          }
    ::= { lcsSetupDhcpNetworkListTable 1 }

LcsSetupDhcpNetworkListEntry ::= SEQUENCE {
            lcsSetupDhcpNetworkListEntryNetworkName DisplayString,
            lcsSetupDhcpNetworkListEntryStartAddressPool IpAddress,
            lcsSetupDhcpNetworkListEntryEndAddressPool IpAddress,
            lcsSetupDhcpNetworkListEntryNetmask IpAddress,
            lcsSetupDhcpNetworkListEntryBroadcastAddress IpAddress,
            lcsSetupDhcpNetworkListEntryGatewayAddress IpAddress,
            lcsSetupDhcpNetworkListEntryDnsDefault IpAddress,
            lcsSetupDhcpNetworkListEntryDnsBackup IpAddress,
            lcsSetupDhcpNetworkListEntryNbnsDefault IpAddress,
            lcsSetupDhcpNetworkListEntryNbnsBackup IpAddress,
            lcsSetupDhcpNetworkListEntryOperating INTEGER,
            lcsSetupDhcpNetworkListEntryBroadcastBit INTEGER,
            lcsSetupDhcpNetworkListEntryMasterServer IpAddress,
            lcsSetupDhcpNetworkListEntryCache INTEGER,
            lcsSetupDhcpNetworkListEntryAdaption INTEGER,
            lcsSetupDhcpNetworkListEntryCluster INTEGER,
            lcsSetupDhcpNetworkListEntry2ndMasterServer IpAddress,
            lcsSetupDhcpNetworkListEntry3rdMasterServer IpAddress,
            lcsSetupDhcpNetworkListEntry4thMasterServer IpAddress,
            lcsSetupDhcpNetworkListEntryMaxLease Integer32,
            lcsSetupDhcpNetworkListEntryDefLease Integer32,
            lcsSetupDhcpNetworkListEntryLoopbackAddress DisplayString,
            lcsSetupDhcpNetworkListEntrySuppressArpCheck INTEGER
    }

-- {COLUMN} 1.3.6.1.4.1.2356.11.2.10.20.1.1
lcsSetupDhcpNetworkListEntryNetworkName OBJECT-TYPE
    SYNTAX     DisplayString (SIZE(0..16))
    MAX-ACCESS read-write
    STATUS     current
    DESCRIPTION
            ""
    ::= { lcsSetupDhcpNetworkListEntry 1 }

-- {COLUMN} 1.3.6.1.4.1.2356.11.2.10.20.1.2
lcsSetupDhcpNetworkListEntryStartAddressPool OBJECT-TYPE
    SYNTAX     IpAddress
    MAX-ACCESS read-write
    STATUS     current
    DESCRIPTION
            ""
    ::= { lcsSetupDhcpNetworkListEntry 2 }

-- {COLUMN} 1.3.6.1.4.1.2356.11.2.10.20.1.3
lcsSetupDhcpNetworkListEntryEndAddressPool OBJECT-TYPE
    SYNTAX     IpAddress
    MAX-ACCESS read-write
    STATUS     current
    DESCRIPTION
            ""
    ::= { lcsSetupDhcpNetworkListEntry 3 }

-- {COLUMN} 1.3.6.1.4.1.2356.11.2.10.20.1.4
lcsSetupDhcpNetworkListEntryNetmask OBJECT-TYPE
    SYNTAX     IpAddress
    MAX-ACCESS read-write
    STATUS     current
    DESCRIPTION
            ""
    ::= { lcsSetupDhcpNetworkListEntry 4 }

-- {COLUMN} 1.3.6.1.4.1.2356.11.2.10.20.1.5
lcsSetupDhcpNetworkListEntryBroadcastAddress OBJECT-TYPE
    SYNTAX     IpAddress
    MAX-ACCESS read-write
    STATUS     current
    DESCRIPTION
            ""
    ::= { lcsSetupDhcpNetworkListEntry 5 }

-- {COLUMN} 1.3.6.1.4.1.2356.11.2.10.20.1.6
lcsSetupDhcpNetworkListEntryGatewayAddress OBJECT-TYPE
    SYNTAX     IpAddress
    MAX-ACCESS read-write
    STATUS     current
    DESCRIPTION
            ""
    ::= { lcsSetupDhcpNetworkListEntry 6 }

-- {COLUMN} 1.3.6.1.4.1.2356.11.2.10.20.1.7
lcsSetupDhcpNetworkListEntryDnsDefault OBJECT-TYPE
    SYNTAX     IpAddress
    MAX-ACCESS read-write
    STATUS     current
    DESCRIPTION
            ""
    ::= { lcsSetupDhcpNetworkListEntry 7 }

-- {COLUMN} 1.3.6.1.4.1.2356.11.2.10.20.1.8
lcsSetupDhcpNetworkListEntryDnsBackup OBJECT-TYPE
    SYNTAX     IpAddress
    MAX-ACCESS read-write
    STATUS     current
    DESCRIPTION
            ""
    ::= { lcsSetupDhcpNetworkListEntry 8 }

-- {COLUMN} 1.3.6.1.4.1.2356.11.2.10.20.1.9
lcsSetupDhcpNetworkListEntryNbnsDefault OBJECT-TYPE
    SYNTAX     IpAddress
    MAX-ACCESS read-write
    STATUS     current
    DESCRIPTION
            ""
    ::= { lcsSetupDhcpNetworkListEntry 9 }

-- {COLUMN} 1.3.6.1.4.1.2356.11.2.10.20.1.10
lcsSetupDhcpNetworkListEntryNbnsBackup OBJECT-TYPE
    SYNTAX     IpAddress
    MAX-ACCESS read-write
    STATUS     current
    DESCRIPTION
            ""
    ::= { lcsSetupDhcpNetworkListEntry 10 }

-- {COLUMN} 1.3.6.1.4.1.2356.11.2.10.20.1.11
lcsSetupDhcpNetworkListEntryOperating OBJECT-TYPE
    SYNTAX     INTEGER {
                  eNo (0),
                  eYes (1),
                  eAuto (2),
                  eClient (4),
                  eRelay (16)
            }
    MAX-ACCESS read-write
    STATUS     current
    DESCRIPTION
            ""
    ::= { lcsSetupDhcpNetworkListEntry 11 }

-- {COLUMN} 1.3.6.1.4.1.2356.11.2.10.20.1.12
lcsSetupDhcpNetworkListEntryBroadcastBit OBJECT-TYPE
    SYNTAX     INTEGER {
                  eNo (0),
                  eYes (1)
            }
    MAX-ACCESS read-write
    STATUS     current
    DESCRIPTION
            ""
    ::= { lcsSetupDhcpNetworkListEntry 12 }

-- {COLUMN} 1.3.6.1.4.1.2356.11.2.10.20.1.13
lcsSetupDhcpNetworkListEntryMasterServer OBJECT-TYPE
    SYNTAX     IpAddress
    MAX-ACCESS read-write
    STATUS     current
    DESCRIPTION
            ""
    ::= { lcsSetupDhcpNetworkListEntry 13 }

-- {COLUMN} 1.3.6.1.4.1.2356.11.2.10.20.1.14
lcsSetupDhcpNetworkListEntryCache OBJECT-TYPE
    SYNTAX     INTEGER {
                  eNo (0),
                  eYes (1)
            }
    MAX-ACCESS read-write
    STATUS     current
    DESCRIPTION
            ""
    ::= { lcsSetupDhcpNetworkListEntry 14 }

-- {COLUMN} 1.3.6.1.4.1.2356.11.2.10.20.1.15
lcsSetupDhcpNetworkListEntryAdaption OBJECT-TYPE
    SYNTAX     INTEGER {
                  eNo (0),
                  eYes (1)
            }
    MAX-ACCESS read-write
    STATUS     current
    DESCRIPTION
            ""
    ::= { lcsSetupDhcpNetworkListEntry 15 }

-- {COLUMN} 1.3.6.1.4.1.2356.11.2.10.20.1.16
lcsSetupDhcpNetworkListEntryCluster OBJECT-TYPE
    SYNTAX     INTEGER {
                  eNo (0),
                  eYes (1)
            }
    MAX-ACCESS read-write
    STATUS     current
    DESCRIPTION
            ""
    ::= { lcsSetupDhcpNetworkListEntry 16 }

-- {COLUMN} 1.3.6.1.4.1.2356.11.2.10.20.1.17
lcsSetupDhcpNetworkListEntry2ndMasterServer OBJECT-TYPE
    SYNTAX     IpAddress
    MAX-ACCESS read-write
    STATUS     current
    DESCRIPTION
            ""
    ::= { lcsSetupDhcpNetworkListEntry 17 }

-- {COLUMN} 1.3.6.1.4.1.2356.11.2.10.20.1.18
lcsSetupDhcpNetworkListEntry3rdMasterServer OBJECT-TYPE
    SYNTAX     IpAddress
    MAX-ACCESS read-write
    STATUS     current
    DESCRIPTION
            ""
    ::= { lcsSetupDhcpNetworkListEntry 18 }

-- {COLUMN} 1.3.6.1.4.1.2356.11.2.10.20.1.19
lcsSetupDhcpNetworkListEntry4thMasterServer OBJECT-TYPE
    SYNTAX     IpAddress
    MAX-ACCESS read-write
    STATUS     current
    DESCRIPTION
            ""
    ::= { lcsSetupDhcpNetworkListEntry 19 }

-- {COLUMN} 1.3.6.1.4.1.2356.11.2.10.20.1.20
lcsSetupDhcpNetworkListEntryMaxLease OBJECT-TYPE
    SYNTAX     Integer32 (0..2147483647)
    MAX-ACCESS read-write
    STATUS     current
    DESCRIPTION
            "-- empty --"
    ::= { lcsSetupDhcpNetworkListEntry 20 }

-- {COLUMN} 1.3.6.1.4.1.2356.11.2.10.20.1.21
lcsSetupDhcpNetworkListEntryDefLease OBJECT-TYPE
    SYNTAX     Integer32 (0..2147483647)
    MAX-ACCESS read-write
    STATUS     current
    DESCRIPTION
            "-- empty --"
    ::= { lcsSetupDhcpNetworkListEntry 21 }

-- {COLUMN} 1.3.6.1.4.1.2356.11.2.10.20.1.22
lcsSetupDhcpNetworkListEntryLoopbackAddress OBJECT-TYPE
    SYNTAX     DisplayString (SIZE(0..16))
    MAX-ACCESS read-write
    STATUS     current
    DESCRIPTION
            "-- empty --"
    ::= { lcsSetupDhcpNetworkListEntry 22 }

-- {COLUMN} 1.3.6.1.4.1.2356.11.2.10.20.1.23
lcsSetupDhcpNetworkListEntrySuppressArpCheck OBJECT-TYPE
    SYNTAX     INTEGER {
                  eNo (0),
                  eYes (1)
            }
    MAX-ACCESS read-write
    STATUS     current
    DESCRIPTION
            "-- empty --"
    ::= { lcsSetupDhcpNetworkListEntry 23 }

-- {TABLE} 1.3.6.1.4.1.2356.11.2.10.21
lcsSetupDhcpAdditionalOptionsTable OBJECT-TYPE
    SYNTAX     SEQUENCE OF LcsSetupDhcpAdditionalOptionsEntry
    MAX-ACCESS not-accessible
    STATUS     current
    DESCRIPTION
            ""
    ::= { lcsSetupDhcp 21 }

-- {ROW} 1.3.6.1.4.1.2356.11.2.10.21.1
lcsSetupDhcpAdditionalOptionsEntry OBJECT-TYPE
    SYNTAX     LcsSetupDhcpAdditionalOptionsEntry
    MAX-ACCESS not-accessible
    STATUS     current
    DESCRIPTION
            ""
    INDEX {
            lcsSetupDhcpAdditionalOptionsEntryOptionNumber,
            lcsSetupDhcpAdditionalOptionsEntryNetworkName
          }
    ::= { lcsSetupDhcpAdditionalOptionsTable 1 }

LcsSetupDhcpAdditionalOptionsEntry ::= SEQUENCE {
            lcsSetupDhcpAdditionalOptionsEntryOptionNumber Integer32,
            lcsSetupDhcpAdditionalOptionsEntryNetworkName DisplayString,
            lcsSetupDhcpAdditionalOptionsEntryOptionValue DisplayString,
            lcsSetupDhcpAdditionalOptionsEntryOptionType INTEGER
    }

-- {COLUMN} 1.3.6.1.4.1.2356.11.2.10.21.1.1
lcsSetupDhcpAdditionalOptionsEntryOptionNumber OBJECT-TYPE
    SYNTAX     Integer32 (0..255)
    MAX-ACCESS read-write
    STATUS     current
    DESCRIPTION
            ""
    ::= { lcsSetupDhcpAdditionalOptionsEntry 1 }

-- {COLUMN} 1.3.6.1.4.1.2356.11.2.10.21.1.2
lcsSetupDhcpAdditionalOptionsEntryNetworkName OBJECT-TYPE
    SYNTAX     DisplayString (SIZE(0..16))
    MAX-ACCESS read-write
    STATUS     current
    DESCRIPTION
            ""
    ::= { lcsSetupDhcpAdditionalOptionsEntry 2 }

-- {COLUMN} 1.3.6.1.4.1.2356.11.2.10.21.1.3
lcsSetupDhcpAdditionalOptionsEntryOptionValue OBJECT-TYPE
    SYNTAX     DisplayString (SIZE(0..251))
    MAX-ACCESS read-write
    STATUS     current
    DESCRIPTION
            ""
    ::= { lcsSetupDhcpAdditionalOptionsEntry 3 }

-- {COLUMN} 1.3.6.1.4.1.2356.11.2.10.21.1.4
lcsSetupDhcpAdditionalOptionsEntryOptionType OBJECT-TYPE
    SYNTAX     INTEGER {
                  eString (0),
                  eInteger32 (1),
                  eIpAddress (2),
                  eInteger16 (3),
                  eInteger8 (4)
            }
    MAX-ACCESS read-write
    STATUS     current
    DESCRIPTION
            ""
    ::= { lcsSetupDhcpAdditionalOptionsEntry 4 }

-- {SCALAR} 1.3.6.1.4.1.2356.11.2.10.22
lcsSetupDhcpVendorClassIdentifer OBJECT-TYPE
    SYNTAX     DisplayString (SIZE(0..63))
    MAX-ACCESS read-write
    STATUS     current
    DESCRIPTION
            "-- empty --"
    ::= { lcsSetupDhcp 22 }

-- {NODE} 1.3.6.1.4.1.2356.11.2.10.23
lcsSetupDhcpRadiusAccounting OBJECT IDENTIFIER ::= { lcsSetupDhcp 23 }

-- {SCALAR} 1.3.6.1.4.1.2356.11.2.10.23.1
lcsSetupDhcpRadiusAccountingOperating OBJECT-TYPE
    SYNTAX     INTEGER {
                  eNo (0),
                  eYes (1)
            }
    MAX-ACCESS read-write
    STATUS     current
    DESCRIPTION
            "-- empty --"
    ::= { lcsSetupDhcpRadiusAccounting 1 }

-- {SCALAR} 1.3.6.1.4.1.2356.11.2.10.23.2
lcsSetupDhcpRadiusAccountingInterimInterval OBJECT-TYPE
    SYNTAX     Integer32 (0..2147483647)
    MAX-ACCESS read-write
    STATUS     current
    DESCRIPTION
            "-- empty --"
    ::= { lcsSetupDhcpRadiusAccounting 2 }

-- {TABLE} 1.3.6.1.4.1.2356.11.2.10.23.20
lcsSetupDhcpRadiusAccountingNetworkListTable OBJECT-TYPE
    SYNTAX     SEQUENCE OF LcsSetupDhcpRadiusAccountingNetworkListEntry
    MAX-ACCESS not-accessible
    STATUS     current
    DESCRIPTION
            "-- empty --"
    ::= { lcsSetupDhcpRadiusAccounting 20 }

-- {ROW} 1.3.6.1.4.1.2356.11.2.10.23.20.1
lcsSetupDhcpRadiusAccountingNetworkListEntry OBJECT-TYPE
    SYNTAX     LcsSetupDhcpRadiusAccountingNetworkListEntry
    MAX-ACCESS not-accessible
    STATUS     current
    DESCRIPTION
            ""
    INDEX {
            lcsSetupDhcpRadiusAccountingNetworkListEntryNetworkName
          }
    ::= { lcsSetupDhcpRadiusAccountingNetworkListTable 1 }

LcsSetupDhcpRadiusAccountingNetworkListEntry ::= SEQUENCE {
            lcsSetupDhcpRadiusAccountingNetworkListEntryNetworkName DisplayString,
            lcsSetupDhcpRadiusAccountingNetworkListEntryServerHostname DisplayString,
            lcsSetupDhcpRadiusAccountingNetworkListEntryAccntPort Integer32,
            lcsSetupDhcpRadiusAccountingNetworkListEntrySecret DisplayString,
            lcsSetupDhcpRadiusAccountingNetworkListEntryLoopbackAddress DisplayString,
            lcsSetupDhcpRadiusAccountingNetworkListEntryProtocol INTEGER,
            lcsSetupDhcpRadiusAccountingNetworkListEntryAttributeValues DisplayString,
            lcsSetupDhcpRadiusAccountingNetworkListEntryBackupServerHostname DisplayString,
            lcsSetupDhcpRadiusAccountingNetworkListEntryBackupAccntPort Integer32,
            lcsSetupDhcpRadiusAccountingNetworkListEntryBackupSecret DisplayString,
            lcsSetupDhcpRadiusAccountingNetworkListEntryBackupLoopbackAddr DisplayString,
            lcsSetupDhcpRadiusAccountingNetworkListEntryBackupProtocol INTEGER,
            lcsSetupDhcpRadiusAccountingNetworkListEntryBackupAttributeVals DisplayString
    }

-- {COLUMN} 1.3.6.1.4.1.2356.11.2.10.23.20.1.1
lcsSetupDhcpRadiusAccountingNetworkListEntryNetworkName OBJECT-TYPE
    SYNTAX     DisplayString (SIZE(0..16))
    MAX-ACCESS read-write
    STATUS     current
    DESCRIPTION
            "-- empty --"
    ::= { lcsSetupDhcpRadiusAccountingNetworkListEntry 1 }

-- {COLUMN} 1.3.6.1.4.1.2356.11.2.10.23.20.1.2
lcsSetupDhcpRadiusAccountingNetworkListEntryServerHostname OBJECT-TYPE
    SYNTAX     DisplayString (SIZE(0..64))
    MAX-ACCESS read-write
    STATUS     current
    DESCRIPTION
            "-- empty --"
    ::= { lcsSetupDhcpRadiusAccountingNetworkListEntry 2 }

-- {COLUMN} 1.3.6.1.4.1.2356.11.2.10.23.20.1.3
lcsSetupDhcpRadiusAccountingNetworkListEntryAccntPort OBJECT-TYPE
    SYNTAX     Integer32 (0..65535)
    MAX-ACCESS read-write
    STATUS     current
    DESCRIPTION
            "-- empty --"
    ::= { lcsSetupDhcpRadiusAccountingNetworkListEntry 3 }

-- {COLUMN} 1.3.6.1.4.1.2356.11.2.10.23.20.1.4
lcsSetupDhcpRadiusAccountingNetworkListEntrySecret OBJECT-TYPE
    SYNTAX     DisplayString (SIZE(0..64))
    MAX-ACCESS read-write
    STATUS     current
    DESCRIPTION
            "-- empty --"
    ::= { lcsSetupDhcpRadiusAccountingNetworkListEntry 4 }

-- {COLUMN} 1.3.6.1.4.1.2356.11.2.10.23.20.1.5
lcsSetupDhcpRadiusAccountingNetworkListEntryLoopbackAddress OBJECT-TYPE
    SYNTAX     DisplayString (SIZE(0..16))
    MAX-ACCESS read-write
    STATUS     current
    DESCRIPTION
            "-- empty --"
    ::= { lcsSetupDhcpRadiusAccountingNetworkListEntry 5 }

-- {COLUMN} 1.3.6.1.4.1.2356.11.2.10.23.20.1.6
lcsSetupDhcpRadiusAccountingNetworkListEntryProtocol OBJECT-TYPE
    SYNTAX     INTEGER {
                  eRadius (0),
                  eRadsec (1)
            }
    MAX-ACCESS read-write
    STATUS     current
    DESCRIPTION
            "-- empty --"
    ::= { lcsSetupDhcpRadiusAccountingNetworkListEntry 6 }

-- {COLUMN} 1.3.6.1.4.1.2356.11.2.10.23.20.1.7
lcsSetupDhcpRadiusAccountingNetworkListEntryAttributeValues OBJECT-TYPE
    SYNTAX     DisplayString (SIZE(0..251))
    MAX-ACCESS read-write
    STATUS     current
    DESCRIPTION
            "-- empty --"
    ::= { lcsSetupDhcpRadiusAccountingNetworkListEntry 7 }

-- {COLUMN} 1.3.6.1.4.1.2356.11.2.10.23.20.1.12
lcsSetupDhcpRadiusAccountingNetworkListEntryBackupServerHostname OBJECT-TYPE
    SYNTAX     DisplayString (SIZE(0..64))
    MAX-ACCESS read-write
    STATUS     current
    DESCRIPTION
            "-- empty --"
    ::= { lcsSetupDhcpRadiusAccountingNetworkListEntry 12 }

-- {COLUMN} 1.3.6.1.4.1.2356.11.2.10.23.20.1.13
lcsSetupDhcpRadiusAccountingNetworkListEntryBackupAccntPort OBJECT-TYPE
    SYNTAX     Integer32 (0..65535)
    MAX-ACCESS read-write
    STATUS     current
    DESCRIPTION
            "-- empty --"
    ::= { lcsSetupDhcpRadiusAccountingNetworkListEntry 13 }

-- {COLUMN} 1.3.6.1.4.1.2356.11.2.10.23.20.1.14
lcsSetupDhcpRadiusAccountingNetworkListEntryBackupSecret OBJECT-TYPE
    SYNTAX     DisplayString (SIZE(0..64))
    MAX-ACCESS read-write
    STATUS     current
    DESCRIPTION
            "-- empty --"
    ::= { lcsSetupDhcpRadiusAccountingNetworkListEntry 14 }

-- {COLUMN} 1.3.6.1.4.1.2356.11.2.10.23.20.1.15
lcsSetupDhcpRadiusAccountingNetworkListEntryBackupLoopbackAddr OBJECT-TYPE
    SYNTAX     DisplayString (SIZE(0..16))
    MAX-ACCESS read-write
    STATUS     current
    DESCRIPTION
            "loopback address for backup server"
    ::= { lcsSetupDhcpRadiusAccountingNetworkListEntry 15 }

-- {COLUMN} 1.3.6.1.4.1.2356.11.2.10.23.20.1.16
lcsSetupDhcpRadiusAccountingNetworkListEntryBackupProtocol OBJECT-TYPE
    SYNTAX     INTEGER {
                  eRadius (0),
                  eRadsec (1)
            }
    MAX-ACCESS read-write
    STATUS     current
    DESCRIPTION
            "-- empty --"
    ::= { lcsSetupDhcpRadiusAccountingNetworkListEntry 16 }

-- {COLUMN} 1.3.6.1.4.1.2356.11.2.10.23.20.1.17
lcsSetupDhcpRadiusAccountingNetworkListEntryBackupAttributeVals OBJECT-TYPE
    SYNTAX     DisplayString (SIZE(0..251))
    MAX-ACCESS read-write
    STATUS     current
    DESCRIPTION
            "attribute value overrides for backup server"
    ::= { lcsSetupDhcpRadiusAccountingNetworkListEntry 17 }

-- {TABLE} 1.3.6.1.4.1.2356.11.2.10.25
lcsSetupDhcpLmcOptionsTable OBJECT-TYPE
    SYNTAX     SEQUENCE OF LcsSetupDhcpLmcOptionsEntry
    MAX-ACCESS not-accessible
    STATUS     current
    DESCRIPTION
            "-- empty --"
    ::= { lcsSetupDhcp 25 }

-- {ROW} 1.3.6.1.4.1.2356.11.2.10.25.1
lcsSetupDhcpLmcOptionsEntry OBJECT-TYPE
    SYNTAX     LcsSetupDhcpLmcOptionsEntry
    MAX-ACCESS not-accessible
    STATUS     current
    DESCRIPTION
            ""
    INDEX {
            lcsSetupDhcpLmcOptionsEntryNetworkName
          }
    ::= { lcsSetupDhcpLmcOptionsTable 1 }

LcsSetupDhcpLmcOptionsEntry ::= SEQUENCE {
            lcsSetupDhcpLmcOptionsEntryNetworkName DisplayString,
            lcsSetupDhcpLmcOptionsEntryLmcDomain DisplayString,
            lcsSetupDhcpLmcOptionsEntryRolloutProjectId DisplayString,
            lcsSetupDhcpLmcOptionsEntryRolloutLocationId DisplayString
    }

-- {COLUMN} 1.3.6.1.4.1.2356.11.2.10.25.1.1
lcsSetupDhcpLmcOptionsEntryNetworkName OBJECT-TYPE
    SYNTAX     DisplayString (SIZE(0..16))
    MAX-ACCESS read-write
    STATUS     current
    DESCRIPTION
            "-- empty --"
    ::= { lcsSetupDhcpLmcOptionsEntry 1 }

-- {COLUMN} 1.3.6.1.4.1.2356.11.2.10.25.1.6
lcsSetupDhcpLmcOptionsEntryLmcDomain OBJECT-TYPE
    SYNTAX     DisplayString (SIZE(0..64))
    MAX-ACCESS read-write
    STATUS     current
    DESCRIPTION
            "-- empty --"
    ::= { lcsSetupDhcpLmcOptionsEntry 6 }

-- {COLUMN} 1.3.6.1.4.1.2356.11.2.10.25.1.7
lcsSetupDhcpLmcOptionsEntryRolloutProjectId OBJECT-TYPE
    SYNTAX     DisplayString (SIZE(0..36))
    MAX-ACCESS read-write
    STATUS     current
    DESCRIPTION
            "-- empty --"
    ::= { lcsSetupDhcpLmcOptionsEntry 7 }

-- {COLUMN} 1.3.6.1.4.1.2356.11.2.10.25.1.8
lcsSetupDhcpLmcOptionsEntryRolloutLocationId OBJECT-TYPE
    SYNTAX     DisplayString (SIZE(0..36))
    MAX-ACCESS read-write
    STATUS     current
    DESCRIPTION
            "-- empty --"
    ::= { lcsSetupDhcpLmcOptionsEntry 8 }

-- {TABLE} 1.3.6.1.4.1.2356.11.2.10.26
lcsSetupDhcpNew-Additional-OptionsTable OBJECT-TYPE
    SYNTAX     SEQUENCE OF LcsSetupDhcpNew-Additional-OptionsEntry
    MAX-ACCESS not-accessible
    STATUS     current
    DESCRIPTION
            ""
    ::= { lcsSetupDhcp 26 }

-- {ROW} 1.3.6.1.4.1.2356.11.2.10.26.1
lcsSetupDhcpNew-Additional-OptionsEntry OBJECT-TYPE
    SYNTAX     LcsSetupDhcpNew-Additional-OptionsEntry
    MAX-ACCESS not-accessible
    STATUS     current
    DESCRIPTION
            ""
    INDEX {
            lcsSetupDhcpNew-Additional-OptionsEntryOptionNumber,
            lcsSetupDhcpNew-Additional-OptionsEntrySubOptionNumber,
            lcsSetupDhcpNew-Additional-OptionsEntryVendorClassMask,
            lcsSetupDhcpNew-Additional-OptionsEntryUserClassMask,
            lcsSetupDhcpNew-Additional-OptionsEntryNetworkName
          }
    ::= { lcsSetupDhcpNew-Additional-OptionsTable 1 }

LcsSetupDhcpNew-Additional-OptionsEntry ::= SEQUENCE {
            lcsSetupDhcpNew-Additional-OptionsEntryOptionNumber Integer32,
            lcsSetupDhcpNew-Additional-OptionsEntryNetworkName DisplayString,
            lcsSetupDhcpNew-Additional-OptionsEntryOptionValue DisplayString,
            lcsSetupDhcpNew-Additional-OptionsEntryOptionType INTEGER,
            lcsSetupDhcpNew-Additional-OptionsEntrySubOptionNumber Integer32,
            lcsSetupDhcpNew-Additional-OptionsEntryVendorClassMask DisplayString,
            lcsSetupDhcpNew-Additional-OptionsEntryUserClassMask DisplayString
    }

-- {COLUMN} 1.3.6.1.4.1.2356.11.2.10.26.1.1
lcsSetupDhcpNew-Additional-OptionsEntryOptionNumber OBJECT-TYPE
    SYNTAX     Integer32 (0..255)
    MAX-ACCESS read-write
    STATUS     current
    DESCRIPTION
            "-- empty --"
    ::= { lcsSetupDhcpNew-Additional-OptionsEntry 1 }

-- {COLUMN} 1.3.6.1.4.1.2356.11.2.10.26.1.2
lcsSetupDhcpNew-Additional-OptionsEntryNetworkName OBJECT-TYPE
    SYNTAX     DisplayString (SIZE(0..16))
    MAX-ACCESS read-write
    STATUS     current
    DESCRIPTION
            "-- empty --"
    ::= { lcsSetupDhcpNew-Additional-OptionsEntry 2 }

-- {COLUMN} 1.3.6.1.4.1.2356.11.2.10.26.1.3
lcsSetupDhcpNew-Additional-OptionsEntryOptionValue OBJECT-TYPE
    SYNTAX     DisplayString (SIZE(0..251))
    MAX-ACCESS read-write
    STATUS     current
    DESCRIPTION
            "-- empty --"
    ::= { lcsSetupDhcpNew-Additional-OptionsEntry 3 }

-- {COLUMN} 1.3.6.1.4.1.2356.11.2.10.26.1.4
lcsSetupDhcpNew-Additional-OptionsEntryOptionType OBJECT-TYPE
    SYNTAX     INTEGER {
                  eString (0),
                  eInteger32 (1),
                  eIpAddress (2),
                  eInteger16 (3),
                  eInteger8 (4)
            }
    MAX-ACCESS read-write
    STATUS     current
    DESCRIPTION
            "-- empty --"
    ::= { lcsSetupDhcpNew-Additional-OptionsEntry 4 }

-- {COLUMN} 1.3.6.1.4.1.2356.11.2.10.26.1.5
lcsSetupDhcpNew-Additional-OptionsEntrySubOptionNumber OBJECT-TYPE
    SYNTAX     Integer32 (0..255)
    MAX-ACCESS read-write
    STATUS     current
    DESCRIPTION
            "-- empty --"
    ::= { lcsSetupDhcpNew-Additional-OptionsEntry 5 }

-- {COLUMN} 1.3.6.1.4.1.2356.11.2.10.26.1.6
lcsSetupDhcpNew-Additional-OptionsEntryVendorClassMask OBJECT-TYPE
    SYNTAX     DisplayString (SIZE(0..32))
    MAX-ACCESS read-write
    STATUS     current
    DESCRIPTION
            "-- empty --"
    ::= { lcsSetupDhcpNew-Additional-OptionsEntry 6 }

-- {COLUMN} 1.3.6.1.4.1.2356.11.2.10.26.1.7
lcsSetupDhcpNew-Additional-OptionsEntryUserClassMask OBJECT-TYPE
    SYNTAX     DisplayString (SIZE(0..32))
    MAX-ACCESS read-write
    STATUS     current
    DESCRIPTION
            "-- empty --"
    ::= { lcsSetupDhcpNew-Additional-OptionsEntry 7 }

-- {TABLE} 1.3.6.1.4.1.2356.11.2.10.27
lcsSetupDhcpRelayInfoListTable OBJECT-TYPE
    SYNTAX     SEQUENCE OF LcsSetupDhcpRelayInfoListEntry
    MAX-ACCESS not-accessible
    STATUS     current
    DESCRIPTION
            "-- empty --"
    ::= { lcsSetupDhcp 27 }

-- {ROW} 1.3.6.1.4.1.2356.11.2.10.27.1
lcsSetupDhcpRelayInfoListEntry OBJECT-TYPE
    SYNTAX     LcsSetupDhcpRelayInfoListEntry
    MAX-ACCESS not-accessible
    STATUS     current
    DESCRIPTION
            ""
    INDEX {
            lcsSetupDhcpRelayInfoListEntryCircuitId
          }
    ::= { lcsSetupDhcpRelayInfoListTable 1 }

LcsSetupDhcpRelayInfoListEntry ::= SEQUENCE {
            lcsSetupDhcpRelayInfoListEntryCircuitId DisplayString,
            lcsSetupDhcpRelayInfoListEntryIpAddress IpAddress,
            lcsSetupDhcpRelayInfoListEntryHostname DisplayString,
            lcsSetupDhcpRelayInfoListEntryImageAlias DisplayString
    }

-- {COLUMN} 1.3.6.1.4.1.2356.11.2.10.27.1.1
lcsSetupDhcpRelayInfoListEntryCircuitId OBJECT-TYPE
    SYNTAX     DisplayString (SIZE(0..64))
    MAX-ACCESS read-write
    STATUS     current
    DESCRIPTION
            "-- empty --"
    ::= { lcsSetupDhcpRelayInfoListEntry 1 }

-- {COLUMN} 1.3.6.1.4.1.2356.11.2.10.27.1.2
lcsSetupDhcpRelayInfoListEntryIpAddress OBJECT-TYPE
    SYNTAX     IpAddress
    MAX-ACCESS read-write
    STATUS     current
    DESCRIPTION
            "-- empty --"
    ::= { lcsSetupDhcpRelayInfoListEntry 2 }

-- {COLUMN} 1.3.6.1.4.1.2356.11.2.10.27.1.3
lcsSetupDhcpRelayInfoListEntryHostname OBJECT-TYPE
    SYNTAX     DisplayString (SIZE(0..64))
    MAX-ACCESS read-write
    STATUS     current
    DESCRIPTION
            "-- empty --"
    ::= { lcsSetupDhcpRelayInfoListEntry 3 }

-- {COLUMN} 1.3.6.1.4.1.2356.11.2.10.27.1.4
lcsSetupDhcpRelayInfoListEntryImageAlias OBJECT-TYPE
    SYNTAX     DisplayString (SIZE(0..16))
    MAX-ACCESS read-write
    STATUS     current
    DESCRIPTION
            "-- empty --"
    ::= { lcsSetupDhcpRelayInfoListEntry 4 }

-- {SCALAR} 1.3.6.1.4.1.2356.11.2.10.29
lcsSetupDhcpEchoClientId OBJECT-TYPE
    SYNTAX     INTEGER {
                  eNo (0),
                  eYes (1)
            }
    MAX-ACCESS read-write
    STATUS     current
    DESCRIPTION
            "-- empty --"
    ::= { lcsSetupDhcp 29 }

-- {NODE} 1.3.6.1.4.1.2356.11.2.11
lcsSetupConfig OBJECT IDENTIFIER ::= { lcsSetup 11 }

-- {SCALAR} 1.3.6.1.4.1.2356.11.2.11.1
lcsSetupConfigLan OBJECT-TYPE
    SYNTAX     Integer32 (0..255)
    MAX-ACCESS read-only
    STATUS     current
    DESCRIPTION
            ""
    ::= { lcsSetupConfig 1 }

-- {SCALAR} 1.3.6.1.4.1.2356.11.2.11.2
lcsSetupConfigWan OBJECT-TYPE
    SYNTAX     Integer32 (0..255)
    MAX-ACCESS read-only
    STATUS     current
    DESCRIPTION
            ""
    ::= { lcsSetupConfig 2 }

-- {SCALAR} 1.3.6.1.4.1.2356.11.2.11.3
lcsSetupConfigPasswordRequiredForSnmpReadAccess OBJECT-TYPE
    SYNTAX     INTEGER {
                  eNo (0),
                  eYes (1)
            }
    MAX-ACCESS read-write
    STATUS     current
    DESCRIPTION
            ""
    ::= { lcsSetupConfig 3 }

-- {SCALAR} 1.3.6.1.4.1.2356.11.2.11.4
lcsSetupConfigMaximumConnections OBJECT-TYPE
    SYNTAX     Integer32 (0..255)
    MAX-ACCESS read-write
    STATUS     current
    DESCRIPTION
            ""
    ::= { lcsSetupConfig 4 }

-- {SCALAR} 1.3.6.1.4.1.2356.11.2.11.5
lcsSetupConfigConfigAgingMinutes OBJECT-TYPE
    SYNTAX     Integer32 (0..255)
    MAX-ACCESS read-write
    STATUS     current
    DESCRIPTION
            ""
    ::= { lcsSetupConfig 5 }

-- {SCALAR} 1.3.6.1.4.1.2356.11.2.11.6
lcsSetupConfigLanguage OBJECT-TYPE
    SYNTAX     INTEGER {
                  eEnglish (1),
                  eDeutsch (2),
                  eFrench (3),
                  eItalian (4),
                  eSpanish (5),
                  eDutch (7)
            }
    MAX-ACCESS read-write
    STATUS     current
    DESCRIPTION
            ""
    ::= { lcsSetupConfig 6 }

-- {SCALAR} 1.3.6.1.4.1.2356.11.2.11.7
lcsSetupConfigLoginErrors OBJECT-TYPE
    SYNTAX     Integer32 (0..255)
    MAX-ACCESS read-write
    STATUS     current
    DESCRIPTION
            ""
    ::= { lcsSetupConfig 7 }

-- {SCALAR} 1.3.6.1.4.1.2356.11.2.11.8
lcsSetupConfigLockMinutes OBJECT-TYPE
    SYNTAX     Integer32 (0..255)
    MAX-ACCESS read-write
    STATUS     current
    DESCRIPTION
            ""
    ::= { lcsSetupConfig 8 }

-- {SCALAR} 1.3.6.1.4.1.2356.11.2.11.9
lcsSetupConfigAdminEazMsn OBJECT-TYPE
    SYNTAX     DisplayString (SIZE(0..31))
    MAX-ACCESS read-write
    STATUS     current
    DESCRIPTION
            ""
    ::= { lcsSetupConfig 9 }

-- {SCALAR} 1.3.6.1.4.1.2356.11.2.11.10
lcsSetupConfigDisplayContrast OBJECT-TYPE
    SYNTAX     INTEGER {
                  eC8 (0),
                  eC7 (1),
                  eC6 (2),
                  eC5 (3),
                  eC4 (4),
                  eC3 (5),
                  eC2 (6),
                  eC1 (7)
            }
    MAX-ACCESS read-write
    STATUS     current
    DESCRIPTION
            ""
    ::= { lcsSetupConfig 10 }

-- {SCALAR} 1.3.6.1.4.1.2356.11.2.11.11
lcsSetupConfigWlanConfig OBJECT-TYPE
    SYNTAX     Integer32 (0..255)
    MAX-ACCESS read-only
    STATUS     current
    DESCRIPTION
            ""
    ::= { lcsSetupConfig 11 }

-- {SCALAR} 1.3.6.1.4.1.2356.11.2.11.12
lcsSetupConfigWlanAuthenticationPagesOnly OBJECT-TYPE
    SYNTAX     INTEGER {
                  eNo (0),
                  eYes (1)
            }
    MAX-ACCESS read-write
    STATUS     current
    DESCRIPTION
            ""
    ::= { lcsSetupConfig 12 }

-- {NODE} 1.3.6.1.4.1.2356.11.2.11.13
lcsSetupConfigTftpClient OBJECT IDENTIFIER ::= { lcsSetupConfig 13 }

-- {SCALAR} 1.3.6.1.4.1.2356.11.2.11.13.1
lcsSetupConfigTftpClientConfigAddress OBJECT-TYPE
    SYNTAX     DisplayString (SIZE(0..31))
    MAX-ACCESS read-only
    STATUS     current
    DESCRIPTION
            ""
    ::= { lcsSetupConfigTftpClient 1 }

-- {SCALAR} 1.3.6.1.4.1.2356.11.2.11.13.2
lcsSetupConfigTftpClientConfigFilename OBJECT-TYPE
    SYNTAX     DisplayString (SIZE(0..63))
    MAX-ACCESS read-only
    STATUS     current
    DESCRIPTION
            ""
    ::= { lcsSetupConfigTftpClient 2 }

-- {SCALAR} 1.3.6.1.4.1.2356.11.2.11.13.3
lcsSetupConfigTftpClientFirmwareAddress OBJECT-TYPE
    SYNTAX     DisplayString (SIZE(0..31))
    MAX-ACCESS read-only
    STATUS     current
    DESCRIPTION
            ""
    ::= { lcsSetupConfigTftpClient 3 }

-- {SCALAR} 1.3.6.1.4.1.2356.11.2.11.13.4
lcsSetupConfigTftpClientFirmwareFilename OBJECT-TYPE
    SYNTAX     DisplayString (SIZE(0..63))
    MAX-ACCESS read-only
    STATUS     current
    DESCRIPTION
            ""
    ::= { lcsSetupConfigTftpClient 4 }

-- {SCALAR} 1.3.6.1.4.1.2356.11.2.11.13.5
lcsSetupConfigTftpClientBytesPerHashmark OBJECT-TYPE
    SYNTAX     Integer32 (0..2147483647)
    MAX-ACCESS read-only
    STATUS     current
    DESCRIPTION
            ""
    ::= { lcsSetupConfigTftpClient 5 }

-- {SCALAR} 1.3.6.1.4.1.2356.11.2.11.13.6
lcsSetupConfigTftpClientScriptAddress OBJECT-TYPE
    SYNTAX     DisplayString (SIZE(0..31))
    MAX-ACCESS read-only
    STATUS     current
    DESCRIPTION
            ""
    ::= { lcsSetupConfigTftpClient 6 }

-- {SCALAR} 1.3.6.1.4.1.2356.11.2.11.13.7
lcsSetupConfigTftpClientScriptFilename OBJECT-TYPE
    SYNTAX     DisplayString (SIZE(0..63))
    MAX-ACCESS read-only
    STATUS     current
    DESCRIPTION
            ""
    ::= { lcsSetupConfigTftpClient 7 }

-- {TABLE} 1.3.6.1.4.1.2356.11.2.11.15
lcsSetupConfigAccessTableTable OBJECT-TYPE
    SYNTAX     SEQUENCE OF LcsSetupConfigAccessTableEntry
    MAX-ACCESS not-accessible
    STATUS     current
    DESCRIPTION
            ""
    ::= { lcsSetupConfig 15 }

-- {ROW} 1.3.6.1.4.1.2356.11.2.11.15.1
lcsSetupConfigAccessTableEntry OBJECT-TYPE
    SYNTAX     LcsSetupConfigAccessTableEntry
    MAX-ACCESS not-accessible
    STATUS     current
    DESCRIPTION
            ""
    INDEX {
            lcsSetupConfigAccessTableEntryIfc
          }
    ::= { lcsSetupConfigAccessTableTable 1 }

LcsSetupConfigAccessTableEntry ::= SEQUENCE {
            lcsSetupConfigAccessTableEntryIfc INTEGER,
            lcsSetupConfigAccessTableEntryTelnet INTEGER,
            lcsSetupConfigAccessTableEntryTftp INTEGER,
            lcsSetupConfigAccessTableEntryHttp INTEGER,
            lcsSetupConfigAccessTableEntrySnmp INTEGER,
            lcsSetupConfigAccessTableEntryHttps INTEGER,
            lcsSetupConfigAccessTableEntryTelnetSsl INTEGER,
            lcsSetupConfigAccessTableEntrySsh INTEGER,
            lcsSetupConfigAccessTableEntrySnmpv3 INTEGER,
            lcsSetupConfigAccessTableEntryConfigSync INTEGER
    }

-- {COLUMN} 1.3.6.1.4.1.2356.11.2.11.15.1.1
lcsSetupConfigAccessTableEntryIfc OBJECT-TYPE
    SYNTAX     INTEGER {
                  eLan (1),
                  eWan (2),
                  eWlan (3)
            }
    MAX-ACCESS read-only
    STATUS     current
    DESCRIPTION
            ""
    ::= { lcsSetupConfigAccessTableEntry 1 }

-- {COLUMN} 1.3.6.1.4.1.2356.11.2.11.15.1.2
lcsSetupConfigAccessTableEntryTelnet OBJECT-TYPE
    SYNTAX     INTEGER {
                  eNo (0),
                  eYes (1),
                  eRead (4),
                  eVpn (16)
            }
    MAX-ACCESS read-write
    STATUS     current
    DESCRIPTION
            ""
    ::= { lcsSetupConfigAccessTableEntry 2 }

-- {COLUMN} 1.3.6.1.4.1.2356.11.2.11.15.1.3
lcsSetupConfigAccessTableEntryTftp OBJECT-TYPE
    SYNTAX     INTEGER {
                  eNo (0),
                  eYes (1),
                  eRead (4),
                  eVpn (16)
            }
    MAX-ACCESS read-write
    STATUS     current
    DESCRIPTION
            ""
    ::= { lcsSetupConfigAccessTableEntry 3 }

-- {COLUMN} 1.3.6.1.4.1.2356.11.2.11.15.1.4
lcsSetupConfigAccessTableEntryHttp OBJECT-TYPE
    SYNTAX     INTEGER {
                  eNo (0),
                  eYes (1),
                  eRead (4),
                  eVpn (16)
            }
    MAX-ACCESS read-write
    STATUS     current
    DESCRIPTION
            ""
    ::= { lcsSetupConfigAccessTableEntry 4 }

-- {COLUMN} 1.3.6.1.4.1.2356.11.2.11.15.1.5
lcsSetupConfigAccessTableEntrySnmp OBJECT-TYPE
    SYNTAX     INTEGER {
                  eNo (0),
                  eYes (1),
                  eRead (4),
                  eVpn (16)
            }
    MAX-ACCESS read-write
    STATUS     current
    DESCRIPTION
            ""
    ::= { lcsSetupConfigAccessTableEntry 5 }

-- {COLUMN} 1.3.6.1.4.1.2356.11.2.11.15.1.6
lcsSetupConfigAccessTableEntryHttps OBJECT-TYPE
    SYNTAX     INTEGER {
                  eNo (0),
                  eYes (1),
                  eRead (4),
                  eVpn (16)
            }
    MAX-ACCESS read-write
    STATUS     current
    DESCRIPTION
            ""
    ::= { lcsSetupConfigAccessTableEntry 6 }

-- {COLUMN} 1.3.6.1.4.1.2356.11.2.11.15.1.7
lcsSetupConfigAccessTableEntryTelnetSsl OBJECT-TYPE
    SYNTAX     INTEGER {
                  eNo (0),
                  eYes (1),
                  eRead (4),
                  eVpn (16)
            }
    MAX-ACCESS read-write
    STATUS     current
    DESCRIPTION
            ""
    ::= { lcsSetupConfigAccessTableEntry 7 }

-- {COLUMN} 1.3.6.1.4.1.2356.11.2.11.15.1.8
lcsSetupConfigAccessTableEntrySsh OBJECT-TYPE
    SYNTAX     INTEGER {
                  eNo (0),
                  eYes (1),
                  eRead (4),
                  eVpn (16)
            }
    MAX-ACCESS read-write
    STATUS     current
    DESCRIPTION
            ""
    ::= { lcsSetupConfigAccessTableEntry 8 }

-- {COLUMN} 1.3.6.1.4.1.2356.11.2.11.15.1.9
lcsSetupConfigAccessTableEntrySnmpv3 OBJECT-TYPE
    SYNTAX     INTEGER {
                  eNo (0),
                  eYes (1),
                  eRead (4),
                  eVpn (16)
            }
    MAX-ACCESS read-write
    STATUS     current
    DESCRIPTION
            "-- empty --"
    ::= { lcsSetupConfigAccessTableEntry 9 }

-- {COLUMN} 1.3.6.1.4.1.2356.11.2.11.15.1.10
lcsSetupConfigAccessTableEntryConfigSync OBJECT-TYPE
    SYNTAX     INTEGER {
                  eNo (0),
                  eYes (1),
                  eRead (4),
                  eVpn (16)
            }
    MAX-ACCESS read-write
    STATUS     current
    DESCRIPTION
            "-- empty --"
    ::= { lcsSetupConfigAccessTableEntry 10 }

-- {SCALAR} 1.3.6.1.4.1.2356.11.2.11.16
lcsSetupConfigScreenHeight OBJECT-TYPE
    SYNTAX     Integer32 (0..65535)
    MAX-ACCESS read-write
    STATUS     current
    DESCRIPTION
            ""
    ::= { lcsSetupConfig 16 }

-- {SCALAR} 1.3.6.1.4.1.2356.11.2.11.17
lcsSetupConfigPrompt OBJECT-TYPE
    SYNTAX     DisplayString (SIZE(0..31))
    MAX-ACCESS read-write
    STATUS     current
    DESCRIPTION
            ""
    ::= { lcsSetupConfig 17 }

-- {SCALAR} 1.3.6.1.4.1.2356.11.2.11.18
lcsSetupConfigLedTest OBJECT-TYPE
    SYNTAX     INTEGER {
                  eOff (0),
                  eRed (1),
                  eGreen (2),
                  eOrange (3),
                  eBlue (4),
                  eNoTest (255)
            }
    MAX-ACCESS read-write
    STATUS     current
    DESCRIPTION
            ""
    ::= { lcsSetupConfig 18 }

-- {TABLE} 1.3.6.1.4.1.2356.11.2.11.20
lcsSetupConfigCronTableTable OBJECT-TYPE
    SYNTAX     SEQUENCE OF LcsSetupConfigCronTableEntry
    MAX-ACCESS not-accessible
    STATUS     current
    DESCRIPTION
            ""
    ::= { lcsSetupConfig 20 }

-- {ROW} 1.3.6.1.4.1.2356.11.2.11.20.1
lcsSetupConfigCronTableEntry OBJECT-TYPE
    SYNTAX     LcsSetupConfigCronTableEntry
    MAX-ACCESS not-accessible
    STATUS     current
    DESCRIPTION
            ""
    INDEX {
            lcsSetupConfigCronTableEntryIndex
          }
    ::= { lcsSetupConfigCronTableTable 1 }

LcsSetupConfigCronTableEntry ::= SEQUENCE {
            lcsSetupConfigCronTableEntryIndex Integer32,
            lcsSetupConfigCronTableEntryMinute DisplayString,
            lcsSetupConfigCronTableEntryHour DisplayString,
            lcsSetupConfigCronTableEntryDayofweek DisplayString,
            lcsSetupConfigCronTableEntryDay DisplayString,
            lcsSetupConfigCronTableEntryMonth DisplayString,
            lcsSetupConfigCronTableEntryCommand DisplayString,
            lcsSetupConfigCronTableEntryBase INTEGER,
            lcsSetupConfigCronTableEntryActive INTEGER,
            lcsSetupConfigCronTableEntryOwner DisplayString,
            lcsSetupConfigCronTableEntryVariation Integer32,
            lcsSetupConfigCronTableEntryComment DisplayString
    }

-- {COLUMN} 1.3.6.1.4.1.2356.11.2.11.20.1.1
lcsSetupConfigCronTableEntryIndex OBJECT-TYPE
    SYNTAX     Integer32 (0..65535)
    MAX-ACCESS read-write
    STATUS     current
    DESCRIPTION
            ""
    ::= { lcsSetupConfigCronTableEntry 1 }

-- {COLUMN} 1.3.6.1.4.1.2356.11.2.11.20.1.2
lcsSetupConfigCronTableEntryMinute OBJECT-TYPE
    SYNTAX     DisplayString (SIZE(0..50))
    MAX-ACCESS read-write
    STATUS     current
    DESCRIPTION
            ""
    ::= { lcsSetupConfigCronTableEntry 2 }

-- {COLUMN} 1.3.6.1.4.1.2356.11.2.11.20.1.3
lcsSetupConfigCronTableEntryHour OBJECT-TYPE
    SYNTAX     DisplayString (SIZE(0..50))
    MAX-ACCESS read-write
    STATUS     current
    DESCRIPTION
            ""
    ::= { lcsSetupConfigCronTableEntry 3 }

-- {COLUMN} 1.3.6.1.4.1.2356.11.2.11.20.1.4
lcsSetupConfigCronTableEntryDayofweek OBJECT-TYPE
    SYNTAX     DisplayString (SIZE(0..50))
    MAX-ACCESS read-write
    STATUS     current
    DESCRIPTION
            ""
    ::= { lcsSetupConfigCronTableEntry 4 }

-- {COLUMN} 1.3.6.1.4.1.2356.11.2.11.20.1.5
lcsSetupConfigCronTableEntryDay OBJECT-TYPE
    SYNTAX     DisplayString (SIZE(0..50))
    MAX-ACCESS read-write
    STATUS     current
    DESCRIPTION
            ""
    ::= { lcsSetupConfigCronTableEntry 5 }

-- {COLUMN} 1.3.6.1.4.1.2356.11.2.11.20.1.6
lcsSetupConfigCronTableEntryMonth OBJECT-TYPE
    SYNTAX     DisplayString (SIZE(0..50))
    MAX-ACCESS read-write
    STATUS     current
    DESCRIPTION
            ""
    ::= { lcsSetupConfigCronTableEntry 6 }

-- {COLUMN} 1.3.6.1.4.1.2356.11.2.11.20.1.7
lcsSetupConfigCronTableEntryCommand OBJECT-TYPE
    SYNTAX     DisplayString (SIZE(0..252))
    MAX-ACCESS read-write
    STATUS     current
    DESCRIPTION
            ""
    ::= { lcsSetupConfigCronTableEntry 7 }

-- {COLUMN} 1.3.6.1.4.1.2356.11.2.11.20.1.8
lcsSetupConfigCronTableEntryBase OBJECT-TYPE
    SYNTAX     INTEGER {
                  eRealTime (0),
                  eOperationTime (1)
            }
    MAX-ACCESS read-write
    STATUS     current
    DESCRIPTION
            ""
    ::= { lcsSetupConfigCronTableEntry 8 }

-- {COLUMN} 1.3.6.1.4.1.2356.11.2.11.20.1.9
lcsSetupConfigCronTableEntryActive OBJECT-TYPE
    SYNTAX     INTEGER {
                  eYes (0),
                  eNo (1)
            }
    MAX-ACCESS read-write
    STATUS     current
    DESCRIPTION
            ""
    ::= { lcsSetupConfigCronTableEntry 9 }

-- {COLUMN} 1.3.6.1.4.1.2356.11.2.11.20.1.10
lcsSetupConfigCronTableEntryOwner OBJECT-TYPE
    SYNTAX     DisplayString (SIZE(0..16))
    MAX-ACCESS read-write
    STATUS     current
    DESCRIPTION
            ""
    ::= { lcsSetupConfigCronTableEntry 10 }

-- {COLUMN} 1.3.6.1.4.1.2356.11.2.11.20.1.11
lcsSetupConfigCronTableEntryVariation OBJECT-TYPE
    SYNTAX     Integer32 (0..65535)
    MAX-ACCESS read-write
    STATUS     current
    DESCRIPTION
            ""
    ::= { lcsSetupConfigCronTableEntry 11 }

-- {COLUMN} 1.3.6.1.4.1.2356.11.2.11.20.1.12
lcsSetupConfigCronTableEntryComment OBJECT-TYPE
    SYNTAX     DisplayString (SIZE(0..63))
    MAX-ACCESS read-write
    STATUS     current
    DESCRIPTION
            "-- empty --"
    ::= { lcsSetupConfigCronTableEntry 12 }

-- {TABLE} 1.3.6.1.4.1.2356.11.2.11.21
lcsSetupConfigAdminsTable OBJECT-TYPE
    SYNTAX     SEQUENCE OF LcsSetupConfigAdminsEntry
    MAX-ACCESS not-accessible
    STATUS     current
    DESCRIPTION
            ""
    ::= { lcsSetupConfig 21 }

-- {ROW} 1.3.6.1.4.1.2356.11.2.11.21.1
lcsSetupConfigAdminsEntry OBJECT-TYPE
    SYNTAX     LcsSetupConfigAdminsEntry
    MAX-ACCESS not-accessible
    STATUS     current
    DESCRIPTION
            ""
    INDEX {
            lcsSetupConfigAdminsEntryAdministrator
          }
    ::= { lcsSetupConfigAdminsTable 1 }

LcsSetupConfigAdminsEntry ::= SEQUENCE {
            lcsSetupConfigAdminsEntryAdministrator DisplayString,
            lcsSetupConfigAdminsEntryPassword DisplayString,
            lcsSetupConfigAdminsEntryFunctionRights BITS,
            lcsSetupConfigAdminsEntryActive INTEGER,
            lcsSetupConfigAdminsEntryAccessRights INTEGER
    }

-- {COLUMN} 1.3.6.1.4.1.2356.11.2.11.21.1.1
lcsSetupConfigAdminsEntryAdministrator OBJECT-TYPE
    SYNTAX     DisplayString (SIZE(0..16))
    MAX-ACCESS read-write
    STATUS     current
    DESCRIPTION
            ""
    ::= { lcsSetupConfigAdminsEntry 1 }

-- {COLUMN} 1.3.6.1.4.1.2356.11.2.11.21.1.2
lcsSetupConfigAdminsEntryPassword OBJECT-TYPE
    SYNTAX     DisplayString (SIZE(0..16))
    MAX-ACCESS read-write
    STATUS     current
    DESCRIPTION
            ""
    ::= { lcsSetupConfigAdminsEntry 2 }

-- {COLUMN} 1.3.6.1.4.1.2356.11.2.11.21.1.3
lcsSetupConfigAdminsEntryFunctionRights OBJECT-TYPE
    SYNTAX     BITS {
                  eCaWebInterface (7),
                  ePrepareVoipProviderAccess (8),
                  eSmsTransmit (9),
                  ePublicSpotConfigurationWizard (10),
                  ePublicSpotUserManagementWizard (11),
                  ePublicSpotXmlInterface (12),
                  eCfProfileWizard (13),
                  eSshCommand (14),
                  eWlcProfileWizard (15),
                  eVoipCallmanagerWizard (16),
                  eDynamicDnsWizard (17),
                  eRolloutWizard (18),
                  eWlanWizard (19),
                  ePublicSpotWizard (20),
                  eWtpAssignmentWizard (21),
                  eWlanLinktest (23),
                  eDeviceSearch (24),
                  eTimeSetting (25),
                  eLanlanWizard (26),
                  eRasWizard (27),
                  eProviderSelection (28),
                  eInternetWizard (29),
                  eSecurityWizard (30),
                  eBasicWizard (31)
            }
    MAX-ACCESS read-write
    STATUS     current
    DESCRIPTION
            ""
    ::= { lcsSetupConfigAdminsEntry 3 }

-- {COLUMN} 1.3.6.1.4.1.2356.11.2.11.21.1.4
lcsSetupConfigAdminsEntryActive OBJECT-TYPE
    SYNTAX     INTEGER {
                  eYes (0),
                  eNo (1)
            }
    MAX-ACCESS read-write
    STATUS     current
    DESCRIPTION
            ""
    ::= { lcsSetupConfigAdminsEntry 4 }

-- {COLUMN} 1.3.6.1.4.1.2356.11.2.11.21.1.5
lcsSetupConfigAdminsEntryAccessRights OBJECT-TYPE
    SYNTAX     INTEGER {
                  eSupervisor (-1),
                  eNone (0),
                  eAdminRoLimit (8388608),
                  eAdminRwLimit (8388864),
                  eAdminRo (16777216),
                  eAdminRw (16777472)
            }
    MAX-ACCESS read-write
    STATUS     current
    DESCRIPTION
            ""
    ::= { lcsSetupConfigAdminsEntry 5 }

-- {SCALAR} 1.3.6.1.4.1.2356.11.2.11.23
lcsSetupConfigTelnetPort OBJECT-TYPE
    SYNTAX     Integer32 (0..65535)
    MAX-ACCESS read-write
    STATUS     current
    DESCRIPTION
            ""
    ::= { lcsSetupConfig 23 }

-- {SCALAR} 1.3.6.1.4.1.2356.11.2.11.24
lcsSetupConfigTelnetSslPort OBJECT-TYPE
    SYNTAX     Integer32 (0..65535)
    MAX-ACCESS read-write
    STATUS     current
    DESCRIPTION
            ""
    ::= { lcsSetupConfig 24 }

-- {SCALAR} 1.3.6.1.4.1.2356.11.2.11.25
lcsSetupConfigSshPort OBJECT-TYPE
    SYNTAX     Integer32 (0..65535)
    MAX-ACCESS read-write
    STATUS     current
    DESCRIPTION
            ""
    ::= { lcsSetupConfig 25 }

-- {TABLE} 1.3.6.1.4.1.2356.11.2.11.26
lcsSetupConfigSshAuthenticationMethodsTable OBJECT-TYPE
    SYNTAX     SEQUENCE OF LcsSetupConfigSshAuthenticationMethodsEntry
    MAX-ACCESS not-accessible
    STATUS     current
    DESCRIPTION
            ""
    ::= { lcsSetupConfig 26 }

-- {ROW} 1.3.6.1.4.1.2356.11.2.11.26.1
lcsSetupConfigSshAuthenticationMethodsEntry OBJECT-TYPE
    SYNTAX     LcsSetupConfigSshAuthenticationMethodsEntry
    MAX-ACCESS not-accessible
    STATUS     current
    DESCRIPTION
            ""
    INDEX {
            lcsSetupConfigSshAuthenticationMethodsEntryIfc
          }
    ::= { lcsSetupConfigSshAuthenticationMethodsTable 1 }

LcsSetupConfigSshAuthenticationMethodsEntry ::= SEQUENCE {
            lcsSetupConfigSshAuthenticationMethodsEntryIfc INTEGER,
            lcsSetupConfigSshAuthenticationMethodsEntryMethods INTEGER
    }

-- {COLUMN} 1.3.6.1.4.1.2356.11.2.11.26.1.1
lcsSetupConfigSshAuthenticationMethodsEntryIfc OBJECT-TYPE
    SYNTAX     INTEGER {
                  eLan (1),
                  eWan (2),
                  eWlan (3)
            }
    MAX-ACCESS read-only
    STATUS     current
    DESCRIPTION
            ""
    ::= { lcsSetupConfigSshAuthenticationMethodsEntry 1 }

-- {COLUMN} 1.3.6.1.4.1.2356.11.2.11.26.1.2
lcsSetupConfigSshAuthenticationMethodsEntryMethods OBJECT-TYPE
    SYNTAX     INTEGER {
                  ePublicKey (1),
                  ePassword (2),
                  ePasswordPlusPublicKey (3),
                  eKeyboardInteractive (4),
                  eKeyboardInteractivePlusPublicKey (5),
                  ePasswordPlusKeyboardInteractive (6),
                  eAll (255)
            }
    MAX-ACCESS read-write
    STATUS     current
    DESCRIPTION
            ""
    ::= { lcsSetupConfigSshAuthenticationMethodsEntry 2 }

-- {TABLE} 1.3.6.1.4.1.2356.11.2.11.27
lcsSetupConfigPredefAdminsTable OBJECT-TYPE
    SYNTAX     SEQUENCE OF LcsSetupConfigPredefAdminsEntry
    MAX-ACCESS not-accessible
    STATUS     current
    DESCRIPTION
            ""
    ::= { lcsSetupConfig 27 }

-- {ROW} 1.3.6.1.4.1.2356.11.2.11.27.1
lcsSetupConfigPredefAdminsEntry OBJECT-TYPE
    SYNTAX     LcsSetupConfigPredefAdminsEntry
    MAX-ACCESS not-accessible
    STATUS     current
    DESCRIPTION
            ""
    INDEX {
            lcsSetupConfigPredefAdminsEntryName
          }
    ::= { lcsSetupConfigPredefAdminsTable 1 }

LcsSetupConfigPredefAdminsEntry ::= SEQUENCE {
            lcsSetupConfigPredefAdminsEntryName DisplayString
    }

-- {COLUMN} 1.3.6.1.4.1.2356.11.2.11.27.1.1
lcsSetupConfigPredefAdminsEntryName OBJECT-TYPE
    SYNTAX     DisplayString (SIZE(0..15))
    MAX-ACCESS read-only
    STATUS     current
    DESCRIPTION
            ""
    ::= { lcsSetupConfigPredefAdminsEntry 1 }

-- {NODE} 1.3.6.1.4.1.2356.11.2.11.28
lcsSetupConfigSsh OBJECT IDENTIFIER ::= { lcsSetupConfig 28 }

-- {SCALAR} 1.3.6.1.4.1.2356.11.2.11.28.1
lcsSetupConfigSshCipherAlgorithms OBJECT-TYPE
    SYNTAX     BITS {
                  eAes256Gcm (16),
                  eAes128Gcm (17),
                  eChacha20Poly1305 (18),
                  eAes256Ctr (19),
                  eAes192Ctr (20),
                  eAes128Ctr (21),
                  eAes256Cbc (22),
                  eAes192Cbc (23),
                  eAes128Cbc (24),
                  eBlowfishCtr (25),
                  eBlowfishCbc (26),
                  eArcfour256 (27),
                  eArcfour128 (28),
                  eArcfour (29),
                  e3desCtr (30),
                  e3desCbc (31)
            }
    MAX-ACCESS read-write
    STATUS     current
    DESCRIPTION
            "-- empty --"
    ::= { lcsSetupConfigSsh 1 }

-- {SCALAR} 1.3.6.1.4.1.2356.11.2.11.28.2
lcsSetupConfigSshMacAlgorithms OBJECT-TYPE
    SYNTAX     BITS {
                  eHmacSha2512 (24),
                  eHmacSha251296 (25),
                  eHmacSha2256 (26),
                  eHmacSha225696 (27),
                  eHmacSha1 (28),
                  eHmacSha196 (29),
                  eHmacMd5 (30),
                  eHmacMd596 (31)
            }
    MAX-ACCESS read-write
    STATUS     current
    DESCRIPTION
            "-- empty --"
    ::= { lcsSetupConfigSsh 2 }

-- {SCALAR} 1.3.6.1.4.1.2356.11.2.11.28.3
lcsSetupConfigSshKeyExchangeAlgorithms OBJECT-TYPE
    SYNTAX     BITS {
                  eCurve25519Sha256 (26),
                  eEcdhSha2 (27),
                  eDiffieHellmanGroupExchangeSha256 (28),
                  eDiffieHellmanGroupExchangeSha1 (29),
                  eDiffieHellmanGroup14Sha1 (30),
                  eDiffieHellmanGroup1Sha1 (31)
            }
    MAX-ACCESS read-write
    STATUS     current
    DESCRIPTION
            "-- empty --"
    ::= { lcsSetupConfigSsh 3 }

-- {SCALAR} 1.3.6.1.4.1.2356.11.2.11.28.4
lcsSetupConfigSshHostkeyAlgorithms OBJECT-TYPE
    SYNTAX     BITS {
                  eRsaSha2512 (26),
                  eRsaSha2256 (27),
                  eSshEd25519 (28),
                  eEcdsaSha2 (29),
                  eSshDss (30),
                  eSshRsa (31)
            }
    MAX-ACCESS read-write
    STATUS     current
    DESCRIPTION
            "-- empty --"
    ::= { lcsSetupConfigSsh 4 }

-- {SCALAR} 1.3.6.1.4.1.2356.11.2.11.28.5
lcsSetupConfigSshMinHostkeyLength OBJECT-TYPE
    SYNTAX     Integer32 (0..65535)
    MAX-ACCESS read-write
    STATUS     current
    DESCRIPTION
            "-- empty --"
    ::= { lcsSetupConfigSsh 5 }

-- {SCALAR} 1.3.6.1.4.1.2356.11.2.11.28.6
lcsSetupConfigSshMaxHostkeyLength OBJECT-TYPE
    SYNTAX     Integer32 (0..65535)
    MAX-ACCESS read-write
    STATUS     current
    DESCRIPTION
            "-- empty --"
    ::= { lcsSetupConfigSsh 6 }

-- {SCALAR} 1.3.6.1.4.1.2356.11.2.11.28.7
lcsSetupConfigSshDhGroups OBJECT-TYPE
    SYNTAX     BITS {
                  eGroup16 (27),
                  eGroup15 (28),
                  eGroup14 (29),
                  eGroup5 (30),
                  eGroup1 (31)
            }
    MAX-ACCESS read-write
    STATUS     current
    DESCRIPTION
            "-- empty --"
    ::= { lcsSetupConfigSsh 7 }

-- {SCALAR} 1.3.6.1.4.1.2356.11.2.11.28.8
lcsSetupConfigSshCompression OBJECT-TYPE
    SYNTAX     INTEGER {
                  eNo (0),
                  eYes (1)
            }
    MAX-ACCESS read-write
    STATUS     current
    DESCRIPTION
            "-- empty --"
    ::= { lcsSetupConfigSsh 8 }

-- {SCALAR} 1.3.6.1.4.1.2356.11.2.11.28.9
lcsSetupConfigSshEllipticCurves OBJECT-TYPE
    SYNTAX     BITS {
                  eNistp521 (29),
                  eNistp384 (30),
                  eNistp256 (31)
            }
    MAX-ACCESS read-write
    STATUS     current
    DESCRIPTION
            "-- empty --"
    ::= { lcsSetupConfigSsh 9 }

-- {NODE} 1.3.6.1.4.1.2356.11.2.11.28.10
lcsSetupConfigSshSftpServer OBJECT IDENTIFIER ::= { lcsSetupConfigSsh 10 }

-- {SCALAR} 1.3.6.1.4.1.2356.11.2.11.28.10.1
lcsSetupConfigSshSftpServerOperating OBJECT-TYPE
    SYNTAX     INTEGER {
                  eNo (0),
                  eYes (1)
            }
    MAX-ACCESS read-write
    STATUS     current
    DESCRIPTION
            "-- empty --"
    ::= { lcsSetupConfigSshSftpServer 1 }

-- {SCALAR} 1.3.6.1.4.1.2356.11.2.11.28.11
lcsSetupConfigSshKeepaliveInterval OBJECT-TYPE
    SYNTAX     Integer32 (0..2147483647)
    MAX-ACCESS read-write
    STATUS     current
    DESCRIPTION
            "-- empty --"
    ::= { lcsSetupConfigSsh 11 }

-- {SCALAR} 1.3.6.1.4.1.2356.11.2.11.28.12
lcsSetupConfigSshOperating OBJECT-TYPE
    SYNTAX     BITS {
                  eNo (0),
                  eYes (7)
            }
    MAX-ACCESS read-write
    STATUS     current
    DESCRIPTION
            "-- empty --"
    ::= { lcsSetupConfigSsh 12 }

-- {SCALAR} 1.3.6.1.4.1.2356.11.2.11.28.13
lcsSetupConfigSshNewPort OBJECT-TYPE
    SYNTAX     Integer32 (0..65535)
    MAX-ACCESS read-write
    STATUS     current
    DESCRIPTION
            "TCP port SSH server is listening on"
    ::= { lcsSetupConfigSsh 13 }

-- {TABLE} 1.3.6.1.4.1.2356.11.2.11.28.14
lcsSetupConfigSshNewAuthenticationMethodsTable OBJECT-TYPE
    SYNTAX     SEQUENCE OF LcsSetupConfigSshNewAuthenticationMethodsEntry
    MAX-ACCESS not-accessible
    STATUS     current
    DESCRIPTION
            "enable/disable SSH authentication methods"
    ::= { lcsSetupConfigSsh 14 }

-- {ROW} 1.3.6.1.4.1.2356.11.2.11.28.14.1
lcsSetupConfigSshNewAuthenticationMethodsEntry OBJECT-TYPE
    SYNTAX     LcsSetupConfigSshNewAuthenticationMethodsEntry
    MAX-ACCESS not-accessible
    STATUS     current
    DESCRIPTION
            ""
    INDEX {
            lcsSetupConfigSshNewAuthenticationMethodsEntryIfc
          }
    ::= { lcsSetupConfigSshNewAuthenticationMethodsTable 1 }

LcsSetupConfigSshNewAuthenticationMethodsEntry ::= SEQUENCE {
            lcsSetupConfigSshNewAuthenticationMethodsEntryIfc INTEGER,
            lcsSetupConfigSshNewAuthenticationMethodsEntryMethods INTEGER
    }

-- {COLUMN} 1.3.6.1.4.1.2356.11.2.11.28.14.1.1
lcsSetupConfigSshNewAuthenticationMethodsEntryIfc OBJECT-TYPE
    SYNTAX     INTEGER {
                  eLan (1),
                  eWan (2),
                  eWlan (3)
            }
    MAX-ACCESS read-only
    STATUS     current
    DESCRIPTION
            "-- empty --"
    ::= { lcsSetupConfigSshNewAuthenticationMethodsEntry 1 }

-- {COLUMN} 1.3.6.1.4.1.2356.11.2.11.28.14.1.2
lcsSetupConfigSshNewAuthenticationMethodsEntryMethods OBJECT-TYPE
    SYNTAX     INTEGER {
                  ePublicKey (1),
                  ePassword (2),
                  ePasswordPlusPublicKey (3),
                  eKeyboardInteractive (4),
                  eKeyboardInteractivePlusPublicKey (5),
                  ePasswordPlusKeyboardInteractive (6),
                  eAll (255)
            }
    MAX-ACCESS read-write
    STATUS     current
    DESCRIPTION
            "-- empty --"
    ::= { lcsSetupConfigSshNewAuthenticationMethodsEntry 2 }

-- {NODE} 1.3.6.1.4.1.2356.11.2.11.29
lcsSetupConfigTelnetSsl OBJECT IDENTIFIER ::= { lcsSetupConfig 29 }

-- {SCALAR} 1.3.6.1.4.1.2356.11.2.11.29.2
lcsSetupConfigTelnetSslVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupConfigTelnetSsl 2 }

-- {SCALAR} 1.3.6.1.4.1.2356.11.2.11.29.3
lcsSetupConfigTelnetSslKeyexAlgorithms OBJECT-TYPE
    SYNTAX     BITS {
                  eEcdhe (27),
                  eDhe (29),
                  eRsa (31)
            }
    MAX-ACCESS read-write
    STATUS     current
    DESCRIPTION
            "-- empty --"
    ::= { lcsSetupConfigTelnetSsl 3 }

-- {SCALAR} 1.3.6.1.4.1.2356.11.2.11.29.4
lcsSetupConfigTelnetSslCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupConfigTelnetSsl 4 }

-- {SCALAR} 1.3.6.1.4.1.2356.11.2.11.29.5
lcsSetupConfigTelnetSslHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupConfigTelnetSsl 5 }

-- {SCALAR} 1.3.6.1.4.1.2356.11.2.11.29.6
lcsSetupConfigTelnetSslPreferPfs OBJECT-TYPE
    SYNTAX     BITS {
                  eNo (0),
                  eYes (7)
            }
    MAX-ACCESS read-write
    STATUS     current
    DESCRIPTION
            "-- empty --"
    ::= { lcsSetupConfigTelnetSsl 6 }

-- {SCALAR} 1.3.6.1.4.1.2356.11.2.11.29.7
lcsSetupConfigTelnetSslRenegotiations OBJECT-TYPE
    SYNTAX     INTEGER {
                  eForbidden (0),
                  eAllowed (1),
                  eIgnored (2)
            }
    MAX-ACCESS read-write
    STATUS     current
    DESCRIPTION
            "-- empty --"
    ::= { lcsSetupConfigTelnetSsl 7 }

-- {SCALAR} 1.3.6.1.4.1.2356.11.2.11.29.8
lcsSetupConfigTelnetSslEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupConfigTelnetSsl 8 }

-- {SCALAR} 1.3.6.1.4.1.2356.11.2.11.29.10
lcsSetupConfigTelnetSslPortNew OBJECT-TYPE
    SYNTAX     Integer32 (0..65535)
    MAX-ACCESS read-write
    STATUS     current
    DESCRIPTION
            "TCP port device is listening on for Telnet/SSL"
    ::= { lcsSetupConfigTelnetSsl 10 }

-- {SCALAR} 1.3.6.1.4.1.2356.11.2.11.29.11
lcsSetupConfigTelnetSslOperating OBJECT-TYPE
    SYNTAX     INTEGER {
                  eNo (0),
                  eYes (1)
            }
    MAX-ACCESS read-write
    STATUS     current
    DESCRIPTION
            "-- empty --"
    ::= { lcsSetupConfigTelnetSsl 11 }

-- {SCALAR} 1.3.6.1.4.1.2356.11.2.11.29.22
lcsSetupConfigTelnetSslSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupConfigTelnetSsl 22 }

-- {NODE} 1.3.6.1.4.1.2356.11.2.11.30
lcsSetupConfigUpdateClient OBJECT IDENTIFIER ::= { lcsSetupConfig 30 }

-- {SCALAR} 1.3.6.1.4.1.2356.11.2.11.30.1
lcsSetupConfigUpdateClientOperating OBJECT-TYPE
    SYNTAX     INTEGER {
                  eNo (0),
                  eYes (1)
            }
    MAX-ACCESS read-only
    STATUS     current
    DESCRIPTION
            ""
    ::= { lcsSetupConfigUpdateClient 1 }

-- {SCALAR} 1.3.6.1.4.1.2356.11.2.11.30.2
lcsSetupConfigUpdateClientServerName OBJECT-TYPE
    SYNTAX     DisplayString (SIZE(0..64))
    MAX-ACCESS read-only
    STATUS     current
    DESCRIPTION
            ""
    ::= { lcsSetupConfigUpdateClient 2 }

-- {SCALAR} 1.3.6.1.4.1.2356.11.2.11.30.3
lcsSetupConfigUpdateClientServerPort OBJECT-TYPE
    SYNTAX     Integer32 (0..65535)
    MAX-ACCESS read-only
    STATUS     current
    DESCRIPTION
            ""
    ::= { lcsSetupConfigUpdateClient 3 }

-- {SCALAR} 1.3.6.1.4.1.2356.11.2.11.30.4
lcsSetupConfigUpdateClientResponseTimeout OBJECT-TYPE
    SYNTAX     Integer32 (0..2147483647)
    MAX-ACCESS read-only
    STATUS     current
    DESCRIPTION
            ""
    ::= { lcsSetupConfigUpdateClient 4 }

-- {SCALAR} 1.3.6.1.4.1.2356.11.2.11.30.5
lcsSetupConfigUpdateClientRetryFailure OBJECT-TYPE
    SYNTAX     Integer32 (0..2147483647)
    MAX-ACCESS read-only
    STATUS     current
    DESCRIPTION
            ""
    ::= { lcsSetupConfigUpdateClient 5 }

-- {SCALAR} 1.3.6.1.4.1.2356.11.2.11.30.6
lcsSetupConfigUpdateClientRetryOk OBJECT-TYPE
    SYNTAX     Integer32 (0..2147483647)
    MAX-ACCESS read-only
    STATUS     current
    DESCRIPTION
            ""
    ::= { lcsSetupConfigUpdateClient 6 }

-- {SCALAR} 1.3.6.1.4.1.2356.11.2.11.30.7
lcsSetupConfigUpdateClientLastFirmwareUpdate OBJECT-TYPE
    SYNTAX     DisplayString (SIZE(0..21))
    MAX-ACCESS read-only
    STATUS     current
    DESCRIPTION
            ""
    ::= { lcsSetupConfigUpdateClient 7 }

-- {SCALAR} 1.3.6.1.4.1.2356.11.2.11.30.8
lcsSetupConfigUpdateClientLastConfigUpdate OBJECT-TYPE
    SYNTAX     DisplayString (SIZE(0..21))
    MAX-ACCESS read-only
    STATUS     current
    DESCRIPTION
            ""
    ::= { lcsSetupConfigUpdateClient 8 }

-- {NODE} 1.3.6.1.4.1.2356.11.2.11.31
lcsSetupConfigAntiTheftProtection OBJECT IDENTIFIER ::= { lcsSetupConfig 31 }

-- {SCALAR} 1.3.6.1.4.1.2356.11.2.11.31.1
lcsSetupConfigAntiTheftProtectionEnabled OBJECT-TYPE
    SYNTAX     INTEGER {
                  eNo (0),
                  eYes (1)
            }
    MAX-ACCESS read-write
    STATUS     current
    DESCRIPTION
            ""
    ::= { lcsSetupConfigAntiTheftProtection 1 }

-- {SCALAR} 1.3.6.1.4.1.2356.11.2.11.31.2
lcsSetupConfigAntiTheftProtectionCalledNumber OBJECT-TYPE
    SYNTAX     DisplayString (SIZE(0..14))
    MAX-ACCESS read-write
    STATUS     current
    DESCRIPTION
            ""
    ::= { lcsSetupConfigAntiTheftProtection 2 }

-- {SCALAR} 1.3.6.1.4.1.2356.11.2.11.31.3
lcsSetupConfigAntiTheftProtectionOutgoingCallingNumber OBJECT-TYPE
    SYNTAX     DisplayString (SIZE(0..14))
    MAX-ACCESS read-write
    STATUS     current
    DESCRIPTION
            ""
    ::= { lcsSetupConfigAntiTheftProtection 3 }

-- {SCALAR} 1.3.6.1.4.1.2356.11.2.11.31.4
lcsSetupConfigAntiTheftProtectionCheckedCallingNumber OBJECT-TYPE
    SYNTAX     DisplayString (SIZE(0..14))
    MAX-ACCESS read-write
    STATUS     current
    DESCRIPTION
            ""
    ::= { lcsSetupConfigAntiTheftProtection 4 }

-- {SCALAR} 1.3.6.1.4.1.2356.11.2.11.31.6
lcsSetupConfigAntiTheftProtectionMethod OBJECT-TYPE
    SYNTAX     INTEGER {
                  eBasicCall (0),
                  eFacility (1),
                  eGps (2)
            }
    MAX-ACCESS read-write
    STATUS     current
    DESCRIPTION
            ""
    ::= { lcsSetupConfigAntiTheftProtection 6 }

-- {SCALAR} 1.3.6.1.4.1.2356.11.2.11.31.7
lcsSetupConfigAntiTheftProtectionIsdnIfc OBJECT-TYPE
    SYNTAX     INTEGER {
                  eS01 (1),
                  eS02 (2)
            }
    MAX-ACCESS read-write
    STATUS     current
    DESCRIPTION
            ""
    ::= { lcsSetupConfigAntiTheftProtection 7 }

-- {SCALAR} 1.3.6.1.4.1.2356.11.2.11.31.8
lcsSetupConfigAntiTheftProtectionDeviationM OBJECT-TYPE
    SYNTAX     Integer32 (0..2147483647)
    MAX-ACCESS read-write
    STATUS     current
    DESCRIPTION
            ""
    ::= { lcsSetupConfigAntiTheftProtection 8 }

-- {SCALAR} 1.3.6.1.4.1.2356.11.2.11.31.9
lcsSetupConfigAntiTheftProtectionLongitudeDeg OBJECT-TYPE
    SYNTAX     DisplayString (SIZE(0..12))
    MAX-ACCESS read-write
    STATUS     current
    DESCRIPTION
            ""
    ::= { lcsSetupConfigAntiTheftProtection 9 }

-- {SCALAR} 1.3.6.1.4.1.2356.11.2.11.31.10
lcsSetupConfigAntiTheftProtectionLatitudeDeg OBJECT-TYPE
    SYNTAX     DisplayString (SIZE(0..11))
    MAX-ACCESS read-write
    STATUS     current
    DESCRIPTION
            ""
    ::= { lcsSetupConfigAntiTheftProtection 10 }

-- {SCALAR} 1.3.6.1.4.1.2356.11.2.11.31.12
lcsSetupConfigAntiTheftProtectionGetGpsPosition OBJECT-TYPE
    SYNTAX     INTEGER {
                  eNo (0),
                  eYes (1)
            }
    MAX-ACCESS read-write
    STATUS     current
    DESCRIPTION
            ""
    ::= { lcsSetupConfigAntiTheftProtection 12 }

-- {SCALAR} 1.3.6.1.4.1.2356.11.2.11.32
lcsSetupConfigResetButton OBJECT-TYPE
    SYNTAX     INTEGER {
                  eIgnore (0),
                  eBootOnly (1),
                  eResetOrBoot (2)
            }
    MAX-ACCESS read-write
    STATUS     current
    DESCRIPTION
            ""
    ::= { lcsSetupConfig 32 }

-- {SCALAR} 1.3.6.1.4.1.2356.11.2.11.33
lcsSetupConfigOutbandAgingMinutes OBJECT-TYPE
    SYNTAX     Integer32 (0..255)
    MAX-ACCESS read-write
    STATUS     current
    DESCRIPTION
            ""
    ::= { lcsSetupConfig 33 }

-- {SCALAR} 1.3.6.1.4.1.2356.11.2.11.34
lcsSetupConfigTelnetOperating OBJECT-TYPE
    SYNTAX     INTEGER {
                  eNo (0),
                  eYes (1)
            }
    MAX-ACCESS read-write
    STATUS     current
    DESCRIPTION
            "-- empty --"
    ::= { lcsSetupConfig 34 }

-- {NODE} 1.3.6.1.4.1.2356.11.2.11.35
lcsSetupConfigMonitortrace OBJECT IDENTIFIER ::= { lcsSetupConfig 35 }

-- {SCALAR} 1.3.6.1.4.1.2356.11.2.11.35.1
lcsSetupConfigMonitortraceTracemask1 OBJECT-TYPE
    SYNTAX     Integer32 (0..2147483647)
    MAX-ACCESS read-only
    STATUS     current
    DESCRIPTION
            ""
    ::= { lcsSetupConfigMonitortrace 1 }

-- {SCALAR} 1.3.6.1.4.1.2356.11.2.11.35.2
lcsSetupConfigMonitortraceTracemask2 OBJECT-TYPE
    SYNTAX     Integer32 (0..2147483647)
    MAX-ACCESS read-only
    STATUS     current
    DESCRIPTION
            ""
    ::= { lcsSetupConfigMonitortrace 2 }

-- {SCALAR} 1.3.6.1.4.1.2356.11.2.11.36
lcsSetupConfigTftpOperating OBJECT-TYPE
    SYNTAX     INTEGER {
                  eNo (0),
                  eYes (1),
                  eSysinfoOnly (2)
            }
    MAX-ACCESS read-write
    STATUS     current
    DESCRIPTION
            "-- empty --"
    ::= { lcsSetupConfig 36 }

-- {SCALAR} 1.3.6.1.4.1.2356.11.2.11.39
lcsSetupConfigLicenseExpiryEmail OBJECT-TYPE
    SYNTAX     DisplayString (SIZE(0..63))
    MAX-ACCESS read-write
    STATUS     current
    DESCRIPTION
            ""
    ::= { lcsSetupConfig 39 }

-- {SCALAR} 1.3.6.1.4.1.2356.11.2.11.40
lcsSetupConfigCrashMessage OBJECT-TYPE
    SYNTAX     DisplayString (SIZE(0..32))
    MAX-ACCESS read-write
    STATUS     current
    DESCRIPTION
            ""
    ::= { lcsSetupConfig 40 }

-- {SCALAR} 1.3.6.1.4.1.2356.11.2.11.41
lcsSetupConfigAdminGender OBJECT-TYPE
    SYNTAX     INTEGER {
                  eUnknown (0),
                  eMale (1),
                  eFemale (2),
                  eGeek (3)
            }
    MAX-ACCESS read-write
    STATUS     current
    DESCRIPTION
            ""
    ::= { lcsSetupConfig 41 }

-- {SCALAR} 1.3.6.1.4.1.2356.11.2.11.42
lcsSetupConfigAssertAction OBJECT-TYPE
    SYNTAX     INTEGER {
                  eLogOnly (0),
                  eReboot (1)
            }
    MAX-ACCESS read-write
    STATUS     current
    DESCRIPTION
            ""
    ::= { lcsSetupConfig 42 }

-- {TABLE} 1.3.6.1.4.1.2356.11.2.11.43
lcsSetupConfigFunctionKeysTable OBJECT-TYPE
    SYNTAX     SEQUENCE OF LcsSetupConfigFunctionKeysEntry
    MAX-ACCESS not-accessible
    STATUS     current
    DESCRIPTION
            ""
    ::= { lcsSetupConfig 43 }

-- {ROW} 1.3.6.1.4.1.2356.11.2.11.43.1
lcsSetupConfigFunctionKeysEntry OBJECT-TYPE
    SYNTAX     LcsSetupConfigFunctionKeysEntry
    MAX-ACCESS not-accessible
    STATUS     current
    DESCRIPTION
            ""
    INDEX {
            lcsSetupConfigFunctionKeysEntryKey
          }
    ::= { lcsSetupConfigFunctionKeysTable 1 }

LcsSetupConfigFunctionKeysEntry ::= SEQUENCE {
            lcsSetupConfigFunctionKeysEntryKey INTEGER,
            lcsSetupConfigFunctionKeysEntryMapping DisplayString
    }

-- {COLUMN} 1.3.6.1.4.1.2356.11.2.11.43.1.1
lcsSetupConfigFunctionKeysEntryKey OBJECT-TYPE
    SYNTAX     INTEGER {
                  eF1 (1),
                  eF2 (2),
                  eF3 (3),
                  eF4 (4),
                  eF5 (5),
                  eF6 (6),
                  eF7 (7),
                  eF8 (8),
                  eF9 (9),
                  eF10 (10),
                  eF11 (11),
                  eF12 (12)
            }
    MAX-ACCESS read-write
    STATUS     current
    DESCRIPTION
            ""
    ::= { lcsSetupConfigFunctionKeysEntry 1 }

-- {COLUMN} 1.3.6.1.4.1.2356.11.2.11.43.1.2
lcsSetupConfigFunctionKeysEntryMapping OBJECT-TYPE
    SYNTAX     DisplayString (SIZE(0..99))
    MAX-ACCESS read-write
    STATUS     current
    DESCRIPTION
            ""
    ::= { lcsSetupConfigFunctionKeysEntry 2 }

-- {SCALAR} 1.3.6.1.4.1.2356.11.2.11.44
lcsSetupConfigConfigDate OBJECT-TYPE
    SYNTAX     Integer32 (0..2147483647)
    MAX-ACCESS read-only
    STATUS     current
    DESCRIPTION
            ""
    ::= { lcsSetupConfig 44 }

-- {SCALAR} 1.3.6.1.4.1.2356.11.2.11.45
lcsSetupConfigConfigDateNew OBJECT-TYPE
    SYNTAX     Counter32
    MAX-ACCESS read-only
    STATUS     current
    DESCRIPTION
            ""
    ::= { lcsSetupConfig 45 }

-- {NODE} 1.3.6.1.4.1.2356.11.2.11.50
lcsSetupConfigLl2m OBJECT IDENTIFIER ::= { lcsSetupConfig 50 }

-- {SCALAR} 1.3.6.1.4.1.2356.11.2.11.50.1
lcsSetupConfigLl2mOperating OBJECT-TYPE
    SYNTAX     INTEGER {
                  eNo (0),
                  eYes (1)
            }
    MAX-ACCESS read-write
    STATUS     current
    DESCRIPTION
            ""
    ::= { lcsSetupConfigLl2m 1 }

-- {SCALAR} 1.3.6.1.4.1.2356.11.2.11.50.2
lcsSetupConfigLl2mTimeLimit OBJECT-TYPE
    SYNTAX     Integer32 (0..2147483647)
    MAX-ACCESS read-write
    STATUS     current
    DESCRIPTION
            ""
    ::= { lcsSetupConfigLl2m 2 }

-- {NODE} 1.3.6.1.4.1.2356.11.2.11.51
lcsSetupConfigSync OBJECT IDENTIFIER ::= { lcsSetupConfig 51 }

-- {SCALAR} 1.3.6.1.4.1.2356.11.2.11.51.1
lcsSetupConfigSyncOperating OBJECT-TYPE
    SYNTAX     INTEGER {
                  eNo (0),
                  eYes (1)
            }
    MAX-ACCESS read-write
    STATUS     current
    DESCRIPTION
            "-- empty --"
    ::= { lcsSetupConfigSync 1 }

-- {NODE} 1.3.6.1.4.1.2356.11.2.11.51.2
lcsSetupConfigSyncNewCluster OBJECT IDENTIFIER ::= { lcsSetupConfigSync 2 }

-- {SCALAR} 1.3.6.1.4.1.2356.11.2.11.51.2.1
lcsSetupConfigSyncNewClusterName OBJECT-TYPE
    SYNTAX     DisplayString (SIZE(0..254))
    MAX-ACCESS read-write
    STATUS     current
    DESCRIPTION
            "-- empty --"
    ::= { lcsSetupConfigSyncNewCluster 1 }

-- {TABLE} 1.3.6.1.4.1.2356.11.2.11.51.2.2
lcsSetupConfigSyncNewClusterGroupMembersTable OBJECT-TYPE
    SYNTAX     SEQUENCE OF LcsSetupConfigSyncNewClusterGroupMembersEntry
    MAX-ACCESS not-accessible
    STATUS     current
    DESCRIPTION
            "-- empty --"
    ::= { lcsSetupConfigSyncNewCluster 2 }

-- {ROW} 1.3.6.1.4.1.2356.11.2.11.51.2.2.1
lcsSetupConfigSyncNewClusterGroupMembersEntry OBJECT-TYPE
    SYNTAX     LcsSetupConfigSyncNewClusterGroupMembersEntry
    MAX-ACCESS not-accessible
    STATUS     current
    DESCRIPTION
            ""
    INDEX {
            lcsSetupConfigSyncNewClusterGroupMembersEntryIdx
          }
    ::= { lcsSetupConfigSyncNewClusterGroupMembersTable 1 }

LcsSetupConfigSyncNewClusterGroupMembersEntry ::= SEQUENCE {
            lcsSetupConfigSyncNewClusterGroupMembersEntryIdx Integer32,
            lcsSetupConfigSyncNewClusterGroupMembersEntryAddress DisplayString
    }

-- {COLUMN} 1.3.6.1.4.1.2356.11.2.11.51.2.2.1.1
lcsSetupConfigSyncNewClusterGroupMembersEntryIdx OBJECT-TYPE
    SYNTAX     Integer32 (0..65535)
    MAX-ACCESS read-write
    STATUS     current
    DESCRIPTION
            "-- empty --"
    ::= { lcsSetupConfigSyncNewClusterGroupMembersEntry 1 }

-- {COLUMN} 1.3.6.1.4.1.2356.11.2.11.51.2.2.1.2
lcsSetupConfigSyncNewClusterGroupMembersEntryAddress OBJECT-TYPE
    SYNTAX     DisplayString (SIZE(0..63))
    MAX-ACCESS read-write
    STATUS     current
    DESCRIPTION
            "-- empty --"
    ::= { lcsSetupConfigSyncNewClusterGroupMembersEntry 2 }

-- {TABLE} 1.3.6.1.4.1.2356.11.2.11.51.2.3
lcsSetupConfigSyncNewClusterMenuNodesTable OBJECT-TYPE
    SYNTAX     SEQUENCE OF LcsSetupConfigSyncNewClusterMenuNodesEntry
    MAX-ACCESS not-accessible
    STATUS     current
    DESCRIPTION
            "-- empty --"
    ::= { lcsSetupConfigSyncNewCluster 3 }

-- {ROW} 1.3.6.1.4.1.2356.11.2.11.51.2.3.1
lcsSetupConfigSyncNewClusterMenuNodesEntry OBJECT-TYPE
    SYNTAX     LcsSetupConfigSyncNewClusterMenuNodesEntry
    MAX-ACCESS not-accessible
    STATUS     current
    DESCRIPTION
            ""
    INDEX {
            lcsSetupConfigSyncNewClusterMenuNodesEntryIdx
          }
    ::= { lcsSetupConfigSyncNewClusterMenuNodesTable 1 }

LcsSetupConfigSyncNewClusterMenuNodesEntry ::= SEQUENCE {
            lcsSetupConfigSyncNewClusterMenuNodesEntryIdx Integer32,
            lcsSetupConfigSyncNewClusterMenuNodesEntryInclude INTEGER,
            lcsSetupConfigSyncNewClusterMenuNodesEntryPath DisplayString,
            lcsSetupConfigSyncNewClusterMenuNodesEntrySnmpOid DisplayString
    }

-- {COLUMN} 1.3.6.1.4.1.2356.11.2.11.51.2.3.1.1
lcsSetupConfigSyncNewClusterMenuNodesEntryIdx OBJECT-TYPE
    SYNTAX     Integer32 (0..65535)
    MAX-ACCESS read-write
    STATUS     current
    DESCRIPTION
            "-- empty --"
    ::= { lcsSetupConfigSyncNewClusterMenuNodesEntry 1 }

-- {COLUMN} 1.3.6.1.4.1.2356.11.2.11.51.2.3.1.2
lcsSetupConfigSyncNewClusterMenuNodesEntryInclude OBJECT-TYPE
    SYNTAX     INTEGER {
                  eExclude (0),
                  eInclude (1)
            }
    MAX-ACCESS read-write
    STATUS     current
    DESCRIPTION
            "-- empty --"
    ::= { lcsSetupConfigSyncNewClusterMenuNodesEntry 2 }

-- {COLUMN} 1.3.6.1.4.1.2356.11.2.11.51.2.3.1.3
lcsSetupConfigSyncNewClusterMenuNodesEntryPath OBJECT-TYPE
    SYNTAX     DisplayString (SIZE(0..127))
    MAX-ACCESS read-write
    STATUS     current
    DESCRIPTION
            "-- empty --"
    ::= { lcsSetupConfigSyncNewClusterMenuNodesEntry 3 }

-- {COLUMN} 1.3.6.1.4.1.2356.11.2.11.51.2.3.1.4
lcsSetupConfigSyncNewClusterMenuNodesEntrySnmpOid OBJECT-TYPE
    SYNTAX     DisplayString (SIZE(0..63))
    MAX-ACCESS read-only
    STATUS     current
    DESCRIPTION
            "-- empty --"
    ::= { lcsSetupConfigSyncNewClusterMenuNodesEntry 4 }

-- {TABLE} 1.3.6.1.4.1.2356.11.2.11.51.2.4
lcsSetupConfigSyncNewClusterIgnoredRowsTable OBJECT-TYPE
    SYNTAX     SEQUENCE OF LcsSetupConfigSyncNewClusterIgnoredRowsEntry
    MAX-ACCESS not-accessible
    STATUS     current
    DESCRIPTION
            "-- empty --"
    ::= { lcsSetupConfigSyncNewCluster 4 }

-- {ROW} 1.3.6.1.4.1.2356.11.2.11.51.2.4.1
lcsSetupConfigSyncNewClusterIgnoredRowsEntry OBJECT-TYPE
    SYNTAX     LcsSetupConfigSyncNewClusterIgnoredRowsEntry
    MAX-ACCESS not-accessible
    STATUS     current
    DESCRIPTION
            ""
    INDEX {
            lcsSetupConfigSyncNewClusterIgnoredRowsEntryIdx
          }
    ::= { lcsSetupConfigSyncNewClusterIgnoredRowsTable 1 }

LcsSetupConfigSyncNewClusterIgnoredRowsEntry ::= SEQUENCE {
            lcsSetupConfigSyncNewClusterIgnoredRowsEntryIdx Integer32,
            lcsSetupConfigSyncNewClusterIgnoredRowsEntryRowIndex DisplayString,
            lcsSetupConfigSyncNewClusterIgnoredRowsEntryPath DisplayString,
            lcsSetupConfigSyncNewClusterIgnoredRowsEntrySnmpOid DisplayString
    }

-- {COLUMN} 1.3.6.1.4.1.2356.11.2.11.51.2.4.1.1
lcsSetupConfigSyncNewClusterIgnoredRowsEntryIdx OBJECT-TYPE
    SYNTAX     Integer32 (0..65535)
    MAX-ACCESS read-write
    STATUS     current
    DESCRIPTION
            "-- empty --"
    ::= { lcsSetupConfigSyncNewClusterIgnoredRowsEntry 1 }

-- {COLUMN} 1.3.6.1.4.1.2356.11.2.11.51.2.4.1.2
lcsSetupConfigSyncNewClusterIgnoredRowsEntryRowIndex OBJECT-TYPE
    SYNTAX     DisplayString (SIZE(0..127))
    MAX-ACCESS read-write
    STATUS     current
    DESCRIPTION
            "-- empty --"
    ::= { lcsSetupConfigSyncNewClusterIgnoredRowsEntry 2 }

-- {COLUMN} 1.3.6.1.4.1.2356.11.2.11.51.2.4.1.3
lcsSetupConfigSyncNewClusterIgnoredRowsEntryPath OBJECT-TYPE
    SYNTAX     DisplayString (SIZE(0..127))
    MAX-ACCESS read-write
    STATUS     current
    DESCRIPTION
            "-- empty --"
    ::= { lcsSetupConfigSyncNewClusterIgnoredRowsEntry 3 }

-- {COLUMN} 1.3.6.1.4.1.2356.11.2.11.51.2.4.1.4
lcsSetupConfigSyncNewClusterIgnoredRowsEntrySnmpOid OBJECT-TYPE
    SYNTAX     DisplayString (SIZE(0..63))
    MAX-ACCESS read-only
    STATUS     current
    DESCRIPTION
            "-- empty --"
    ::= { lcsSetupConfigSyncNewClusterIgnoredRowsEntry 4 }

-- {SCALAR} 1.3.6.1.4.1.2356.11.2.11.51.2.5
lcsSetupConfigSyncNewClusterLaunch OBJECT-TYPE
    SYNTAX     DisplayString
    MAX-ACCESS read-write
    STATUS     current
    DESCRIPTION
            "-- empty --"
    ::= { lcsSetupConfigSyncNewCluster 5 }

-- {NODE} 1.3.6.1.4.1.2356.11.2.11.51.3
lcsSetupConfigSyncTlsConnections OBJECT IDENTIFIER ::= { lcsSetupConfigSync 3 }

-- {SCALAR} 1.3.6.1.4.1.2356.11.2.11.51.3.1
lcsSetupConfigSyncTlsConnectionsPort OBJECT-TYPE
    SYNTAX     Integer32 (0..65535)
    MAX-ACCESS read-write
    STATUS     current
    DESCRIPTION
            "-- empty --"
    ::= { lcsSetupConfigSyncTlsConnections 1 }

-- {SCALAR} 1.3.6.1.4.1.2356.11.2.11.51.3.2
lcsSetupConfigSyncTlsConnectionsLoopbackAddress OBJECT-TYPE
    SYNTAX     DisplayString (SIZE(0..39))
    MAX-ACCESS read-write
    STATUS     current
    DESCRIPTION
            "-- empty --"
    ::= { lcsSetupConfigSyncTlsConnections 2 }

-- {NODE} 1.3.6.1.4.1.2356.11.2.11.51.4
lcsSetupConfigSyncRenewSnapshot OBJECT IDENTIFIER ::= { lcsSetupConfigSync 4 }

-- {SCALAR} 1.3.6.1.4.1.2356.11.2.11.51.4.1
lcsSetupConfigSyncRenewSnapshotModificationLimit OBJECT-TYPE
    SYNTAX     Integer32 (0..2147483647)
    MAX-ACCESS read-write
    STATUS     current
    DESCRIPTION
            "-- empty --"
    ::= { lcsSetupConfigSyncRenewSnapshot 1 }

-- {SCALAR} 1.3.6.1.4.1.2356.11.2.11.51.4.2
lcsSetupConfigSyncRenewSnapshotKeptModifications OBJECT-TYPE
    SYNTAX     Integer32 (0..2147483647)
    MAX-ACCESS read-write
    STATUS     current
    DESCRIPTION
            "-- empty --"
    ::= { lcsSetupConfigSyncRenewSnapshot 2 }

-- {SCALAR} 1.3.6.1.4.1.2356.11.2.11.51.4.3
lcsSetupConfigSyncRenewSnapshotRenewSnapshot OBJECT-TYPE
    SYNTAX     DisplayString
    MAX-ACCESS read-write
    STATUS     current
    DESCRIPTION
            "-- empty --"
    ::= { lcsSetupConfigSyncRenewSnapshot 3 }

-- {NODE} 1.3.6.1.4.1.2356.11.2.11.51.5
lcsSetupConfigSyncLocalConfig OBJECT IDENTIFIER ::= { lcsSetupConfigSync 5 }

-- {SCALAR} 1.3.6.1.4.1.2356.11.2.11.51.5.1
lcsSetupConfigSyncLocalConfigDetectedModificationsTabSize OBJECT-TYPE
    SYNTAX     Integer32 (0..2147483647)
    MAX-ACCESS read-write
    STATUS     current
    DESCRIPTION
            "-- empty --"
    ::= { lcsSetupConfigSyncLocalConfig 1 }

-- {SCALAR} 1.3.6.1.4.1.2356.11.2.11.51.5.2
lcsSetupConfigSyncLocalConfigAppliedModificationsTabSize OBJECT-TYPE
    SYNTAX     Integer32 (0..2147483647)
    MAX-ACCESS read-write
    STATUS     current
    DESCRIPTION
            "-- empty --"
    ::= { lcsSetupConfigSyncLocalConfig 2 }

-- {NODE} 1.3.6.1.4.1.2356.11.2.11.55
lcsSetupConfigSslForCronTable OBJECT IDENTIFIER ::= { lcsSetupConfig 55 }

-- {SCALAR} 1.3.6.1.4.1.2356.11.2.11.55.1
lcsSetupConfigSslForCronTableVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupConfigSslForCronTable 1 }

-- {SCALAR} 1.3.6.1.4.1.2356.11.2.11.55.2
lcsSetupConfigSslForCronTableKeyexAlgorithms OBJECT-TYPE
    SYNTAX     BITS {
                  eEcdhe (27),
                  eDhe (29),
                  eRsa (31)
            }
    MAX-ACCESS read-write
    STATUS     current
    DESCRIPTION
            "-- empty --"
    ::= { lcsSetupConfigSslForCronTable 2 }

-- {SCALAR} 1.3.6.1.4.1.2356.11.2.11.55.3
lcsSetupConfigSslForCronTableCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupConfigSslForCronTable 3 }

-- {SCALAR} 1.3.6.1.4.1.2356.11.2.11.55.4
lcsSetupConfigSslForCronTableHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupConfigSslForCronTable 4 }

-- {SCALAR} 1.3.6.1.4.1.2356.11.2.11.55.5
lcsSetupConfigSslForCronTablePreferPfs OBJECT-TYPE
    SYNTAX     BITS {
                  eNo (0),
                  eYes (7)
            }
    MAX-ACCESS read-write
    STATUS     current
    DESCRIPTION
            "-- empty --"
    ::= { lcsSetupConfigSslForCronTable 5 }

-- {SCALAR} 1.3.6.1.4.1.2356.11.2.11.55.6
lcsSetupConfigSslForCronTableRenegotiations OBJECT-TYPE
    SYNTAX     INTEGER {
                  eForbidden (0),
                  eAllowed (1),
                  eIgnored (2)
            }
    MAX-ACCESS read-write
    STATUS     current
    DESCRIPTION
            "-- empty --"
    ::= { lcsSetupConfigSslForCronTable 6 }

-- {SCALAR} 1.3.6.1.4.1.2356.11.2.11.55.7
lcsSetupConfigSslForCronTableEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupConfigSslForCronTable 7 }

-- {SCALAR} 1.3.6.1.4.1.2356.11.2.11.55.21
lcsSetupConfigSslForCronTableSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupConfigSslForCronTable 21 }

-- {SCALAR} 1.3.6.1.4.1.2356.11.2.11.60
lcsSetupConfigCpuLoadInterval OBJECT-TYPE
    SYNTAX     INTEGER {
                  eT1s (1),
                  eT5s (5),
                  eT60s (60),
                  eT300s (300)
            }
    MAX-ACCESS read-write
    STATUS     current
    DESCRIPTION
            ""
    ::= { lcsSetupConfig 60 }

-- {SCALAR} 1.3.6.1.4.1.2356.11.2.11.65
lcsSetupConfigErrorAgingMinutes OBJECT-TYPE
    SYNTAX     Integer32 (0..255)
    MAX-ACCESS read-write
    STATUS     current
    DESCRIPTION
            "-- empty --"
    ::= { lcsSetupConfig 65 }

-- {SCALAR} 1.3.6.1.4.1.2356.11.2.11.70
lcsSetupConfigFirmwareCheck OBJECT-TYPE
    SYNTAX     INTEGER {
                  eOnlyCertified (0),
                  eAny (1)
            }
    MAX-ACCESS read-write
    STATUS     current
    DESCRIPTION
            "-- empty --"
    ::= { lcsSetupConfig 70 }

-- {SCALAR} 1.3.6.1.4.1.2356.11.2.11.71
lcsSetupConfigSaveBootlog OBJECT-TYPE
    SYNTAX     INTEGER {
                  eNo (0),
                  eYes (1)
            }
    MAX-ACCESS read-write
    STATUS     current
    DESCRIPTION
            "-- empty --"
    ::= { lcsSetupConfig 71 }

-- {SCALAR} 1.3.6.1.4.1.2356.11.2.11.72
lcsSetupConfigSaveEventlog OBJECT-TYPE
    SYNTAX     INTEGER {
                  eNo (0),
                  eYes (1)
            }
    MAX-ACCESS read-write
    STATUS     current
    DESCRIPTION
            "-- empty --"
    ::= { lcsSetupConfig 72 }

-- {SCALAR} 1.3.6.1.4.1.2356.11.2.11.73
lcsSetupConfigSortMenu OBJECT-TYPE
    SYNTAX     INTEGER {
                  eNo (0),
                  eYes (1)
            }
    MAX-ACCESS read-write
    STATUS     current
    DESCRIPTION
            "-- empty --"
    ::= { lcsSetupConfig 73 }

-- {SCALAR} 1.3.6.1.4.1.2356.11.2.11.80
lcsSetupConfigAuthentication OBJECT-TYPE
    SYNTAX     INTEGER {
                  eIntern (0),
                  eRadius (1),
                  eTacacsPlus (2)
            }
    MAX-ACCESS read-write
    STATUS     current
    DESCRIPTION
            "-- empty --"
    ::= { lcsSetupConfig 80 }

-- {NODE} 1.3.6.1.4.1.2356.11.2.11.81
lcsSetupConfigRadius OBJECT IDENTIFIER ::= { lcsSetupConfig 81 }

-- {TABLE} 1.3.6.1.4.1.2356.11.2.11.81.1
lcsSetupConfigRadiusServerTable OBJECT-TYPE
    SYNTAX     SEQUENCE OF LcsSetupConfigRadiusServerEntry
    MAX-ACCESS not-accessible
    STATUS     current
    DESCRIPTION
            "-- empty --"
    ::= { lcsSetupConfigRadius 1 }

-- {ROW} 1.3.6.1.4.1.2356.11.2.11.81.1.1
lcsSetupConfigRadiusServerEntry OBJECT-TYPE
    SYNTAX     LcsSetupConfigRadiusServerEntry
    MAX-ACCESS not-accessible
    STATUS     current
    DESCRIPTION
            ""
    INDEX {
            lcsSetupConfigRadiusServerEntryName
          }
    ::= { lcsSetupConfigRadiusServerTable 1 }

LcsSetupConfigRadiusServerEntry ::= SEQUENCE {
            lcsSetupConfigRadiusServerEntryName DisplayString,
            lcsSetupConfigRadiusServerEntryServer DisplayString,
            lcsSetupConfigRadiusServerEntryPort Integer32,
            lcsSetupConfigRadiusServerEntryProtocol INTEGER,
            lcsSetupConfigRadiusServerEntryLoopbackAddress DisplayString,
            lcsSetupConfigRadiusServerEntrySecret DisplayString,
            lcsSetupConfigRadiusServerEntryBackup DisplayString,
            lcsSetupConfigRadiusServerEntryCategory BITS,
            lcsSetupConfigRadiusServerEntryAttributeValues DisplayString
    }

-- {COLUMN} 1.3.6.1.4.1.2356.11.2.11.81.1.1.1
lcsSetupConfigRadiusServerEntryName OBJECT-TYPE
    SYNTAX     DisplayString (SIZE(0..16))
    MAX-ACCESS read-write
    STATUS     current
    DESCRIPTION
            "-- empty --"
    ::= { lcsSetupConfigRadiusServerEntry 1 }

-- {COLUMN} 1.3.6.1.4.1.2356.11.2.11.81.1.1.2
lcsSetupConfigRadiusServerEntryServer OBJECT-TYPE
    SYNTAX     DisplayString (SIZE(0..64))
    MAX-ACCESS read-write
    STATUS     current
    DESCRIPTION
            "-- empty --"
    ::= { lcsSetupConfigRadiusServerEntry 2 }

-- {COLUMN} 1.3.6.1.4.1.2356.11.2.11.81.1.1.3
lcsSetupConfigRadiusServerEntryPort OBJECT-TYPE
    SYNTAX     Integer32 (0..65535)
    MAX-ACCESS read-write
    STATUS     current
    DESCRIPTION
            "-- empty --"
    ::= { lcsSetupConfigRadiusServerEntry 3 }

-- {COLUMN} 1.3.6.1.4.1.2356.11.2.11.81.1.1.4
lcsSetupConfigRadiusServerEntryProtocol OBJECT-TYPE
    SYNTAX     INTEGER {
                  eRadius (0),
                  eRadsec (1)
            }
    MAX-ACCESS read-write
    STATUS     current
    DESCRIPTION
            "-- empty --"
    ::= { lcsSetupConfigRadiusServerEntry 4 }

-- {COLUMN} 1.3.6.1.4.1.2356.11.2.11.81.1.1.5
lcsSetupConfigRadiusServerEntryLoopbackAddress OBJECT-TYPE
    SYNTAX     DisplayString (SIZE(0..16))
    MAX-ACCESS read-write
    STATUS     current
    DESCRIPTION
            "-- empty --"
    ::= { lcsSetupConfigRadiusServerEntry 5 }

-- {COLUMN} 1.3.6.1.4.1.2356.11.2.11.81.1.1.6
lcsSetupConfigRadiusServerEntrySecret OBJECT-TYPE
    SYNTAX     DisplayString (SIZE(0..64))
    MAX-ACCESS read-write
    STATUS     current
    DESCRIPTION
            "-- empty --"
    ::= { lcsSetupConfigRadiusServerEntry 6 }

-- {COLUMN} 1.3.6.1.4.1.2356.11.2.11.81.1.1.7
lcsSetupConfigRadiusServerEntryBackup OBJECT-TYPE
    SYNTAX     DisplayString (SIZE(0..16))
    MAX-ACCESS read-write
    STATUS     current
    DESCRIPTION
            "-- empty --"
    ::= { lcsSetupConfigRadiusServerEntry 7 }

-- {COLUMN} 1.3.6.1.4.1.2356.11.2.11.81.1.1.8
lcsSetupConfigRadiusServerEntryCategory OBJECT-TYPE
    SYNTAX     BITS {
                  eAccounting (6),
                  eAuthentication (7)
            }
    MAX-ACCESS read-write
    STATUS     current
    DESCRIPTION
            "-- empty --"
    ::= { lcsSetupConfigRadiusServerEntry 8 }

-- {COLUMN} 1.3.6.1.4.1.2356.11.2.11.81.1.1.9
lcsSetupConfigRadiusServerEntryAttributeValues OBJECT-TYPE
    SYNTAX     DisplayString (SIZE(0..251))
    MAX-ACCESS read-write
    STATUS     current
    DESCRIPTION
            "-- empty --"
    ::= { lcsSetupConfigRadiusServerEntry 9 }

-- {SCALAR} 1.3.6.1.4.1.2356.11.2.11.81.2
lcsSetupConfigRadiusAccessRightsTransfer OBJECT-TYPE
    SYNTAX     INTEGER {
                  eVendorSpecific (0),
                  eMapped (1),
                  eShellPrivilege (2)
            }
    MAX-ACCESS read-write
    STATUS     current
    DESCRIPTION
            "-- empty --"
    ::= { lcsSetupConfigRadius 2 }

-- {SCALAR} 1.3.6.1.4.1.2356.11.2.11.81.3
lcsSetupConfigRadiusAccounting OBJECT-TYPE
    SYNTAX     INTEGER {
                  eNo (0),
                  eYes (1)
            }
    MAX-ACCESS read-write
    STATUS     current
    DESCRIPTION
            "-- empty --"
    ::= { lcsSetupConfigRadius 3 }

-- {SCALAR} 1.3.6.1.4.1.2356.11.2.11.90
lcsSetupConfigLedMode OBJECT-TYPE
    SYNTAX     INTEGER {
                  eOn (0),
                  eOff (1),
                  eTimedOff (2)
            }
    MAX-ACCESS read-write
    STATUS     current
    DESCRIPTION
            "-- empty --"
    ::= { lcsSetupConfig 90 }

-- {SCALAR} 1.3.6.1.4.1.2356.11.2.11.91
lcsSetupConfigLedOffSeconds OBJECT-TYPE
    SYNTAX     Integer32 (0..2147483647)
    MAX-ACCESS read-write
    STATUS     current
    DESCRIPTION
            "-- empty --"
    ::= { lcsSetupConfig 91 }

-- {NODE} 1.3.6.1.4.1.2356.11.2.11.92
lcsSetupConfigRolloutAgent OBJECT IDENTIFIER ::= { lcsSetupConfig 92 }

-- {SCALAR} 1.3.6.1.4.1.2356.11.2.11.92.1
lcsSetupConfigRolloutAgentOperating OBJECT-TYPE
    SYNTAX     INTEGER {
                  eNo (0),
                  eYes (1),
                  eDhcpInitiated (2)
            }
    MAX-ACCESS read-write
    STATUS     current
    DESCRIPTION
            "-- empty --"
    ::= { lcsSetupConfigRolloutAgent 1 }

-- {SCALAR} 1.3.6.1.4.1.2356.11.2.11.92.2
lcsSetupConfigRolloutAgentConfigServer OBJECT-TYPE
    SYNTAX     DisplayString (SIZE(0..255))
    MAX-ACCESS read-write
    STATUS     current
    DESCRIPTION
            "-- empty --"
    ::= { lcsSetupConfigRolloutAgent 2 }

-- {SCALAR} 1.3.6.1.4.1.2356.11.2.11.92.3
lcsSetupConfigRolloutAgentFirmwareServer OBJECT-TYPE
    SYNTAX     DisplayString (SIZE(0..255))
    MAX-ACCESS read-write
    STATUS     current
    DESCRIPTION
            "-- empty --"
    ::= { lcsSetupConfigRolloutAgent 3 }

-- {SCALAR} 1.3.6.1.4.1.2356.11.2.11.92.4
lcsSetupConfigRolloutAgentUsername OBJECT-TYPE
    SYNTAX     DisplayString (SIZE(0..255))
    MAX-ACCESS read-write
    STATUS     current
    DESCRIPTION
            "-- empty --"
    ::= { lcsSetupConfigRolloutAgent 4 }

-- {SCALAR} 1.3.6.1.4.1.2356.11.2.11.92.5
lcsSetupConfigRolloutAgentPassword OBJECT-TYPE
    SYNTAX     DisplayString (SIZE(0..255))
    MAX-ACCESS read-write
    STATUS     current
    DESCRIPTION
            "-- empty --"
    ::= { lcsSetupConfigRolloutAgent 5 }

-- {SCALAR} 1.3.6.1.4.1.2356.11.2.11.92.6
lcsSetupConfigRolloutAgentProjectNumber OBJECT-TYPE
    SYNTAX     DisplayString (SIZE(0..255))
    MAX-ACCESS read-write
    STATUS     current
    DESCRIPTION
            "-- empty --"
    ::= { lcsSetupConfigRolloutAgent 6 }

-- {SCALAR} 1.3.6.1.4.1.2356.11.2.11.92.7
lcsSetupConfigRolloutAgentAdditionalParameter OBJECT-TYPE
    SYNTAX     DisplayString (SIZE(0..255))
    MAX-ACCESS read-write
    STATUS     current
    DESCRIPTION
            "-- empty --"
    ::= { lcsSetupConfigRolloutAgent 7 }

-- {SCALAR} 1.3.6.1.4.1.2356.11.2.11.92.8
lcsSetupConfigRolloutAgentRebootTime OBJECT-TYPE
    SYNTAX     Integer32 (0..2147483647)
    MAX-ACCESS read-write
    STATUS     current
    DESCRIPTION
            "-- empty --"
    ::= { lcsSetupConfigRolloutAgent 8 }

-- {SCALAR} 1.3.6.1.4.1.2356.11.2.11.92.9
lcsSetupConfigRolloutAgentRequestInterval OBJECT-TYPE
    SYNTAX     Integer32 (0..2147483647)
    MAX-ACCESS read-write
    STATUS     current
    DESCRIPTION
            "-- empty --"
    ::= { lcsSetupConfigRolloutAgent 9 }

-- {SCALAR} 1.3.6.1.4.1.2356.11.2.11.92.10
lcsSetupConfigRolloutAgentTan OBJECT-TYPE
    SYNTAX     DisplayString (SIZE(0..255))
    MAX-ACCESS read-write
    STATUS     current
    DESCRIPTION
            "-- empty --"
    ::= { lcsSetupConfigRolloutAgent 10 }

-- {SCALAR} 1.3.6.1.4.1.2356.11.2.11.92.11
lcsSetupConfigRolloutAgentDeviceId OBJECT-TYPE
    SYNTAX     DisplayString (SIZE(0..255))
    MAX-ACCESS read-write
    STATUS     current
    DESCRIPTION
            "-- empty --"
    ::= { lcsSetupConfigRolloutAgent 11 }

-- {SCALAR} 1.3.6.1.4.1.2356.11.2.11.92.12
lcsSetupConfigRolloutAgentRequestDelay OBJECT-TYPE
    SYNTAX     Integer32 (0..2147483647)
    MAX-ACCESS read-write
    STATUS     current
    DESCRIPTION
            "-- empty --"
    ::= { lcsSetupConfigRolloutAgent 12 }

-- {SCALAR} 1.3.6.1.4.1.2356.11.2.11.92.13
lcsSetupConfigRolloutAgentRequestTimeRandom OBJECT-TYPE
    SYNTAX     INTEGER {
                  eNo (0),
                  eYes (1)
            }
    MAX-ACCESS read-write
    STATUS     current
    DESCRIPTION
            "-- empty --"
    ::= { lcsSetupConfigRolloutAgent 13 }

-- {SCALAR} 1.3.6.1.4.1.2356.11.2.11.92.14
lcsSetupConfigRolloutAgentOmitCertificateCheck OBJECT-TYPE
    SYNTAX     INTEGER {
                  eDefaultNo (0),
                  eNo (1),
                  eYes (2)
            }
    MAX-ACCESS read-write
    STATUS     current
    DESCRIPTION
            "-- empty --"
    ::= { lcsSetupConfigRolloutAgent 14 }

-- {NODE} 1.3.6.1.4.1.2356.11.2.11.92.15
lcsSetupConfigRolloutAgentSslNew OBJECT IDENTIFIER ::= { lcsSetupConfigRolloutAgent 15 }

-- {SCALAR} 1.3.6.1.4.1.2356.11.2.11.92.15.1
lcsSetupConfigRolloutAgentSslNewVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupConfigRolloutAgentSslNew 1 }

-- {SCALAR} 1.3.6.1.4.1.2356.11.2.11.92.15.2
lcsSetupConfigRolloutAgentSslNewKeyexAlgorithms OBJECT-TYPE
    SYNTAX     BITS {
                  eEcdhe (27),
                  eDhe (29),
                  eRsa (31)
            }
    MAX-ACCESS read-write
    STATUS     current
    DESCRIPTION
            "-- empty --"
    ::= { lcsSetupConfigRolloutAgentSslNew 2 }

-- {SCALAR} 1.3.6.1.4.1.2356.11.2.11.92.15.3
lcsSetupConfigRolloutAgentSslNewCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupConfigRolloutAgentSslNew 3 }

-- {SCALAR} 1.3.6.1.4.1.2356.11.2.11.92.15.4
lcsSetupConfigRolloutAgentSslNewHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupConfigRolloutAgentSslNew 4 }

-- {SCALAR} 1.3.6.1.4.1.2356.11.2.11.92.15.5
lcsSetupConfigRolloutAgentSslNewPreferPfs OBJECT-TYPE
    SYNTAX     BITS {
                  eNo (0),
                  eYes (7)
            }
    MAX-ACCESS read-write
    STATUS     current
    DESCRIPTION
            "-- empty --"
    ::= { lcsSetupConfigRolloutAgentSslNew 5 }

-- {SCALAR} 1.3.6.1.4.1.2356.11.2.11.92.15.6
lcsSetupConfigRolloutAgentSslNewRenegotiations OBJECT-TYPE
    SYNTAX     INTEGER {
                  eForbidden (0),
                  eAllowed (1),
                  eIgnored (2)
            }
    MAX-ACCESS read-write
    STATUS     current
    DESCRIPTION
            "-- empty --"
    ::= { lcsSetupConfigRolloutAgentSslNew 6 }

-- {SCALAR} 1.3.6.1.4.1.2356.11.2.11.92.15.7
lcsSetupConfigRolloutAgentSslNewEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupConfigRolloutAgentSslNew 7 }

-- {SCALAR} 1.3.6.1.4.1.2356.11.2.11.92.15.21
lcsSetupConfigRolloutAgentSslNewSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupConfigRolloutAgentSslNew 21 }

-- {SCALAR} 1.3.6.1.4.1.2356.11.2.11.92.16
lcsSetupConfigRolloutAgentUseOcsp OBJECT-TYPE
    SYNTAX     INTEGER {
                  eNo (0),
                  eYes (1)
            }
    MAX-ACCESS read-write
    STATUS     current
    DESCRIPTION
            "-- empty --"
    ::= { lcsSetupConfigRolloutAgent 16 }

-- {SCALAR} 1.3.6.1.4.1.2356.11.2.11.93
lcsSetupConfigEnforcePasswordRules OBJECT-TYPE
    SYNTAX     INTEGER {
                  eNo (0),
                  eYes (1)
            }
    MAX-ACCESS read-write
    STATUS     current
    DESCRIPTION
            "-- empty --"
    ::= { lcsSetupConfig 93 }

-- {TABLE} 1.3.6.1.4.1.2356.11.2.11.94
lcsSetupConfigDscpMarkingTable OBJECT-TYPE
    SYNTAX     SEQUENCE OF LcsSetupConfigDscpMarkingEntry
    MAX-ACCESS not-accessible
    STATUS     current
    DESCRIPTION
            "-- empty --"
    ::= { lcsSetupConfig 94 }

-- {ROW} 1.3.6.1.4.1.2356.11.2.11.94.1
lcsSetupConfigDscpMarkingEntry OBJECT-TYPE
    SYNTAX     LcsSetupConfigDscpMarkingEntry
    MAX-ACCESS not-accessible
    STATUS     current
    DESCRIPTION
            ""
    INDEX {
            lcsSetupConfigDscpMarkingEntryApplication
          }
    ::= { lcsSetupConfigDscpMarkingTable 1 }

LcsSetupConfigDscpMarkingEntry ::= SEQUENCE {
            lcsSetupConfigDscpMarkingEntryApplication INTEGER,
            lcsSetupConfigDscpMarkingEntryDscp INTEGER
    }

-- {COLUMN} 1.3.6.1.4.1.2356.11.2.11.94.1.1
lcsSetupConfigDscpMarkingEntryApplication OBJECT-TYPE
    SYNTAX     INTEGER {
                  eBgp (1),
                  eTftp (2),
                  eTacacsPlus (3),
                  eLisp (4),
                  eOspf (5),
                  eRip (6),
                  eIke (7),
                  eSnmp (10),
                  eL2tp (11),
                  ePptp (12),
                  eIcmp (13),
                  eIcmpv6 (14),
                  eIgmp (15),
                  eMld (16),
                  eNetflow (17),
                  ePim (18)
            }
    MAX-ACCESS read-only
    STATUS     current
    DESCRIPTION
            "-- empty --"
    ::= { lcsSetupConfigDscpMarkingEntry 1 }

-- {COLUMN} 1.3.6.1.4.1.2356.11.2.11.94.1.2
lcsSetupConfigDscpMarkingEntryDscp OBJECT-TYPE
    SYNTAX     INTEGER {
                  eBeCs0 (0),
                  eCs1 (32),
                  eAf11 (40),
                  eAf12 (48),
                  eAf13 (56),
                  eCs2 (64),
                  eAf21 (72),
                  eAf22 (80),
                  eAf23 (88),
                  eCs3 (96),
                  eAf31 (104),
                  eAf32 (112),
                  eAf33 (120),
                  eCs4 (128),
                  eAf41 (136),
                  eAf42 (144),
                  eAf43 (152),
                  eCs5 (160),
                  eEf (184),
                  eCs6 (192),
                  eCs7 (224)
            }
    MAX-ACCESS read-write
    STATUS     current
    DESCRIPTION
            "-- empty --"
    ::= { lcsSetupConfigDscpMarkingEntry 2 }

-- {SCALAR} 1.3.6.1.4.1.2356.11.2.11.95
lcsSetupConfigLedStrip OBJECT-TYPE
    SYNTAX     DisplayString (SIZE(0..6))
    MAX-ACCESS read-write
    STATUS     current
    DESCRIPTION
            "-- empty --"
    ::= { lcsSetupConfig 95 }

-- {NODE} 1.3.6.1.4.1.2356.11.2.12
lcsSetupWlan OBJECT IDENTIFIER ::= { lcsSetup 12 }

-- {SCALAR} 1.3.6.1.4.1.2356.11.2.12.3
lcsSetupWlanSpareHeap OBJECT-TYPE
    SYNTAX     Integer32 (0..65535)
    MAX-ACCESS read-write
    STATUS     current
    DESCRIPTION
            ""
    ::= { lcsSetupWlan 3 }

-- {TABLE} 1.3.6.1.4.1.2356.11.2.12.7
lcsSetupWlanAccessListTable OBJECT-TYPE
    SYNTAX     SEQUENCE OF LcsSetupWlanAccessListEntry
    MAX-ACCESS not-accessible
    STATUS     current
    DESCRIPTION
            ""
    ::= { lcsSetupWlan 7 }

-- {ROW} 1.3.6.1.4.1.2356.11.2.12.7.1
lcsSetupWlanAccessListEntry OBJECT-TYPE
    SYNTAX     LcsSetupWlanAccessListEntry
    MAX-ACCESS not-accessible
    STATUS     current
    DESCRIPTION
            ""
    INDEX {
            lcsSetupWlanAccessListEntryMacAddress
          }
    ::= { lcsSetupWlanAccessListTable 1 }

LcsSetupWlanAccessListEntry ::= SEQUENCE {
            lcsSetupWlanAccessListEntryMacAddress MacAddress,
            lcsSetupWlanAccessListEntryName DisplayString,
            lcsSetupWlanAccessListEntryComment DisplayString,
            lcsSetupWlanAccessListEntryWpaPassphrase DisplayString,
            lcsSetupWlanAccessListEntryTxLimit Integer32,
            lcsSetupWlanAccessListEntryRxLimit Integer32,
            lcsSetupWlanAccessListEntryVlanId Integer32
    }

-- {COLUMN} 1.3.6.1.4.1.2356.11.2.12.7.1.1
lcsSetupWlanAccessListEntryMacAddress OBJECT-TYPE
    SYNTAX     MacAddress
    MAX-ACCESS read-write
    STATUS     current
    DESCRIPTION
            ""
    ::= { lcsSetupWlanAccessListEntry 1 }

-- {COLUMN} 1.3.6.1.4.1.2356.11.2.12.7.1.2
lcsSetupWlanAccessListEntryName OBJECT-TYPE
    SYNTAX     DisplayString (SIZE(0..32))
    MAX-ACCESS read-write
    STATUS     current
    DESCRIPTION
            ""
    ::= { lcsSetupWlanAccessListEntry 2 }

-- {COLUMN} 1.3.6.1.4.1.2356.11.2.12.7.1.3
lcsSetupWlanAccessListEntryComment OBJECT-TYPE
    SYNTAX     DisplayString (SIZE(0..30))
    MAX-ACCESS read-write
    STATUS     current
    DESCRIPTION
            ""
    ::= { lcsSetupWlanAccessListEntry 3 }

-- {COLUMN} 1.3.6.1.4.1.2356.11.2.12.7.1.4
lcsSetupWlanAccessListEntryWpaPassphrase OBJECT-TYPE
    SYNTAX     DisplayString (SIZE(0..63))
    MAX-ACCESS read-write
    STATUS     current
    DESCRIPTION
            ""
    ::= { lcsSetupWlanAccessListEntry 4 }

-- {COLUMN} 1.3.6.1.4.1.2356.11.2.12.7.1.5
lcsSetupWlanAccessListEntryTxLimit OBJECT-TYPE
    SYNTAX     Integer32 (0..2147483647)
    MAX-ACCESS read-write
    STATUS     current
    DESCRIPTION
            ""
    ::= { lcsSetupWlanAccessListEntry 5 }

-- {COLUMN} 1.3.6.1.4.1.2356.11.2.12.7.1.6
lcsSetupWlanAccessListEntryRxLimit OBJECT-TYPE
    SYNTAX     Integer32 (0..2147483647)
    MAX-ACCESS read-write
    STATUS     current
    DESCRIPTION
            ""
    ::= { lcsSetupWlanAccessListEntry 6 }

-- {COLUMN} 1.3.6.1.4.1.2356.11.2.12.7.1.7
lcsSetupWlanAccessListEntryVlanId OBJECT-TYPE
    SYNTAX     Integer32 (0..65535)
    MAX-ACCESS read-write
    STATUS     current
    DESCRIPTION
            ""
    ::= { lcsSetupWlanAccessListEntry 7 }

-- {SCALAR} 1.3.6.1.4.1.2356.11.2.12.8
lcsSetupWlanAccessMode OBJECT-TYPE
    SYNTAX     INTEGER {
                  eNegative (0),
                  ePositive (1)
            }
    MAX-ACCESS read-write
    STATUS     current
    DESCRIPTION
            ""
    ::= { lcsSetupWlan 8 }

-- {SCALAR} 1.3.6.1.4.1.2356.11.2.12.12
lcsSetupWlanIappProtocol OBJECT-TYPE
    SYNTAX     INTEGER {
                  eNo (0),
                  eYes (1)
            }
    MAX-ACCESS read-write
    STATUS     current
    DESCRIPTION
            ""
    ::= { lcsSetupWlan 12 }

-- {SCALAR} 1.3.6.1.4.1.2356.11.2.12.13
lcsSetupWlanIappAnnounceInterval OBJECT-TYPE
    SYNTAX     Integer32 (0..65535)
    MAX-ACCESS read-write
    STATUS     current
    DESCRIPTION
            ""
    ::= { lcsSetupWlan 13 }

-- {SCALAR} 1.3.6.1.4.1.2356.11.2.12.14
lcsSetupWlanIappHandoverTimeout OBJECT-TYPE
    SYNTAX     Integer32 (0..65535)
    MAX-ACCESS read-write
    STATUS     current
    DESCRIPTION
            ""
    ::= { lcsSetupWlan 14 }

-- {SCALAR} 1.3.6.1.4.1.2356.11.2.12.26
lcsSetupWlanInterSsidTraffic OBJECT-TYPE
    SYNTAX     INTEGER {
                  eLocallyOff (0),
                  eYes (1),
                  eGloballyOff (2)
            }
    MAX-ACCESS read-write
    STATUS     current
    DESCRIPTION
            ""
    ::= { lcsSetupWlan 26 }

-- {SCALAR} 1.3.6.1.4.1.2356.11.2.12.27
lcsSetupWlanSuperviseStations OBJECT-TYPE
    SYNTAX     INTEGER {
                  eNo (0),
                  eYes (1)
            }
    MAX-ACCESS read-write
    STATUS     current
    DESCRIPTION
            ""
    ::= { lcsSetupWlan 27 }

-- {NODE} 1.3.6.1.4.1.2356.11.2.12.29
lcsSetupWlanRadiusAccessCheck OBJECT IDENTIFIER ::= { lcsSetupWlan 29 }

-- {SCALAR} 1.3.6.1.4.1.2356.11.2.12.29.1
lcsSetupWlanRadiusAccessCheckServerAddress OBJECT-TYPE
    SYNTAX     IpAddress
    MAX-ACCESS read-write
    STATUS     current
    DESCRIPTION
            ""
    ::= { lcsSetupWlanRadiusAccessCheck 1 }

-- {SCALAR} 1.3.6.1.4.1.2356.11.2.12.29.2
lcsSetupWlanRadiusAccessCheckAuthPort OBJECT-TYPE
    SYNTAX     Integer32 (0..65535)
    MAX-ACCESS read-write
    STATUS     current
    DESCRIPTION
            ""
    ::= { lcsSetupWlanRadiusAccessCheck 2 }

-- {SCALAR} 1.3.6.1.4.1.2356.11.2.12.29.3
lcsSetupWlanRadiusAccessCheckSecret OBJECT-TYPE
    SYNTAX     DisplayString (SIZE(0..64))
    MAX-ACCESS read-write
    STATUS     current
    DESCRIPTION
            ""
    ::= { lcsSetupWlanRadiusAccessCheck 3 }

-- {SCALAR} 1.3.6.1.4.1.2356.11.2.12.29.4
lcsSetupWlanRadiusAccessCheckBackupServerIpAddress OBJECT-TYPE
    SYNTAX     IpAddress
    MAX-ACCESS read-write
    STATUS     current
    DESCRIPTION
            ""
    ::= { lcsSetupWlanRadiusAccessCheck 4 }

-- {SCALAR} 1.3.6.1.4.1.2356.11.2.12.29.5
lcsSetupWlanRadiusAccessCheckBackupAuthPort OBJECT-TYPE
    SYNTAX     Integer32 (0..65535)
    MAX-ACCESS read-write
    STATUS     current
    DESCRIPTION
            ""
    ::= { lcsSetupWlanRadiusAccessCheck 5 }

-- {SCALAR} 1.3.6.1.4.1.2356.11.2.12.29.6
lcsSetupWlanRadiusAccessCheckBackupSecret OBJECT-TYPE
    SYNTAX     DisplayString (SIZE(0..64))
    MAX-ACCESS read-write
    STATUS     current
    DESCRIPTION
            ""
    ::= { lcsSetupWlanRadiusAccessCheck 6 }

-- {SCALAR} 1.3.6.1.4.1.2356.11.2.12.29.7
lcsSetupWlanRadiusAccessCheckResponseLifetime OBJECT-TYPE
    SYNTAX     Integer32 (0..2147483647)
    MAX-ACCESS read-write
    STATUS     current
    DESCRIPTION
            ""
    ::= { lcsSetupWlanRadiusAccessCheck 7 }

-- {SCALAR} 1.3.6.1.4.1.2356.11.2.12.29.8
lcsSetupWlanRadiusAccessCheckPasswordSource OBJECT-TYPE
    SYNTAX     INTEGER {
                  eSecret (0),
                  eMacAddress (1)
            }
    MAX-ACCESS read-write
    STATUS     current
    DESCRIPTION
            ""
    ::= { lcsSetupWlanRadiusAccessCheck 8 }

-- {SCALAR} 1.3.6.1.4.1.2356.11.2.12.29.9
lcsSetupWlanRadiusAccessCheckRecheckCycle OBJECT-TYPE
    SYNTAX     Integer32 (0..2147483647)
    MAX-ACCESS read-write
    STATUS     current
    DESCRIPTION
            ""
    ::= { lcsSetupWlanRadiusAccessCheck 9 }

-- {SCALAR} 1.3.6.1.4.1.2356.11.2.12.29.10
lcsSetupWlanRadiusAccessCheckProvideServerDatabase OBJECT-TYPE
    SYNTAX     INTEGER {
                  eNo (0),
                  eYes (1)
            }
    MAX-ACCESS read-write
    STATUS     current
    DESCRIPTION
            ""
    ::= { lcsSetupWlanRadiusAccessCheck 10 }

-- {SCALAR} 1.3.6.1.4.1.2356.11.2.12.29.11
lcsSetupWlanRadiusAccessCheckLoopbackAddress OBJECT-TYPE
    SYNTAX     DisplayString (SIZE(0..16))
    MAX-ACCESS read-write
    STATUS     current
    DESCRIPTION
            ""
    ::= { lcsSetupWlanRadiusAccessCheck 11 }

-- {SCALAR} 1.3.6.1.4.1.2356.11.2.12.29.12
lcsSetupWlanRadiusAccessCheckBackupLoopbackAddress OBJECT-TYPE
    SYNTAX     DisplayString (SIZE(0..16))
    MAX-ACCESS read-write
    STATUS     current
    DESCRIPTION
            ""
    ::= { lcsSetupWlanRadiusAccessCheck 12 }

-- {SCALAR} 1.3.6.1.4.1.2356.11.2.12.29.13
lcsSetupWlanRadiusAccessCheckProtocol OBJECT-TYPE
    SYNTAX     INTEGER {
                  eRadius (0),
                  eRadsec (1)
            }
    MAX-ACCESS read-write
    STATUS     current
    DESCRIPTION
            ""
    ::= { lcsSetupWlanRadiusAccessCheck 13 }

-- {SCALAR} 1.3.6.1.4.1.2356.11.2.12.29.14
lcsSetupWlanRadiusAccessCheckBackupProtocol OBJECT-TYPE
    SYNTAX     INTEGER {
                  eRadius (0),
                  eRadsec (1)
            }
    MAX-ACCESS read-write
    STATUS     current
    DESCRIPTION
            ""
    ::= { lcsSetupWlanRadiusAccessCheck 14 }

-- {SCALAR} 1.3.6.1.4.1.2356.11.2.12.29.15
lcsSetupWlanRadiusAccessCheckForceRecheck OBJECT-TYPE
    SYNTAX     DisplayString
    MAX-ACCESS read-write
    STATUS     current
    DESCRIPTION
            "-- empty --"
    ::= { lcsSetupWlanRadiusAccessCheck 15 }

-- {SCALAR} 1.3.6.1.4.1.2356.11.2.12.29.16
lcsSetupWlanRadiusAccessCheckServerHostname OBJECT-TYPE
    SYNTAX     DisplayString (SIZE(0..64))
    MAX-ACCESS read-write
    STATUS     current
    DESCRIPTION
            "-- empty --"
    ::= { lcsSetupWlanRadiusAccessCheck 16 }

-- {SCALAR} 1.3.6.1.4.1.2356.11.2.12.29.17
lcsSetupWlanRadiusAccessCheckBackupServerHostname OBJECT-TYPE
    SYNTAX     DisplayString (SIZE(0..64))
    MAX-ACCESS read-write
    STATUS     current
    DESCRIPTION
            "-- empty --"
    ::= { lcsSetupWlanRadiusAccessCheck 17 }

-- {SCALAR} 1.3.6.1.4.1.2356.11.2.12.29.18
lcsSetupWlanRadiusAccessCheckAttributeValues OBJECT-TYPE
    SYNTAX     DisplayString (SIZE(0..251))
    MAX-ACCESS read-write
    STATUS     current
    DESCRIPTION
            "-- empty --"
    ::= { lcsSetupWlanRadiusAccessCheck 18 }

-- {SCALAR} 1.3.6.1.4.1.2356.11.2.12.29.19
lcsSetupWlanRadiusAccessCheckBackupAttributeValues OBJECT-TYPE
    SYNTAX     DisplayString (SIZE(0..251))
    MAX-ACCESS read-write
    STATUS     current
    DESCRIPTION
            "-- empty --"
    ::= { lcsSetupWlanRadiusAccessCheck 19 }

-- {SCALAR} 1.3.6.1.4.1.2356.11.2.12.29.20
lcsSetupWlanRadiusAccessCheckUsernameAttributeFormat OBJECT-TYPE
    SYNTAX     DisplayString (SIZE(0..30))
    MAX-ACCESS read-write
    STATUS     current
    DESCRIPTION
            "-- empty --"
    ::= { lcsSetupWlanRadiusAccessCheck 20 }

-- {SCALAR} 1.3.6.1.4.1.2356.11.2.12.36
lcsSetupWlanCountry OBJECT-TYPE
    SYNTAX     INTEGER {
                  eUnknown (0),
                  eAlbania (8),
                  eAlgeria (12),
                  eArgentina (32),
                  eAustralia (36),
                  eAustria (40),
                  eBahrain (48),
                  eBangladesh (50),
                  eBelgium (56),
                  eBosniaHerzegovina (70),
                  eBrazil (76),
                  eBruneiDarussalam (96),
                  eBulgaria (100),
                  eBelarus (112),
                  eCanada (124),
                  eChile (152),
                  eChina (156),
                  eTaiwan (158),
                  eColombia (170),
                  eCostaRica (188),
                  eCroatia (191),
                  eCyprus (196),
                  eCzech (203),
                  eDenmark (208),
                  eEcuador (218),
                  eEstonia (233),
                  eFinland (246),
                  eFrance (250),
                  eGermany (276),
                  eGhana (288),
                  eGreece (300),
                  eGuatemala (320),
                  eHonduras (340),
                  eHongKong (344),
                  eHungary (348),
                  eIceland (352),
                  eIndia (356),
                  eIndonesia (360),
                  eIreland (372),
                  eIsrael (376),
                  eItaly (380),
                  eJapan (392),
                  eJordan (400),
                  eSouthKorea (410),
                  eKuwait (414),
                  eLebanon (422),
                  eLatvia (428),
                  eLiechtenstein (438),
                  eLithuania (440),
                  eLuxembourg (442),
                  eMacau (446),
                  eMalaysia (458),
                  eMalta (470),
                  eMexico (484),
                  eMoldavia (498),
                  eMorocco (504),
                  eOman (512),
                  eNetherlands (528),
                  eNewZealand (554),
                  eNicaragua (558),
                  eNorway (578),
                  ePakistan (586),
                  ePanama (591),
                  eParaguay (600),
                  ePeru (604),
                  ePhilippines (608),
                  ePoland (616),
                  ePortugal (620),
                  ePuertoRico (630),
                  eQatar (634),
                  eRomania (642),
                  eRussia (643),
                  eSaudiArabia (682),
                  eSingapore (702),
                  eSlovak (703),
                  eSlovenia (705),
                  eSouthAfrica (710),
                  eSpain (724),
                  eSweden (752),
                  eSwitzerland (756),
                  eThailand (764),
                  eUnitedArabEmirates (784),
                  eTunisia (788),
                  eTurkey (792),
                  eUganda (800),
                  eUkraine (804),
                  eMacedonia (807),
                  eEgypt (818),
                  eUnitedKingdom (826),
                  eTanzania (834),
                  eUnitedStatesFcc (840),
                  eUruguay (858),
                  eVenezuela (862),
                  eEurope (998),
                  eEgalistan (999)
            }
    MAX-ACCESS read-write
    STATUS     current
    DESCRIPTION
            ""
    ::= { lcsSetupWlan 36 }

-- {SCALAR} 1.3.6.1.4.1.2356.11.2.12.38
lcsSetupWlanArpHandling OBJECT-TYPE
    SYNTAX     INTEGER {
                  eNo (0),
                  eYes (1)
            }
    MAX-ACCESS read-write
    STATUS     current
    DESCRIPTION
            ""
    ::= { lcsSetupWlan 38 }

-- {SCALAR} 1.3.6.1.4.1.2356.11.2.12.41
lcsSetupWlanMailAddress OBJECT-TYPE
    SYNTAX     DisplayString (SIZE(0..254))
    MAX-ACCESS read-write
    STATUS     current
    DESCRIPTION
            ""
    ::= { lcsSetupWlan 41 }

-- {SCALAR} 1.3.6.1.4.1.2356.11.2.12.44
lcsSetupWlanAllowIllegalAssociationWithoutAuthentication OBJECT-TYPE
    SYNTAX     INTEGER {
                  eNo (0),
                  eYes (1)
            }
    MAX-ACCESS read-write
    STATUS     current
    DESCRIPTION
            ""
    ::= { lcsSetupWlan 44 }

-- {NODE} 1.3.6.1.4.1.2356.11.2.12.45
lcsSetupWlanRadiusAccounting OBJECT IDENTIFIER ::= { lcsSetupWlan 45 }

-- {SCALAR} 1.3.6.1.4.1.2356.11.2.12.45.1
lcsSetupWlanRadiusAccountingServerAddress OBJECT-TYPE
    SYNTAX     IpAddress
    MAX-ACCESS read-write
    STATUS     current
    DESCRIPTION
            ""
    ::= { lcsSetupWlanRadiusAccounting 1 }

-- {SCALAR} 1.3.6.1.4.1.2356.11.2.12.45.2
lcsSetupWlanRadiusAccountingAccntPort OBJECT-TYPE
    SYNTAX     Integer32 (0..65535)
    MAX-ACCESS read-write
    STATUS     current
    DESCRIPTION
            ""
    ::= { lcsSetupWlanRadiusAccounting 2 }

-- {SCALAR} 1.3.6.1.4.1.2356.11.2.12.45.3
lcsSetupWlanRadiusAccountingSecret OBJECT-TYPE
    SYNTAX     DisplayString (SIZE(0..64))
    MAX-ACCESS read-write
    STATUS     current
    DESCRIPTION
            ""
    ::= { lcsSetupWlanRadiusAccounting 3 }

-- {SCALAR} 1.3.6.1.4.1.2356.11.2.12.45.4
lcsSetupWlanRadiusAccountingBackupServerIpAddress OBJECT-TYPE
    SYNTAX     IpAddress
    MAX-ACCESS read-write
    STATUS     current
    DESCRIPTION
            ""
    ::= { lcsSetupWlanRadiusAccounting 4 }

-- {SCALAR} 1.3.6.1.4.1.2356.11.2.12.45.5
lcsSetupWlanRadiusAccountingBackupAccntPort OBJECT-TYPE
    SYNTAX     Integer32 (0..65535)
    MAX-ACCESS read-write
    STATUS     current
    DESCRIPTION
            ""
    ::= { lcsSetupWlanRadiusAccounting 5 }

-- {SCALAR} 1.3.6.1.4.1.2356.11.2.12.45.6
lcsSetupWlanRadiusAccountingBackupSecret OBJECT-TYPE
    SYNTAX     DisplayString (SIZE(0..64))
    MAX-ACCESS read-write
    STATUS     current
    DESCRIPTION
            ""
    ::= { lcsSetupWlanRadiusAccounting 6 }

-- {SCALAR} 1.3.6.1.4.1.2356.11.2.12.45.7
lcsSetupWlanRadiusAccountingClientBrgHandling OBJECT-TYPE
    SYNTAX     INTEGER {
                  eAllTraffic (0),
                  eBridgeTrafficOnly (1),
                  eClientTrafficOnly (2),
                  eSeparateAccounting (3)
            }
    MAX-ACCESS read-write
    STATUS     current
    DESCRIPTION
            ""
    ::= { lcsSetupWlanRadiusAccounting 7 }

-- {SCALAR} 1.3.6.1.4.1.2356.11.2.12.45.8
lcsSetupWlanRadiusAccountingInterimUpdatePeriod OBJECT-TYPE
    SYNTAX     Integer32 (0..2147483647)
    MAX-ACCESS read-write
    STATUS     current
    DESCRIPTION
            ""
    ::= { lcsSetupWlanRadiusAccounting 8 }

-- {SCALAR} 1.3.6.1.4.1.2356.11.2.12.45.9
lcsSetupWlanRadiusAccountingExcludedVlan OBJECT-TYPE
    SYNTAX     Integer32 (0..65535)
    MAX-ACCESS read-write
    STATUS     current
    DESCRIPTION
            ""
    ::= { lcsSetupWlanRadiusAccounting 9 }

-- {SCALAR} 1.3.6.1.4.1.2356.11.2.12.45.10
lcsSetupWlanRadiusAccountingLoopbackAddress OBJECT-TYPE
    SYNTAX     DisplayString (SIZE(0..16))
    MAX-ACCESS read-write
    STATUS     current
    DESCRIPTION
            ""
    ::= { lcsSetupWlanRadiusAccounting 10 }

-- {SCALAR} 1.3.6.1.4.1.2356.11.2.12.45.11
lcsSetupWlanRadiusAccountingBackupLoopbackAddress OBJECT-TYPE
    SYNTAX     DisplayString (SIZE(0..16))
    MAX-ACCESS read-write
    STATUS     current
    DESCRIPTION
            ""
    ::= { lcsSetupWlanRadiusAccounting 11 }

-- {SCALAR} 1.3.6.1.4.1.2356.11.2.12.45.12
lcsSetupWlanRadiusAccountingProtocol OBJECT-TYPE
    SYNTAX     INTEGER {
                  eRadius (0),
                  eRadsec (1)
            }
    MAX-ACCESS read-write
    STATUS     current
    DESCRIPTION
            ""
    ::= { lcsSetupWlanRadiusAccounting 12 }

-- {SCALAR} 1.3.6.1.4.1.2356.11.2.12.45.13
lcsSetupWlanRadiusAccountingBackupProtocol OBJECT-TYPE
    SYNTAX     INTEGER {
                  eRadius (0),
                  eRadsec (1)
            }
    MAX-ACCESS read-write
    STATUS     current
    DESCRIPTION
            ""
    ::= { lcsSetupWlanRadiusAccounting 13 }

-- {SCALAR} 1.3.6.1.4.1.2356.11.2.12.45.14
lcsSetupWlanRadiusAccountingRestartAccounting OBJECT-TYPE
    SYNTAX     DisplayString
    MAX-ACCESS read-write
    STATUS     current
    DESCRIPTION
            ""
    ::= { lcsSetupWlanRadiusAccounting 14 }

-- {TABLE} 1.3.6.1.4.1.2356.11.2.12.45.17
lcsSetupWlanRadiusAccountingServersTable OBJECT-TYPE
    SYNTAX     SEQUENCE OF LcsSetupWlanRadiusAccountingServersEntry
    MAX-ACCESS not-accessible
    STATUS     current
    DESCRIPTION
            "-- empty --"
    ::= { lcsSetupWlanRadiusAccounting 17 }

-- {ROW} 1.3.6.1.4.1.2356.11.2.12.45.17.1
lcsSetupWlanRadiusAccountingServersEntry OBJECT-TYPE
    SYNTAX     LcsSetupWlanRadiusAccountingServersEntry
    MAX-ACCESS not-accessible
    STATUS     current
    DESCRIPTION
            ""
    INDEX {
            lcsSetupWlanRadiusAccountingServersEntryName
          }
    ::= { lcsSetupWlanRadiusAccountingServersTable 1 }

LcsSetupWlanRadiusAccountingServersEntry ::= SEQUENCE {
            lcsSetupWlanRadiusAccountingServersEntryName DisplayString,
            lcsSetupWlanRadiusAccountingServersEntryServerAddress IpAddress,
            lcsSetupWlanRadiusAccountingServersEntryPort Integer32,
            lcsSetupWlanRadiusAccountingServersEntrySecret DisplayString,
            lcsSetupWlanRadiusAccountingServersEntryLoopbackAddr DisplayString,
            lcsSetupWlanRadiusAccountingServersEntryProtocol INTEGER,
            lcsSetupWlanRadiusAccountingServersEntryBackup DisplayString,
            lcsSetupWlanRadiusAccountingServersEntryHostName DisplayString,
            lcsSetupWlanRadiusAccountingServersEntryAttributeValues DisplayString
    }

-- {COLUMN} 1.3.6.1.4.1.2356.11.2.12.45.17.1.1
lcsSetupWlanRadiusAccountingServersEntryName OBJECT-TYPE
    SYNTAX     DisplayString (SIZE(0..16))
    MAX-ACCESS read-write
    STATUS     current
    DESCRIPTION
            "-- empty --"
    ::= { lcsSetupWlanRadiusAccountingServersEntry 1 }

-- {COLUMN} 1.3.6.1.4.1.2356.11.2.12.45.17.1.2
lcsSetupWlanRadiusAccountingServersEntryServerAddress OBJECT-TYPE
    SYNTAX     IpAddress
    MAX-ACCESS read-write
    STATUS     current
    DESCRIPTION
            "-- empty --"
    ::= { lcsSetupWlanRadiusAccountingServersEntry 2 }

-- {COLUMN} 1.3.6.1.4.1.2356.11.2.12.45.17.1.3
lcsSetupWlanRadiusAccountingServersEntryPort OBJECT-TYPE
    SYNTAX     Integer32 (0..65535)
    MAX-ACCESS read-write
    STATUS     current
    DESCRIPTION
            "-- empty --"
    ::= { lcsSetupWlanRadiusAccountingServersEntry 3 }

-- {COLUMN} 1.3.6.1.4.1.2356.11.2.12.45.17.1.4
lcsSetupWlanRadiusAccountingServersEntrySecret OBJECT-TYPE
    SYNTAX     DisplayString (SIZE(0..64))
    MAX-ACCESS read-write
    STATUS     current
    DESCRIPTION
            "-- empty --"
    ::= { lcsSetupWlanRadiusAccountingServersEntry 4 }

-- {COLUMN} 1.3.6.1.4.1.2356.11.2.12.45.17.1.5
lcsSetupWlanRadiusAccountingServersEntryLoopbackAddr OBJECT-TYPE
    SYNTAX     DisplayString (SIZE(0..16))
    MAX-ACCESS read-write
    STATUS     current
    DESCRIPTION
            "-- empty --"
    ::= { lcsSetupWlanRadiusAccountingServersEntry 5 }

-- {COLUMN} 1.3.6.1.4.1.2356.11.2.12.45.17.1.6
lcsSetupWlanRadiusAccountingServersEntryProtocol OBJECT-TYPE
    SYNTAX     INTEGER {
                  eRadius (0),
                  eRadsec (1)
            }
    MAX-ACCESS read-write
    STATUS     current
    DESCRIPTION
            "-- empty --"
    ::= { lcsSetupWlanRadiusAccountingServersEntry 6 }

-- {COLUMN} 1.3.6.1.4.1.2356.11.2.12.45.17.1.7
lcsSetupWlanRadiusAccountingServersEntryBackup OBJECT-TYPE
    SYNTAX     DisplayString (SIZE(0..16))
    MAX-ACCESS read-write
    STATUS     current
    DESCRIPTION
            "-- empty --"
    ::= { lcsSetupWlanRadiusAccountingServersEntry 7 }

-- {COLUMN} 1.3.6.1.4.1.2356.11.2.12.45.17.1.8
lcsSetupWlanRadiusAccountingServersEntryHostName OBJECT-TYPE
    SYNTAX     DisplayString (SIZE(0..64))
    MAX-ACCESS read-write
    STATUS     current
    DESCRIPTION
            "-- empty --"
    ::= { lcsSetupWlanRadiusAccountingServersEntry 8 }

-- {COLUMN} 1.3.6.1.4.1.2356.11.2.12.45.17.1.9
lcsSetupWlanRadiusAccountingServersEntryAttributeValues OBJECT-TYPE
    SYNTAX     DisplayString (SIZE(0..251))
    MAX-ACCESS read-write
    STATUS     current
    DESCRIPTION
            "-- empty --"
    ::= { lcsSetupWlanRadiusAccountingServersEntry 9 }

-- {SCALAR} 1.3.6.1.4.1.2356.11.2.12.46
lcsSetupWlanIndoorOnlyOperation OBJECT-TYPE
    SYNTAX     INTEGER {
                  eNo (0),
                  eYes (1)
            }
    MAX-ACCESS read-write
    STATUS     current
    DESCRIPTION
            ""
    ::= { lcsSetupWlan 46 }

-- {SCALAR} 1.3.6.1.4.1.2356.11.2.12.47
lcsSetupWlanIdleTimeout OBJECT-TYPE
    SYNTAX     Integer32 (0..2147483647)
    MAX-ACCESS read-write
    STATUS     current
    DESCRIPTION
            ""
    ::= { lcsSetupWlan 47 }

-- {SCALAR} 1.3.6.1.4.1.2356.11.2.12.48
lcsSetupWlanUseFullChannelset OBJECT-TYPE
    SYNTAX     INTEGER {
                  eNo (0),
                  eYes (1)
            }
    MAX-ACCESS read-write
    STATUS     current
    DESCRIPTION
            ""
    ::= { lcsSetupWlan 48 }

-- {NODE} 1.3.6.1.4.1.2356.11.2.12.50
lcsSetupWlanSigAvrg OBJECT IDENTIFIER ::= { lcsSetupWlan 50 }

-- {SCALAR} 1.3.6.1.4.1.2356.11.2.12.50.1
lcsSetupWlanSigAvrgMeth OBJECT-TYPE
    SYNTAX     INTEGER {
                  eStd (0),
                  eFilt (1)
            }
    MAX-ACCESS read-write
    STATUS     current
    DESCRIPTION
            ""
    ::= { lcsSetupWlanSigAvrg 1 }

-- {NODE} 1.3.6.1.4.1.2356.11.2.12.50.2
lcsSetupWlanSigAvrgStdParams OBJECT IDENTIFIER ::= { lcsSetupWlanSigAvrg 2 }

-- {SCALAR} 1.3.6.1.4.1.2356.11.2.12.50.2.1
lcsSetupWlanSigAvrgStdParamsFactor OBJECT-TYPE
    SYNTAX     Integer32 (0..255)
    MAX-ACCESS read-write
    STATUS     current
    DESCRIPTION
            ""
    ::= { lcsSetupWlanSigAvrgStdParams 1 }

-- {NODE} 1.3.6.1.4.1.2356.11.2.12.50.3
lcsSetupWlanSigAvrgFiltParms OBJECT IDENTIFIER ::= { lcsSetupWlanSigAvrg 3 }

-- {SCALAR} 1.3.6.1.4.1.2356.11.2.12.50.3.1
lcsSetupWlanSigAvrgFiltParmsCt OBJECT-TYPE
    SYNTAX     Integer32 (0..2147483647)
    MAX-ACCESS read-write
    STATUS     current
    DESCRIPTION
            ""
    ::= { lcsSetupWlanSigAvrgFiltParms 1 }

-- {TABLE} 1.3.6.1.4.1.2356.11.2.12.50.3.2
lcsSetupWlanSigAvrgFiltParmsCoeffTable OBJECT-TYPE
    SYNTAX     SEQUENCE OF LcsSetupWlanSigAvrgFiltParmsCoeffEntry
    MAX-ACCESS not-accessible
    STATUS     current
    DESCRIPTION
            ""
    ::= { lcsSetupWlanSigAvrgFiltParms 2 }

-- {ROW} 1.3.6.1.4.1.2356.11.2.12.50.3.2.1
lcsSetupWlanSigAvrgFiltParmsCoeffEntry OBJECT-TYPE
    SYNTAX     LcsSetupWlanSigAvrgFiltParmsCoeffEntry
    MAX-ACCESS not-accessible
    STATUS     current
    DESCRIPTION
            ""
    INDEX {
            lcsSetupWlanSigAvrgFiltParmsCoeffEntryIdx
          }
    ::= { lcsSetupWlanSigAvrgFiltParmsCoeffTable 1 }

LcsSetupWlanSigAvrgFiltParmsCoeffEntry ::= SEQUENCE {
            lcsSetupWlanSigAvrgFiltParmsCoeffEntryIdx Integer32,
            lcsSetupWlanSigAvrgFiltParmsCoeffEntryVal Integer32
    }

-- {COLUMN} 1.3.6.1.4.1.2356.11.2.12.50.3.2.1.1
lcsSetupWlanSigAvrgFiltParmsCoeffEntryIdx OBJECT-TYPE
    SYNTAX     Integer32 (0..255)
    MAX-ACCESS read-only
    STATUS     current
    DESCRIPTION
            ""
    ::= { lcsSetupWlanSigAvrgFiltParmsCoeffEntry 1 }

-- {COLUMN} 1.3.6.1.4.1.2356.11.2.12.50.3.2.1.2
lcsSetupWlanSigAvrgFiltParmsCoeffEntryVal OBJECT-TYPE
    SYNTAX     Integer32 (-2147483648..2147483647)
    MAX-ACCESS read-write
    STATUS     current
    DESCRIPTION
            ""
    ::= { lcsSetupWlanSigAvrgFiltParmsCoeffEntry 2 }

-- {NODE} 1.3.6.1.4.1.2356.11.2.12.51
lcsSetupWlanRateAdaption OBJECT IDENTIFIER ::= { lcsSetupWlan 51 }

-- {SCALAR} 1.3.6.1.4.1.2356.11.2.12.51.2
lcsSetupWlanRateAdaptionInitialRate OBJECT-TYPE
    SYNTAX     INTEGER {
                  eMinimum (0),
                  eRssiDerived (1)
            }
    MAX-ACCESS read-write
    STATUS     current
    DESCRIPTION
            "-- empty --"
    ::= { lcsSetupWlanRateAdaption 2 }

-- {SCALAR} 1.3.6.1.4.1.2356.11.2.12.51.3
lcsSetupWlanRateAdaptionMinstrelAveragingFactor OBJECT-TYPE
    SYNTAX     Integer32 (0..255)
    MAX-ACCESS read-write
    STATUS     current
    DESCRIPTION
            "-- empty --"
    ::= { lcsSetupWlanRateAdaption 3 }

-- {SCALAR} 1.3.6.1.4.1.2356.11.2.12.51.4
lcsSetupWlanRateAdaptionStandardAveragingFactor OBJECT-TYPE
    SYNTAX     Integer32 (0..255)
    MAX-ACCESS read-write
    STATUS     current
    DESCRIPTION
            "-- empty --"
    ::= { lcsSetupWlanRateAdaption 4 }

-- {SCALAR} 1.3.6.1.4.1.2356.11.2.12.51.5
lcsSetupWlanRateAdaptionMethod OBJECT-TYPE
    SYNTAX     INTEGER {
                  eStandard (0),
                  eMinstrel (1)
            }
    MAX-ACCESS read-write
    STATUS     current
    DESCRIPTION
            "-- empty --"
    ::= { lcsSetupWlanRateAdaption 5 }

-- {SCALAR} 1.3.6.1.4.1.2356.11.2.12.60
lcsSetupWlanIappIpNetwork OBJECT-TYPE
    SYNTAX     DisplayString (SIZE(0..16))
    MAX-ACCESS read-write
    STATUS     current
    DESCRIPTION
            ""
    ::= { lcsSetupWlan 60 }

-- {TABLE} 1.3.6.1.4.1.2356.11.2.12.70
lcsSetupWlanVlanGroupkeyMappingTable OBJECT-TYPE
    SYNTAX     SEQUENCE OF LcsSetupWlanVlanGroupkeyMappingEntry
    MAX-ACCESS not-accessible
    STATUS     current
    DESCRIPTION
            "-- empty --"
    ::= { lcsSetupWlan 70 }

-- {ROW} 1.3.6.1.4.1.2356.11.2.12.70.1
lcsSetupWlanVlanGroupkeyMappingEntry OBJECT-TYPE
    SYNTAX     LcsSetupWlanVlanGroupkeyMappingEntry
    MAX-ACCESS not-accessible
    STATUS     current
    DESCRIPTION
            ""
    INDEX {
            lcsSetupWlanVlanGroupkeyMappingEntryNetwork,
            lcsSetupWlanVlanGroupkeyMappingEntryVlanId
          }
    ::= { lcsSetupWlanVlanGroupkeyMappingTable 1 }

LcsSetupWlanVlanGroupkeyMappingEntry ::= SEQUENCE {
            lcsSetupWlanVlanGroupkeyMappingEntryNetwork INTEGER,
            lcsSetupWlanVlanGroupkeyMappingEntryVlanId Integer32,
            lcsSetupWlanVlanGroupkeyMappingEntryGroupkeyIndex Integer32
    }

-- {COLUMN} 1.3.6.1.4.1.2356.11.2.12.70.1.1
lcsSetupWlanVlanGroupkeyMappingEntryNetwork OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-write
    STATUS     current
    DESCRIPTION
            "-- empty --"
    ::= { lcsSetupWlanVlanGroupkeyMappingEntry 1 }

-- {COLUMN} 1.3.6.1.4.1.2356.11.2.12.70.1.2
lcsSetupWlanVlanGroupkeyMappingEntryVlanId OBJECT-TYPE
    SYNTAX     Integer32 (0..65535)
    MAX-ACCESS read-write
    STATUS     current
    DESCRIPTION
            "-- empty --"
    ::= { lcsSetupWlanVlanGroupkeyMappingEntry 2 }

-- {COLUMN} 1.3.6.1.4.1.2356.11.2.12.70.1.3
lcsSetupWlanVlanGroupkeyMappingEntryGroupkeyIndex OBJECT-TYPE
    SYNTAX     Integer32 (0..255)
    MAX-ACCESS read-write
    STATUS     current
    DESCRIPTION
            "-- empty --"
    ::= { lcsSetupWlanVlanGroupkeyMappingEntry 3 }

-- {TABLE} 1.3.6.1.4.1.2356.11.2.12.71
lcsSetupWlanVlanNoInterstationTrafficTable OBJECT-TYPE
    SYNTAX     SEQUENCE OF LcsSetupWlanVlanNoInterstationTrafficEntry
    MAX-ACCESS not-accessible
    STATUS     current
    DESCRIPTION
            "-- empty --"
    ::= { lcsSetupWlan 71 }

-- {ROW} 1.3.6.1.4.1.2356.11.2.12.71.1
lcsSetupWlanVlanNoInterstationTrafficEntry OBJECT-TYPE
    SYNTAX     LcsSetupWlanVlanNoInterstationTrafficEntry
    MAX-ACCESS not-accessible
    STATUS     current
    DESCRIPTION
            ""
    INDEX {
            lcsSetupWlanVlanNoInterstationTrafficEntryNetwork,
            lcsSetupWlanVlanNoInterstationTrafficEntryVlanId
          }
    ::= { lcsSetupWlanVlanNoInterstationTrafficTable 1 }

LcsSetupWlanVlanNoInterstationTrafficEntry ::= SEQUENCE {
            lcsSetupWlanVlanNoInterstationTrafficEntryNetwork INTEGER,
            lcsSetupWlanVlanNoInterstationTrafficEntryVlanId Integer32
    }

-- {COLUMN} 1.3.6.1.4.1.2356.11.2.12.71.1.1
lcsSetupWlanVlanNoInterstationTrafficEntryNetwork OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-write
    STATUS     current
    DESCRIPTION
            "-- empty --"
    ::= { lcsSetupWlanVlanNoInterstationTrafficEntry 1 }

-- {COLUMN} 1.3.6.1.4.1.2356.11.2.12.71.1.2
lcsSetupWlanVlanNoInterstationTrafficEntryVlanId OBJECT-TYPE
    SYNTAX     Integer32 (0..65535)
    MAX-ACCESS read-write
    STATUS     current
    DESCRIPTION
            "-- empty --"
    ::= { lcsSetupWlanVlanNoInterstationTrafficEntry 2 }

-- {NODE} 1.3.6.1.4.1.2356.11.2.12.80
lcsSetupWlanDualRoaming OBJECT IDENTIFIER ::= { lcsSetupWlan 80 }

-- {SCALAR} 1.3.6.1.4.1.2356.11.2.12.80.1
lcsSetupWlanDualRoamingGroup OBJECT-TYPE
    SYNTAX     INTEGER {
                  eOff (0),
                  eWlan1PlusWlan2 (3)
            }
    MAX-ACCESS read-write
    STATUS     current
    DESCRIPTION
            "-- empty --"
    ::= { lcsSetupWlanDualRoaming 1 }

-- {SCALAR} 1.3.6.1.4.1.2356.11.2.12.80.2
lcsSetupWlanDualRoamingBlockTimeMs OBJECT-TYPE
    SYNTAX     Integer32 (0..2147483647)
    MAX-ACCESS read-write
    STATUS     current
    DESCRIPTION
            "-- empty --"
    ::= { lcsSetupWlanDualRoaming 2 }

-- {NODE} 1.3.6.1.4.1.2356.11.2.12.85
lcsSetupWlanPmkCaching OBJECT IDENTIFIER ::= { lcsSetupWlan 85 }

-- {SCALAR} 1.3.6.1.4.1.2356.11.2.12.85.1
lcsSetupWlanPmkCachingDefaultLifetime OBJECT-TYPE
    SYNTAX     Integer32 (0..2147483647)
    MAX-ACCESS read-write
    STATUS     current
    DESCRIPTION
            "-- empty --"
    ::= { lcsSetupWlanPmkCaching 1 }

-- {SCALAR} 1.3.6.1.4.1.2356.11.2.12.85.2
lcsSetupWlanPmkCachingMaxEntries OBJECT-TYPE
    SYNTAX     Integer32 (0..2147483647)
    MAX-ACCESS read-write
    STATUS     current
    DESCRIPTION
            "-- empty --"
    ::= { lcsSetupWlanPmkCaching 2 }

-- {NODE} 1.3.6.1.4.1.2356.11.2.12.86
lcsSetupWlanPacketCapture OBJECT IDENTIFIER ::= { lcsSetupWlan 86 }

-- {SCALAR} 1.3.6.1.4.1.2356.11.2.12.86.1
lcsSetupWlanPacketCaptureWlanCaptureFormat OBJECT-TYPE
    SYNTAX     INTEGER {
                  ePlain (105),
                  ePrism (119),
                  eRadiotap (127),
                  eAvs (163),
                  ePpi (192)
            }
    MAX-ACCESS read-write
    STATUS     current
    DESCRIPTION
            "-- empty --"
    ::= { lcsSetupWlanPacketCapture 1 }

-- {NODE} 1.3.6.1.4.1.2356.11.2.12.87
lcsSetupWlanClientSteering OBJECT IDENTIFIER ::= { lcsSetupWlan 87 }

-- {SCALAR} 1.3.6.1.4.1.2356.11.2.12.87.1
lcsSetupWlanClientSteeringOperating OBJECT-TYPE
    SYNTAX     INTEGER {
                  eNo (0),
                  eYes (1),
                  eController (2),
                  eClientManagement (3)
            }
    MAX-ACCESS read-write
    STATUS     current
    DESCRIPTION
            "-- empty --"
    ::= { lcsSetupWlanClientSteering 1 }

-- {SCALAR} 1.3.6.1.4.1.2356.11.2.12.87.2
lcsSetupWlanClientSteeringCriteria OBJECT-TYPE
    SYNTAX     INTEGER {
                  eRadioBand (1)
            }
    MAX-ACCESS read-write
    STATUS     current
    DESCRIPTION
            "-- empty --"
    ::= { lcsSetupWlanClientSteering 2 }

-- {SCALAR} 1.3.6.1.4.1.2356.11.2.12.87.3
lcsSetupWlanClientSteeringPreferredBand OBJECT-TYPE
    SYNTAX     INTEGER {
                  e24ghz (1),
                  e5ghz (2)
            }
    MAX-ACCESS read-write
    STATUS     current
    DESCRIPTION
            "-- empty --"
    ::= { lcsSetupWlanClientSteering 3 }

-- {SCALAR} 1.3.6.1.4.1.2356.11.2.12.87.4
lcsSetupWlanClientSteeringProberequestAgeoutSeconds OBJECT-TYPE
    SYNTAX     Integer32 (0..2147483647)
    MAX-ACCESS read-write
    STATUS     current
    DESCRIPTION
            "-- empty --"
    ::= { lcsSetupWlanClientSteering 4 }

-- {SCALAR} 1.3.6.1.4.1.2356.11.2.12.87.5
lcsSetupWlanClientSteeringInitialBlocktimeSeconds OBJECT-TYPE
    SYNTAX     Integer32 (0..2147483647)
    MAX-ACCESS read-write
    STATUS     current
    DESCRIPTION
            "-- empty --"
    ::= { lcsSetupWlanClientSteering 5 }

-- {SCALAR} 1.3.6.1.4.1.2356.11.2.12.87.6
lcsSetupWlanClientSteeringDryRun OBJECT-TYPE
    SYNTAX     INTEGER {
                  eNo (0),
                  eYes (1)
            }
    MAX-ACCESS read-write
    STATUS     current
    DESCRIPTION
            "-- empty --"
    ::= { lcsSetupWlanClientSteering 6 }

-- {SCALAR} 1.3.6.1.4.1.2356.11.2.12.87.7
lcsSetupWlanClientSteeringLoadRecalculationInterval OBJECT-TYPE
    SYNTAX     Integer32 (0..255)
    MAX-ACCESS read-write
    STATUS     current
    DESCRIPTION
            "-- empty --"
    ::= { lcsSetupWlanClientSteering 7 }

-- {SCALAR} 1.3.6.1.4.1.2356.11.2.12.87.8
lcsSetupWlanClientSteeringLoadAnnouncementDelta OBJECT-TYPE
    SYNTAX     Integer32 (0..255)
    MAX-ACCESS read-write
    STATUS     current
    DESCRIPTION
            "-- empty --"
    ::= { lcsSetupWlanClientSteering 8 }

-- {SCALAR} 1.3.6.1.4.1.2356.11.2.12.87.9
lcsSetupWlanClientSteeringLoadThreshold OBJECT-TYPE
    SYNTAX     Integer32 (0..255)
    MAX-ACCESS read-write
    STATUS     current
    DESCRIPTION
            "-- empty --"
    ::= { lcsSetupWlanClientSteering 9 }

-- {SCALAR} 1.3.6.1.4.1.2356.11.2.12.87.10
lcsSetupWlanClientSteeringBalancingDifference OBJECT-TYPE
    SYNTAX     Integer32 (0..255)
    MAX-ACCESS read-write
    STATUS     current
    DESCRIPTION
            "-- empty --"
    ::= { lcsSetupWlanClientSteering 10 }

-- {SCALAR} 1.3.6.1.4.1.2356.11.2.12.87.11
lcsSetupWlanClientSteeringMaximumNeighborCount OBJECT-TYPE
    SYNTAX     Integer32 (0..255)
    MAX-ACCESS read-write
    STATUS     current
    DESCRIPTION
            "-- empty --"
    ::= { lcsSetupWlanClientSteering 11 }

-- {SCALAR} 1.3.6.1.4.1.2356.11.2.12.87.12
lcsSetupWlanClientSteeringNeighborSignalThreshold OBJECT-TYPE
    SYNTAX     Integer32 (-128..127)
    MAX-ACCESS read-write
    STATUS     current
    DESCRIPTION
            "-- empty --"
    ::= { lcsSetupWlanClientSteering 12 }

-- {SCALAR} 1.3.6.1.4.1.2356.11.2.12.87.13
lcsSetupWlanClientSteeringLegacySteering OBJECT-TYPE
    SYNTAX     INTEGER {
                  eNo (0),
                  eYes (1)
            }
    MAX-ACCESS read-write
    STATUS     current
    DESCRIPTION
            "-- empty --"
    ::= { lcsSetupWlanClientSteering 13 }

-- {SCALAR} 1.3.6.1.4.1.2356.11.2.12.87.14
lcsSetupWlanClientSteeringMinimalLoadDifference OBJECT-TYPE
    SYNTAX     Integer32 (0..255)
    MAX-ACCESS read-write
    STATUS     current
    DESCRIPTION
            "-- empty --"
    ::= { lcsSetupWlanClientSteering 14 }

-- {SCALAR} 1.3.6.1.4.1.2356.11.2.12.87.15
lcsSetupWlanClientSteeringDailyEnvScanHour OBJECT-TYPE
    SYNTAX     Integer32 (0..255)
    MAX-ACCESS read-write
    STATUS     current
    DESCRIPTION
            "-- empty --"
    ::= { lcsSetupWlanClientSteering 15 }

-- {SCALAR} 1.3.6.1.4.1.2356.11.2.12.87.16
lcsSetupWlanClientSteeringScanPeriod OBJECT-TYPE
    SYNTAX     Integer32 (0..65535)
    MAX-ACCESS read-write
    STATUS     current
    DESCRIPTION
            "-- empty --"
    ::= { lcsSetupWlanClientSteering 16 }

-- {SCALAR} 1.3.6.1.4.1.2356.11.2.12.87.17
lcsSetupWlanClientSteeringApSteeringRssiThreshold OBJECT-TYPE
    SYNTAX     Integer32 (-128..127)
    MAX-ACCESS read-write
    STATUS     current
    DESCRIPTION
            "-- empty --"
    ::= { lcsSetupWlanClientSteering 17 }

-- {SCALAR} 1.3.6.1.4.1.2356.11.2.12.87.18
lcsSetupWlanClientSteeringRemoteStationExpiration OBJECT-TYPE
    SYNTAX     Integer32 (0..65535)
    MAX-ACCESS read-write
    STATUS     current
    DESCRIPTION
            "-- empty --"
    ::= { lcsSetupWlanClientSteering 18 }

-- {TABLE} 1.3.6.1.4.1.2356.11.2.12.87.19
lcsSetupWlanClientSteeringBlacklistClientsTable OBJECT-TYPE
    SYNTAX     SEQUENCE OF LcsSetupWlanClientSteeringBlacklistClientsEntry
    MAX-ACCESS not-accessible
    STATUS     current
    DESCRIPTION
            "-- empty --"
    ::= { lcsSetupWlanClientSteering 19 }

-- {ROW} 1.3.6.1.4.1.2356.11.2.12.87.19.1
lcsSetupWlanClientSteeringBlacklistClientsEntry OBJECT-TYPE
    SYNTAX     LcsSetupWlanClientSteeringBlacklistClientsEntry
    MAX-ACCESS not-accessible
    STATUS     current
    DESCRIPTION
            ""
    INDEX {
            lcsSetupWlanClientSteeringBlacklistClientsEntryMacAddress
          }
    ::= { lcsSetupWlanClientSteeringBlacklistClientsTable 1 }

LcsSetupWlanClientSteeringBlacklistClientsEntry ::= SEQUENCE {
            lcsSetupWlanClientSteeringBlacklistClientsEntryMacAddress DisplayString
    }

-- {COLUMN} 1.3.6.1.4.1.2356.11.2.12.87.19.1.1
lcsSetupWlanClientSteeringBlacklistClientsEntryMacAddress OBJECT-TYPE
    SYNTAX     DisplayString (SIZE(0..20))
    MAX-ACCESS read-write
    STATUS     current
    DESCRIPTION
            "-- empty --"
    ::= { lcsSetupWlanClientSteeringBlacklistClientsEntry 1 }

-- {SCALAR} 1.3.6.1.4.1.2356.11.2.12.87.20
lcsSetupWlanClientSteeringStartEnvironmentScan OBJECT-TYPE
    SYNTAX     DisplayString
    MAX-ACCESS read-write
    STATUS     current
    DESCRIPTION
            "-- empty --"
    ::= { lcsSetupWlanClientSteering 20 }

-- {SCALAR} 1.3.6.1.4.1.2356.11.2.12.87.21
lcsSetupWlanClientSteeringClientManagementMode OBJECT-TYPE
    SYNTAX     INTEGER {
                  eApSteering (0),
                  eApPlusBandSteering (1)
            }
    MAX-ACCESS read-write
    STATUS     current
    DESCRIPTION
            "-- empty --"
    ::= { lcsSetupWlanClientSteering 21 }

-- {SCALAR} 1.3.6.1.4.1.2356.11.2.12.87.22
lcsSetupWlanClientSteeringBandRatio OBJECT-TYPE
    SYNTAX     Integer32 (0..255)
    MAX-ACCESS read-write
    STATUS     current
    DESCRIPTION
            "-- empty --"
    ::= { lcsSetupWlanClientSteering 22 }

-- {SCALAR} 1.3.6.1.4.1.2356.11.2.12.87.23
lcsSetupWlanClientSteeringBandSteeringRssiThreshold OBJECT-TYPE
    SYNTAX     Integer32 (-128..127)
    MAX-ACCESS read-write
    STATUS     current
    DESCRIPTION
            "-- empty --"
    ::= { lcsSetupWlanClientSteering 23 }

-- {TABLE} 1.3.6.1.4.1.2356.11.2.12.89
lcsSetupWlanAccessRulesTable OBJECT-TYPE
    SYNTAX     SEQUENCE OF LcsSetupWlanAccessRulesEntry
    MAX-ACCESS not-accessible
    STATUS     current
    DESCRIPTION
            "-- empty --"
    ::= { lcsSetupWlan 89 }

-- {ROW} 1.3.6.1.4.1.2356.11.2.12.89.1
lcsSetupWlanAccessRulesEntry OBJECT-TYPE
    SYNTAX     LcsSetupWlanAccessRulesEntry
    MAX-ACCESS not-accessible
    STATUS     current
    DESCRIPTION
            ""
    INDEX {
            lcsSetupWlanAccessRulesEntryMacAddressPattern,
            lcsSetupWlanAccessRulesEntrySsidPattern
          }
    ::= { lcsSetupWlanAccessRulesTable 1 }

LcsSetupWlanAccessRulesEntry ::= SEQUENCE {
            lcsSetupWlanAccessRulesEntryMacAddressPattern DisplayString,
            lcsSetupWlanAccessRulesEntryName DisplayString,
            lcsSetupWlanAccessRulesEntryComment DisplayString,
            lcsSetupWlanAccessRulesEntryWpaPassphrase DisplayString,
            lcsSetupWlanAccessRulesEntryTxLimit Integer32,
            lcsSetupWlanAccessRulesEntryRxLimit Integer32,
            lcsSetupWlanAccessRulesEntryVlanId Integer32,
            lcsSetupWlanAccessRulesEntrySsidPattern DisplayString
    }

-- {COLUMN} 1.3.6.1.4.1.2356.11.2.12.89.1.1
lcsSetupWlanAccessRulesEntryMacAddressPattern OBJECT-TYPE
    SYNTAX     DisplayString (SIZE(0..20))
    MAX-ACCESS read-write
    STATUS     current
    DESCRIPTION
            "-- empty --"
    ::= { lcsSetupWlanAccessRulesEntry 1 }

-- {COLUMN} 1.3.6.1.4.1.2356.11.2.12.89.1.2
lcsSetupWlanAccessRulesEntryName OBJECT-TYPE
    SYNTAX     DisplayString (SIZE(0..32))
    MAX-ACCESS read-write
    STATUS     current
    DESCRIPTION
            "-- empty --"
    ::= { lcsSetupWlanAccessRulesEntry 2 }

-- {COLUMN} 1.3.6.1.4.1.2356.11.2.12.89.1.3
lcsSetupWlanAccessRulesEntryComment OBJECT-TYPE
    SYNTAX     DisplayString (SIZE(0..30))
    MAX-ACCESS read-write
    STATUS     current
    DESCRIPTION
            "-- empty --"
    ::= { lcsSetupWlanAccessRulesEntry 3 }

-- {COLUMN} 1.3.6.1.4.1.2356.11.2.12.89.1.4
lcsSetupWlanAccessRulesEntryWpaPassphrase OBJECT-TYPE
    SYNTAX     DisplayString (SIZE(0..63))
    MAX-ACCESS read-write
    STATUS     current
    DESCRIPTION
            "-- empty --"
    ::= { lcsSetupWlanAccessRulesEntry 4 }

-- {COLUMN} 1.3.6.1.4.1.2356.11.2.12.89.1.5
lcsSetupWlanAccessRulesEntryTxLimit OBJECT-TYPE
    SYNTAX     Integer32 (0..2147483647)
    MAX-ACCESS read-write
    STATUS     current
    DESCRIPTION
            "-- empty --"
    ::= { lcsSetupWlanAccessRulesEntry 5 }

-- {COLUMN} 1.3.6.1.4.1.2356.11.2.12.89.1.6
lcsSetupWlanAccessRulesEntryRxLimit OBJECT-TYPE
    SYNTAX     Integer32 (0..2147483647)
    MAX-ACCESS read-write
    STATUS     current
    DESCRIPTION
            "-- empty --"
    ::= { lcsSetupWlanAccessRulesEntry 6 }

-- {COLUMN} 1.3.6.1.4.1.2356.11.2.12.89.1.7
lcsSetupWlanAccessRulesEntryVlanId OBJECT-TYPE
    SYNTAX     Integer32 (0..65535)
    MAX-ACCESS read-write
    STATUS     current
    DESCRIPTION
            "-- empty --"
    ::= { lcsSetupWlanAccessRulesEntry 7 }

-- {COLUMN} 1.3.6.1.4.1.2356.11.2.12.89.1.8
lcsSetupWlanAccessRulesEntrySsidPattern OBJECT-TYPE
    SYNTAX     DisplayString (SIZE(0..40))
    MAX-ACCESS read-write
    STATUS     current
    DESCRIPTION
            "-- empty --"
    ::= { lcsSetupWlanAccessRulesEntry 8 }

-- {SCALAR} 1.3.6.1.4.1.2356.11.2.12.100
lcsSetupWlanCardReinitCycle OBJECT-TYPE
    SYNTAX     Integer32 (0..2147483647)
    MAX-ACCESS read-write
    STATUS     current
    DESCRIPTION
            ""
    ::= { lcsSetupWlan 100 }

-- {SCALAR} 1.3.6.1.4.1.2356.11.2.12.101
lcsSetupWlanNoiseCalibrationCycle OBJECT-TYPE
    SYNTAX     Integer32 (0..2147483647)
    MAX-ACCESS read-write
    STATUS     current
    DESCRIPTION
            ""
    ::= { lcsSetupWlan 101 }

-- {SCALAR} 1.3.6.1.4.1.2356.11.2.12.103
lcsSetupWlanTraceMac OBJECT-TYPE
    SYNTAX     MacAddress
    MAX-ACCESS read-write
    STATUS     current
    DESCRIPTION
            ""
    ::= { lcsSetupWlan 103 }

-- {SCALAR} 1.3.6.1.4.1.2356.11.2.12.105
lcsSetupWlanThermRecalCycle OBJECT-TYPE
    SYNTAX     Integer32 (0..2147483647)
    MAX-ACCESS read-write
    STATUS     current
    DESCRIPTION
            ""
    ::= { lcsSetupWlan 105 }

-- {TABLE} 1.3.6.1.4.1.2356.11.2.12.107
lcsSetupWlanRadarPatternThresholdsTable OBJECT-TYPE
    SYNTAX     SEQUENCE OF LcsSetupWlanRadarPatternThresholdsEntry
    MAX-ACCESS not-accessible
    STATUS     current
    DESCRIPTION
            ""
    ::= { lcsSetupWlan 107 }

-- {ROW} 1.3.6.1.4.1.2356.11.2.12.107.1
lcsSetupWlanRadarPatternThresholdsEntry OBJECT-TYPE
    SYNTAX     LcsSetupWlanRadarPatternThresholdsEntry
    MAX-ACCESS not-accessible
    STATUS     current
    DESCRIPTION
            ""
    INDEX {
            lcsSetupWlanRadarPatternThresholdsEntryPatternPps
          }
    ::= { lcsSetupWlanRadarPatternThresholdsTable 1 }

LcsSetupWlanRadarPatternThresholdsEntry ::= SEQUENCE {
            lcsSetupWlanRadarPatternThresholdsEntryPatternPps INTEGER,
            lcsSetupWlanRadarPatternThresholdsEntryThreshold Integer32
    }

-- {COLUMN} 1.3.6.1.4.1.2356.11.2.12.107.1.1
lcsSetupWlanRadarPatternThresholdsEntryPatternPps OBJECT-TYPE
    SYNTAX     INTEGER {
                  eEn30189313200pps (200),
                  eEn30189313300pps (300),
                  eEn30189312330pps (330),
                  eEn30189313500pps (500),
                  eEn30189312700pps (700),
                  eEn30189313750pps (750),
                  eEn30189313800pps (800),
                  eEn301893131000pps (1000),
                  eEn301893131200pps (1200),
                  eEn301893131500pps (1500),
                  eEn301893131600pps (1600),
                  eEn301893121800pps (1800),
                  eEn301893132000pps (2000),
                  eEn301893132300pps (2300),
                  eEn301893133000pps (3000),
                  eEn301893133500pps (3500),
                  eEn301893134000pps (4000),
                  eEn302502200pps (262344),
                  eEn302502300pps (262444),
                  eEn302502500pps (262644),
                  eEn302502750pps (262894),
                  eEn302502800pps (262944),
                  eEn3025021000pps (263144),
                  eEn3025021200pps (263344),
                  eEn3025021500pps (263644),
                  eEn3025021600pps (263744),
                  eEn3025022000pps (264144),
                  eEn3025022300pps (264444),
                  eEn3025023000pps (265144),
                  eEn3025023500pps (265644),
                  eEn3025024000pps (266144),
                  eEn3025024500pps (266644)
            }
    MAX-ACCESS read-write
    STATUS     current
    DESCRIPTION
            ""
    ::= { lcsSetupWlanRadarPatternThresholdsEntry 1 }

-- {COLUMN} 1.3.6.1.4.1.2356.11.2.12.107.1.2
lcsSetupWlanRadarPatternThresholdsEntryThreshold OBJECT-TYPE
    SYNTAX     Integer32 (0..2147483647)
    MAX-ACCESS read-write
    STATUS     current
    DESCRIPTION
            ""
    ::= { lcsSetupWlanRadarPatternThresholdsEntry 2 }

-- {SCALAR} 1.3.6.1.4.1.2356.11.2.12.108
lcsSetupWlanRadarLoadThreshold OBJECT-TYPE
    SYNTAX     Integer32 (0..255)
    MAX-ACCESS read-write
    STATUS     current
    DESCRIPTION
            ""
    ::= { lcsSetupWlan 108 }

-- {TABLE} 1.3.6.1.4.1.2356.11.2.12.109
lcsSetupWlanNoiseOffsetsTable OBJECT-TYPE
    SYNTAX     SEQUENCE OF LcsSetupWlanNoiseOffsetsEntry
    MAX-ACCESS not-accessible
    STATUS     current
    DESCRIPTION
            ""
    ::= { lcsSetupWlan 109 }

-- {ROW} 1.3.6.1.4.1.2356.11.2.12.109.1
lcsSetupWlanNoiseOffsetsEntry OBJECT-TYPE
    SYNTAX     LcsSetupWlanNoiseOffsetsEntry
    MAX-ACCESS not-accessible
    STATUS     current
    DESCRIPTION
            ""
    INDEX {
            lcsSetupWlanNoiseOffsetsEntryBand,
            lcsSetupWlanNoiseOffsetsEntryChannel,
            lcsSetupWlanNoiseOffsetsEntryInterface
          }
    ::= { lcsSetupWlanNoiseOffsetsTable 1 }

LcsSetupWlanNoiseOffsetsEntry ::= SEQUENCE {
            lcsSetupWlanNoiseOffsetsEntryBand INTEGER,
            lcsSetupWlanNoiseOffsetsEntryChannel Integer32,
            lcsSetupWlanNoiseOffsetsEntryInterface INTEGER,
            lcsSetupWlanNoiseOffsetsEntryValue Integer32
    }

-- {COLUMN} 1.3.6.1.4.1.2356.11.2.12.109.1.1
lcsSetupWlanNoiseOffsetsEntryBand OBJECT-TYPE
    SYNTAX     INTEGER {
                  e24ghz (1),
                  e5ghz (2)
            }
    MAX-ACCESS read-write
    STATUS     current
    DESCRIPTION
            ""
    ::= { lcsSetupWlanNoiseOffsetsEntry 1 }

-- {COLUMN} 1.3.6.1.4.1.2356.11.2.12.109.1.2
lcsSetupWlanNoiseOffsetsEntryChannel OBJECT-TYPE
    SYNTAX     Integer32 (0..65535)
    MAX-ACCESS read-write
    STATUS     current
    DESCRIPTION
            ""
    ::= { lcsSetupWlanNoiseOffsetsEntry 2 }

-- {COLUMN} 1.3.6.1.4.1.2356.11.2.12.109.1.3
lcsSetupWlanNoiseOffsetsEntryInterface OBJECT-TYPE
    SYNTAX     INTEGER {
                  eWlan1 (1),
                  eWlan2 (2)
            }
    MAX-ACCESS read-write
    STATUS     current
    DESCRIPTION
            ""
    ::= { lcsSetupWlanNoiseOffsetsEntry 3 }

-- {COLUMN} 1.3.6.1.4.1.2356.11.2.12.109.1.4
lcsSetupWlanNoiseOffsetsEntryValue OBJECT-TYPE
    SYNTAX     Integer32 (-128..127)
    MAX-ACCESS read-write
    STATUS     current
    DESCRIPTION
            ""
    ::= { lcsSetupWlanNoiseOffsetsEntry 4 }

-- {SCALAR} 1.3.6.1.4.1.2356.11.2.12.110
lcsSetupWlanTraceLevel OBJECT-TYPE
    SYNTAX     Integer32 (0..255)
    MAX-ACCESS read-write
    STATUS     current
    DESCRIPTION
            ""
    ::= { lcsSetupWlan 110 }

-- {NODE} 1.3.6.1.4.1.2356.11.2.12.111
lcsSetupWlanNoiseImmunity OBJECT IDENTIFIER ::= { lcsSetupWlan 111 }

-- {SCALAR} 1.3.6.1.4.1.2356.11.2.12.111.1
lcsSetupWlanNoiseImmunityNoiseImmunityLevel OBJECT-TYPE
    SYNTAX     Integer32 (0..255)
    MAX-ACCESS read-write
    STATUS     current
    DESCRIPTION
            ""
    ::= { lcsSetupWlanNoiseImmunity 1 }

-- {SCALAR} 1.3.6.1.4.1.2356.11.2.12.111.2
lcsSetupWlanNoiseImmunityOfdmWeakSignalDetection OBJECT-TYPE
    SYNTAX     Integer32 (0..255)
    MAX-ACCESS read-write
    STATUS     current
    DESCRIPTION
            ""
    ::= { lcsSetupWlanNoiseImmunity 2 }

-- {SCALAR} 1.3.6.1.4.1.2356.11.2.12.111.3
lcsSetupWlanNoiseImmunityCckWeakSignalDetectionThreshold OBJECT-TYPE
    SYNTAX     Integer32 (0..255)
    MAX-ACCESS read-write
    STATUS     current
    DESCRIPTION
            ""
    ::= { lcsSetupWlanNoiseImmunity 3 }

-- {SCALAR} 1.3.6.1.4.1.2356.11.2.12.111.4
lcsSetupWlanNoiseImmunityFirStepLevel OBJECT-TYPE
    SYNTAX     Integer32 (0..255)
    MAX-ACCESS read-write
    STATUS     current
    DESCRIPTION
            ""
    ::= { lcsSetupWlanNoiseImmunity 4 }

-- {SCALAR} 1.3.6.1.4.1.2356.11.2.12.111.5
lcsSetupWlanNoiseImmunitySpuriousImmunityLevel OBJECT-TYPE
    SYNTAX     Integer32 (0..255)
    MAX-ACCESS read-write
    STATUS     current
    DESCRIPTION
            ""
    ::= { lcsSetupWlanNoiseImmunity 5 }

-- {SCALAR} 1.3.6.1.4.1.2356.11.2.12.111.6
lcsSetupWlanNoiseImmunityMrcCck OBJECT-TYPE
    SYNTAX     Integer32 (0..255)
    MAX-ACCESS read-write
    STATUS     current
    DESCRIPTION
            "-- empty --"
    ::= { lcsSetupWlanNoiseImmunity 6 }

-- {SCALAR} 1.3.6.1.4.1.2356.11.2.12.114
lcsSetupWlanAggregateRetryLimit OBJECT-TYPE
    SYNTAX     Integer32 (0..255)
    MAX-ACCESS read-write
    STATUS     current
    DESCRIPTION
            ""
    ::= { lcsSetupWlan 114 }

-- {SCALAR} 1.3.6.1.4.1.2356.11.2.12.115
lcsSetupWlanOmitGlobalCryptoSequenceCheck OBJECT-TYPE
    SYNTAX     INTEGER {
                  eAuto (0),
                  eNo (1),
                  eYes (2)
            }
    MAX-ACCESS read-write
    STATUS     current
    DESCRIPTION
            ""
    ::= { lcsSetupWlan 115 }

-- {SCALAR} 1.3.6.1.4.1.2356.11.2.12.116
lcsSetupWlanTracePackets OBJECT-TYPE
    SYNTAX     BITS {
                  eAll (0),
                  eEapol (4),
                  eData (5),
                  eControl (6),
                  eManagement (7)
            }
    MAX-ACCESS read-write
    STATUS     current
    DESCRIPTION
            ""
    ::= { lcsSetupWlan 116 }

-- {SCALAR} 1.3.6.1.4.1.2356.11.2.12.117
lcsSetupWlanWpaHandshakeDelayMs OBJECT-TYPE
    SYNTAX     Integer32 (0..2147483647)
    MAX-ACCESS read-write
    STATUS     current
    DESCRIPTION
            ""
    ::= { lcsSetupWlan 117 }

-- {SCALAR} 1.3.6.1.4.1.2356.11.2.12.118
lcsSetupWlanWpaHandshakeTimeoutOverrideMs OBJECT-TYPE
    SYNTAX     Integer32 (0..2147483647)
    MAX-ACCESS read-write
    STATUS     current
    DESCRIPTION
            "-- empty --"
    ::= { lcsSetupWlan 118 }

-- {SCALAR} 1.3.6.1.4.1.2356.11.2.12.119
lcsSetupWlanTraceBeacons OBJECT-TYPE
    SYNTAX     INTEGER {
                  eNo (0),
                  eYes (1)
            }
    MAX-ACCESS read-write
    STATUS     current
    DESCRIPTION
            "-- empty --"
    ::= { lcsSetupWlan 119 }

-- {SCALAR} 1.3.6.1.4.1.2356.11.2.12.120
lcsSetupWlanRxAggregateFlushTimeoutMs OBJECT-TYPE
    SYNTAX     Integer32 (0..2147483647)
    MAX-ACCESS read-write
    STATUS     current
    DESCRIPTION
            "-- empty --"
    ::= { lcsSetupWlan 120 }

-- {SCALAR} 1.3.6.1.4.1.2356.11.2.12.121
lcsSetupWlanHtFairness OBJECT-TYPE
    SYNTAX     INTEGER {
                  eNo (0),
                  eYes (1)
            }
    MAX-ACCESS read-write
    STATUS     current
    DESCRIPTION
            "-- empty --"
    ::= { lcsSetupWlan 121 }

-- {SCALAR} 1.3.6.1.4.1.2356.11.2.12.122
lcsSetupWlanDfsTestmode OBJECT-TYPE
    SYNTAX     INTEGER {
                  eNo (0),
                  eYes (1)
            }
    MAX-ACCESS read-write
    STATUS     current
    DESCRIPTION
            "-- empty --"
    ::= { lcsSetupWlan 122 }

-- {SCALAR} 1.3.6.1.4.1.2356.11.2.12.124
lcsSetupWlanTraceMgmtPackets OBJECT-TYPE
    SYNTAX     BITS {
                  eOther (2),
                  eBeacon (3),
                  eAction (4),
                  eProbe (5),
                  eAuthentication (6),
                  eAssociation (7)
            }
    MAX-ACCESS read-write
    STATUS     current
    DESCRIPTION
            "-- empty --"
    ::= { lcsSetupWlan 124 }

-- {SCALAR} 1.3.6.1.4.1.2356.11.2.12.125
lcsSetupWlanTraceDataPackets OBJECT-TYPE
    SYNTAX     BITS {
                  eOther (5),
                  eNull (6),
                  eNormal (7)
            }
    MAX-ACCESS read-write
    STATUS     current
    DESCRIPTION
            "-- empty --"
    ::= { lcsSetupWlan 125 }

-- {SCALAR} 1.3.6.1.4.1.2356.11.2.12.126
lcsSetupWlanTraceTxCompleteWithPacket OBJECT-TYPE
    SYNTAX     INTEGER {
                  eNo (0),
                  eYes (1)
            }
    MAX-ACCESS read-write
    STATUS     current
    DESCRIPTION
            "-- empty --"
    ::= { lcsSetupWlan 126 }

-- {NODE} 1.3.6.1.4.1.2356.11.2.12.128
lcsSetupWlanSae OBJECT IDENTIFIER ::= { lcsSetupWlan 128 }

-- {SCALAR} 1.3.6.1.4.1.2356.11.2.12.128.1
lcsSetupWlanSaeAlwaysIncludePmkid OBJECT-TYPE
    SYNTAX     INTEGER {
                  eNo (0),
                  eYes (1)
            }
    MAX-ACCESS read-write
    STATUS     current
    DESCRIPTION
            "-- empty --"
    ::= { lcsSetupWlanSae 1 }

-- {SCALAR} 1.3.6.1.4.1.2356.11.2.12.128.3
lcsSetupWlanSaeUseLockstep OBJECT-TYPE
    SYNTAX     INTEGER {
                  eNo (0),
                  eYes (1)
            }
    MAX-ACCESS read-write
    STATUS     current
    DESCRIPTION
            "-- empty --"
    ::= { lcsSetupWlanSae 3 }

-- {SCALAR} 1.3.6.1.4.1.2356.11.2.12.128.4
lcsSetupWlanSaeEccMinInterations OBJECT-TYPE
    SYNTAX     Integer32 (0..255)
    MAX-ACCESS read-write
    STATUS     current
    DESCRIPTION
            "-- empty --"
    ::= { lcsSetupWlanSae 4 }

-- {NODE} 1.3.6.1.4.1.2356.11.2.12.130
lcsSetupWlanDfs OBJECT IDENTIFIER ::= { lcsSetupWlan 130 }

-- {SCALAR} 1.3.6.1.4.1.2356.11.2.12.130.1
lcsSetupWlanDfsUseFullChannelset OBJECT-TYPE
    SYNTAX     INTEGER {
                  eNo (0),
                  eYes (1)
            }
    MAX-ACCESS read-write
    STATUS     current
    DESCRIPTION
            "-- empty --"
    ::= { lcsSetupWlanDfs 1 }

-- {SCALAR} 1.3.6.1.4.1.2356.11.2.12.130.2
lcsSetupWlanDfsRadarLoadThreshold OBJECT-TYPE
    SYNTAX     Integer32 (0..255)
    MAX-ACCESS read-write
    STATUS     current
    DESCRIPTION
            "-- empty --"
    ::= { lcsSetupWlanDfs 2 }

-- {SCALAR} 1.3.6.1.4.1.2356.11.2.12.130.3
lcsSetupWlanDfsDirectChannelswitching OBJECT-TYPE
    SYNTAX     INTEGER {
                  eNo (0),
                  eYes (1)
            }
    MAX-ACCESS read-write
    STATUS     current
    DESCRIPTION
            "-- empty --"
    ::= { lcsSetupWlanDfs 3 }

-- {SCALAR} 1.3.6.1.4.1.2356.11.2.12.130.4
lcsSetupWlanDfsDfsTestmode OBJECT-TYPE
    SYNTAX     INTEGER {
                  eNo (0),
                  eYes (1)
            }
    MAX-ACCESS read-write
    STATUS     current
    DESCRIPTION
            "-- empty --"
    ::= { lcsSetupWlanDfs 4 }

-- {SCALAR} 1.3.6.1.4.1.2356.11.2.12.130.5
lcsSetupWlanDfsIgnoreCrcErrors OBJECT-TYPE
    SYNTAX     INTEGER {
                  eNo (0),
                  eYes (1)
            }
    MAX-ACCESS read-write
    STATUS     current
    DESCRIPTION
            "-- empty --"
    ::= { lcsSetupWlanDfs 5 }

-- {SCALAR} 1.3.6.1.4.1.2356.11.2.12.130.6
lcsSetupWlanDfsTraceIgnoredPulses OBJECT-TYPE
    SYNTAX     INTEGER {
                  eNo (0),
                  eYes (1)
            }
    MAX-ACCESS read-write
    STATUS     current
    DESCRIPTION
            "-- empty --"
    ::= { lcsSetupWlanDfs 6 }

-- {SCALAR} 1.3.6.1.4.1.2356.11.2.12.130.7
lcsSetupWlanDfsGoForHighestBandwidth OBJECT-TYPE
    SYNTAX     INTEGER {
                  eNo (0),
                  eYes (1),
                  eOverUserPreference (2)
            }
    MAX-ACCESS read-write
    STATUS     current
    DESCRIPTION
            "-- empty --"
    ::= { lcsSetupWlanDfs 7 }

-- {SCALAR} 1.3.6.1.4.1.2356.11.2.12.130.8
lcsSetupWlanDfsPreferFastSwitch OBJECT-TYPE
    SYNTAX     INTEGER {
                  eNo (0),
                  eYes (1)
            }
    MAX-ACCESS read-write
    STATUS     current
    DESCRIPTION
            "-- empty --"
    ::= { lcsSetupWlanDfs 8 }

-- {SCALAR} 1.3.6.1.4.1.2356.11.2.12.130.9
lcsSetupWlanDfsChannelChangeDelay OBJECT-TYPE
    SYNTAX     Integer32 (0..255)
    MAX-ACCESS read-write
    STATUS     current
    DESCRIPTION
            "-- empty --"
    ::= { lcsSetupWlanDfs 9 }

-- {TABLE} 1.3.6.1.4.1.2356.11.2.12.130.10
lcsSetupWlanDfsRadarPatternThresholdsTable OBJECT-TYPE
    SYNTAX     SEQUENCE OF LcsSetupWlanDfsRadarPatternThresholdsEntry
    MAX-ACCESS not-accessible
    STATUS     current
    DESCRIPTION
            "-- empty --"
    ::= { lcsSetupWlanDfs 10 }

-- {ROW} 1.3.6.1.4.1.2356.11.2.12.130.10.1
lcsSetupWlanDfsRadarPatternThresholdsEntry OBJECT-TYPE
    SYNTAX     LcsSetupWlanDfsRadarPatternThresholdsEntry
    MAX-ACCESS not-accessible
    STATUS     current
    DESCRIPTION
            ""
    INDEX {
            lcsSetupWlanDfsRadarPatternThresholdsEntryPatternPps
          }
    ::= { lcsSetupWlanDfsRadarPatternThresholdsTable 1 }

LcsSetupWlanDfsRadarPatternThresholdsEntry ::= SEQUENCE {
            lcsSetupWlanDfsRadarPatternThresholdsEntryPatternPps INTEGER,
            lcsSetupWlanDfsRadarPatternThresholdsEntryThreshold Integer32
    }

-- {COLUMN} 1.3.6.1.4.1.2356.11.2.12.130.10.1.1
lcsSetupWlanDfsRadarPatternThresholdsEntryPatternPps OBJECT-TYPE
    SYNTAX     INTEGER {
                  eEn30189313200pps (200),
                  eEn30189313300pps (300),
                  eEn30189312330pps (330),
                  eEn30189313500pps (500),
                  eEn30189312700pps (700),
                  eEn30189313750pps (750),
                  eEn30189313800pps (800),
                  eEn301893131000pps (1000),
                  eEn301893131200pps (1200),
                  eEn301893131500pps (1500),
                  eEn301893131600pps (1600),
                  eEn301893121800pps (1800),
                  eEn301893132000pps (2000),
                  eEn301893132300pps (2300),
                  eEn301893133000pps (3000),
                  eEn301893133500pps (3500),
                  eEn301893134000pps (4000),
                  eEn302502200pps (262344),
                  eEn302502300pps (262444),
                  eEn302502500pps (262644),
                  eEn302502750pps (262894),
                  eEn302502800pps (262944),
                  eEn3025021000pps (263144),
                  eEn3025021200pps (263344),
                  eEn3025021500pps (263644),
                  eEn3025021600pps (263744),
                  eEn3025022000pps (264144),
                  eEn3025022300pps (264444),
                  eEn3025023000pps (265144),
                  eEn3025023500pps (265644),
                  eEn3025024000pps (266144),
                  eEn3025024500pps (266644)
            }
    MAX-ACCESS read-write
    STATUS     current
    DESCRIPTION
            "-- empty --"
    ::= { lcsSetupWlanDfsRadarPatternThresholdsEntry 1 }

-- {COLUMN} 1.3.6.1.4.1.2356.11.2.12.130.10.1.2
lcsSetupWlanDfsRadarPatternThresholdsEntryThreshold OBJECT-TYPE
    SYNTAX     Integer32 (0..2147483647)
    MAX-ACCESS read-write
    STATUS     current
    DESCRIPTION
            "-- empty --"
    ::= { lcsSetupWlanDfsRadarPatternThresholdsEntry 2 }

-- {SCALAR} 1.3.6.1.4.1.2356.11.2.12.130.11
lcsSetupWlanDfsMinInternalChannelDistance OBJECT-TYPE
    SYNTAX     Integer32 (0..255)
    MAX-ACCESS read-write
    STATUS     current
    DESCRIPTION
            "-- empty --"
    ::= { lcsSetupWlanDfs 11 }

-- {SCALAR} 1.3.6.1.4.1.2356.11.2.12.130.15
lcsSetupWlanDfsCacTime56ghz OBJECT-TYPE
    SYNTAX     Integer32 (0..65535)
    MAX-ACCESS read-write
    STATUS     current
    DESCRIPTION
            "-- empty --"
    ::= { lcsSetupWlanDfs 15 }

-- {NODE} 1.3.6.1.4.1.2356.11.2.12.131
lcsSetupWlanBlinkMode OBJECT IDENTIFIER ::= { lcsSetupWlan 131 }

-- {SCALAR} 1.3.6.1.4.1.2356.11.2.12.131.1
lcsSetupWlanBlinkModeServerAddress OBJECT-TYPE
    SYNTAX     DisplayString (SIZE(0..64))
    MAX-ACCESS read-write
    STATUS     current
    DESCRIPTION
            "-- empty --"
    ::= { lcsSetupWlanBlinkMode 1 }

-- {SCALAR} 1.3.6.1.4.1.2356.11.2.12.131.2
lcsSetupWlanBlinkModeServerPort OBJECT-TYPE
    SYNTAX     Integer32 (0..65535)
    MAX-ACCESS read-write
    STATUS     current
    DESCRIPTION
            "-- empty --"
    ::= { lcsSetupWlanBlinkMode 2 }

-- {SCALAR} 1.3.6.1.4.1.2356.11.2.12.131.3
lcsSetupWlanBlinkModeLoopbackAddress OBJECT-TYPE
    SYNTAX     DisplayString (SIZE(0..16))
    MAX-ACCESS read-write
    STATUS     current
    DESCRIPTION
            "-- empty --"
    ::= { lcsSetupWlanBlinkMode 3 }

-- {TABLE} 1.3.6.1.4.1.2356.11.2.12.132
lcsSetupWlanRoamingTargetsTable OBJECT-TYPE
    SYNTAX     SEQUENCE OF LcsSetupWlanRoamingTargetsEntry
    MAX-ACCESS not-accessible
    STATUS     current
    DESCRIPTION
            "-- empty --"
    ::= { lcsSetupWlan 132 }

-- {ROW} 1.3.6.1.4.1.2356.11.2.12.132.1
lcsSetupWlanRoamingTargetsEntry OBJECT-TYPE
    SYNTAX     LcsSetupWlanRoamingTargetsEntry
    MAX-ACCESS not-accessible
    STATUS     current
    DESCRIPTION
            ""
    INDEX {
            lcsSetupWlanRoamingTargetsEntryName
          }
    ::= { lcsSetupWlanRoamingTargetsTable 1 }

LcsSetupWlanRoamingTargetsEntry ::= SEQUENCE {
            lcsSetupWlanRoamingTargetsEntryName DisplayString
    }

-- {COLUMN} 1.3.6.1.4.1.2356.11.2.12.132.1.1
lcsSetupWlanRoamingTargetsEntryName OBJECT-TYPE
    SYNTAX     DisplayString (SIZE(0..64))
    MAX-ACCESS read-write
    STATUS     current
    DESCRIPTION
            "-- empty --"
    ::= { lcsSetupWlanRoamingTargetsEntry 1 }

-- {NODE} 1.3.6.1.4.1.2356.11.2.12.133
lcsSetupWlanLepsU OBJECT IDENTIFIER ::= { lcsSetupWlan 133 }

-- {SCALAR} 1.3.6.1.4.1.2356.11.2.12.133.1
lcsSetupWlanLepsUOperating OBJECT-TYPE
    SYNTAX     INTEGER {
                  eNo (0),
                  eYes (1)
            }
    MAX-ACCESS read-write
    STATUS     current
    DESCRIPTION
            "-- empty --"
    ::= { lcsSetupWlanLepsU 1 }

-- {TABLE} 1.3.6.1.4.1.2356.11.2.12.133.2
lcsSetupWlanLepsUProfilesTable OBJECT-TYPE
    SYNTAX     SEQUENCE OF LcsSetupWlanLepsUProfilesEntry
    MAX-ACCESS not-accessible
    STATUS     current
    DESCRIPTION
            "-- empty --"
    ::= { lcsSetupWlanLepsU 2 }

-- {ROW} 1.3.6.1.4.1.2356.11.2.12.133.2.1
lcsSetupWlanLepsUProfilesEntry OBJECT-TYPE
    SYNTAX     LcsSetupWlanLepsUProfilesEntry
    MAX-ACCESS not-accessible
    STATUS     current
    DESCRIPTION
            ""
    INDEX {
            lcsSetupWlanLepsUProfilesEntryName
          }
    ::= { lcsSetupWlanLepsUProfilesTable 1 }

LcsSetupWlanLepsUProfilesEntry ::= SEQUENCE {
            lcsSetupWlanLepsUProfilesEntryName DisplayString,
            lcsSetupWlanLepsUProfilesEntryNetworkName DisplayString,
            lcsSetupWlanLepsUProfilesEntryPerClientTxLimit Integer32,
            lcsSetupWlanLepsUProfilesEntryPerClientRxLimit Integer32,
            lcsSetupWlanLepsUProfilesEntryVlanId Integer32
    }

-- {COLUMN} 1.3.6.1.4.1.2356.11.2.12.133.2.1.1
lcsSetupWlanLepsUProfilesEntryName OBJECT-TYPE
    SYNTAX     DisplayString (SIZE(0..32))
    MAX-ACCESS read-write
    STATUS     current
    DESCRIPTION
            "-- empty --"
    ::= { lcsSetupWlanLepsUProfilesEntry 1 }

-- {COLUMN} 1.3.6.1.4.1.2356.11.2.12.133.2.1.2
lcsSetupWlanLepsUProfilesEntryNetworkName OBJECT-TYPE
    SYNTAX     DisplayString (SIZE(0..32))
    MAX-ACCESS read-write
    STATUS     current
    DESCRIPTION
            "-- empty --"
    ::= { lcsSetupWlanLepsUProfilesEntry 2 }

-- {COLUMN} 1.3.6.1.4.1.2356.11.2.12.133.2.1.3
lcsSetupWlanLepsUProfilesEntryPerClientTxLimit OBJECT-TYPE
    SYNTAX     Integer32 (0..2147483647)
    MAX-ACCESS read-write
    STATUS     current
    DESCRIPTION
            "-- empty --"
    ::= { lcsSetupWlanLepsUProfilesEntry 3 }

-- {COLUMN} 1.3.6.1.4.1.2356.11.2.12.133.2.1.4
lcsSetupWlanLepsUProfilesEntryPerClientRxLimit OBJECT-TYPE
    SYNTAX     Integer32 (0..2147483647)
    MAX-ACCESS read-write
    STATUS     current
    DESCRIPTION
            "-- empty --"
    ::= { lcsSetupWlanLepsUProfilesEntry 4 }

-- {COLUMN} 1.3.6.1.4.1.2356.11.2.12.133.2.1.5
lcsSetupWlanLepsUProfilesEntryVlanId OBJECT-TYPE
    SYNTAX     Integer32 (0..65535)
    MAX-ACCESS read-write
    STATUS     current
    DESCRIPTION
            "-- empty --"
    ::= { lcsSetupWlanLepsUProfilesEntry 5 }

-- {TABLE} 1.3.6.1.4.1.2356.11.2.12.133.3
lcsSetupWlanLepsUUsersTable OBJECT-TYPE
    SYNTAX     SEQUENCE OF LcsSetupWlanLepsUUsersEntry
    MAX-ACCESS not-accessible
    STATUS     current
    DESCRIPTION
            "-- empty --"
    ::= { lcsSetupWlanLepsU 3 }

-- {ROW} 1.3.6.1.4.1.2356.11.2.12.133.3.1
lcsSetupWlanLepsUUsersEntry OBJECT-TYPE
    SYNTAX     LcsSetupWlanLepsUUsersEntry
    MAX-ACCESS not-accessible
    STATUS     current
    DESCRIPTION
            ""
    INDEX {
            lcsSetupWlanLepsUUsersEntryName
          }
    ::= { lcsSetupWlanLepsUUsersTable 1 }

LcsSetupWlanLepsUUsersEntry ::= SEQUENCE {
            lcsSetupWlanLepsUUsersEntryName DisplayString,
            lcsSetupWlanLepsUUsersEntryProfile DisplayString,
            lcsSetupWlanLepsUUsersEntryWpaPassphrase DisplayString,
            lcsSetupWlanLepsUUsersEntryPerClientTxLimit Integer32,
            lcsSetupWlanLepsUUsersEntryPerClientRxLimit Integer32,
            lcsSetupWlanLepsUUsersEntryVlanId Integer32
    }

-- {COLUMN} 1.3.6.1.4.1.2356.11.2.12.133.3.1.1
lcsSetupWlanLepsUUsersEntryName OBJECT-TYPE
    SYNTAX     DisplayString (SIZE(0..32))
    MAX-ACCESS read-write
    STATUS     current
    DESCRIPTION
            "-- empty --"
    ::= { lcsSetupWlanLepsUUsersEntry 1 }

-- {COLUMN} 1.3.6.1.4.1.2356.11.2.12.133.3.1.2
lcsSetupWlanLepsUUsersEntryProfile OBJECT-TYPE
    SYNTAX     DisplayString (SIZE(0..32))
    MAX-ACCESS read-write
    STATUS     current
    DESCRIPTION
            "-- empty --"
    ::= { lcsSetupWlanLepsUUsersEntry 2 }

-- {COLUMN} 1.3.6.1.4.1.2356.11.2.12.133.3.1.3
lcsSetupWlanLepsUUsersEntryWpaPassphrase OBJECT-TYPE
    SYNTAX     DisplayString (SIZE(0..63))
    MAX-ACCESS read-write
    STATUS     current
    DESCRIPTION
            "-- empty --"
    ::= { lcsSetupWlanLepsUUsersEntry 3 }

-- {COLUMN} 1.3.6.1.4.1.2356.11.2.12.133.3.1.4
lcsSetupWlanLepsUUsersEntryPerClientTxLimit OBJECT-TYPE
    SYNTAX     Integer32 (0..2147483647)
    MAX-ACCESS read-write
    STATUS     current
    DESCRIPTION
            "-- empty --"
    ::= { lcsSetupWlanLepsUUsersEntry 4 }

-- {COLUMN} 1.3.6.1.4.1.2356.11.2.12.133.3.1.5
lcsSetupWlanLepsUUsersEntryPerClientRxLimit OBJECT-TYPE
    SYNTAX     Integer32 (0..2147483647)
    MAX-ACCESS read-write
    STATUS     current
    DESCRIPTION
            "-- empty --"
    ::= { lcsSetupWlanLepsUUsersEntry 5 }

-- {COLUMN} 1.3.6.1.4.1.2356.11.2.12.133.3.1.6
lcsSetupWlanLepsUUsersEntryVlanId OBJECT-TYPE
    SYNTAX     Integer32 (0..65535)
    MAX-ACCESS read-write
    STATUS     current
    DESCRIPTION
            "-- empty --"
    ::= { lcsSetupWlanLepsUUsersEntry 6 }

-- {NODE} 1.3.6.1.4.1.2356.11.2.12.134
lcsSetupWlanQos OBJECT IDENTIFIER ::= { lcsSetupWlan 134 }

-- {SCALAR} 1.3.6.1.4.1.2356.11.2.12.134.1
lcsSetupWlanQosQosMapSource OBJECT-TYPE
    SYNTAX     INTEGER {
                  eLanConfig (0),
                  eId1 (1),
                  eId2 (2)
            }
    MAX-ACCESS read-write
    STATUS     current
    DESCRIPTION
            "-- empty --"
    ::= { lcsSetupWlanQos 1 }

-- {NODE} 1.3.6.1.4.1.2356.11.2.12.135
lcsSetupWlanHotspot20 OBJECT IDENTIFIER ::= { lcsSetupWlan 135 }

-- {SCALAR} 1.3.6.1.4.1.2356.11.2.12.135.1
lcsSetupWlanHotspot20CheckRelease OBJECT-TYPE
    SYNTAX     INTEGER {
                  eNo (0),
                  eYes (1)
            }
    MAX-ACCESS read-write
    STATUS     current
    DESCRIPTION
            "-- empty --"
    ::= { lcsSetupWlanHotspot20 1 }

-- {NODE} 1.3.6.1.4.1.2356.11.2.12.136
lcsSetupWlanArpHandlingSettings OBJECT IDENTIFIER ::= { lcsSetupWlan 136 }

-- {SCALAR} 1.3.6.1.4.1.2356.11.2.12.136.2
lcsSetupWlanArpHandlingSettingsUnknownAddressAction OBJECT-TYPE
    SYNTAX     INTEGER {
                  eForward (0),
                  eDiscard (1)
            }
    MAX-ACCESS read-write
    STATUS     current
    DESCRIPTION
            "-- empty --"
    ::= { lcsSetupWlanArpHandlingSettings 2 }

-- {SCALAR} 1.3.6.1.4.1.2356.11.2.12.136.3
lcsSetupWlanArpHandlingSettingsBroadcastResponseAction OBJECT-TYPE
    SYNTAX     INTEGER {
                  eForward (0),
                  eDiscard (1)
            }
    MAX-ACCESS read-write
    STATUS     current
    DESCRIPTION
            "-- empty --"
    ::= { lcsSetupWlanArpHandlingSettings 3 }

-- {SCALAR} 1.3.6.1.4.1.2356.11.2.12.141
lcsSetupWlanSendMails OBJECT-TYPE
    SYNTAX     INTEGER {
                  eNo (0),
                  eYes (1)
            }
    MAX-ACCESS read-write
    STATUS     current
    DESCRIPTION
            "-- empty --"
    ::= { lcsSetupWlan 141 }

-- {NODE} 1.3.6.1.4.1.2356.11.2.12.248
lcsSetupWlanWIds OBJECT IDENTIFIER ::= { lcsSetupWlan 248 }

-- {SCALAR} 1.3.6.1.4.1.2356.11.2.12.248.9
lcsSetupWlanWIdsIdsOperational OBJECT-TYPE
    SYNTAX     INTEGER {
                  eNo (0),
                  eYes (1)
            }
    MAX-ACCESS read-write
    STATUS     current
    DESCRIPTION
            "-- empty --"
    ::= { lcsSetupWlanWIds 9 }

-- {SCALAR} 1.3.6.1.4.1.2356.11.2.12.248.10
lcsSetupWlanWIdsSyslogOperational OBJECT-TYPE
    SYNTAX     INTEGER {
                  eNo (0),
                  eYes (1)
            }
    MAX-ACCESS read-write
    STATUS     current
    DESCRIPTION
            "-- empty --"
    ::= { lcsSetupWlanWIds 10 }

-- {SCALAR} 1.3.6.1.4.1.2356.11.2.12.248.11
lcsSetupWlanWIdsSnmptrapsOperational OBJECT-TYPE
    SYNTAX     INTEGER {
                  eNo (0),
                  eYes (1)
            }
    MAX-ACCESS read-write
    STATUS     current
    DESCRIPTION
            "-- empty --"
    ::= { lcsSetupWlanWIds 11 }

-- {SCALAR} 1.3.6.1.4.1.2356.11.2.12.248.12
lcsSetupWlanWIdsEMail OBJECT-TYPE
    SYNTAX     INTEGER {
                  eNo (0),
                  eYes (1)
            }
    MAX-ACCESS read-write
    STATUS     current
    DESCRIPTION
            "-- empty --"
    ::= { lcsSetupWlanWIds 12 }

-- {SCALAR} 1.3.6.1.4.1.2356.11.2.12.248.13
lcsSetupWlanWIdsEMailReceiver OBJECT-TYPE
    SYNTAX     DisplayString (SIZE(0..63))
    MAX-ACCESS read-write
    STATUS     current
    DESCRIPTION
            "-- empty --"
    ::= { lcsSetupWlanWIds 13 }

-- {SCALAR} 1.3.6.1.4.1.2356.11.2.12.248.14
lcsSetupWlanWIdsEMailAggregateInterval OBJECT-TYPE
    SYNTAX     Integer32 (0..2147483647)
    MAX-ACCESS read-write
    STATUS     current
    DESCRIPTION
            "-- empty --"
    ::= { lcsSetupWlanWIds 14 }

-- {NODE} 1.3.6.1.4.1.2356.11.2.12.248.50
lcsSetupWlanWIdsSig OBJECT IDENTIFIER ::= { lcsSetupWlanWIds 50 }

-- {NODE} 1.3.6.1.4.1.2356.11.2.12.248.50.1
lcsSetupWlanWIdsSigAssociatereqflood OBJECT IDENTIFIER ::= { lcsSetupWlanWIdsSig 1 }

-- {SCALAR} 1.3.6.1.4.1.2356.11.2.12.248.50.1.1
lcsSetupWlanWIdsSigAssociatereqfloodCtrLim OBJECT-TYPE
    SYNTAX     Integer32 (0..2147483647)
    MAX-ACCESS read-write
    STATUS     current
    DESCRIPTION
            ""
    ::= { lcsSetupWlanWIdsSigAssociatereqflood 1 }

-- {SCALAR} 1.3.6.1.4.1.2356.11.2.12.248.50.1.2
lcsSetupWlanWIdsSigAssociatereqfloodCtrInt OBJECT-TYPE
    SYNTAX     Integer32 (0..2147483647)
    MAX-ACCESS read-write
    STATUS     current
    DESCRIPTION
            ""
    ::= { lcsSetupWlanWIdsSigAssociatereqflood 2 }

-- {NODE} 1.3.6.1.4.1.2356.11.2.12.248.50.2
lcsSetupWlanWIdsSigReassociatereqflood OBJECT IDENTIFIER ::= { lcsSetupWlanWIdsSig 2 }

-- {SCALAR} 1.3.6.1.4.1.2356.11.2.12.248.50.2.1
lcsSetupWlanWIdsSigReassociatereqfloodCtrLim OBJECT-TYPE
    SYNTAX     Integer32 (0..2147483647)
    MAX-ACCESS read-write
    STATUS     current
    DESCRIPTION
            ""
    ::= { lcsSetupWlanWIdsSigReassociatereqflood 1 }

-- {SCALAR} 1.3.6.1.4.1.2356.11.2.12.248.50.2.2
lcsSetupWlanWIdsSigReassociatereqfloodCtrInt OBJECT-TYPE
    SYNTAX     Integer32 (0..2147483647)
    MAX-ACCESS read-write
    STATUS     current
    DESCRIPTION
            ""
    ::= { lcsSetupWlanWIdsSigReassociatereqflood 2 }

-- {NODE} 1.3.6.1.4.1.2356.11.2.12.248.50.3
lcsSetupWlanWIdsSigAuthenticatereqflood OBJECT IDENTIFIER ::= { lcsSetupWlanWIdsSig 3 }

-- {SCALAR} 1.3.6.1.4.1.2356.11.2.12.248.50.3.1
lcsSetupWlanWIdsSigAuthenticatereqfloodCtrLim OBJECT-TYPE
    SYNTAX     Integer32 (0..2147483647)
    MAX-ACCESS read-write
    STATUS     current
    DESCRIPTION
            ""
    ::= { lcsSetupWlanWIdsSigAuthenticatereqflood 1 }

-- {SCALAR} 1.3.6.1.4.1.2356.11.2.12.248.50.3.2
lcsSetupWlanWIdsSigAuthenticatereqfloodCtrInt OBJECT-TYPE
    SYNTAX     Integer32 (0..2147483647)
    MAX-ACCESS read-write
    STATUS     current
    DESCRIPTION
            ""
    ::= { lcsSetupWlanWIdsSigAuthenticatereqflood 2 }

-- {NODE} 1.3.6.1.4.1.2356.11.2.12.248.50.4
lcsSetupWlanWIdsSigEapolstart OBJECT IDENTIFIER ::= { lcsSetupWlanWIdsSig 4 }

-- {SCALAR} 1.3.6.1.4.1.2356.11.2.12.248.50.4.1
lcsSetupWlanWIdsSigEapolstartCtrLim OBJECT-TYPE
    SYNTAX     Integer32 (0..2147483647)
    MAX-ACCESS read-write
    STATUS     current
    DESCRIPTION
            ""
    ::= { lcsSetupWlanWIdsSigEapolstart 1 }

-- {SCALAR} 1.3.6.1.4.1.2356.11.2.12.248.50.4.2
lcsSetupWlanWIdsSigEapolstartCtrInt OBJECT-TYPE
    SYNTAX     Integer32 (0..2147483647)
    MAX-ACCESS read-write
    STATUS     current
    DESCRIPTION
            ""
    ::= { lcsSetupWlanWIdsSigEapolstart 2 }

-- {NODE} 1.3.6.1.4.1.2356.11.2.12.248.50.5
lcsSetupWlanWIdsSigProbebroadcast OBJECT IDENTIFIER ::= { lcsSetupWlanWIdsSig 5 }

-- {SCALAR} 1.3.6.1.4.1.2356.11.2.12.248.50.5.1
lcsSetupWlanWIdsSigProbebroadcastCtrLim OBJECT-TYPE
    SYNTAX     Integer32 (0..2147483647)
    MAX-ACCESS read-write
    STATUS     current
    DESCRIPTION
            ""
    ::= { lcsSetupWlanWIdsSigProbebroadcast 1 }

-- {SCALAR} 1.3.6.1.4.1.2356.11.2.12.248.50.5.2
lcsSetupWlanWIdsSigProbebroadcastCtrInt OBJECT-TYPE
    SYNTAX     Integer32 (0..2147483647)
    MAX-ACCESS read-write
    STATUS     current
    DESCRIPTION
            ""
    ::= { lcsSetupWlanWIdsSigProbebroadcast 2 }

-- {NODE} 1.3.6.1.4.1.2356.11.2.12.248.50.6
lcsSetupWlanWIdsSigDisassociatebroadcast OBJECT IDENTIFIER ::= { lcsSetupWlanWIdsSig 6 }

-- {SCALAR} 1.3.6.1.4.1.2356.11.2.12.248.50.6.1
lcsSetupWlanWIdsSigDisassociatebroadcastCtrLim OBJECT-TYPE
    SYNTAX     Integer32 (0..2147483647)
    MAX-ACCESS read-write
    STATUS     current
    DESCRIPTION
            ""
    ::= { lcsSetupWlanWIdsSigDisassociatebroadcast 1 }

-- {SCALAR} 1.3.6.1.4.1.2356.11.2.12.248.50.6.2
lcsSetupWlanWIdsSigDisassociatebroadcastCtrInt OBJECT-TYPE
    SYNTAX     Integer32 (0..2147483647)
    MAX-ACCESS read-write
    STATUS     current
    DESCRIPTION
            ""
    ::= { lcsSetupWlanWIdsSigDisassociatebroadcast 2 }

-- {NODE} 1.3.6.1.4.1.2356.11.2.12.248.50.7
lcsSetupWlanWIdsSigDeauthenticatebroadcast OBJECT IDENTIFIER ::= { lcsSetupWlanWIdsSig 7 }

-- {SCALAR} 1.3.6.1.4.1.2356.11.2.12.248.50.7.1
lcsSetupWlanWIdsSigDeauthenticatebroadcastCtrLim OBJECT-TYPE
    SYNTAX     Integer32 (0..2147483647)
    MAX-ACCESS read-write
    STATUS     current
    DESCRIPTION
            ""
    ::= { lcsSetupWlanWIdsSigDeauthenticatebroadcast 1 }

-- {SCALAR} 1.3.6.1.4.1.2356.11.2.12.248.50.7.2
lcsSetupWlanWIdsSigDeauthenticatebroadcastCtrInt OBJECT-TYPE
    SYNTAX     Integer32 (0..2147483647)
    MAX-ACCESS read-write
    STATUS     current
    DESCRIPTION
            ""
    ::= { lcsSetupWlanWIdsSigDeauthenticatebroadcast 2 }

-- {NODE} 1.3.6.1.4.1.2356.11.2.12.248.50.8
lcsSetupWlanWIdsSigDisassociatereqflood OBJECT IDENTIFIER ::= { lcsSetupWlanWIdsSig 8 }

-- {SCALAR} 1.3.6.1.4.1.2356.11.2.12.248.50.8.1
lcsSetupWlanWIdsSigDisassociatereqfloodCtrLim OBJECT-TYPE
    SYNTAX     Integer32 (0..2147483647)
    MAX-ACCESS read-write
    STATUS     current
    DESCRIPTION
            ""
    ::= { lcsSetupWlanWIdsSigDisassociatereqflood 1 }

-- {SCALAR} 1.3.6.1.4.1.2356.11.2.12.248.50.8.2
lcsSetupWlanWIdsSigDisassociatereqfloodCtrInt OBJECT-TYPE
    SYNTAX     Integer32 (0..2147483647)
    MAX-ACCESS read-write
    STATUS     current
    DESCRIPTION
            ""
    ::= { lcsSetupWlanWIdsSigDisassociatereqflood 2 }

-- {NODE} 1.3.6.1.4.1.2356.11.2.12.248.50.9
lcsSetupWlanWIdsSigBlockackoutofwindow OBJECT IDENTIFIER ::= { lcsSetupWlanWIdsSig 9 }

-- {SCALAR} 1.3.6.1.4.1.2356.11.2.12.248.50.9.1
lcsSetupWlanWIdsSigBlockackoutofwindowCtrLim OBJECT-TYPE
    SYNTAX     Integer32 (0..2147483647)
    MAX-ACCESS read-write
    STATUS     current
    DESCRIPTION
            ""
    ::= { lcsSetupWlanWIdsSigBlockackoutofwindow 1 }

-- {SCALAR} 1.3.6.1.4.1.2356.11.2.12.248.50.9.2
lcsSetupWlanWIdsSigBlockackoutofwindowCtrInt OBJECT-TYPE
    SYNTAX     Integer32 (0..2147483647)
    MAX-ACCESS read-write
    STATUS     current
    DESCRIPTION
            ""
    ::= { lcsSetupWlanWIdsSigBlockackoutofwindow 2 }

-- {NODE} 1.3.6.1.4.1.2356.11.2.12.248.50.10
lcsSetupWlanWIdsSigBlockackafterdelba OBJECT IDENTIFIER ::= { lcsSetupWlanWIdsSig 10 }

-- {SCALAR} 1.3.6.1.4.1.2356.11.2.12.248.50.10.1
lcsSetupWlanWIdsSigBlockackafterdelbaCtrLim OBJECT-TYPE
    SYNTAX     Integer32 (0..2147483647)
    MAX-ACCESS read-write
    STATUS     current
    DESCRIPTION
            ""
    ::= { lcsSetupWlanWIdsSigBlockackafterdelba 1 }

-- {SCALAR} 1.3.6.1.4.1.2356.11.2.12.248.50.10.2
lcsSetupWlanWIdsSigBlockackafterdelbaCtrInt OBJECT-TYPE
    SYNTAX     Integer32 (0..2147483647)
    MAX-ACCESS read-write
    STATUS     current
    DESCRIPTION
            ""
    ::= { lcsSetupWlanWIdsSigBlockackafterdelba 2 }

-- {NODE} 1.3.6.1.4.1.2356.11.2.12.248.50.11
lcsSetupWlanWIdsSigNulldataflood OBJECT IDENTIFIER ::= { lcsSetupWlanWIdsSig 11 }

-- {SCALAR} 1.3.6.1.4.1.2356.11.2.12.248.50.11.1
lcsSetupWlanWIdsSigNulldatafloodCtrLim OBJECT-TYPE
    SYNTAX     Integer32 (0..2147483647)
    MAX-ACCESS read-write
    STATUS     current
    DESCRIPTION
            ""
    ::= { lcsSetupWlanWIdsSigNulldataflood 1 }

-- {SCALAR} 1.3.6.1.4.1.2356.11.2.12.248.50.11.2
lcsSetupWlanWIdsSigNulldatafloodCtrInt OBJECT-TYPE
    SYNTAX     Integer32 (0..2147483647)
    MAX-ACCESS read-write
    STATUS     current
    DESCRIPTION
            ""
    ::= { lcsSetupWlanWIdsSigNulldataflood 2 }

-- {NODE} 1.3.6.1.4.1.2356.11.2.12.248.50.12
lcsSetupWlanWIdsSigNullDataPSOv OBJECT IDENTIFIER ::= { lcsSetupWlanWIdsSig 12 }

-- {SCALAR} 1.3.6.1.4.1.2356.11.2.12.248.50.12.1
lcsSetupWlanWIdsSigNullDataPSOvCtrLim OBJECT-TYPE
    SYNTAX     Integer32 (0..2147483647)
    MAX-ACCESS read-write
    STATUS     current
    DESCRIPTION
            ""
    ::= { lcsSetupWlanWIdsSigNullDataPSOv 1 }

-- {SCALAR} 1.3.6.1.4.1.2356.11.2.12.248.50.12.2
lcsSetupWlanWIdsSigNullDataPSOvCtrInt OBJECT-TYPE
    SYNTAX     Integer32 (0..2147483647)
    MAX-ACCESS read-write
    STATUS     current
    DESCRIPTION
            ""
    ::= { lcsSetupWlanWIdsSigNullDataPSOv 2 }

-- {NODE} 1.3.6.1.4.1.2356.11.2.12.248.50.13
lcsSetupWlanWIdsSigPspolltiminterval OBJECT IDENTIFIER ::= { lcsSetupWlanWIdsSig 13 }

-- {SCALAR} 1.3.6.1.4.1.2356.11.2.12.248.50.13.1
lcsSetupWlanWIdsSigPspolltimintervalCtrLim OBJECT-TYPE
    SYNTAX     Integer32 (0..2147483647)
    MAX-ACCESS read-write
    STATUS     current
    DESCRIPTION
            ""
    ::= { lcsSetupWlanWIdsSigPspolltiminterval 1 }

-- {SCALAR} 1.3.6.1.4.1.2356.11.2.12.248.50.13.2
lcsSetupWlanWIdsSigPspolltimintervalCtrInt OBJECT-TYPE
    SYNTAX     Integer32 (0..2147483647)
    MAX-ACCESS read-write
    STATUS     current
    DESCRIPTION
            ""
    ::= { lcsSetupWlanWIdsSigPspolltiminterval 2 }

-- {SCALAR} 1.3.6.1.4.1.2356.11.2.12.248.50.13.3
lcsSetupWlanWIdsSigPspolltimintervalIntervalDiff OBJECT-TYPE
    SYNTAX     Integer32 (0..2147483647)
    MAX-ACCESS read-write
    STATUS     current
    DESCRIPTION
            "-- empty --"
    ::= { lcsSetupWlanWIdsSigPspolltiminterval 3 }

-- {NODE} 1.3.6.1.4.1.2356.11.2.12.248.50.14
lcsSetupWlanWIdsSigSmpsmultistream OBJECT IDENTIFIER ::= { lcsSetupWlanWIdsSig 14 }

-- {SCALAR} 1.3.6.1.4.1.2356.11.2.12.248.50.14.1
lcsSetupWlanWIdsSigSmpsmultistreamCtrLim OBJECT-TYPE
    SYNTAX     Integer32 (0..2147483647)
    MAX-ACCESS read-write
    STATUS     current
    DESCRIPTION
            ""
    ::= { lcsSetupWlanWIdsSigSmpsmultistream 1 }

-- {SCALAR} 1.3.6.1.4.1.2356.11.2.12.248.50.14.2
lcsSetupWlanWIdsSigSmpsmultistreamCtrInt OBJECT-TYPE
    SYNTAX     Integer32 (0..2147483647)
    MAX-ACCESS read-write
    STATUS     current
    DESCRIPTION
            ""
    ::= { lcsSetupWlanWIdsSigSmpsmultistream 2 }

-- {NODE} 1.3.6.1.4.1.2356.11.2.12.248.50.15
lcsSetupWlanWIdsSigDeauthenticatereqflood OBJECT IDENTIFIER ::= { lcsSetupWlanWIdsSig 15 }

-- {SCALAR} 1.3.6.1.4.1.2356.11.2.12.248.50.15.1
lcsSetupWlanWIdsSigDeauthenticatereqfloodCtrLim OBJECT-TYPE
    SYNTAX     Integer32 (0..2147483647)
    MAX-ACCESS read-write
    STATUS     current
    DESCRIPTION
            ""
    ::= { lcsSetupWlanWIdsSigDeauthenticatereqflood 1 }

-- {SCALAR} 1.3.6.1.4.1.2356.11.2.12.248.50.15.2
lcsSetupWlanWIdsSigDeauthenticatereqfloodCtrInt OBJECT-TYPE
    SYNTAX     Integer32 (0..2147483647)
    MAX-ACCESS read-write
    STATUS     current
    DESCRIPTION
            ""
    ::= { lcsSetupWlanWIdsSigDeauthenticatereqflood 2 }

-- {NODE} 1.3.6.1.4.1.2356.11.2.12.248.50.16
lcsSetupWlanWIdsSigPrematureeapolsuccess OBJECT IDENTIFIER ::= { lcsSetupWlanWIdsSig 16 }

-- {SCALAR} 1.3.6.1.4.1.2356.11.2.12.248.50.16.1
lcsSetupWlanWIdsSigPrematureeapolsuccessCtrLim OBJECT-TYPE
    SYNTAX     Integer32 (0..2147483647)
    MAX-ACCESS read-write
    STATUS     current
    DESCRIPTION
            ""
    ::= { lcsSetupWlanWIdsSigPrematureeapolsuccess 1 }

-- {SCALAR} 1.3.6.1.4.1.2356.11.2.12.248.50.16.2
lcsSetupWlanWIdsSigPrematureeapolsuccessCtrInt OBJECT-TYPE
    SYNTAX     Integer32 (0..2147483647)
    MAX-ACCESS read-write
    STATUS     current
    DESCRIPTION
            ""
    ::= { lcsSetupWlanWIdsSigPrematureeapolsuccess 2 }

-- {NODE} 1.3.6.1.4.1.2356.11.2.12.248.50.17
lcsSetupWlanWIdsSigPrematureeapolfailure OBJECT IDENTIFIER ::= { lcsSetupWlanWIdsSig 17 }

-- {SCALAR} 1.3.6.1.4.1.2356.11.2.12.248.50.17.1
lcsSetupWlanWIdsSigPrematureeapolfailureCtrLim OBJECT-TYPE
    SYNTAX     Integer32 (0..2147483647)
    MAX-ACCESS read-write
    STATUS     current
    DESCRIPTION
            ""
    ::= { lcsSetupWlanWIdsSigPrematureeapolfailure 1 }

-- {SCALAR} 1.3.6.1.4.1.2356.11.2.12.248.50.17.2
lcsSetupWlanWIdsSigPrematureeapolfailureCtrInt OBJECT-TYPE
    SYNTAX     Integer32 (0..2147483647)
    MAX-ACCESS read-write
    STATUS     current
    DESCRIPTION
            ""
    ::= { lcsSetupWlanWIdsSigPrematureeapolfailure 2 }

-- {SCALAR} 1.3.6.1.4.1.2356.11.2.12.248.51
lcsSetupWlanWIdsPromiscuousMode OBJECT-TYPE
    SYNTAX     INTEGER {
                  eNo (0),
                  eYes (1)
            }
    MAX-ACCESS read-write
    STATUS     current
    DESCRIPTION
            "-- empty --"
    ::= { lcsSetupWlanWIds 51 }

-- {NODE} 1.3.6.1.4.1.2356.11.2.13
lcsSetupLancapi OBJECT IDENTIFIER ::= { lcsSetup 13 }

-- {TABLE} 1.3.6.1.4.1.2356.11.2.13.1
lcsSetupLancapiAccessListTable OBJECT-TYPE
    SYNTAX     SEQUENCE OF LcsSetupLancapiAccessListEntry
    MAX-ACCESS not-accessible
    STATUS     current
    DESCRIPTION
            ""
    ::= { lcsSetupLancapi 1 }

-- {ROW} 1.3.6.1.4.1.2356.11.2.13.1.1
lcsSetupLancapiAccessListEntry OBJECT-TYPE
    SYNTAX     LcsSetupLancapiAccessListEntry
    MAX-ACCESS not-accessible
    STATUS     current
    DESCRIPTION
            ""
    INDEX {
            lcsSetupLancapiAccessListEntryIpAddress,
            lcsSetupLancapiAccessListEntryIpNetmask,
            lcsSetupLancapiAccessListEntryRtgTag
          }
    ::= { lcsSetupLancapiAccessListTable 1 }

LcsSetupLancapiAccessListEntry ::= SEQUENCE {
            lcsSetupLancapiAccessListEntryIpAddress IpAddress,
            lcsSetupLancapiAccessListEntryIpNetmask IpAddress,
            lcsSetupLancapiAccessListEntryRtgTag Integer32
    }

-- {COLUMN} 1.3.6.1.4.1.2356.11.2.13.1.1.1
lcsSetupLancapiAccessListEntryIpAddress OBJECT-TYPE
    SYNTAX     IpAddress
    MAX-ACCESS read-write
    STATUS     current
    DESCRIPTION
            ""
    ::= { lcsSetupLancapiAccessListEntry 1 }

-- {COLUMN} 1.3.6.1.4.1.2356.11.2.13.1.1.2
lcsSetupLancapiAccessListEntryIpNetmask OBJECT-TYPE
    SYNTAX     IpAddress
    MAX-ACCESS read-write
    STATUS     current
    DESCRIPTION
            ""
    ::= { lcsSetupLancapiAccessListEntry 2 }

-- {COLUMN} 1.3.6.1.4.1.2356.11.2.13.1.1.3
lcsSetupLancapiAccessListEntryRtgTag OBJECT-TYPE
    SYNTAX     Integer32 (0..65535)
    MAX-ACCESS read-write
    STATUS     current
    DESCRIPTION
            ""
    ::= { lcsSetupLancapiAccessListEntry 3 }

-- {SCALAR} 1.3.6.1.4.1.2356.11.2.13.3
lcsSetupLancapiUdpPort OBJECT-TYPE
    SYNTAX     Integer32 (0..65535)
    MAX-ACCESS read-write
    STATUS     current
    DESCRIPTION
            ""
    ::= { lcsSetupLancapi 3 }

-- {TABLE} 1.3.6.1.4.1.2356.11.2.13.6
lcsSetupLancapiInterfaceListTable OBJECT-TYPE
    SYNTAX     SEQUENCE OF LcsSetupLancapiInterfaceListEntry
    MAX-ACCESS not-accessible
    STATUS     current
    DESCRIPTION
            ""
    ::= { lcsSetupLancapi 6 }

-- {ROW} 1.3.6.1.4.1.2356.11.2.13.6.1
lcsSetupLancapiInterfaceListEntry OBJECT-TYPE
    SYNTAX     LcsSetupLancapiInterfaceListEntry
    MAX-ACCESS not-accessible
    STATUS     current
    DESCRIPTION
            ""
    INDEX {
            lcsSetupLancapiInterfaceListEntryIfc
          }
    ::= { lcsSetupLancapiInterfaceListTable 1 }

LcsSetupLancapiInterfaceListEntry ::= SEQUENCE {
            lcsSetupLancapiInterfaceListEntryIfc INTEGER,
            lcsSetupLancapiInterfaceListEntryOperating INTEGER,
            lcsSetupLancapiInterfaceListEntryEazMsnS DisplayString,
            lcsSetupLancapiInterfaceListEntryForceOutMsn INTEGER,
            lcsSetupLancapiInterfaceListEntryMaxConnections Integer32,
            lcsSetupLancapiInterfaceListEntryVoipMode INTEGER
    }

-- {COLUMN} 1.3.6.1.4.1.2356.11.2.13.6.1.1
lcsSetupLancapiInterfaceListEntryIfc OBJECT-TYPE
    SYNTAX     INTEGER {
                  eS01 (1),
                  eS02 (2)
            }
    MAX-ACCESS read-only
    STATUS     current
    DESCRIPTION
            ""
    ::= { lcsSetupLancapiInterfaceListEntry 1 }

-- {COLUMN} 1.3.6.1.4.1.2356.11.2.13.6.1.2
lcsSetupLancapiInterfaceListEntryOperating OBJECT-TYPE
    SYNTAX     INTEGER {
                  eNo (0),
                  eYes (1),
                  eDialOnly (2),
                  eDialInOnly (3)
            }
    MAX-ACCESS read-write
    STATUS     current
    DESCRIPTION
            ""
    ::= { lcsSetupLancapiInterfaceListEntry 2 }

-- {COLUMN} 1.3.6.1.4.1.2356.11.2.13.6.1.3
lcsSetupLancapiInterfaceListEntryEazMsnS OBJECT-TYPE
    SYNTAX     DisplayString (SIZE(0..30))
    MAX-ACCESS read-write
    STATUS     current
    DESCRIPTION
            ""
    ::= { lcsSetupLancapiInterfaceListEntry 3 }

-- {COLUMN} 1.3.6.1.4.1.2356.11.2.13.6.1.5
lcsSetupLancapiInterfaceListEntryForceOutMsn OBJECT-TYPE
    SYNTAX     INTEGER {
                  eNo (0),
                  eYes (1)
            }
    MAX-ACCESS read-write
    STATUS     current
    DESCRIPTION
            ""
    ::= { lcsSetupLancapiInterfaceListEntry 5 }

-- {COLUMN} 1.3.6.1.4.1.2356.11.2.13.6.1.6
lcsSetupLancapiInterfaceListEntryMaxConnections OBJECT-TYPE
    SYNTAX     Integer32 (0..255)
    MAX-ACCESS read-write
    STATUS     current
    DESCRIPTION
            ""
    ::= { lcsSetupLancapiInterfaceListEntry 6 }

-- {COLUMN} 1.3.6.1.4.1.2356.11.2.13.6.1.7
lcsSetupLancapiInterfaceListEntryVoipMode OBJECT-TYPE
    SYNTAX     INTEGER {
                  eNo (0),
                  eYes (1)
            }
    MAX-ACCESS read-write
    STATUS     current
    DESCRIPTION
            "-- empty --"
    ::= { lcsSetupLancapiInterfaceListEntry 7 }

-- {TABLE} 1.3.6.1.4.1.2356.11.2.13.7
lcsSetupLancapiPriorityListTable OBJECT-TYPE
    SYNTAX     SEQUENCE OF LcsSetupLancapiPriorityListEntry
    MAX-ACCESS not-accessible
    STATUS     current
    DESCRIPTION
            ""
    ::= { lcsSetupLancapi 7 }

-- {ROW} 1.3.6.1.4.1.2356.11.2.13.7.1
lcsSetupLancapiPriorityListEntry OBJECT-TYPE
    SYNTAX     LcsSetupLancapiPriorityListEntry
    MAX-ACCESS not-accessible
    STATUS     current
    DESCRIPTION
            ""
    INDEX {
            lcsSetupLancapiPriorityListEntryIfc
          }
    ::= { lcsSetupLancapiPriorityListTable 1 }

LcsSetupLancapiPriorityListEntry ::= SEQUENCE {
            lcsSetupLancapiPriorityListEntryIfc INTEGER,
            lcsSetupLancapiPriorityListEntryPrioOut INTEGER
    }

-- {COLUMN} 1.3.6.1.4.1.2356.11.2.13.7.1.1
lcsSetupLancapiPriorityListEntryIfc OBJECT-TYPE
    SYNTAX     INTEGER {
                  eS01 (1),
                  eS02 (2)
            }
    MAX-ACCESS read-only
    STATUS     current
    DESCRIPTION
            ""
    ::= { lcsSetupLancapiPriorityListEntry 1 }

-- {COLUMN} 1.3.6.1.4.1.2356.11.2.13.7.1.2
lcsSetupLancapiPriorityListEntryPrioOut OBJECT-TYPE
    SYNTAX     INTEGER {
                  eP1 (0),
                  eP2 (1),
                  eP3 (2)
            }
    MAX-ACCESS read-write
    STATUS     current
    DESCRIPTION
            ""
    ::= { lcsSetupLancapiPriorityListEntry 2 }

-- {NODE} 1.3.6.1.4.1.2356.11.2.14
lcsSetupTime OBJECT IDENTIFIER ::= { lcsSetup 14 }

-- {SCALAR} 1.3.6.1.4.1.2356.11.2.14.1
lcsSetupTimeFetchMethod OBJECT-TYPE
    SYNTAX     INTEGER {
                  eNone (0),
                  eIsdn (1),
                  eNtp (2),
                  eGps (3)
            }
    MAX-ACCESS read-write
    STATUS     current
    DESCRIPTION
            ""
    ::= { lcsSetupTime 1 }

-- {SCALAR} 1.3.6.1.4.1.2356.11.2.14.2
lcsSetupTimeCurrentTime OBJECT-TYPE
    SYNTAX     DisplayString
    MAX-ACCESS read-only
    STATUS     current
    DESCRIPTION
            ""
    ::= { lcsSetupTime 2 }

-- {SCALAR} 1.3.6.1.4.1.2356.11.2.14.3
lcsSetupTimeTimeCallNumber OBJECT-TYPE
    SYNTAX     DisplayString (SIZE(0..39))
    MAX-ACCESS read-write
    STATUS     current
    DESCRIPTION
            ""
    ::= { lcsSetupTime 3 }

-- {SCALAR} 1.3.6.1.4.1.2356.11.2.14.5
lcsSetupTimeCallAttempts OBJECT-TYPE
    SYNTAX     Integer32 (0..255)
    MAX-ACCESS read-write
    STATUS     current
    DESCRIPTION
            ""
    ::= { lcsSetupTime 5 }

-- {SCALAR} 1.3.6.1.4.1.2356.11.2.14.7
lcsSetupTimeUtcInSeconds OBJECT-TYPE
    SYNTAX     Counter32
    MAX-ACCESS read-only
    STATUS     current
    DESCRIPTION
            ""
    ::= { lcsSetupTime 7 }

-- {SCALAR} 1.3.6.1.4.1.2356.11.2.14.10
lcsSetupTimeTimezone OBJECT-TYPE
    SYNTAX     INTEGER {
                  e0 (0),
                  eplus1 (1),
                  eplus2 (2),
                  eplus3 (3),
                  eplus4 (4),
                  eplus5 (5),
                  eplus6 (6),
                  eplus7 (7),
                  eplus8 (8),
                  eplus9 (9),
                  eplus10 (10),
                  eplus11 (11),
                  eplus12 (12),
                  eplus13 (13),
                  eplus14 (14),
                  eminus12 (244),
                  eminus11 (245),
                  eminus10 (246),
                  eminus9 (247),
                  eminus8 (248),
                  eminus7 (249),
                  eminus6 (250),
                  eminus5 (251),
                  eminus4 (252),
                  eminus3 (253),
                  eminus2 (254),
                  eminus1 (255)
            }
    MAX-ACCESS read-write
    STATUS     current
    DESCRIPTION
            ""
    ::= { lcsSetupTime 10 }

-- {SCALAR} 1.3.6.1.4.1.2356.11.2.14.11
lcsSetupTimeDaylightSavingTime OBJECT-TYPE
    SYNTAX     INTEGER {
                  eNo (0),
                  eYes (1),
                  eEuropeEu (2),
                  eRussia (3),
                  eUsa (4),
                  eUserDefined (255)
            }
    MAX-ACCESS read-write
    STATUS     current
    DESCRIPTION
            ""
    ::= { lcsSetupTime 11 }

-- {TABLE} 1.3.6.1.4.1.2356.11.2.14.12
lcsSetupTimeDstClockChangesTable OBJECT-TYPE
    SYNTAX     SEQUENCE OF LcsSetupTimeDstClockChangesEntry
    MAX-ACCESS not-accessible
    STATUS     current
    DESCRIPTION
            ""
    ::= { lcsSetupTime 12 }

-- {ROW} 1.3.6.1.4.1.2356.11.2.14.12.1
lcsSetupTimeDstClockChangesEntry OBJECT-TYPE
    SYNTAX     LcsSetupTimeDstClockChangesEntry
    MAX-ACCESS not-accessible
    STATUS     current
    DESCRIPTION
            ""
    INDEX {
            lcsSetupTimeDstClockChangesEntryEvent
          }
    ::= { lcsSetupTimeDstClockChangesTable 1 }

LcsSetupTimeDstClockChangesEntry ::= SEQUENCE {
            lcsSetupTimeDstClockChangesEntryEvent INTEGER,
            lcsSetupTimeDstClockChangesEntryIndex INTEGER,
            lcsSetupTimeDstClockChangesEntryDay INTEGER,
            lcsSetupTimeDstClockChangesEntryMonth INTEGER,
            lcsSetupTimeDstClockChangesEntryHour Integer32,
            lcsSetupTimeDstClockChangesEntryMinute Integer32,
            lcsSetupTimeDstClockChangesEntryTimeType INTEGER
    }

-- {COLUMN} 1.3.6.1.4.1.2356.11.2.14.12.1.1
lcsSetupTimeDstClockChangesEntryEvent OBJECT-TYPE
    SYNTAX     INTEGER {
                  eStart (1),
                  eEnd (2)
            }
    MAX-ACCESS read-only
    STATUS     current
    DESCRIPTION
            ""
    ::= { lcsSetupTimeDstClockChangesEntry 1 }

-- {COLUMN} 1.3.6.1.4.1.2356.11.2.14.12.1.2
lcsSetupTimeDstClockChangesEntryIndex OBJECT-TYPE
    SYNTAX     INTEGER {
                  eFirst (1),
                  eSecond (2),
                  eThird (3),
                  eFourth (4),
                  e4Last (252),
                  e3Last (253),
                  e2Last (254),
                  eLast (255)
            }
    MAX-ACCESS read-write
    STATUS     current
    DESCRIPTION
            ""
    ::= { lcsSetupTimeDstClockChangesEntry 2 }

-- {COLUMN} 1.3.6.1.4.1.2356.11.2.14.12.1.3
lcsSetupTimeDstClockChangesEntryDay OBJECT-TYPE
    SYNTAX     INTEGER {
                  eSunday (0),
                  eMonday (1),
                  eTuesday (2),
                  eWednesday (3),
                  eThursday (4),
                  eFriday (5),
                  eSaturday (6)
            }
    MAX-ACCESS read-write
    STATUS     current
    DESCRIPTION
            ""
    ::= { lcsSetupTimeDstClockChangesEntry 3 }

-- {COLUMN} 1.3.6.1.4.1.2356.11.2.14.12.1.4
lcsSetupTimeDstClockChangesEntryMonth OBJECT-TYPE
    SYNTAX     INTEGER {
                  eJanuary (1),
                  eFebruary (2),
                  eMarch (3),
                  eApril (4),
                  eMay (5),
                  eJune (6),
                  eJuly (7),
                  eAugust (8),
                  eSeptember (9),
                  eOctober (10),
                  eNovember (11),
                  eDecember (12)
            }
    MAX-ACCESS read-write
    STATUS     current
    DESCRIPTION
            ""
    ::= { lcsSetupTimeDstClockChangesEntry 4 }

-- {COLUMN} 1.3.6.1.4.1.2356.11.2.14.12.1.5
lcsSetupTimeDstClockChangesEntryHour OBJECT-TYPE
    SYNTAX     Integer32 (0..255)
    MAX-ACCESS read-write
    STATUS     current
    DESCRIPTION
            ""
    ::= { lcsSetupTimeDstClockChangesEntry 5 }

-- {COLUMN} 1.3.6.1.4.1.2356.11.2.14.12.1.6
lcsSetupTimeDstClockChangesEntryMinute OBJECT-TYPE
    SYNTAX     Integer32 (0..255)
    MAX-ACCESS read-write
    STATUS     current
    DESCRIPTION
            ""
    ::= { lcsSetupTimeDstClockChangesEntry 6 }

-- {COLUMN} 1.3.6.1.4.1.2356.11.2.14.12.1.7
lcsSetupTimeDstClockChangesEntryTimeType OBJECT-TYPE
    SYNTAX     INTEGER {
                  eLst (0),
                  eUtc (1)
            }
    MAX-ACCESS read-write
    STATUS     current
    DESCRIPTION
            ""
    ::= { lcsSetupTimeDstClockChangesEntry 7 }

-- {SCALAR} 1.3.6.1.4.1.2356.11.2.14.13
lcsSetupTimeGetTime OBJECT-TYPE
    SYNTAX     DisplayString
    MAX-ACCESS read-write
    STATUS     current
    DESCRIPTION
            ""
    ::= { lcsSetupTime 13 }

-- {TABLE} 1.3.6.1.4.1.2356.11.2.14.15
lcsSetupTimeHolidaysTable OBJECT-TYPE
    SYNTAX     SEQUENCE OF LcsSetupTimeHolidaysEntry
    MAX-ACCESS not-accessible
    STATUS     current
    DESCRIPTION
            ""
    ::= { lcsSetupTime 15 }

-- {ROW} 1.3.6.1.4.1.2356.11.2.14.15.1
lcsSetupTimeHolidaysEntry OBJECT-TYPE
    SYNTAX     LcsSetupTimeHolidaysEntry
    MAX-ACCESS not-accessible
    STATUS     current
    DESCRIPTION
            ""
    INDEX {
            lcsSetupTimeHolidaysEntryIndex
          }
    ::= { lcsSetupTimeHolidaysTable 1 }

LcsSetupTimeHolidaysEntry ::= SEQUENCE {
            lcsSetupTimeHolidaysEntryIndex Integer32,
            lcsSetupTimeHolidaysEntryDate DisplayString
    }

-- {COLUMN} 1.3.6.1.4.1.2356.11.2.14.15.1.1
lcsSetupTimeHolidaysEntryIndex OBJECT-TYPE
    SYNTAX     Integer32 (0..65535)
    MAX-ACCESS read-write
    STATUS     current
    DESCRIPTION
            ""
    ::= { lcsSetupTimeHolidaysEntry 1 }

-- {COLUMN} 1.3.6.1.4.1.2356.11.2.14.15.1.2
lcsSetupTimeHolidaysEntryDate OBJECT-TYPE
    SYNTAX     DisplayString (SIZE(0..13))
    MAX-ACCESS read-write
    STATUS     current
    DESCRIPTION
            ""
    ::= { lcsSetupTimeHolidaysEntry 2 }

-- {TABLE} 1.3.6.1.4.1.2356.11.2.14.16
lcsSetupTimeTimeframeTable OBJECT-TYPE
    SYNTAX     SEQUENCE OF LcsSetupTimeTimeframeEntry
    MAX-ACCESS not-accessible
    STATUS     current
    DESCRIPTION
            ""
    ::= { lcsSetupTime 16 }

-- {ROW} 1.3.6.1.4.1.2356.11.2.14.16.1
lcsSetupTimeTimeframeEntry OBJECT-TYPE
    SYNTAX     LcsSetupTimeTimeframeEntry
    MAX-ACCESS not-accessible
    STATUS     current
    DESCRIPTION
            ""
    INDEX {
            lcsSetupTimeTimeframeEntryName,
            lcsSetupTimeTimeframeEntryStart,
            lcsSetupTimeTimeframeEntryStop,
            lcsSetupTimeTimeframeEntryWeekdays
          }
    ::= { lcsSetupTimeTimeframeTable 1 }

LcsSetupTimeTimeframeEntry ::= SEQUENCE {
            lcsSetupTimeTimeframeEntryName DisplayString,
            lcsSetupTimeTimeframeEntryStart DisplayString,
            lcsSetupTimeTimeframeEntryStop DisplayString,
            lcsSetupTimeTimeframeEntryWeekdays BITS
    }

-- {COLUMN} 1.3.6.1.4.1.2356.11.2.14.16.1.1
lcsSetupTimeTimeframeEntryName OBJECT-TYPE
    SYNTAX     DisplayString (SIZE(0..31))
    MAX-ACCESS read-write
    STATUS     current
    DESCRIPTION
            ""
    ::= { lcsSetupTimeTimeframeEntry 1 }

-- {COLUMN} 1.3.6.1.4.1.2356.11.2.14.16.1.2
lcsSetupTimeTimeframeEntryStart OBJECT-TYPE
    SYNTAX     DisplayString (SIZE(0..5))
    MAX-ACCESS read-write
    STATUS     current
    DESCRIPTION
            ""
    ::= { lcsSetupTimeTimeframeEntry 2 }

-- {COLUMN} 1.3.6.1.4.1.2356.11.2.14.16.1.3
lcsSetupTimeTimeframeEntryStop OBJECT-TYPE
    SYNTAX     DisplayString (SIZE(0..5))
    MAX-ACCESS read-write
    STATUS     current
    DESCRIPTION
            ""
    ::= { lcsSetupTimeTimeframeEntry 3 }

-- {COLUMN} 1.3.6.1.4.1.2356.11.2.14.16.1.4
lcsSetupTimeTimeframeEntryWeekdays OBJECT-TYPE
    SYNTAX     BITS {
                  eHoliday (0),
                  eSaturday (1),
                  eFriday (2),
                  eThursday (3),
                  eWednesday (4),
                  eTuesday (5),
                  eMonday (6),
                  eSunday (7)
            }
    MAX-ACCESS read-write
    STATUS     current
    DESCRIPTION
            ""
    ::= { lcsSetupTimeTimeframeEntry 4 }

-- {NODE} 1.3.6.1.4.1.2356.11.2.15
lcsSetupLcr OBJECT IDENTIFIER ::= { lcsSetup 15 }

-- {SCALAR} 1.3.6.1.4.1.2356.11.2.15.1
lcsSetupLcrRouterUsage OBJECT-TYPE
    SYNTAX     INTEGER {
                  eNo (0),
                  eYes (1)
            }
    MAX-ACCESS read-write
    STATUS     current
    DESCRIPTION
            ""
    ::= { lcsSetupLcr 1 }

-- {SCALAR} 1.3.6.1.4.1.2356.11.2.15.2
lcsSetupLcrLancapiUsage OBJECT-TYPE
    SYNTAX     INTEGER {
                  eNo (0),
                  eYes (1)
            }
    MAX-ACCESS read-write
    STATUS     current
    DESCRIPTION
            ""
    ::= { lcsSetupLcr 2 }

-- {TABLE} 1.3.6.1.4.1.2356.11.2.15.4
lcsSetupLcrTimeListTable OBJECT-TYPE
    SYNTAX     SEQUENCE OF LcsSetupLcrTimeListEntry
    MAX-ACCESS not-accessible
    STATUS     current
    DESCRIPTION
            ""
    ::= { lcsSetupLcr 4 }

-- {ROW} 1.3.6.1.4.1.2356.11.2.15.4.1
lcsSetupLcrTimeListEntry OBJECT-TYPE
    SYNTAX     LcsSetupLcrTimeListEntry
    MAX-ACCESS not-accessible
    STATUS     current
    DESCRIPTION
            ""
    INDEX {
            lcsSetupLcrTimeListEntryIndex
          }
    ::= { lcsSetupLcrTimeListTable 1 }

LcsSetupLcrTimeListEntry ::= SEQUENCE {
            lcsSetupLcrTimeListEntryIndex Integer32,
            lcsSetupLcrTimeListEntryPrefix DisplayString,
            lcsSetupLcrTimeListEntryDays BITS,
            lcsSetupLcrTimeListEntryStart DisplayString,
            lcsSetupLcrTimeListEntryStop DisplayString,
            lcsSetupLcrTimeListEntryNumberList DisplayString,
            lcsSetupLcrTimeListEntryFallback INTEGER
    }

-- {COLUMN} 1.3.6.1.4.1.2356.11.2.15.4.1.1
lcsSetupLcrTimeListEntryIndex OBJECT-TYPE
    SYNTAX     Integer32 (0..65535)
    MAX-ACCESS read-write
    STATUS     current
    DESCRIPTION
            ""
    ::= { lcsSetupLcrTimeListEntry 1 }

-- {COLUMN} 1.3.6.1.4.1.2356.11.2.15.4.1.2
lcsSetupLcrTimeListEntryPrefix OBJECT-TYPE
    SYNTAX     DisplayString (SIZE(0..10))
    MAX-ACCESS read-write
    STATUS     current
    DESCRIPTION
            ""
    ::= { lcsSetupLcrTimeListEntry 2 }

-- {COLUMN} 1.3.6.1.4.1.2356.11.2.15.4.1.3
lcsSetupLcrTimeListEntryDays OBJECT-TYPE
    SYNTAX     BITS {
                  eHoliday (0),
                  eSunday (1),
                  eSaturday (2),
                  eFriday (3),
                  eThursday (4),
                  eWednesday (5),
                  eTuesday (6),
                  eMonday (7)
            }
    MAX-ACCESS read-write
    STATUS     current
    DESCRIPTION
            ""
    ::= { lcsSetupLcrTimeListEntry 3 }

-- {COLUMN} 1.3.6.1.4.1.2356.11.2.15.4.1.4
lcsSetupLcrTimeListEntryStart OBJECT-TYPE
    SYNTAX     DisplayString (SIZE(0..5))
    MAX-ACCESS read-write
    STATUS     current
    DESCRIPTION
            ""
    ::= { lcsSetupLcrTimeListEntry 4 }

-- {COLUMN} 1.3.6.1.4.1.2356.11.2.15.4.1.5
lcsSetupLcrTimeListEntryStop OBJECT-TYPE
    SYNTAX     DisplayString (SIZE(0..5))
    MAX-ACCESS read-write
    STATUS     current
    DESCRIPTION
            ""
    ::= { lcsSetupLcrTimeListEntry 5 }

-- {COLUMN} 1.3.6.1.4.1.2356.11.2.15.4.1.6
lcsSetupLcrTimeListEntryNumberList OBJECT-TYPE
    SYNTAX     DisplayString (SIZE(0..29))
    MAX-ACCESS read-write
    STATUS     current
    DESCRIPTION
            ""
    ::= { lcsSetupLcrTimeListEntry 6 }

-- {COLUMN} 1.3.6.1.4.1.2356.11.2.15.4.1.7
lcsSetupLcrTimeListEntryFallback OBJECT-TYPE
    SYNTAX     INTEGER {
                  eNo (0),
                  eYes (1)
            }
    MAX-ACCESS read-write
    STATUS     current
    DESCRIPTION
            ""
    ::= { lcsSetupLcrTimeListEntry 7 }

-- {NODE} 1.3.6.1.4.1.2356.11.2.16
lcsSetupNetbios OBJECT IDENTIFIER ::= { lcsSetup 16 }

-- {SCALAR} 1.3.6.1.4.1.2356.11.2.16.1
lcsSetupNetbiosOperating OBJECT-TYPE
    SYNTAX     INTEGER {
                  eNo (0),
                  eYes (1)
            }
    MAX-ACCESS read-write
    STATUS     current
    DESCRIPTION
            ""
    ::= { lcsSetupNetbios 1 }

-- {SCALAR} 1.3.6.1.4.1.2356.11.2.16.2
lcsSetupNetbiosScopeId OBJECT-TYPE
    SYNTAX     DisplayString (SIZE(0..64))
    MAX-ACCESS read-write
    STATUS     current
    DESCRIPTION
            ""
    ::= { lcsSetupNetbios 2 }

-- {TABLE} 1.3.6.1.4.1.2356.11.2.16.4
lcsSetupNetbiosPeersTable OBJECT-TYPE
    SYNTAX     SEQUENCE OF LcsSetupNetbiosPeersEntry
    MAX-ACCESS not-accessible
    STATUS     current
    DESCRIPTION
            ""
    ::= { lcsSetupNetbios 4 }

-- {ROW} 1.3.6.1.4.1.2356.11.2.16.4.1
lcsSetupNetbiosPeersEntry OBJECT-TYPE
    SYNTAX     LcsSetupNetbiosPeersEntry
    MAX-ACCESS not-accessible
    STATUS     current
    DESCRIPTION
            ""
    INDEX {
            lcsSetupNetbiosPeersEntryName
          }
    ::= { lcsSetupNetbiosPeersTable 1 }

LcsSetupNetbiosPeersEntry ::= SEQUENCE {
            lcsSetupNetbiosPeersEntryName DisplayString,
            lcsSetupNetbiosPeersEntryType INTEGER
    }

-- {COLUMN} 1.3.6.1.4.1.2356.11.2.16.4.1.1
lcsSetupNetbiosPeersEntryName OBJECT-TYPE
    SYNTAX     DisplayString (SIZE(0..16))
    MAX-ACCESS read-write
    STATUS     current
    DESCRIPTION
            ""
    ::= { lcsSetupNetbiosPeersEntry 1 }

-- {COLUMN} 1.3.6.1.4.1.2356.11.2.16.4.1.3
lcsSetupNetbiosPeersEntryType OBJECT-TYPE
    SYNTAX     INTEGER {
                  eRouter (0),
                  eWorkstation (1)
            }
    MAX-ACCESS read-write
    STATUS     current
    DESCRIPTION
            ""
    ::= { lcsSetupNetbiosPeersEntry 3 }

-- {TABLE} 1.3.6.1.4.1.2356.11.2.16.5
lcsSetupNetbiosGroupListTable OBJECT-TYPE
    SYNTAX     SEQUENCE OF LcsSetupNetbiosGroupListEntry
    MAX-ACCESS not-accessible
    STATUS     current
    DESCRIPTION
            ""
    ::= { lcsSetupNetbios 5 }

-- {ROW} 1.3.6.1.4.1.2356.11.2.16.5.1
lcsSetupNetbiosGroupListEntry OBJECT-TYPE
    SYNTAX     LcsSetupNetbiosGroupListEntry
    MAX-ACCESS not-accessible
    STATUS     current
    DESCRIPTION
            ""
    INDEX {
            lcsSetupNetbiosGroupListEntryGroupDomain,
            lcsSetupNetbiosGroupListEntryType,
            lcsSetupNetbiosGroupListEntryIpAddress,
            lcsSetupNetbiosGroupListEntryRtgTag
          }
    ::= { lcsSetupNetbiosGroupListTable 1 }

LcsSetupNetbiosGroupListEntry ::= SEQUENCE {
            lcsSetupNetbiosGroupListEntryGroupDomain DisplayString,
            lcsSetupNetbiosGroupListEntryType DisplayString,
            lcsSetupNetbiosGroupListEntryIpAddress IpAddress,
            lcsSetupNetbiosGroupListEntryPeer DisplayString,
            lcsSetupNetbiosGroupListEntryTimeout Integer32,
            lcsSetupNetbiosGroupListEntryFlags DisplayString,
            lcsSetupNetbiosGroupListEntryNetworkName DisplayString,
            lcsSetupNetbiosGroupListEntryRtgTag Integer32
    }

-- {COLUMN} 1.3.6.1.4.1.2356.11.2.16.5.1.1
lcsSetupNetbiosGroupListEntryGroupDomain OBJECT-TYPE
    SYNTAX     DisplayString (SIZE(0..15))
    MAX-ACCESS read-only
    STATUS     current
    DESCRIPTION
            ""
    ::= { lcsSetupNetbiosGroupListEntry 1 }

-- {COLUMN} 1.3.6.1.4.1.2356.11.2.16.5.1.2
lcsSetupNetbiosGroupListEntryType OBJECT-TYPE
    SYNTAX     DisplayString (SIZE(0..1))
    MAX-ACCESS read-only
    STATUS     current
    DESCRIPTION
            ""
    ::= { lcsSetupNetbiosGroupListEntry 2 }

-- {COLUMN} 1.3.6.1.4.1.2356.11.2.16.5.1.3
lcsSetupNetbiosGroupListEntryIpAddress OBJECT-TYPE
    SYNTAX     IpAddress
    MAX-ACCESS read-only
    STATUS     current
    DESCRIPTION
            ""
    ::= { lcsSetupNetbiosGroupListEntry 3 }

-- {COLUMN} 1.3.6.1.4.1.2356.11.2.16.5.1.4
lcsSetupNetbiosGroupListEntryPeer OBJECT-TYPE
    SYNTAX     DisplayString (SIZE(0..16))
    MAX-ACCESS read-only
    STATUS     current
    DESCRIPTION
            ""
    ::= { lcsSetupNetbiosGroupListEntry 4 }

-- {COLUMN} 1.3.6.1.4.1.2356.11.2.16.5.1.5
lcsSetupNetbiosGroupListEntryTimeout OBJECT-TYPE
    SYNTAX     Integer32 (0..2147483647)
    MAX-ACCESS read-only
    STATUS     current
    DESCRIPTION
            ""
    ::= { lcsSetupNetbiosGroupListEntry 5 }

-- {COLUMN} 1.3.6.1.4.1.2356.11.2.16.5.1.6
lcsSetupNetbiosGroupListEntryFlags OBJECT-TYPE
    SYNTAX     DisplayString (SIZE(0..2))
    MAX-ACCESS read-only
    STATUS     current
    DESCRIPTION
            ""
    ::= { lcsSetupNetbiosGroupListEntry 6 }

-- {COLUMN} 1.3.6.1.4.1.2356.11.2.16.5.1.7
lcsSetupNetbiosGroupListEntryNetworkName OBJECT-TYPE
    SYNTAX     DisplayString (SIZE(0..16))
    MAX-ACCESS read-only
    STATUS     current
    DESCRIPTION
            ""
    ::= { lcsSetupNetbiosGroupListEntry 7 }

-- {COLUMN} 1.3.6.1.4.1.2356.11.2.16.5.1.8
lcsSetupNetbiosGroupListEntryRtgTag OBJECT-TYPE
    SYNTAX     Integer32 (0..65535)
    MAX-ACCESS read-only
    STATUS     current
    DESCRIPTION
            ""
    ::= { lcsSetupNetbiosGroupListEntry 8 }

-- {TABLE} 1.3.6.1.4.1.2356.11.2.16.6
lcsSetupNetbiosHostListTable OBJECT-TYPE
    SYNTAX     SEQUENCE OF LcsSetupNetbiosHostListEntry
    MAX-ACCESS not-accessible
    STATUS     current
    DESCRIPTION
            ""
    ::= { lcsSetupNetbios 6 }

-- {ROW} 1.3.6.1.4.1.2356.11.2.16.6.1
lcsSetupNetbiosHostListEntry OBJECT-TYPE
    SYNTAX     LcsSetupNetbiosHostListEntry
    MAX-ACCESS not-accessible
    STATUS     current
    DESCRIPTION
            ""
    INDEX {
            lcsSetupNetbiosHostListEntryName,
            lcsSetupNetbiosHostListEntryType,
            lcsSetupNetbiosHostListEntryIpAddress,
            lcsSetupNetbiosHostListEntryRtgTag
          }
    ::= { lcsSetupNetbiosHostListTable 1 }

LcsSetupNetbiosHostListEntry ::= SEQUENCE {
            lcsSetupNetbiosHostListEntryName DisplayString,
            lcsSetupNetbiosHostListEntryType DisplayString,
            lcsSetupNetbiosHostListEntryIpAddress IpAddress,
            lcsSetupNetbiosHostListEntryPeer DisplayString,
            lcsSetupNetbiosHostListEntryTimeout Integer32,
            lcsSetupNetbiosHostListEntryFlags DisplayString,
            lcsSetupNetbiosHostListEntryNetworkName DisplayString,
            lcsSetupNetbiosHostListEntryRtgTag Integer32
    }

-- {COLUMN} 1.3.6.1.4.1.2356.11.2.16.6.1.1
lcsSetupNetbiosHostListEntryName OBJECT-TYPE
    SYNTAX     DisplayString (SIZE(0..15))
    MAX-ACCESS read-only
    STATUS     current
    DESCRIPTION
            ""
    ::= { lcsSetupNetbiosHostListEntry 1 }

-- {COLUMN} 1.3.6.1.4.1.2356.11.2.16.6.1.2
lcsSetupNetbiosHostListEntryType OBJECT-TYPE
    SYNTAX     DisplayString (SIZE(0..1))
    MAX-ACCESS read-only
    STATUS     current
    DESCRIPTION
            ""
    ::= { lcsSetupNetbiosHostListEntry 2 }

-- {COLUMN} 1.3.6.1.4.1.2356.11.2.16.6.1.3
lcsSetupNetbiosHostListEntryIpAddress OBJECT-TYPE
    SYNTAX     IpAddress
    MAX-ACCESS read-only
    STATUS     current
    DESCRIPTION
            ""
    ::= { lcsSetupNetbiosHostListEntry 3 }

-- {COLUMN} 1.3.6.1.4.1.2356.11.2.16.6.1.4
lcsSetupNetbiosHostListEntryPeer OBJECT-TYPE
    SYNTAX     DisplayString (SIZE(0..16))
    MAX-ACCESS read-only
    STATUS     current
    DESCRIPTION
            ""
    ::= { lcsSetupNetbiosHostListEntry 4 }

-- {COLUMN} 1.3.6.1.4.1.2356.11.2.16.6.1.5
lcsSetupNetbiosHostListEntryTimeout OBJECT-TYPE
    SYNTAX     Integer32 (0..2147483647)
    MAX-ACCESS read-only
    STATUS     current
    DESCRIPTION
            ""
    ::= { lcsSetupNetbiosHostListEntry 5 }

-- {COLUMN} 1.3.6.1.4.1.2356.11.2.16.6.1.6
lcsSetupNetbiosHostListEntryFlags OBJECT-TYPE
    SYNTAX     DisplayString (SIZE(0..2))
    MAX-ACCESS read-only
    STATUS     current
    DESCRIPTION
            ""
    ::= { lcsSetupNetbiosHostListEntry 6 }

-- {COLUMN} 1.3.6.1.4.1.2356.11.2.16.6.1.7
lcsSetupNetbiosHostListEntryNetworkName OBJECT-TYPE
    SYNTAX     DisplayString (SIZE(0..16))
    MAX-ACCESS read-only
    STATUS     current
    DESCRIPTION
            ""
    ::= { lcsSetupNetbiosHostListEntry 7 }

-- {COLUMN} 1.3.6.1.4.1.2356.11.2.16.6.1.8
lcsSetupNetbiosHostListEntryRtgTag OBJECT-TYPE
    SYNTAX     Integer32 (0..65535)
    MAX-ACCESS read-only
    STATUS     current
    DESCRIPTION
            ""
    ::= { lcsSetupNetbiosHostListEntry 8 }

-- {TABLE} 1.3.6.1.4.1.2356.11.2.16.7
lcsSetupNetbiosServerListTable OBJECT-TYPE
    SYNTAX     SEQUENCE OF LcsSetupNetbiosServerListEntry
    MAX-ACCESS not-accessible
    STATUS     current
    DESCRIPTION
            ""
    ::= { lcsSetupNetbios 7 }

-- {ROW} 1.3.6.1.4.1.2356.11.2.16.7.1
lcsSetupNetbiosServerListEntry OBJECT-TYPE
    SYNTAX     LcsSetupNetbiosServerListEntry
    MAX-ACCESS not-accessible
    STATUS     current
    DESCRIPTION
            ""
    INDEX {
            lcsSetupNetbiosServerListEntryHost,
            lcsSetupNetbiosServerListEntryGroupDomain,
            lcsSetupNetbiosServerListEntryIpAddress,
            lcsSetupNetbiosServerListEntryRtgTag
          }
    ::= { lcsSetupNetbiosServerListTable 1 }

LcsSetupNetbiosServerListEntry ::= SEQUENCE {
            lcsSetupNetbiosServerListEntryHost DisplayString,
            lcsSetupNetbiosServerListEntryGroupDomain DisplayString,
            lcsSetupNetbiosServerListEntryIpAddress DisplayString,
            lcsSetupNetbiosServerListEntryOsVer DisplayString,
            lcsSetupNetbiosServerListEntrySmbVer DisplayString,
            lcsSetupNetbiosServerListEntryServerTyp DisplayString,
            lcsSetupNetbiosServerListEntryPeer DisplayString,
            lcsSetupNetbiosServerListEntryTimeout Integer32,
            lcsSetupNetbiosServerListEntryFlags DisplayString,
            lcsSetupNetbiosServerListEntryNetworkName DisplayString,
            lcsSetupNetbiosServerListEntryRtgTag Integer32
    }

-- {COLUMN} 1.3.6.1.4.1.2356.11.2.16.7.1.1
lcsSetupNetbiosServerListEntryHost OBJECT-TYPE
    SYNTAX     DisplayString (SIZE(0..15))
    MAX-ACCESS read-only
    STATUS     current
    DESCRIPTION
            ""
    ::= { lcsSetupNetbiosServerListEntry 1 }

-- {COLUMN} 1.3.6.1.4.1.2356.11.2.16.7.1.2
lcsSetupNetbiosServerListEntryGroupDomain OBJECT-TYPE
    SYNTAX     DisplayString (SIZE(0..16))
    MAX-ACCESS read-only
    STATUS     current
    DESCRIPTION
            ""
    ::= { lcsSetupNetbiosServerListEntry 2 }

-- {COLUMN} 1.3.6.1.4.1.2356.11.2.16.7.1.4
lcsSetupNetbiosServerListEntryIpAddress OBJECT-TYPE
    SYNTAX     DisplayString (SIZE(0..15))
    MAX-ACCESS read-only
    STATUS     current
    DESCRIPTION
            ""
    ::= { lcsSetupNetbiosServerListEntry 4 }

-- {COLUMN} 1.3.6.1.4.1.2356.11.2.16.7.1.5
lcsSetupNetbiosServerListEntryOsVer OBJECT-TYPE
    SYNTAX     DisplayString (SIZE(0..2))
    MAX-ACCESS read-only
    STATUS     current
    DESCRIPTION
            ""
    ::= { lcsSetupNetbiosServerListEntry 5 }

-- {COLUMN} 1.3.6.1.4.1.2356.11.2.16.7.1.6
lcsSetupNetbiosServerListEntrySmbVer OBJECT-TYPE
    SYNTAX     DisplayString (SIZE(0..2))
    MAX-ACCESS read-only
    STATUS     current
    DESCRIPTION
            ""
    ::= { lcsSetupNetbiosServerListEntry 6 }

-- {COLUMN} 1.3.6.1.4.1.2356.11.2.16.7.1.7
lcsSetupNetbiosServerListEntryServerTyp OBJECT-TYPE
    SYNTAX     DisplayString (SIZE(0..4))
    MAX-ACCESS read-only
    STATUS     current
    DESCRIPTION
            ""
    ::= { lcsSetupNetbiosServerListEntry 7 }

-- {COLUMN} 1.3.6.1.4.1.2356.11.2.16.7.1.8
lcsSetupNetbiosServerListEntryPeer OBJECT-TYPE
    SYNTAX     DisplayString (SIZE(0..16))
    MAX-ACCESS read-only
    STATUS     current
    DESCRIPTION
            ""
    ::= { lcsSetupNetbiosServerListEntry 8 }

-- {COLUMN} 1.3.6.1.4.1.2356.11.2.16.7.1.9
lcsSetupNetbiosServerListEntryTimeout OBJECT-TYPE
    SYNTAX     Integer32 (0..2147483647)
    MAX-ACCESS read-only
    STATUS     current
    DESCRIPTION
            ""
    ::= { lcsSetupNetbiosServerListEntry 9 }

-- {COLUMN} 1.3.6.1.4.1.2356.11.2.16.7.1.10
lcsSetupNetbiosServerListEntryFlags OBJECT-TYPE
    SYNTAX     DisplayString (SIZE(0..2))
    MAX-ACCESS read-only
    STATUS     current
    DESCRIPTION
            ""
    ::= { lcsSetupNetbiosServerListEntry 10 }

-- {COLUMN} 1.3.6.1.4.1.2356.11.2.16.7.1.11
lcsSetupNetbiosServerListEntryNetworkName OBJECT-TYPE
    SYNTAX     DisplayString (SIZE(0..16))
    MAX-ACCESS read-only
    STATUS     current
    DESCRIPTION
            ""
    ::= { lcsSetupNetbiosServerListEntry 11 }

-- {COLUMN} 1.3.6.1.4.1.2356.11.2.16.7.1.12
lcsSetupNetbiosServerListEntryRtgTag OBJECT-TYPE
    SYNTAX     Integer32 (0..65535)
    MAX-ACCESS read-only
    STATUS     current
    DESCRIPTION
            ""
    ::= { lcsSetupNetbiosServerListEntry 12 }

-- {SCALAR} 1.3.6.1.4.1.2356.11.2.16.8
lcsSetupNetbiosWatchdogs OBJECT-TYPE
    SYNTAX     INTEGER {
                  eRoute (0),
                  eSpoof (1)
            }
    MAX-ACCESS read-write
    STATUS     current
    DESCRIPTION
            ""
    ::= { lcsSetupNetbios 8 }

-- {SCALAR} 1.3.6.1.4.1.2356.11.2.16.9
lcsSetupNetbiosUpdate OBJECT-TYPE
    SYNTAX     INTEGER {
                  ePback (0),
                  eTrig (1),
                  eTime (2)
            }
    MAX-ACCESS read-write
    STATUS     current
    DESCRIPTION
            ""
    ::= { lcsSetupNetbios 9 }

-- {SCALAR} 1.3.6.1.4.1.2356.11.2.16.10
lcsSetupNetbiosWanUpdateMinutes OBJECT-TYPE
    SYNTAX     Integer32 (0..65535)
    MAX-ACCESS read-write
    STATUS     current
    DESCRIPTION
            ""
    ::= { lcsSetupNetbios 10 }

-- {SCALAR} 1.3.6.1.4.1.2356.11.2.16.11
lcsSetupNetbiosLeasetime OBJECT-TYPE
    SYNTAX     Integer32 (0..65535)
    MAX-ACCESS read-write
    STATUS     current
    DESCRIPTION
            ""
    ::= { lcsSetupNetbios 11 }

-- {TABLE} 1.3.6.1.4.1.2356.11.2.16.12
lcsSetupNetbiosNetworksTable OBJECT-TYPE
    SYNTAX     SEQUENCE OF LcsSetupNetbiosNetworksEntry
    MAX-ACCESS not-accessible
    STATUS     current
    DESCRIPTION
            ""
    ::= { lcsSetupNetbios 12 }

-- {ROW} 1.3.6.1.4.1.2356.11.2.16.12.1
lcsSetupNetbiosNetworksEntry OBJECT-TYPE
    SYNTAX     LcsSetupNetbiosNetworksEntry
    MAX-ACCESS not-accessible
    STATUS     current
    DESCRIPTION
            ""
    INDEX {
            lcsSetupNetbiosNetworksEntryNetworkName
          }
    ::= { lcsSetupNetbiosNetworksTable 1 }

LcsSetupNetbiosNetworksEntry ::= SEQUENCE {
            lcsSetupNetbiosNetworksEntryNetworkName DisplayString,
            lcsSetupNetbiosNetworksEntryOperating INTEGER,
            lcsSetupNetbiosNetworksEntryNtDomain DisplayString
    }

-- {COLUMN} 1.3.6.1.4.1.2356.11.2.16.12.1.1
lcsSetupNetbiosNetworksEntryNetworkName OBJECT-TYPE
    SYNTAX     DisplayString (SIZE(0..16))
    MAX-ACCESS read-write
    STATUS     current
    DESCRIPTION
            ""
    ::= { lcsSetupNetbiosNetworksEntry 1 }

-- {COLUMN} 1.3.6.1.4.1.2356.11.2.16.12.1.2
lcsSetupNetbiosNetworksEntryOperating OBJECT-TYPE
    SYNTAX     INTEGER {
                  eNo (0),
                  eYes (1)
            }
    MAX-ACCESS read-write
    STATUS     current
    DESCRIPTION
            ""
    ::= { lcsSetupNetbiosNetworksEntry 2 }

-- {COLUMN} 1.3.6.1.4.1.2356.11.2.16.12.1.3
lcsSetupNetbiosNetworksEntryNtDomain OBJECT-TYPE
    SYNTAX     DisplayString (SIZE(0..15))
    MAX-ACCESS read-write
    STATUS     current
    DESCRIPTION
            ""
    ::= { lcsSetupNetbiosNetworksEntry 3 }

-- {TABLE} 1.3.6.1.4.1.2356.11.2.16.13
lcsSetupNetbiosBrowserListTable OBJECT-TYPE
    SYNTAX     SEQUENCE OF LcsSetupNetbiosBrowserListEntry
    MAX-ACCESS not-accessible
    STATUS     current
    DESCRIPTION
            ""
    ::= { lcsSetupNetbios 13 }

-- {ROW} 1.3.6.1.4.1.2356.11.2.16.13.1
lcsSetupNetbiosBrowserListEntry OBJECT-TYPE
    SYNTAX     LcsSetupNetbiosBrowserListEntry
    MAX-ACCESS not-accessible
    STATUS     current
    DESCRIPTION
            ""
    INDEX {
            lcsSetupNetbiosBrowserListEntryBrowser,
            lcsSetupNetbiosBrowserListEntryGroupDomain,
            lcsSetupNetbiosBrowserListEntryIpAddress,
            lcsSetupNetbiosBrowserListEntryRtgTag
          }
    ::= { lcsSetupNetbiosBrowserListTable 1 }

LcsSetupNetbiosBrowserListEntry ::= SEQUENCE {
            lcsSetupNetbiosBrowserListEntryBrowser DisplayString,
            lcsSetupNetbiosBrowserListEntryGroupDomain DisplayString,
            lcsSetupNetbiosBrowserListEntryIpAddress DisplayString,
            lcsSetupNetbiosBrowserListEntryOsVer DisplayString,
            lcsSetupNetbiosBrowserListEntryServerTyp DisplayString,
            lcsSetupNetbiosBrowserListEntryPeer DisplayString,
            lcsSetupNetbiosBrowserListEntryTimeout Integer32,
            lcsSetupNetbiosBrowserListEntryFlags DisplayString,
            lcsSetupNetbiosBrowserListEntryNetworkName DisplayString,
            lcsSetupNetbiosBrowserListEntryRtgTag Integer32
    }

-- {COLUMN} 1.3.6.1.4.1.2356.11.2.16.13.1.1
lcsSetupNetbiosBrowserListEntryBrowser OBJECT-TYPE
    SYNTAX     DisplayString (SIZE(0..15))
    MAX-ACCESS read-only
    STATUS     current
    DESCRIPTION
            ""
    ::= { lcsSetupNetbiosBrowserListEntry 1 }

-- {COLUMN} 1.3.6.1.4.1.2356.11.2.16.13.1.2
lcsSetupNetbiosBrowserListEntryGroupDomain OBJECT-TYPE
    SYNTAX     DisplayString (SIZE(0..16))
    MAX-ACCESS read-only
    STATUS     current
    DESCRIPTION
            ""
    ::= { lcsSetupNetbiosBrowserListEntry 2 }

-- {COLUMN} 1.3.6.1.4.1.2356.11.2.16.13.1.4
lcsSetupNetbiosBrowserListEntryIpAddress OBJECT-TYPE
    SYNTAX     DisplayString (SIZE(0..15))
    MAX-ACCESS read-only
    STATUS     current
    DESCRIPTION
            ""
    ::= { lcsSetupNetbiosBrowserListEntry 4 }

-- {COLUMN} 1.3.6.1.4.1.2356.11.2.16.13.1.5
lcsSetupNetbiosBrowserListEntryOsVer OBJECT-TYPE
    SYNTAX     DisplayString (SIZE(0..2))
    MAX-ACCESS read-only
    STATUS     current
    DESCRIPTION
            ""
    ::= { lcsSetupNetbiosBrowserListEntry 5 }

-- {COLUMN} 1.3.6.1.4.1.2356.11.2.16.13.1.7
lcsSetupNetbiosBrowserListEntryServerTyp OBJECT-TYPE
    SYNTAX     DisplayString (SIZE(0..4))
    MAX-ACCESS read-only
    STATUS     current
    DESCRIPTION
            ""
    ::= { lcsSetupNetbiosBrowserListEntry 7 }

-- {COLUMN} 1.3.6.1.4.1.2356.11.2.16.13.1.8
lcsSetupNetbiosBrowserListEntryPeer OBJECT-TYPE
    SYNTAX     DisplayString (SIZE(0..16))
    MAX-ACCESS read-only
    STATUS     current
    DESCRIPTION
            ""
    ::= { lcsSetupNetbiosBrowserListEntry 8 }

-- {COLUMN} 1.3.6.1.4.1.2356.11.2.16.13.1.9
lcsSetupNetbiosBrowserListEntryTimeout OBJECT-TYPE
    SYNTAX     Integer32 (0..2147483647)
    MAX-ACCESS read-only
    STATUS     current
    DESCRIPTION
            ""
    ::= { lcsSetupNetbiosBrowserListEntry 9 }

-- {COLUMN} 1.3.6.1.4.1.2356.11.2.16.13.1.10
lcsSetupNetbiosBrowserListEntryFlags OBJECT-TYPE
    SYNTAX     DisplayString (SIZE(0..2))
    MAX-ACCESS read-only
    STATUS     current
    DESCRIPTION
            ""
    ::= { lcsSetupNetbiosBrowserListEntry 10 }

-- {COLUMN} 1.3.6.1.4.1.2356.11.2.16.13.1.11
lcsSetupNetbiosBrowserListEntryNetworkName OBJECT-TYPE
    SYNTAX     DisplayString (SIZE(0..16))
    MAX-ACCESS read-only
    STATUS     current
    DESCRIPTION
            ""
    ::= { lcsSetupNetbiosBrowserListEntry 11 }

-- {COLUMN} 1.3.6.1.4.1.2356.11.2.16.13.1.12
lcsSetupNetbiosBrowserListEntryRtgTag OBJECT-TYPE
    SYNTAX     Integer32 (0..65535)
    MAX-ACCESS read-only
    STATUS     current
    DESCRIPTION
            ""
    ::= { lcsSetupNetbiosBrowserListEntry 12 }

-- {SCALAR} 1.3.6.1.4.1.2356.11.2.16.14
lcsSetupNetbiosSupportBrowsing OBJECT-TYPE
    SYNTAX     INTEGER {
                  eNo (0),
                  eYes (1)
            }
    MAX-ACCESS read-write
    STATUS     current
    DESCRIPTION
            ""
    ::= { lcsSetupNetbios 14 }

-- {NODE} 1.3.6.1.4.1.2356.11.2.17
lcsSetupDns OBJECT IDENTIFIER ::= { lcsSetup 17 }

-- {SCALAR} 1.3.6.1.4.1.2356.11.2.17.1
lcsSetupDnsOperating OBJECT-TYPE
    SYNTAX     INTEGER {
                  eNo (0),
                  eYes (1)
            }
    MAX-ACCESS read-write
    STATUS     current
    DESCRIPTION
            ""
    ::= { lcsSetupDns 1 }

-- {SCALAR} 1.3.6.1.4.1.2356.11.2.17.2
lcsSetupDnsDomain OBJECT-TYPE
    SYNTAX     DisplayString (SIZE(0..64))
    MAX-ACCESS read-write
    STATUS     current
    DESCRIPTION
            ""
    ::= { lcsSetupDns 2 }

-- {SCALAR} 1.3.6.1.4.1.2356.11.2.17.3
lcsSetupDnsDhcpUsage OBJECT-TYPE
    SYNTAX     INTEGER {
                  eNo (0),
                  eYes (1)
            }
    MAX-ACCESS read-write
    STATUS     current
    DESCRIPTION
            ""
    ::= { lcsSetupDns 3 }

-- {SCALAR} 1.3.6.1.4.1.2356.11.2.17.4
lcsSetupDnsNetbiosUsage OBJECT-TYPE
    SYNTAX     INTEGER {
                  eNo (0),
                  eYes (1)
            }
    MAX-ACCESS read-write
    STATUS     current
    DESCRIPTION
            ""
    ::= { lcsSetupDns 4 }

-- {TABLE} 1.3.6.1.4.1.2356.11.2.17.5
lcsSetupDnsDnsListTable OBJECT-TYPE
    SYNTAX     SEQUENCE OF LcsSetupDnsDnsListEntry
    MAX-ACCESS not-accessible
    STATUS     current
    DESCRIPTION
            ""
    ::= { lcsSetupDns 5 }

-- {ROW} 1.3.6.1.4.1.2356.11.2.17.5.1
lcsSetupDnsDnsListEntry OBJECT-TYPE
    SYNTAX     LcsSetupDnsDnsListEntry
    MAX-ACCESS not-accessible
    STATUS     current
    DESCRIPTION
            ""
    INDEX {
            lcsSetupDnsDnsListEntryHostName,
            lcsSetupDnsDnsListEntryRtgTag
          }
    ::= { lcsSetupDnsDnsListTable 1 }

LcsSetupDnsDnsListEntry ::= SEQUENCE {
            lcsSetupDnsDnsListEntryHostName DisplayString,
            lcsSetupDnsDnsListEntryIpAddress IpAddress,
            lcsSetupDnsDnsListEntryIpv6Address DisplayString,
            lcsSetupDnsDnsListEntryRtgTag Integer32
    }

-- {COLUMN} 1.3.6.1.4.1.2356.11.2.17.5.1.1
lcsSetupDnsDnsListEntryHostName OBJECT-TYPE
    SYNTAX     DisplayString (SIZE(0..64))
    MAX-ACCESS read-write
    STATUS     current
    DESCRIPTION
            ""
    ::= { lcsSetupDnsDnsListEntry 1 }

-- {COLUMN} 1.3.6.1.4.1.2356.11.2.17.5.1.2
lcsSetupDnsDnsListEntryIpAddress OBJECT-TYPE
    SYNTAX     IpAddress
    MAX-ACCESS read-write
    STATUS     current
    DESCRIPTION
            ""
    ::= { lcsSetupDnsDnsListEntry 2 }

-- {COLUMN} 1.3.6.1.4.1.2356.11.2.17.5.1.3
lcsSetupDnsDnsListEntryIpv6Address OBJECT-TYPE
    SYNTAX     DisplayString (SIZE(0..39))
    MAX-ACCESS read-write
    STATUS     current
    DESCRIPTION
            "-- empty --"
    ::= { lcsSetupDnsDnsListEntry 3 }

-- {COLUMN} 1.3.6.1.4.1.2356.11.2.17.5.1.4
lcsSetupDnsDnsListEntryRtgTag OBJECT-TYPE
    SYNTAX     Integer32 (0..65535)
    MAX-ACCESS read-write
    STATUS     current
    DESCRIPTION
            "-- empty --"
    ::= { lcsSetupDnsDnsListEntry 4 }

-- {TABLE} 1.3.6.1.4.1.2356.11.2.17.6
lcsSetupDnsFilterListTable OBJECT-TYPE
    SYNTAX     SEQUENCE OF LcsSetupDnsFilterListEntry
    MAX-ACCESS not-accessible
    STATUS     current
    DESCRIPTION
            ""
    ::= { lcsSetupDns 6 }

-- {ROW} 1.3.6.1.4.1.2356.11.2.17.6.1
lcsSetupDnsFilterListEntry OBJECT-TYPE
    SYNTAX     LcsSetupDnsFilterListEntry
    MAX-ACCESS not-accessible
    STATUS     current
    DESCRIPTION
            ""
    INDEX {
            lcsSetupDnsFilterListEntryIdx
          }
    ::= { lcsSetupDnsFilterListTable 1 }

LcsSetupDnsFilterListEntry ::= SEQUENCE {
            lcsSetupDnsFilterListEntryIdx DisplayString,
            lcsSetupDnsFilterListEntryDomain DisplayString,
            lcsSetupDnsFilterListEntryIpAddress IpAddress,
            lcsSetupDnsFilterListEntryNetmask IpAddress,
            lcsSetupDnsFilterListEntryIpv6Prefix DisplayString,
            lcsSetupDnsFilterListEntryRtgTag Integer32
    }

-- {COLUMN} 1.3.6.1.4.1.2356.11.2.17.6.1.1
lcsSetupDnsFilterListEntryIdx OBJECT-TYPE
    SYNTAX     DisplayString (SIZE(0..4))
    MAX-ACCESS read-write
    STATUS     current
    DESCRIPTION
            ""
    ::= { lcsSetupDnsFilterListEntry 1 }

-- {COLUMN} 1.3.6.1.4.1.2356.11.2.17.6.1.2
lcsSetupDnsFilterListEntryDomain OBJECT-TYPE
    SYNTAX     DisplayString (SIZE(0..64))
    MAX-ACCESS read-write
    STATUS     current
    DESCRIPTION
            ""
    ::= { lcsSetupDnsFilterListEntry 2 }

-- {COLUMN} 1.3.6.1.4.1.2356.11.2.17.6.1.3
lcsSetupDnsFilterListEntryIpAddress OBJECT-TYPE
    SYNTAX     IpAddress
    MAX-ACCESS read-write
    STATUS     current
    DESCRIPTION
            ""
    ::= { lcsSetupDnsFilterListEntry 3 }

-- {COLUMN} 1.3.6.1.4.1.2356.11.2.17.6.1.4
lcsSetupDnsFilterListEntryNetmask OBJECT-TYPE
    SYNTAX     IpAddress
    MAX-ACCESS read-write
    STATUS     current
    DESCRIPTION
            ""
    ::= { lcsSetupDnsFilterListEntry 4 }

-- {COLUMN} 1.3.6.1.4.1.2356.11.2.17.6.1.5
lcsSetupDnsFilterListEntryIpv6Prefix OBJECT-TYPE
    SYNTAX     DisplayString (SIZE(0..43))
    MAX-ACCESS read-write
    STATUS     current
    DESCRIPTION
            "-- empty --"
    ::= { lcsSetupDnsFilterListEntry 5 }

-- {COLUMN} 1.3.6.1.4.1.2356.11.2.17.6.1.6
lcsSetupDnsFilterListEntryRtgTag OBJECT-TYPE
    SYNTAX     Integer32 (0..65535)
    MAX-ACCESS read-write
    STATUS     current
    DESCRIPTION
            "-- empty --"
    ::= { lcsSetupDnsFilterListEntry 6 }

-- {SCALAR} 1.3.6.1.4.1.2356.11.2.17.7
lcsSetupDnsLeasetime OBJECT-TYPE
    SYNTAX     Integer32 (0..65535)
    MAX-ACCESS read-write
    STATUS     current
    DESCRIPTION
            ""
    ::= { lcsSetupDns 7 }

-- {TABLE} 1.3.6.1.4.1.2356.11.2.17.8
lcsSetupDnsDynDnsListTable OBJECT-TYPE
    SYNTAX     SEQUENCE OF LcsSetupDnsDynDnsListEntry
    MAX-ACCESS not-accessible
    STATUS     current
    DESCRIPTION
            ""
    ::= { lcsSetupDns 8 }

-- {ROW} 1.3.6.1.4.1.2356.11.2.17.8.1
lcsSetupDnsDynDnsListEntry OBJECT-TYPE
    SYNTAX     LcsSetupDnsDynDnsListEntry
    MAX-ACCESS not-accessible
    STATUS     current
    DESCRIPTION
            ""
    INDEX {
            lcsSetupDnsDynDnsListEntryHostName,
            lcsSetupDnsDynDnsListEntryNetworkName
          }
    ::= { lcsSetupDnsDynDnsListTable 1 }

LcsSetupDnsDynDnsListEntry ::= SEQUENCE {
            lcsSetupDnsDynDnsListEntryHostName DisplayString,
            lcsSetupDnsDynDnsListEntryIpAddress IpAddress,
            lcsSetupDnsDynDnsListEntryTimeout Integer32,
            lcsSetupDnsDynDnsListEntryIpv6Address DisplayString,
            lcsSetupDnsDynDnsListEntryNetworkName DisplayString
    }

-- {COLUMN} 1.3.6.1.4.1.2356.11.2.17.8.1.1
lcsSetupDnsDynDnsListEntryHostName OBJECT-TYPE
    SYNTAX     DisplayString (SIZE(0..64))
    MAX-ACCESS read-only
    STATUS     current
    DESCRIPTION
            ""
    ::= { lcsSetupDnsDynDnsListEntry 1 }

-- {COLUMN} 1.3.6.1.4.1.2356.11.2.17.8.1.2
lcsSetupDnsDynDnsListEntryIpAddress OBJECT-TYPE
    SYNTAX     IpAddress
    MAX-ACCESS read-only
    STATUS     current
    DESCRIPTION
            ""
    ::= { lcsSetupDnsDynDnsListEntry 2 }

-- {COLUMN} 1.3.6.1.4.1.2356.11.2.17.8.1.3
lcsSetupDnsDynDnsListEntryTimeout OBJECT-TYPE
    SYNTAX     Integer32 (0..2147483647)
    MAX-ACCESS read-only
    STATUS     current
    DESCRIPTION
            ""
    ::= { lcsSetupDnsDynDnsListEntry 3 }

-- {COLUMN} 1.3.6.1.4.1.2356.11.2.17.8.1.4
lcsSetupDnsDynDnsListEntryIpv6Address OBJECT-TYPE
    SYNTAX     DisplayString (SIZE(0..255))
    MAX-ACCESS read-only
    STATUS     current
    DESCRIPTION
            "-- empty --"
    ::= { lcsSetupDnsDynDnsListEntry 4 }

-- {COLUMN} 1.3.6.1.4.1.2356.11.2.17.8.1.5
lcsSetupDnsDynDnsListEntryNetworkName OBJECT-TYPE
    SYNTAX     DisplayString (SIZE(0..16))
    MAX-ACCESS read-only
    STATUS     current
    DESCRIPTION
            "-- empty --"
    ::= { lcsSetupDnsDynDnsListEntry 5 }

-- {TABLE} 1.3.6.1.4.1.2356.11.2.17.9
lcsSetupDnsDnsDestinationsTable OBJECT-TYPE
    SYNTAX     SEQUENCE OF LcsSetupDnsDnsDestinationsEntry
    MAX-ACCESS not-accessible
    STATUS     current
    DESCRIPTION
            ""
    ::= { lcsSetupDns 9 }

-- {ROW} 1.3.6.1.4.1.2356.11.2.17.9.1
lcsSetupDnsDnsDestinationsEntry OBJECT-TYPE
    SYNTAX     LcsSetupDnsDnsDestinationsEntry
    MAX-ACCESS not-accessible
    STATUS     current
    DESCRIPTION
            ""
    INDEX {
            lcsSetupDnsDnsDestinationsEntryDomainName,
            lcsSetupDnsDnsDestinationsEntryRtgTag
          }
    ::= { lcsSetupDnsDnsDestinationsTable 1 }

LcsSetupDnsDnsDestinationsEntry ::= SEQUENCE {
            lcsSetupDnsDnsDestinationsEntryDomainName DisplayString,
            lcsSetupDnsDnsDestinationsEntryDestination DisplayString,
            lcsSetupDnsDnsDestinationsEntryRtgTag Integer32
    }

-- {COLUMN} 1.3.6.1.4.1.2356.11.2.17.9.1.1
lcsSetupDnsDnsDestinationsEntryDomainName OBJECT-TYPE
    SYNTAX     DisplayString (SIZE(0..64))
    MAX-ACCESS read-write
    STATUS     current
    DESCRIPTION
            ""
    ::= { lcsSetupDnsDnsDestinationsEntry 1 }

-- {COLUMN} 1.3.6.1.4.1.2356.11.2.17.9.1.2
lcsSetupDnsDnsDestinationsEntryDestination OBJECT-TYPE
    SYNTAX     DisplayString (SIZE(0..80))
    MAX-ACCESS read-write
    STATUS     current
    DESCRIPTION
            ""
    ::= { lcsSetupDnsDnsDestinationsEntry 2 }

-- {COLUMN} 1.3.6.1.4.1.2356.11.2.17.9.1.3
lcsSetupDnsDnsDestinationsEntryRtgTag OBJECT-TYPE
    SYNTAX     Integer32 (0..65535)
    MAX-ACCESS read-write
    STATUS     current
    DESCRIPTION
            "-- empty --"
    ::= { lcsSetupDnsDnsDestinationsEntry 3 }

-- {TABLE} 1.3.6.1.4.1.2356.11.2.17.10
lcsSetupDnsServiceLocationListTable OBJECT-TYPE
    SYNTAX     SEQUENCE OF LcsSetupDnsServiceLocationListEntry
    MAX-ACCESS not-accessible
    STATUS     current
    DESCRIPTION
            ""
    ::= { lcsSetupDns 10 }

-- {ROW} 1.3.6.1.4.1.2356.11.2.17.10.1
lcsSetupDnsServiceLocationListEntry OBJECT-TYPE
    SYNTAX     LcsSetupDnsServiceLocationListEntry
    MAX-ACCESS not-accessible
    STATUS     current
    DESCRIPTION
            ""
    INDEX {
            lcsSetupDnsServiceLocationListEntryServiceName,
            lcsSetupDnsServiceLocationListEntryRtgTag
          }
    ::= { lcsSetupDnsServiceLocationListTable 1 }

LcsSetupDnsServiceLocationListEntry ::= SEQUENCE {
            lcsSetupDnsServiceLocationListEntryServiceName DisplayString,
            lcsSetupDnsServiceLocationListEntryHostName DisplayString,
            lcsSetupDnsServiceLocationListEntryPort Integer32,
            lcsSetupDnsServiceLocationListEntryRtgTag Integer32
    }

-- {COLUMN} 1.3.6.1.4.1.2356.11.2.17.10.1.1
lcsSetupDnsServiceLocationListEntryServiceName OBJECT-TYPE
    SYNTAX     DisplayString (SIZE(0..64))
    MAX-ACCESS read-write
    STATUS     current
    DESCRIPTION
            ""
    ::= { lcsSetupDnsServiceLocationListEntry 1 }

-- {COLUMN} 1.3.6.1.4.1.2356.11.2.17.10.1.2
lcsSetupDnsServiceLocationListEntryHostName OBJECT-TYPE
    SYNTAX     DisplayString (SIZE(0..64))
    MAX-ACCESS read-write
    STATUS     current
    DESCRIPTION
            ""
    ::= { lcsSetupDnsServiceLocationListEntry 2 }

-- {COLUMN} 1.3.6.1.4.1.2356.11.2.17.10.1.3
lcsSetupDnsServiceLocationListEntryPort OBJECT-TYPE
    SYNTAX     Integer32 (0..65535)
    MAX-ACCESS read-write
    STATUS     current
    DESCRIPTION
            ""
    ::= { lcsSetupDnsServiceLocationListEntry 3 }

-- {COLUMN} 1.3.6.1.4.1.2356.11.2.17.10.1.4
lcsSetupDnsServiceLocationListEntryRtgTag OBJECT-TYPE
    SYNTAX     Integer32 (0..65535)
    MAX-ACCESS read-write
    STATUS     current
    DESCRIPTION
            "-- empty --"
    ::= { lcsSetupDnsServiceLocationListEntry 4 }

-- {TABLE} 1.3.6.1.4.1.2356.11.2.17.11
lcsSetupDnsDynamicSrvListTable OBJECT-TYPE
    SYNTAX     SEQUENCE OF LcsSetupDnsDynamicSrvListEntry
    MAX-ACCESS not-accessible
    STATUS     current
    DESCRIPTION
            ""
    ::= { lcsSetupDns 11 }

-- {ROW} 1.3.6.1.4.1.2356.11.2.17.11.1
lcsSetupDnsDynamicSrvListEntry OBJECT-TYPE
    SYNTAX     LcsSetupDnsDynamicSrvListEntry
    MAX-ACCESS not-accessible
    STATUS     current
    DESCRIPTION
            ""
    INDEX {
            lcsSetupDnsDynamicSrvListEntryServiceName
          }
    ::= { lcsSetupDnsDynamicSrvListTable 1 }

LcsSetupDnsDynamicSrvListEntry ::= SEQUENCE {
            lcsSetupDnsDynamicSrvListEntryServiceName DisplayString,
            lcsSetupDnsDynamicSrvListEntryHostName DisplayString,
            lcsSetupDnsDynamicSrvListEntryPort Integer32
    }

-- {COLUMN} 1.3.6.1.4.1.2356.11.2.17.11.1.1
lcsSetupDnsDynamicSrvListEntryServiceName OBJECT-TYPE
    SYNTAX     DisplayString (SIZE(0..64))
    MAX-ACCESS read-only
    STATUS     current
    DESCRIPTION
            ""
    ::= { lcsSetupDnsDynamicSrvListEntry 1 }

-- {COLUMN} 1.3.6.1.4.1.2356.11.2.17.11.1.2
lcsSetupDnsDynamicSrvListEntryHostName OBJECT-TYPE
    SYNTAX     DisplayString (SIZE(0..64))
    MAX-ACCESS read-only
    STATUS     current
    DESCRIPTION
            ""
    ::= { lcsSetupDnsDynamicSrvListEntry 2 }

-- {COLUMN} 1.3.6.1.4.1.2356.11.2.17.11.1.3
lcsSetupDnsDynamicSrvListEntryPort OBJECT-TYPE
    SYNTAX     Integer32 (0..65535)
    MAX-ACCESS read-only
    STATUS     current
    DESCRIPTION
            ""
    ::= { lcsSetupDnsDynamicSrvListEntry 3 }

-- {SCALAR} 1.3.6.1.4.1.2356.11.2.17.12
lcsSetupDnsResolveDomain OBJECT-TYPE
    SYNTAX     INTEGER {
                  eNo (0),
                  eYes (1)
            }
    MAX-ACCESS read-write
    STATUS     current
    DESCRIPTION
            ""
    ::= { lcsSetupDns 12 }

-- {TABLE} 1.3.6.1.4.1.2356.11.2.17.13
lcsSetupDnsSubDomainsTable OBJECT-TYPE
    SYNTAX     SEQUENCE OF LcsSetupDnsSubDomainsEntry
    MAX-ACCESS not-accessible
    STATUS     current
    DESCRIPTION
            ""
    ::= { lcsSetupDns 13 }

-- {ROW} 1.3.6.1.4.1.2356.11.2.17.13.1
lcsSetupDnsSubDomainsEntry OBJECT-TYPE
    SYNTAX     LcsSetupDnsSubDomainsEntry
    MAX-ACCESS not-accessible
    STATUS     current
    DESCRIPTION
            ""
    INDEX {
            lcsSetupDnsSubDomainsEntryNetworkName
          }
    ::= { lcsSetupDnsSubDomainsTable 1 }

LcsSetupDnsSubDomainsEntry ::= SEQUENCE {
            lcsSetupDnsSubDomainsEntryNetworkName DisplayString,
            lcsSetupDnsSubDomainsEntrySubDomain DisplayString
    }

-- {COLUMN} 1.3.6.1.4.1.2356.11.2.17.13.1.1
lcsSetupDnsSubDomainsEntryNetworkName OBJECT-TYPE
    SYNTAX     DisplayString (SIZE(0..16))
    MAX-ACCESS read-write
    STATUS     current
    DESCRIPTION
            ""
    ::= { lcsSetupDnsSubDomainsEntry 1 }

-- {COLUMN} 1.3.6.1.4.1.2356.11.2.17.13.1.2
lcsSetupDnsSubDomainsEntrySubDomain OBJECT-TYPE
    SYNTAX     DisplayString (SIZE(0..64))
    MAX-ACCESS read-write
    STATUS     current
    DESCRIPTION
            ""
    ::= { lcsSetupDnsSubDomainsEntry 2 }

-- {SCALAR} 1.3.6.1.4.1.2356.11.2.17.14
lcsSetupDnsForwarder OBJECT-TYPE
    SYNTAX     INTEGER {
                  eNo (0),
                  eYes (1)
            }
    MAX-ACCESS read-write
    STATUS     current
    DESCRIPTION
            "-- empty --"
    ::= { lcsSetupDns 14 }

-- {TABLE} 1.3.6.1.4.1.2356.11.2.17.15
lcsSetupDnsTagConfigurationTable OBJECT-TYPE
    SYNTAX     SEQUENCE OF LcsSetupDnsTagConfigurationEntry
    MAX-ACCESS not-accessible
    STATUS     current
    DESCRIPTION
            "-- empty --"
    ::= { lcsSetupDns 15 }

-- {ROW} 1.3.6.1.4.1.2356.11.2.17.15.1
lcsSetupDnsTagConfigurationEntry OBJECT-TYPE
    SYNTAX     LcsSetupDnsTagConfigurationEntry
    MAX-ACCESS not-accessible
    STATUS     current
    DESCRIPTION
            ""
    INDEX {
            lcsSetupDnsTagConfigurationEntryRtgTag
          }
    ::= { lcsSetupDnsTagConfigurationTable 1 }

LcsSetupDnsTagConfigurationEntry ::= SEQUENCE {
            lcsSetupDnsTagConfigurationEntryRtgTag Integer32,
            lcsSetupDnsTagConfigurationEntryOperating INTEGER,
            lcsSetupDnsTagConfigurationEntryForwarder INTEGER,
            lcsSetupDnsTagConfigurationEntryDhcpUsage INTEGER,
            lcsSetupDnsTagConfigurationEntryNetbiosUsage INTEGER,
            lcsSetupDnsTagConfigurationEntryResolveDomain INTEGER
    }

-- {COLUMN} 1.3.6.1.4.1.2356.11.2.17.15.1.1
lcsSetupDnsTagConfigurationEntryRtgTag OBJECT-TYPE
    SYNTAX     Integer32 (0..65535)
    MAX-ACCESS read-write
    STATUS     current
    DESCRIPTION
            "-- empty --"
    ::= { lcsSetupDnsTagConfigurationEntry 1 }

-- {COLUMN} 1.3.6.1.4.1.2356.11.2.17.15.1.2
lcsSetupDnsTagConfigurationEntryOperating OBJECT-TYPE
    SYNTAX     INTEGER {
                  eNo (0),
                  eYes (1)
            }
    MAX-ACCESS read-write
    STATUS     current
    DESCRIPTION
            "-- empty --"
    ::= { lcsSetupDnsTagConfigurationEntry 2 }

-- {COLUMN} 1.3.6.1.4.1.2356.11.2.17.15.1.3
lcsSetupDnsTagConfigurationEntryForwarder OBJECT-TYPE
    SYNTAX     INTEGER {
                  eNo (0),
                  eYes (1)
            }
    MAX-ACCESS read-write
    STATUS     current
    DESCRIPTION
            "-- empty --"
    ::= { lcsSetupDnsTagConfigurationEntry 3 }

-- {COLUMN} 1.3.6.1.4.1.2356.11.2.17.15.1.4
lcsSetupDnsTagConfigurationEntryDhcpUsage OBJECT-TYPE
    SYNTAX     INTEGER {
                  eNo (0),
                  eYes (1)
            }
    MAX-ACCESS read-write
    STATUS     current
    DESCRIPTION
            "-- empty --"
    ::= { lcsSetupDnsTagConfigurationEntry 4 }

-- {COLUMN} 1.3.6.1.4.1.2356.11.2.17.15.1.5
lcsSetupDnsTagConfigurationEntryNetbiosUsage OBJECT-TYPE
    SYNTAX     INTEGER {
                  eNo (0),
                  eYes (1)
            }
    MAX-ACCESS read-write
    STATUS     current
    DESCRIPTION
            "-- empty --"
    ::= { lcsSetupDnsTagConfigurationEntry 5 }

-- {COLUMN} 1.3.6.1.4.1.2356.11.2.17.15.1.6
lcsSetupDnsTagConfigurationEntryResolveDomain OBJECT-TYPE
    SYNTAX     INTEGER {
                  eNo (0),
                  eYes (1)
            }
    MAX-ACCESS read-write
    STATUS     current
    DESCRIPTION
            "-- empty --"
    ::= { lcsSetupDnsTagConfigurationEntry 6 }

-- {TABLE} 1.3.6.1.4.1.2356.11.2.17.16
lcsSetupDnsAliasListTable OBJECT-TYPE
    SYNTAX     SEQUENCE OF LcsSetupDnsAliasListEntry
    MAX-ACCESS not-accessible
    STATUS     current
    DESCRIPTION
            "-- empty --"
    ::= { lcsSetupDns 16 }

-- {ROW} 1.3.6.1.4.1.2356.11.2.17.16.1
lcsSetupDnsAliasListEntry OBJECT-TYPE
    SYNTAX     LcsSetupDnsAliasListEntry
    MAX-ACCESS not-accessible
    STATUS     current
    DESCRIPTION
            ""
    INDEX {
            lcsSetupDnsAliasListEntryAliasName,
            lcsSetupDnsAliasListEntryRtgTag
          }
    ::= { lcsSetupDnsAliasListTable 1 }

LcsSetupDnsAliasListEntry ::= SEQUENCE {
            lcsSetupDnsAliasListEntryAliasName DisplayString,
            lcsSetupDnsAliasListEntryRtgTag Integer32,
            lcsSetupDnsAliasListEntryCanonicalName DisplayString
    }

-- {COLUMN} 1.3.6.1.4.1.2356.11.2.17.16.1.1
lcsSetupDnsAliasListEntryAliasName OBJECT-TYPE
    SYNTAX     DisplayString (SIZE(0..64))
    MAX-ACCESS read-write
    STATUS     current
    DESCRIPTION
            "-- empty --"
    ::= { lcsSetupDnsAliasListEntry 1 }

-- {COLUMN} 1.3.6.1.4.1.2356.11.2.17.16.1.2
lcsSetupDnsAliasListEntryRtgTag OBJECT-TYPE
    SYNTAX     Integer32 (0..65535)
    MAX-ACCESS read-write
    STATUS     current
    DESCRIPTION
            "-- empty --"
    ::= { lcsSetupDnsAliasListEntry 2 }

-- {COLUMN} 1.3.6.1.4.1.2356.11.2.17.16.1.3
lcsSetupDnsAliasListEntryCanonicalName OBJECT-TYPE
    SYNTAX     DisplayString (SIZE(0..64))
    MAX-ACCESS read-write
    STATUS     current
    DESCRIPTION
            "-- empty --"
    ::= { lcsSetupDnsAliasListEntry 3 }

-- {TABLE} 1.3.6.1.4.1.2356.11.2.17.17
lcsSetupDnsLoopbackAddressesTable OBJECT-TYPE
    SYNTAX     SEQUENCE OF LcsSetupDnsLoopbackAddressesEntry
    MAX-ACCESS not-accessible
    STATUS     current
    DESCRIPTION
            "-- empty --"
    ::= { lcsSetupDns 17 }

-- {ROW} 1.3.6.1.4.1.2356.11.2.17.17.1
lcsSetupDnsLoopbackAddressesEntry OBJECT-TYPE
    SYNTAX     LcsSetupDnsLoopbackAddressesEntry
    MAX-ACCESS not-accessible
    STATUS     current
    DESCRIPTION
            ""
    INDEX {
            lcsSetupDnsLoopbackAddressesEntryDestination
          }
    ::= { lcsSetupDnsLoopbackAddressesTable 1 }

LcsSetupDnsLoopbackAddressesEntry ::= SEQUENCE {
            lcsSetupDnsLoopbackAddressesEntryDestination DisplayString,
            lcsSetupDnsLoopbackAddressesEntryLoopbackAddress DisplayString
    }

-- {COLUMN} 1.3.6.1.4.1.2356.11.2.17.17.1.1
lcsSetupDnsLoopbackAddressesEntryDestination OBJECT-TYPE
    SYNTAX     DisplayString (SIZE(0..39))
    MAX-ACCESS read-write
    STATUS     current
    DESCRIPTION
            "-- empty --"
    ::= { lcsSetupDnsLoopbackAddressesEntry 1 }

-- {COLUMN} 1.3.6.1.4.1.2356.11.2.17.17.1.2
lcsSetupDnsLoopbackAddressesEntryLoopbackAddress OBJECT-TYPE
    SYNTAX     DisplayString (SIZE(0..39))
    MAX-ACCESS read-write
    STATUS     current
    DESCRIPTION
            "-- empty --"
    ::= { lcsSetupDnsLoopbackAddressesEntry 2 }

-- {NODE} 1.3.6.1.4.1.2356.11.2.17.20
lcsSetupDnsSyslog OBJECT IDENTIFIER ::= { lcsSetupDns 20 }

-- {SCALAR} 1.3.6.1.4.1.2356.11.2.17.20.1
lcsSetupDnsSyslogLogDnsResolutions OBJECT-TYPE
    SYNTAX     INTEGER {
                  eNo (0),
                  eYes (1)
            }
    MAX-ACCESS read-write
    STATUS     current
    DESCRIPTION
            "-- empty --"
    ::= { lcsSetupDnsSyslog 1 }

-- {SCALAR} 1.3.6.1.4.1.2356.11.2.17.20.2
lcsSetupDnsSyslogLogServerAddress OBJECT-TYPE
    SYNTAX     DisplayString (SIZE(0..64))
    MAX-ACCESS read-write
    STATUS     current
    DESCRIPTION
            "-- empty --"
    ::= { lcsSetupDnsSyslog 2 }

-- {SCALAR} 1.3.6.1.4.1.2356.11.2.17.20.3
lcsSetupDnsSyslogLogSource OBJECT-TYPE
    SYNTAX     INTEGER {
                  eSystem (0),
                  eLogin (1),
                  eSystemtime (2),
                  eConsoleLogin (3),
                  eConnections (4),
                  eAccounting (5),
                  eAdministration (6),
                  eRouter (7)
            }
    MAX-ACCESS read-write
    STATUS     current
    DESCRIPTION
            "-- empty --"
    ::= { lcsSetupDnsSyslog 3 }

-- {SCALAR} 1.3.6.1.4.1.2356.11.2.17.20.4
lcsSetupDnsSyslogLogLevel OBJECT-TYPE
    SYNTAX     INTEGER {
                  eEmergency (0),
                  eAlarm (1),
                  eCritical (2),
                  eError (3),
                  eWarning (4),
                  eNotice (5),
                  eInfo (6),
                  eDebug (7)
            }
    MAX-ACCESS read-write
    STATUS     current
    DESCRIPTION
            "-- empty --"
    ::= { lcsSetupDnsSyslog 4 }

-- {SCALAR} 1.3.6.1.4.1.2356.11.2.17.20.5
lcsSetupDnsSyslogLoopbackAddr OBJECT-TYPE
    SYNTAX     DisplayString (SIZE(0..16))
    MAX-ACCESS read-write
    STATUS     current
    DESCRIPTION
            "-- empty --"
    ::= { lcsSetupDnsSyslog 5 }

-- {SCALAR} 1.3.6.1.4.1.2356.11.2.17.20.6
lcsSetupDnsSyslogFilterName OBJECT-TYPE
    SYNTAX     DisplayString (SIZE(0..32))
    MAX-ACCESS read-write
    STATUS     current
    DESCRIPTION
            "-- empty --"
    ::= { lcsSetupDnsSyslog 6 }

-- {SCALAR} 1.3.6.1.4.1.2356.11.2.17.20.7
lcsSetupDnsSyslogFilterPolicy OBJECT-TYPE
    SYNTAX     INTEGER {
                  eAllow (0),
                  eDeny (1)
            }
    MAX-ACCESS read-write
    STATUS     current
    DESCRIPTION
            "-- empty --"
    ::= { lcsSetupDnsSyslog 7 }

-- {NODE} 1.3.6.1.4.1.2356.11.2.18
lcsSetupAccounting OBJECT IDENTIFIER ::= { lcsSetup 18 }

-- {SCALAR} 1.3.6.1.4.1.2356.11.2.18.1
lcsSetupAccountingOperating OBJECT-TYPE
    SYNTAX     INTEGER {
                  eNo (0),
                  eYes (1)
            }
    MAX-ACCESS read-write
    STATUS     current
    DESCRIPTION
            ""
    ::= { lcsSetupAccounting 1 }

-- {SCALAR} 1.3.6.1.4.1.2356.11.2.18.2
lcsSetupAccountingSaveToFlashrom OBJECT-TYPE
    SYNTAX     INTEGER {
                  eNo (0),
                  eYes (1)
            }
    MAX-ACCESS read-write
    STATUS     current
    DESCRIPTION
            ""
    ::= { lcsSetupAccounting 2 }

-- {SCALAR} 1.3.6.1.4.1.2356.11.2.18.3
lcsSetupAccountingSortBy OBJECT-TYPE
    SYNTAX     INTEGER {
                  eTime (0),
                  eData (1)
            }
    MAX-ACCESS read-write
    STATUS     current
    DESCRIPTION
            ""
    ::= { lcsSetupAccounting 3 }

-- {TABLE} 1.3.6.1.4.1.2356.11.2.18.4
lcsSetupAccountingCurrentUserTable OBJECT-TYPE
    SYNTAX     SEQUENCE OF LcsSetupAccountingCurrentUserEntry
    MAX-ACCESS not-accessible
    STATUS     current
    DESCRIPTION
            ""
    ::= { lcsSetupAccounting 4 }

-- {ROW} 1.3.6.1.4.1.2356.11.2.18.4.1
lcsSetupAccountingCurrentUserEntry OBJECT-TYPE
    SYNTAX     LcsSetupAccountingCurrentUserEntry
    MAX-ACCESS not-accessible
    STATUS     current
    DESCRIPTION
            ""
    INDEX {
            lcsSetupAccountingCurrentUserEntryUsername,
            lcsSetupAccountingCurrentUserEntryMacAddress,
            lcsSetupAccountingCurrentUserEntryPeer,
            lcsSetupAccountingCurrentUserEntryConnType
          }
    ::= { lcsSetupAccountingCurrentUserTable 1 }

LcsSetupAccountingCurrentUserEntry ::= SEQUENCE {
            lcsSetupAccountingCurrentUserEntryUsername DisplayString,
            lcsSetupAccountingCurrentUserEntryMacAddress DisplayString,
            lcsSetupAccountingCurrentUserEntryPeer DisplayString,
            lcsSetupAccountingCurrentUserEntryConnType INTEGER,
            lcsSetupAccountingCurrentUserEntryRxKbytes Integer32,
            lcsSetupAccountingCurrentUserEntryTxKbytes Integer32,
            lcsSetupAccountingCurrentUserEntryTotalTime Gauge32,
            lcsSetupAccountingCurrentUserEntryConnections Integer32
    }

-- {COLUMN} 1.3.6.1.4.1.2356.11.2.18.4.1.1
lcsSetupAccountingCurrentUserEntryUsername OBJECT-TYPE
    SYNTAX     DisplayString (SIZE(0..28))
    MAX-ACCESS read-only
    STATUS     current
    DESCRIPTION
            ""
    ::= { lcsSetupAccountingCurrentUserEntry 1 }

-- {COLUMN} 1.3.6.1.4.1.2356.11.2.18.4.1.2
lcsSetupAccountingCurrentUserEntryMacAddress OBJECT-TYPE
    SYNTAX     DisplayString (SIZE(0..255))
    MAX-ACCESS read-only
    STATUS     current
    DESCRIPTION
            ""
    ::= { lcsSetupAccountingCurrentUserEntry 2 }

-- {COLUMN} 1.3.6.1.4.1.2356.11.2.18.4.1.3
lcsSetupAccountingCurrentUserEntryPeer OBJECT-TYPE
    SYNTAX     DisplayString (SIZE(0..16))
    MAX-ACCESS read-only
    STATUS     current
    DESCRIPTION
            ""
    ::= { lcsSetupAccountingCurrentUserEntry 3 }

-- {COLUMN} 1.3.6.1.4.1.2356.11.2.18.4.1.4
lcsSetupAccountingCurrentUserEntryConnType OBJECT-TYPE
    SYNTAX     INTEGER {
                  eUnknown (0),
                  eDialUp (1),
                  eLeasedLine (2),
                  eDslLine (4),
                  eVpnConn (7),
                  ePptpConn (8),
                  eL2tpConn (9),
                  eDsLiteConn (10),
                  eGreConn (11),
                  eLispConn (12)
            }
    MAX-ACCESS read-only
    STATUS     current
    DESCRIPTION
            ""
    ::= { lcsSetupAccountingCurrentUserEntry 4 }

-- {COLUMN} 1.3.6.1.4.1.2356.11.2.18.4.1.5
lcsSetupAccountingCurrentUserEntryRxKbytes OBJECT-TYPE
    SYNTAX     Integer32 (0..2147483647)
    MAX-ACCESS read-only
    STATUS     current
    DESCRIPTION
            ""
    ::= { lcsSetupAccountingCurrentUserEntry 5 }

-- {COLUMN} 1.3.6.1.4.1.2356.11.2.18.4.1.6
lcsSetupAccountingCurrentUserEntryTxKbytes OBJECT-TYPE
    SYNTAX     Integer32 (0..2147483647)
    MAX-ACCESS read-only
    STATUS     current
    DESCRIPTION
            ""
    ::= { lcsSetupAccountingCurrentUserEntry 6 }

-- {COLUMN} 1.3.6.1.4.1.2356.11.2.18.4.1.8
lcsSetupAccountingCurrentUserEntryTotalTime OBJECT-TYPE
    SYNTAX     Gauge32
    MAX-ACCESS read-only
    STATUS     current
    DESCRIPTION
            ""
    ::= { lcsSetupAccountingCurrentUserEntry 8 }

-- {COLUMN} 1.3.6.1.4.1.2356.11.2.18.4.1.9
lcsSetupAccountingCurrentUserEntryConnections OBJECT-TYPE
    SYNTAX     Integer32 (0..2147483647)
    MAX-ACCESS read-only
    STATUS     current
    DESCRIPTION
            ""
    ::= { lcsSetupAccountingCurrentUserEntry 9 }

-- {TABLE} 1.3.6.1.4.1.2356.11.2.18.5
lcsSetupAccountingAccountingListTable OBJECT-TYPE
    SYNTAX     SEQUENCE OF LcsSetupAccountingAccountingListEntry
    MAX-ACCESS not-accessible
    STATUS     current
    DESCRIPTION
            ""
    ::= { lcsSetupAccounting 5 }

-- {ROW} 1.3.6.1.4.1.2356.11.2.18.5.1
lcsSetupAccountingAccountingListEntry OBJECT-TYPE
    SYNTAX     LcsSetupAccountingAccountingListEntry
    MAX-ACCESS not-accessible
    STATUS     current
    DESCRIPTION
            ""
    INDEX {
            lcsSetupAccountingAccountingListEntryUsername,
            lcsSetupAccountingAccountingListEntryMacAddress,
            lcsSetupAccountingAccountingListEntryPeer,
            lcsSetupAccountingAccountingListEntryConnType
          }
    ::= { lcsSetupAccountingAccountingListTable 1 }

LcsSetupAccountingAccountingListEntry ::= SEQUENCE {
            lcsSetupAccountingAccountingListEntryUsername DisplayString,
            lcsSetupAccountingAccountingListEntryMacAddress DisplayString,
            lcsSetupAccountingAccountingListEntryPeer DisplayString,
            lcsSetupAccountingAccountingListEntryConnType INTEGER,
            lcsSetupAccountingAccountingListEntryRxKbytes Integer32,
            lcsSetupAccountingAccountingListEntryTxKbytes Integer32,
            lcsSetupAccountingAccountingListEntryTotalTime Gauge32,
            lcsSetupAccountingAccountingListEntryConnections Integer32
    }

-- {COLUMN} 1.3.6.1.4.1.2356.11.2.18.5.1.1
lcsSetupAccountingAccountingListEntryUsername OBJECT-TYPE
    SYNTAX     DisplayString (SIZE(0..28))
    MAX-ACCESS read-only
    STATUS     current
    DESCRIPTION
            ""
    ::= { lcsSetupAccountingAccountingListEntry 1 }

-- {COLUMN} 1.3.6.1.4.1.2356.11.2.18.5.1.2
lcsSetupAccountingAccountingListEntryMacAddress OBJECT-TYPE
    SYNTAX     DisplayString (SIZE(0..255))
    MAX-ACCESS read-only
    STATUS     current
    DESCRIPTION
            ""
    ::= { lcsSetupAccountingAccountingListEntry 2 }

-- {COLUMN} 1.3.6.1.4.1.2356.11.2.18.5.1.3
lcsSetupAccountingAccountingListEntryPeer OBJECT-TYPE
    SYNTAX     DisplayString (SIZE(0..16))
    MAX-ACCESS read-only
    STATUS     current
    DESCRIPTION
            ""
    ::= { lcsSetupAccountingAccountingListEntry 3 }

-- {COLUMN} 1.3.6.1.4.1.2356.11.2.18.5.1.4
lcsSetupAccountingAccountingListEntryConnType OBJECT-TYPE
    SYNTAX     INTEGER {
                  eUnknown (0),
                  eDialUp (1),
                  eLeasedLine (2),
                  eDslLine (4),
                  eVpnConn (7),
                  ePptpConn (8),
                  eL2tpConn (9),
                  eDsLiteConn (10),
                  eGreConn (11),
                  eLispConn (12)
            }
    MAX-ACCESS read-only
    STATUS     current
    DESCRIPTION
            ""
    ::= { lcsSetupAccountingAccountingListEntry 4 }

-- {COLUMN} 1.3.6.1.4.1.2356.11.2.18.5.1.5
lcsSetupAccountingAccountingListEntryRxKbytes OBJECT-TYPE
    SYNTAX     Integer32 (0..2147483647)
    MAX-ACCESS read-only
    STATUS     current
    DESCRIPTION
            ""
    ::= { lcsSetupAccountingAccountingListEntry 5 }

-- {COLUMN} 1.3.6.1.4.1.2356.11.2.18.5.1.6
lcsSetupAccountingAccountingListEntryTxKbytes OBJECT-TYPE
    SYNTAX     Integer32 (0..2147483647)
    MAX-ACCESS read-only
    STATUS     current
    DESCRIPTION
            ""
    ::= { lcsSetupAccountingAccountingListEntry 6 }

-- {COLUMN} 1.3.6.1.4.1.2356.11.2.18.5.1.8
lcsSetupAccountingAccountingListEntryTotalTime OBJECT-TYPE
    SYNTAX     Gauge32
    MAX-ACCESS read-only
    STATUS     current
    DESCRIPTION
            ""
    ::= { lcsSetupAccountingAccountingListEntry 8 }

-- {COLUMN} 1.3.6.1.4.1.2356.11.2.18.5.1.9
lcsSetupAccountingAccountingListEntryConnections OBJECT-TYPE
    SYNTAX     Integer32 (0..2147483647)
    MAX-ACCESS read-only
    STATUS     current
    DESCRIPTION
            ""
    ::= { lcsSetupAccountingAccountingListEntry 9 }

-- {SCALAR} 1.3.6.1.4.1.2356.11.2.18.6
lcsSetupAccountingDeleteAccountingList OBJECT-TYPE
    SYNTAX     DisplayString
    MAX-ACCESS read-write
    STATUS     current
    DESCRIPTION
            ""
    ::= { lcsSetupAccounting 6 }

-- {SCALAR} 1.3.6.1.4.1.2356.11.2.18.7
lcsSetupAccountingCreateSnapshot OBJECT-TYPE
    SYNTAX     DisplayString
    MAX-ACCESS read-write
    STATUS     current
    DESCRIPTION
            "-- empty --"
    ::= { lcsSetupAccounting 7 }

-- {TABLE} 1.3.6.1.4.1.2356.11.2.18.8
lcsSetupAccountingTimeSnapshotTable OBJECT-TYPE
    SYNTAX     SEQUENCE OF LcsSetupAccountingTimeSnapshotEntry
    MAX-ACCESS not-accessible
    STATUS     current
    DESCRIPTION
            ""
    ::= { lcsSetupAccounting 8 }

-- {ROW} 1.3.6.1.4.1.2356.11.2.18.8.1
lcsSetupAccountingTimeSnapshotEntry OBJECT-TYPE
    SYNTAX     LcsSetupAccountingTimeSnapshotEntry
    MAX-ACCESS not-accessible
    STATUS     current
    DESCRIPTION
            ""
    INDEX {
            lcsSetupAccountingTimeSnapshotEntryIndex
          }
    ::= { lcsSetupAccountingTimeSnapshotTable 1 }

LcsSetupAccountingTimeSnapshotEntry ::= SEQUENCE {
            lcsSetupAccountingTimeSnapshotEntryIndex Integer32,
            lcsSetupAccountingTimeSnapshotEntryActive INTEGER,
            lcsSetupAccountingTimeSnapshotEntryType INTEGER,
            lcsSetupAccountingTimeSnapshotEntryDay Integer32,
            lcsSetupAccountingTimeSnapshotEntryDayofweek INTEGER,
            lcsSetupAccountingTimeSnapshotEntryHour Integer32,
            lcsSetupAccountingTimeSnapshotEntryMinute Integer32
    }

-- {COLUMN} 1.3.6.1.4.1.2356.11.2.18.8.1.1
lcsSetupAccountingTimeSnapshotEntryIndex OBJECT-TYPE
    SYNTAX     Integer32 (0..255)
    MAX-ACCESS read-only
    STATUS     current
    DESCRIPTION
            ""
    ::= { lcsSetupAccountingTimeSnapshotEntry 1 }

-- {COLUMN} 1.3.6.1.4.1.2356.11.2.18.8.1.2
lcsSetupAccountingTimeSnapshotEntryActive OBJECT-TYPE
    SYNTAX     INTEGER {
                  eNo (0),
                  eYes (1)
            }
    MAX-ACCESS read-write
    STATUS     current
    DESCRIPTION
            ""
    ::= { lcsSetupAccountingTimeSnapshotEntry 2 }

-- {COLUMN} 1.3.6.1.4.1.2356.11.2.18.8.1.3
lcsSetupAccountingTimeSnapshotEntryType OBJECT-TYPE
    SYNTAX     INTEGER {
                  eMonthly (0),
                  eWeekly (1),
                  eDaily (2)
            }
    MAX-ACCESS read-write
    STATUS     current
    DESCRIPTION
            ""
    ::= { lcsSetupAccountingTimeSnapshotEntry 3 }

-- {COLUMN} 1.3.6.1.4.1.2356.11.2.18.8.1.4
lcsSetupAccountingTimeSnapshotEntryDay OBJECT-TYPE
    SYNTAX     Integer32 (0..255)
    MAX-ACCESS read-write
    STATUS     current
    DESCRIPTION
            ""
    ::= { lcsSetupAccountingTimeSnapshotEntry 4 }

-- {COLUMN} 1.3.6.1.4.1.2356.11.2.18.8.1.5
lcsSetupAccountingTimeSnapshotEntryDayofweek OBJECT-TYPE
    SYNTAX     INTEGER {
                  eUnknown (0),
                  eSunday (1),
                  eMonday (2),
                  eTuesday (3),
                  eWednesday (4),
                  eThursday (5),
                  eFriday (6),
                  eSaturday (7)
            }
    MAX-ACCESS read-write
    STATUS     current
    DESCRIPTION
            ""
    ::= { lcsSetupAccountingTimeSnapshotEntry 5 }

-- {COLUMN} 1.3.6.1.4.1.2356.11.2.18.8.1.6
lcsSetupAccountingTimeSnapshotEntryHour OBJECT-TYPE
    SYNTAX     Integer32 (0..255)
    MAX-ACCESS read-write
    STATUS     current
    DESCRIPTION
            ""
    ::= { lcsSetupAccountingTimeSnapshotEntry 6 }

-- {COLUMN} 1.3.6.1.4.1.2356.11.2.18.8.1.7
lcsSetupAccountingTimeSnapshotEntryMinute OBJECT-TYPE
    SYNTAX     Integer32 (0..255)
    MAX-ACCESS read-write
    STATUS     current
    DESCRIPTION
            ""
    ::= { lcsSetupAccountingTimeSnapshotEntry 7 }

-- {TABLE} 1.3.6.1.4.1.2356.11.2.18.9
lcsSetupAccountingLastSnapshotTable OBJECT-TYPE
    SYNTAX     SEQUENCE OF LcsSetupAccountingLastSnapshotEntry
    MAX-ACCESS not-accessible
    STATUS     current
    DESCRIPTION
            ""
    ::= { lcsSetupAccounting 9 }

-- {ROW} 1.3.6.1.4.1.2356.11.2.18.9.1
lcsSetupAccountingLastSnapshotEntry OBJECT-TYPE
    SYNTAX     LcsSetupAccountingLastSnapshotEntry
    MAX-ACCESS not-accessible
    STATUS     current
    DESCRIPTION
            ""
    INDEX {
            lcsSetupAccountingLastSnapshotEntryUsername,
            lcsSetupAccountingLastSnapshotEntryMacAddress,
            lcsSetupAccountingLastSnapshotEntryPeer,
            lcsSetupAccountingLastSnapshotEntryConnType
          }
    ::= { lcsSetupAccountingLastSnapshotTable 1 }

LcsSetupAccountingLastSnapshotEntry ::= SEQUENCE {
            lcsSetupAccountingLastSnapshotEntryUsername DisplayString,
            lcsSetupAccountingLastSnapshotEntryMacAddress DisplayString,
            lcsSetupAccountingLastSnapshotEntryPeer DisplayString,
            lcsSetupAccountingLastSnapshotEntryConnType INTEGER,
            lcsSetupAccountingLastSnapshotEntryRxKbytes Integer32,
            lcsSetupAccountingLastSnapshotEntryTxKbytes Integer32,
            lcsSetupAccountingLastSnapshotEntryTotalTime Gauge32,
            lcsSetupAccountingLastSnapshotEntryConnections Integer32
    }

-- {COLUMN} 1.3.6.1.4.1.2356.11.2.18.9.1.1
lcsSetupAccountingLastSnapshotEntryUsername OBJECT-TYPE
    SYNTAX     DisplayString (SIZE(0..28))
    MAX-ACCESS read-only
    STATUS     current
    DESCRIPTION
            ""
    ::= { lcsSetupAccountingLastSnapshotEntry 1 }

-- {COLUMN} 1.3.6.1.4.1.2356.11.2.18.9.1.2
lcsSetupAccountingLastSnapshotEntryMacAddress OBJECT-TYPE
    SYNTAX     DisplayString (SIZE(0..255))
    MAX-ACCESS read-only
    STATUS     current
    DESCRIPTION
            ""
    ::= { lcsSetupAccountingLastSnapshotEntry 2 }

-- {COLUMN} 1.3.6.1.4.1.2356.11.2.18.9.1.3
lcsSetupAccountingLastSnapshotEntryPeer OBJECT-TYPE
    SYNTAX     DisplayString (SIZE(0..16))
    MAX-ACCESS read-only
    STATUS     current
    DESCRIPTION
            ""
    ::= { lcsSetupAccountingLastSnapshotEntry 3 }

-- {COLUMN} 1.3.6.1.4.1.2356.11.2.18.9.1.4
lcsSetupAccountingLastSnapshotEntryConnType OBJECT-TYPE
    SYNTAX     INTEGER {
                  eUnknown (0),
                  eDialUp (1),
                  eLeasedLine (2),
                  eDslLine (4),
                  eVpnConn (7),
                  ePptpConn (8),
                  eL2tpConn (9),
                  eDsLiteConn (10),
                  eGreConn (11),
                  eLispConn (12)
            }
    MAX-ACCESS read-only
    STATUS     current
    DESCRIPTION
            ""
    ::= { lcsSetupAccountingLastSnapshotEntry 4 }

-- {COLUMN} 1.3.6.1.4.1.2356.11.2.18.9.1.5
lcsSetupAccountingLastSnapshotEntryRxKbytes OBJECT-TYPE
    SYNTAX     Integer32 (0..2147483647)
    MAX-ACCESS read-only
    STATUS     current
    DESCRIPTION
            ""
    ::= { lcsSetupAccountingLastSnapshotEntry 5 }

-- {COLUMN} 1.3.6.1.4.1.2356.11.2.18.9.1.6
lcsSetupAccountingLastSnapshotEntryTxKbytes OBJECT-TYPE
    SYNTAX     Integer32 (0..2147483647)
    MAX-ACCESS read-only
    STATUS     current
    DESCRIPTION
            ""
    ::= { lcsSetupAccountingLastSnapshotEntry 6 }

-- {COLUMN} 1.3.6.1.4.1.2356.11.2.18.9.1.8
lcsSetupAccountingLastSnapshotEntryTotalTime OBJECT-TYPE
    SYNTAX     Gauge32
    MAX-ACCESS read-only
    STATUS     current
    DESCRIPTION
            ""
    ::= { lcsSetupAccountingLastSnapshotEntry 8 }

-- {COLUMN} 1.3.6.1.4.1.2356.11.2.18.9.1.9
lcsSetupAccountingLastSnapshotEntryConnections OBJECT-TYPE
    SYNTAX     Integer32 (0..2147483647)
    MAX-ACCESS read-only
    STATUS     current
    DESCRIPTION
            ""
    ::= { lcsSetupAccountingLastSnapshotEntry 9 }

-- {SCALAR} 1.3.6.1.4.1.2356.11.2.18.10
lcsSetupAccountingDiscriminator OBJECT-TYPE
    SYNTAX     INTEGER {
                  eMacAddress (0),
                  eIpAddress (1)
            }
    MAX-ACCESS read-write
    STATUS     current
    DESCRIPTION
            ""
    ::= { lcsSetupAccounting 10 }

-- {NODE} 1.3.6.1.4.1.2356.11.2.19
lcsSetupVpn OBJECT IDENTIFIER ::= { lcsSetup 19 }

-- {NODE} 1.3.6.1.4.1.2356.11.2.19.3
lcsSetupVpnIsakmp OBJECT IDENTIFIER ::= { lcsSetupVpn 3 }

-- {TABLE} 1.3.6.1.4.1.2356.11.2.19.3.4
lcsSetupVpnIsakmpTimerTable OBJECT-TYPE
    SYNTAX     SEQUENCE OF LcsSetupVpnIsakmpTimerEntry
    MAX-ACCESS not-accessible
    STATUS     current
    DESCRIPTION
            ""
    ::= { lcsSetupVpnIsakmp 4 }

-- {ROW} 1.3.6.1.4.1.2356.11.2.19.3.4.1
lcsSetupVpnIsakmpTimerEntry OBJECT-TYPE
    SYNTAX     LcsSetupVpnIsakmpTimerEntry
    MAX-ACCESS not-accessible
    STATUS     current
    DESCRIPTION
            ""
    INDEX {
            lcsSetupVpnIsakmpTimerEntryIdx
          }
    ::= { lcsSetupVpnIsakmpTimerTable 1 }

LcsSetupVpnIsakmpTimerEntry ::= SEQUENCE {
            lcsSetupVpnIsakmpTimerEntryRetrLim Integer32,
            lcsSetupVpnIsakmpTimerEntryRetrTim Integer32,
            lcsSetupVpnIsakmpTimerEntryRetrTimUsec Integer32,
            lcsSetupVpnIsakmpTimerEntryRetrTimMax Integer32,
            lcsSetupVpnIsakmpTimerEntryExpTim Integer32,
            lcsSetupVpnIsakmpTimerEntryIdx Integer32
    }

-- {COLUMN} 1.3.6.1.4.1.2356.11.2.19.3.4.1.1
lcsSetupVpnIsakmpTimerEntryRetrLim OBJECT-TYPE
    SYNTAX     Integer32 (0..65535)
    MAX-ACCESS read-write
    STATUS     current
    DESCRIPTION
            ""
    ::= { lcsSetupVpnIsakmpTimerEntry 1 }

-- {COLUMN} 1.3.6.1.4.1.2356.11.2.19.3.4.1.2
lcsSetupVpnIsakmpTimerEntryRetrTim OBJECT-TYPE
    SYNTAX     Integer32 (0..65535)
    MAX-ACCESS read-write
    STATUS     current
    DESCRIPTION
            ""
    ::= { lcsSetupVpnIsakmpTimerEntry 2 }

-- {COLUMN} 1.3.6.1.4.1.2356.11.2.19.3.4.1.3
lcsSetupVpnIsakmpTimerEntryRetrTimUsec OBJECT-TYPE
    SYNTAX     Integer32 (0..2147483647)
    MAX-ACCESS read-write
    STATUS     current
    DESCRIPTION
            ""
    ::= { lcsSetupVpnIsakmpTimerEntry 3 }

-- {COLUMN} 1.3.6.1.4.1.2356.11.2.19.3.4.1.4
lcsSetupVpnIsakmpTimerEntryRetrTimMax OBJECT-TYPE
    SYNTAX     Integer32 (0..65535)
    MAX-ACCESS read-write
    STATUS     current
    DESCRIPTION
            ""
    ::= { lcsSetupVpnIsakmpTimerEntry 4 }

-- {COLUMN} 1.3.6.1.4.1.2356.11.2.19.3.4.1.5
lcsSetupVpnIsakmpTimerEntryExpTim OBJECT-TYPE
    SYNTAX     Integer32 (0..65535)
    MAX-ACCESS read-write
    STATUS     current
    DESCRIPTION
            ""
    ::= { lcsSetupVpnIsakmpTimerEntry 5 }

-- {COLUMN} 1.3.6.1.4.1.2356.11.2.19.3.4.1.6
lcsSetupVpnIsakmpTimerEntryIdx OBJECT-TYPE
    SYNTAX     Integer32 (0..255)
    MAX-ACCESS read-only
    STATUS     current
    DESCRIPTION
            ""
    ::= { lcsSetupVpnIsakmpTimerEntry 6 }

-- {NODE} 1.3.6.1.4.1.2356.11.2.19.3.29
lcsSetupVpnIsakmpDhGroups OBJECT IDENTIFIER ::= { lcsSetupVpnIsakmp 29 }

-- {SCALAR} 1.3.6.1.4.1.2356.11.2.19.3.29.1
lcsSetupVpnIsakmpDhGroupsPrecalculation OBJECT-TYPE
    SYNTAX     INTEGER {
                  eNo (0),
                  eYes (1)
            }
    MAX-ACCESS read-write
    STATUS     current
    DESCRIPTION
            "-- empty --"
    ::= { lcsSetupVpnIsakmpDhGroups 1 }

-- {TABLE} 1.3.6.1.4.1.2356.11.2.19.3.29.2
lcsSetupVpnIsakmpDhGroupsGroupConfigTable OBJECT-TYPE
    SYNTAX     SEQUENCE OF LcsSetupVpnIsakmpDhGroupsGroupConfigEntry
    MAX-ACCESS not-accessible
    STATUS     current
    DESCRIPTION
            "-- empty --"
    ::= { lcsSetupVpnIsakmpDhGroups 2 }

-- {ROW} 1.3.6.1.4.1.2356.11.2.19.3.29.2.1
lcsSetupVpnIsakmpDhGroupsGroupConfigEntry OBJECT-TYPE
    SYNTAX     LcsSetupVpnIsakmpDhGroupsGroupConfigEntry
    MAX-ACCESS not-accessible
    STATUS     current
    DESCRIPTION
            ""
    INDEX {
            lcsSetupVpnIsakmpDhGroupsGroupConfigEntryDhGroup
          }
    ::= { lcsSetupVpnIsakmpDhGroupsGroupConfigTable 1 }

LcsSetupVpnIsakmpDhGroupsGroupConfigEntry ::= SEQUENCE {
            lcsSetupVpnIsakmpDhGroupsGroupConfigEntryDhGroup Integer32,
            lcsSetupVpnIsakmpDhGroupsGroupConfigEntryPrecalcTarget Integer32
    }

-- {COLUMN} 1.3.6.1.4.1.2356.11.2.19.3.29.2.1.1
lcsSetupVpnIsakmpDhGroupsGroupConfigEntryDhGroup OBJECT-TYPE
    SYNTAX     Integer32 (0..255)
    MAX-ACCESS read-only
    STATUS     current
    DESCRIPTION
            "-- empty --"
    ::= { lcsSetupVpnIsakmpDhGroupsGroupConfigEntry 1 }

-- {COLUMN} 1.3.6.1.4.1.2356.11.2.19.3.29.2.1.2
lcsSetupVpnIsakmpDhGroupsGroupConfigEntryPrecalcTarget OBJECT-TYPE
    SYNTAX     Integer32 (0..2147483647)
    MAX-ACCESS read-write
    STATUS     current
    DESCRIPTION
            "-- empty --"
    ::= { lcsSetupVpnIsakmpDhGroupsGroupConfigEntry 2 }

-- {NODE} 1.3.6.1.4.1.2356.11.2.19.4
lcsSetupVpnProposals OBJECT IDENTIFIER ::= { lcsSetupVpn 4 }

-- {TABLE} 1.3.6.1.4.1.2356.11.2.19.4.9
lcsSetupVpnProposalsIkeProposalListsTable OBJECT-TYPE
    SYNTAX     SEQUENCE OF LcsSetupVpnProposalsIkeProposalListsEntry
    MAX-ACCESS not-accessible
    STATUS     current
    DESCRIPTION
            ""
    ::= { lcsSetupVpnProposals 9 }

-- {ROW} 1.3.6.1.4.1.2356.11.2.19.4.9.1
lcsSetupVpnProposalsIkeProposalListsEntry OBJECT-TYPE
    SYNTAX     LcsSetupVpnProposalsIkeProposalListsEntry
    MAX-ACCESS not-accessible
    STATUS     current
    DESCRIPTION
            ""
    INDEX {
            lcsSetupVpnProposalsIkeProposalListsEntryIkeProposalLists
          }
    ::= { lcsSetupVpnProposalsIkeProposalListsTable 1 }

LcsSetupVpnProposalsIkeProposalListsEntry ::= SEQUENCE {
            lcsSetupVpnProposalsIkeProposalListsEntryIkeProposalLists DisplayString,
            lcsSetupVpnProposalsIkeProposalListsEntryIkeProposal1 DisplayString,
            lcsSetupVpnProposalsIkeProposalListsEntryIkeProposal2 DisplayString,
            lcsSetupVpnProposalsIkeProposalListsEntryIkeProposal3 DisplayString,
            lcsSetupVpnProposalsIkeProposalListsEntryIkeProposal4 DisplayString,
            lcsSetupVpnProposalsIkeProposalListsEntryIkeProposal5 DisplayString,
            lcsSetupVpnProposalsIkeProposalListsEntryIkeProposal6 DisplayString,
            lcsSetupVpnProposalsIkeProposalListsEntryIkeProposal7 DisplayString,
            lcsSetupVpnProposalsIkeProposalListsEntryIkeProposal8 DisplayString
    }

-- {COLUMN} 1.3.6.1.4.1.2356.11.2.19.4.9.1.1
lcsSetupVpnProposalsIkeProposalListsEntryIkeProposalLists OBJECT-TYPE
    SYNTAX     DisplayString (SIZE(0..17))
    MAX-ACCESS read-write
    STATUS     current
    DESCRIPTION
            ""
    ::= { lcsSetupVpnProposalsIkeProposalListsEntry 1 }

-- {COLUMN} 1.3.6.1.4.1.2356.11.2.19.4.9.1.2
lcsSetupVpnProposalsIkeProposalListsEntryIkeProposal1 OBJECT-TYPE
    SYNTAX     DisplayString (SIZE(0..17))
    MAX-ACCESS read-write
    STATUS     current
    DESCRIPTION
            ""
    ::= { lcsSetupVpnProposalsIkeProposalListsEntry 2 }

-- {COLUMN} 1.3.6.1.4.1.2356.11.2.19.4.9.1.3
lcsSetupVpnProposalsIkeProposalListsEntryIkeProposal2 OBJECT-TYPE
    SYNTAX     DisplayString (SIZE(0..17))
    MAX-ACCESS read-write
    STATUS     current
    DESCRIPTION
            ""
    ::= { lcsSetupVpnProposalsIkeProposalListsEntry 3 }

-- {COLUMN} 1.3.6.1.4.1.2356.11.2.19.4.9.1.4
lcsSetupVpnProposalsIkeProposalListsEntryIkeProposal3 OBJECT-TYPE
    SYNTAX     DisplayString (SIZE(0..17))
    MAX-ACCESS read-write
    STATUS     current
    DESCRIPTION
            ""
    ::= { lcsSetupVpnProposalsIkeProposalListsEntry 4 }

-- {COLUMN} 1.3.6.1.4.1.2356.11.2.19.4.9.1.5
lcsSetupVpnProposalsIkeProposalListsEntryIkeProposal4 OBJECT-TYPE
    SYNTAX     DisplayString (SIZE(0..17))
    MAX-ACCESS read-write
    STATUS     current
    DESCRIPTION
            ""
    ::= { lcsSetupVpnProposalsIkeProposalListsEntry 5 }

-- {COLUMN} 1.3.6.1.4.1.2356.11.2.19.4.9.1.6
lcsSetupVpnProposalsIkeProposalListsEntryIkeProposal5 OBJECT-TYPE
    SYNTAX     DisplayString (SIZE(0..17))
    MAX-ACCESS read-write
    STATUS     current
    DESCRIPTION
            ""
    ::= { lcsSetupVpnProposalsIkeProposalListsEntry 6 }

-- {COLUMN} 1.3.6.1.4.1.2356.11.2.19.4.9.1.7
lcsSetupVpnProposalsIkeProposalListsEntryIkeProposal6 OBJECT-TYPE
    SYNTAX     DisplayString (SIZE(0..17))
    MAX-ACCESS read-write
    STATUS     current
    DESCRIPTION
            ""
    ::= { lcsSetupVpnProposalsIkeProposalListsEntry 7 }

-- {COLUMN} 1.3.6.1.4.1.2356.11.2.19.4.9.1.8
lcsSetupVpnProposalsIkeProposalListsEntryIkeProposal7 OBJECT-TYPE
    SYNTAX     DisplayString (SIZE(0..17))
    MAX-ACCESS read-write
    STATUS     current
    DESCRIPTION
            ""
    ::= { lcsSetupVpnProposalsIkeProposalListsEntry 8 }

-- {COLUMN} 1.3.6.1.4.1.2356.11.2.19.4.9.1.9
lcsSetupVpnProposalsIkeProposalListsEntryIkeProposal8 OBJECT-TYPE
    SYNTAX     DisplayString (SIZE(0..17))
    MAX-ACCESS read-write
    STATUS     current
    DESCRIPTION
            ""
    ::= { lcsSetupVpnProposalsIkeProposalListsEntry 9 }

-- {TABLE} 1.3.6.1.4.1.2356.11.2.19.4.10
lcsSetupVpnProposalsIpsecProposalListsTable OBJECT-TYPE
    SYNTAX     SEQUENCE OF LcsSetupVpnProposalsIpsecProposalListsEntry
    MAX-ACCESS not-accessible
    STATUS     current
    DESCRIPTION
            ""
    ::= { lcsSetupVpnProposals 10 }

-- {ROW} 1.3.6.1.4.1.2356.11.2.19.4.10.1
lcsSetupVpnProposalsIpsecProposalListsEntry OBJECT-TYPE
    SYNTAX     LcsSetupVpnProposalsIpsecProposalListsEntry
    MAX-ACCESS not-accessible
    STATUS     current
    DESCRIPTION
            ""
    INDEX {
            lcsSetupVpnProposalsIpsecProposalListsEntryIpsecProposalLists
          }
    ::= { lcsSetupVpnProposalsIpsecProposalListsTable 1 }

LcsSetupVpnProposalsIpsecProposalListsEntry ::= SEQUENCE {
            lcsSetupVpnProposalsIpsecProposalListsEntryIpsecProposalLists DisplayString,
            lcsSetupVpnProposalsIpsecProposalListsEntryIpsecProposal1 DisplayString,
            lcsSetupVpnProposalsIpsecProposalListsEntryIpsecProposal2 DisplayString,
            lcsSetupVpnProposalsIpsecProposalListsEntryIpsecProposal3 DisplayString,
            lcsSetupVpnProposalsIpsecProposalListsEntryIpsecProposal4 DisplayString,
            lcsSetupVpnProposalsIpsecProposalListsEntryIpsecProposal5 DisplayString,
            lcsSetupVpnProposalsIpsecProposalListsEntryIpsecProposal6 DisplayString,
            lcsSetupVpnProposalsIpsecProposalListsEntryIpsecProposal7 DisplayString,
            lcsSetupVpnProposalsIpsecProposalListsEntryIpsecProposal8 DisplayString
    }

-- {COLUMN} 1.3.6.1.4.1.2356.11.2.19.4.10.1.1
lcsSetupVpnProposalsIpsecProposalListsEntryIpsecProposalLists OBJECT-TYPE
    SYNTAX     DisplayString (SIZE(0..17))
    MAX-ACCESS read-write
    STATUS     current
    DESCRIPTION
            ""
    ::= { lcsSetupVpnProposalsIpsecProposalListsEntry 1 }

-- {COLUMN} 1.3.6.1.4.1.2356.11.2.19.4.10.1.2
lcsSetupVpnProposalsIpsecProposalListsEntryIpsecProposal1 OBJECT-TYPE
    SYNTAX     DisplayString (SIZE(0..17))
    MAX-ACCESS read-write
    STATUS     current
    DESCRIPTION
            ""
    ::= { lcsSetupVpnProposalsIpsecProposalListsEntry 2 }

-- {COLUMN} 1.3.6.1.4.1.2356.11.2.19.4.10.1.3
lcsSetupVpnProposalsIpsecProposalListsEntryIpsecProposal2 OBJECT-TYPE
    SYNTAX     DisplayString (SIZE(0..17))
    MAX-ACCESS read-write
    STATUS     current
    DESCRIPTION
            ""
    ::= { lcsSetupVpnProposalsIpsecProposalListsEntry 3 }

-- {COLUMN} 1.3.6.1.4.1.2356.11.2.19.4.10.1.4
lcsSetupVpnProposalsIpsecProposalListsEntryIpsecProposal3 OBJECT-TYPE
    SYNTAX     DisplayString (SIZE(0..17))
    MAX-ACCESS read-write
    STATUS     current
    DESCRIPTION
            ""
    ::= { lcsSetupVpnProposalsIpsecProposalListsEntry 4 }

-- {COLUMN} 1.3.6.1.4.1.2356.11.2.19.4.10.1.5
lcsSetupVpnProposalsIpsecProposalListsEntryIpsecProposal4 OBJECT-TYPE
    SYNTAX     DisplayString (SIZE(0..17))
    MAX-ACCESS read-write
    STATUS     current
    DESCRIPTION
            ""
    ::= { lcsSetupVpnProposalsIpsecProposalListsEntry 5 }

-- {COLUMN} 1.3.6.1.4.1.2356.11.2.19.4.10.1.6
lcsSetupVpnProposalsIpsecProposalListsEntryIpsecProposal5 OBJECT-TYPE
    SYNTAX     DisplayString (SIZE(0..17))
    MAX-ACCESS read-write
    STATUS     current
    DESCRIPTION
            ""
    ::= { lcsSetupVpnProposalsIpsecProposalListsEntry 6 }

-- {COLUMN} 1.3.6.1.4.1.2356.11.2.19.4.10.1.7
lcsSetupVpnProposalsIpsecProposalListsEntryIpsecProposal6 OBJECT-TYPE
    SYNTAX     DisplayString (SIZE(0..17))
    MAX-ACCESS read-write
    STATUS     current
    DESCRIPTION
            ""
    ::= { lcsSetupVpnProposalsIpsecProposalListsEntry 7 }

-- {COLUMN} 1.3.6.1.4.1.2356.11.2.19.4.10.1.8
lcsSetupVpnProposalsIpsecProposalListsEntryIpsecProposal7 OBJECT-TYPE
    SYNTAX     DisplayString (SIZE(0..17))
    MAX-ACCESS read-write
    STATUS     current
    DESCRIPTION
            ""
    ::= { lcsSetupVpnProposalsIpsecProposalListsEntry 8 }

-- {COLUMN} 1.3.6.1.4.1.2356.11.2.19.4.10.1.9
lcsSetupVpnProposalsIpsecProposalListsEntryIpsecProposal8 OBJECT-TYPE
    SYNTAX     DisplayString (SIZE(0..17))
    MAX-ACCESS read-write
    STATUS     current
    DESCRIPTION
            ""
    ::= { lcsSetupVpnProposalsIpsecProposalListsEntry 9 }

-- {TABLE} 1.3.6.1.4.1.2356.11.2.19.4.11
lcsSetupVpnProposalsIkeTable OBJECT-TYPE
    SYNTAX     SEQUENCE OF LcsSetupVpnProposalsIkeEntry
    MAX-ACCESS not-accessible
    STATUS     current
    DESCRIPTION
            ""
    ::= { lcsSetupVpnProposals 11 }

-- {ROW} 1.3.6.1.4.1.2356.11.2.19.4.11.1
lcsSetupVpnProposalsIkeEntry OBJECT-TYPE
    SYNTAX     LcsSetupVpnProposalsIkeEntry
    MAX-ACCESS not-accessible
    STATUS     current
    DESCRIPTION
            ""
    INDEX {
            lcsSetupVpnProposalsIkeEntryName
          }
    ::= { lcsSetupVpnProposalsIkeTable 1 }

LcsSetupVpnProposalsIkeEntry ::= SEQUENCE {
            lcsSetupVpnProposalsIkeEntryName DisplayString,
            lcsSetupVpnProposalsIkeEntryIkeCryptAlg INTEGER,
            lcsSetupVpnProposalsIkeEntryIkeCryptKeylen Integer32,
            lcsSetupVpnProposalsIkeEntryIkeAuthAlg INTEGER,
            lcsSetupVpnProposalsIkeEntryIkeAuthMode INTEGER,
            lcsSetupVpnProposalsIkeEntryLifetimeSec Integer32,
            lcsSetupVpnProposalsIkeEntryLifetimeKb Integer32
    }

-- {COLUMN} 1.3.6.1.4.1.2356.11.2.19.4.11.1.1
lcsSetupVpnProposalsIkeEntryName OBJECT-TYPE
    SYNTAX     DisplayString (SIZE(0..17))
    MAX-ACCESS read-write
    STATUS     current
    DESCRIPTION
            ""
    ::= { lcsSetupVpnProposalsIkeEntry 1 }

-- {COLUMN} 1.3.6.1.4.1.2356.11.2.19.4.11.1.2
lcsSetupVpnProposalsIkeEntryIkeCryptAlg OBJECT-TYPE
    SYNTAX     INTEGER {
                  eDesCbc (1),
                  eBlowfishCbc (3),
                  e3desCbc (5),
                  eCast128Cbc (6),
                  eAesCbc (7),
                  eNull (42)
            }
    MAX-ACCESS read-write
    STATUS     current
    DESCRIPTION
            ""
    ::= { lcsSetupVpnProposalsIkeEntry 2 }

-- {COLUMN} 1.3.6.1.4.1.2356.11.2.19.4.11.1.3
lcsSetupVpnProposalsIkeEntryIkeCryptKeylen OBJECT-TYPE
    SYNTAX     Integer32 (0..65535)
    MAX-ACCESS read-write
    STATUS     current
    DESCRIPTION
            ""
    ::= { lcsSetupVpnProposalsIkeEntry 3 }

-- {COLUMN} 1.3.6.1.4.1.2356.11.2.19.4.11.1.4
lcsSetupVpnProposalsIkeEntryIkeAuthAlg OBJECT-TYPE
    SYNTAX     INTEGER {
                  eMd5 (1),
                  eSha1 (2),
                  eSha256 (4),
                  eSha384 (5),
                  eSha512 (6)
            }
    MAX-ACCESS read-write
    STATUS     current
    DESCRIPTION
            ""
    ::= { lcsSetupVpnProposalsIkeEntry 4 }

-- {COLUMN} 1.3.6.1.4.1.2356.11.2.19.4.11.1.5
lcsSetupVpnProposalsIkeEntryIkeAuthMode OBJECT-TYPE
    SYNTAX     INTEGER {
                  ePresharedKey (1),
                  eRsaSignature (3)
            }
    MAX-ACCESS read-write
    STATUS     current
    DESCRIPTION
            ""
    ::= { lcsSetupVpnProposalsIkeEntry 5 }

-- {COLUMN} 1.3.6.1.4.1.2356.11.2.19.4.11.1.6
lcsSetupVpnProposalsIkeEntryLifetimeSec OBJECT-TYPE
    SYNTAX     Integer32 (0..2147483647)
    MAX-ACCESS read-write
    STATUS     current
    DESCRIPTION
            ""
    ::= { lcsSetupVpnProposalsIkeEntry 6 }

-- {COLUMN} 1.3.6.1.4.1.2356.11.2.19.4.11.1.7
lcsSetupVpnProposalsIkeEntryLifetimeKb OBJECT-TYPE
    SYNTAX     Integer32 (0..2147483647)
    MAX-ACCESS read-write
    STATUS     current
    DESCRIPTION
            ""
    ::= { lcsSetupVpnProposalsIkeEntry 7 }

-- {TABLE} 1.3.6.1.4.1.2356.11.2.19.4.12
lcsSetupVpnProposalsIpsecTable OBJECT-TYPE
    SYNTAX     SEQUENCE OF LcsSetupVpnProposalsIpsecEntry
    MAX-ACCESS not-accessible
    STATUS     current
    DESCRIPTION
            ""
    ::= { lcsSetupVpnProposals 12 }

-- {ROW} 1.3.6.1.4.1.2356.11.2.19.4.12.1
lcsSetupVpnProposalsIpsecEntry OBJECT-TYPE
    SYNTAX     LcsSetupVpnProposalsIpsecEntry
    MAX-ACCESS not-accessible
    STATUS     current
    DESCRIPTION
            ""
    INDEX {
            lcsSetupVpnProposalsIpsecEntryName
          }
    ::= { lcsSetupVpnProposalsIpsecTable 1 }

LcsSetupVpnProposalsIpsecEntry ::= SEQUENCE {
            lcsSetupVpnProposalsIpsecEntryName DisplayString,
            lcsSetupVpnProposalsIpsecEntryEncapsMode INTEGER,
            lcsSetupVpnProposalsIpsecEntryEspCryptAlg INTEGER,
            lcsSetupVpnProposalsIpsecEntryEspCryptKeylen Integer32,
            lcsSetupVpnProposalsIpsecEntryEspAuthAlg INTEGER,
            lcsSetupVpnProposalsIpsecEntryAhAuthAlg INTEGER,
            lcsSetupVpnProposalsIpsecEntryIpcompAlg INTEGER,
            lcsSetupVpnProposalsIpsecEntryLifetimeSec Integer32,
            lcsSetupVpnProposalsIpsecEntryLifetimeKb Integer32
    }

-- {COLUMN} 1.3.6.1.4.1.2356.11.2.19.4.12.1.1
lcsSetupVpnProposalsIpsecEntryName OBJECT-TYPE
    SYNTAX     DisplayString (SIZE(0..17))
    MAX-ACCESS read-write
    STATUS     current
    DESCRIPTION
            ""
    ::= { lcsSetupVpnProposalsIpsecEntry 1 }

-- {COLUMN} 1.3.6.1.4.1.2356.11.2.19.4.12.1.2
lcsSetupVpnProposalsIpsecEntryEncapsMode OBJECT-TYPE
    SYNTAX     INTEGER {
                  eTunnel (1),
                  eTransport (2),
                  eMixedLcos4 (65001)
            }
    MAX-ACCESS read-write
    STATUS     current
    DESCRIPTION
            ""
    ::= { lcsSetupVpnProposalsIpsecEntry 2 }

-- {COLUMN} 1.3.6.1.4.1.2356.11.2.19.4.12.1.3
lcsSetupVpnProposalsIpsecEntryEspCryptAlg OBJECT-TYPE
    SYNTAX     INTEGER {
                  eNone (0),
                  eDesCbc (2),
                  e3desCbc (3),
                  eCast128Cbc (6),
                  eBlowfishCbc (7),
                  eNull (11),
                  eAesCbc (12)
            }
    MAX-ACCESS read-write
    STATUS     current
    DESCRIPTION
            ""
    ::= { lcsSetupVpnProposalsIpsecEntry 3 }

-- {COLUMN} 1.3.6.1.4.1.2356.11.2.19.4.12.1.4
lcsSetupVpnProposalsIpsecEntryEspCryptKeylen OBJECT-TYPE
    SYNTAX     Integer32 (0..65535)
    MAX-ACCESS read-write
    STATUS     current
    DESCRIPTION
            ""
    ::= { lcsSetupVpnProposalsIpsecEntry 4 }

-- {COLUMN} 1.3.6.1.4.1.2356.11.2.19.4.12.1.5
lcsSetupVpnProposalsIpsecEntryEspAuthAlg OBJECT-TYPE
    SYNTAX     INTEGER {
                  eNone (0),
                  eHmacMd5 (1),
                  eHmacSha1 (2),
                  eHmacSha256 (5),
                  eHmacSha384 (6),
                  eHmacSha512 (7)
            }
    MAX-ACCESS read-write
    STATUS     current
    DESCRIPTION
            ""
    ::= { lcsSetupVpnProposalsIpsecEntry 5 }

-- {COLUMN} 1.3.6.1.4.1.2356.11.2.19.4.12.1.6
lcsSetupVpnProposalsIpsecEntryAhAuthAlg OBJECT-TYPE
    SYNTAX     INTEGER {
                  eNone (0),
                  eHmacMd5 (1),
                  eHmacSha1 (2),
                  eHmacSha256 (5),
                  eHmacSha384 (6),
                  eHmacSha512 (7)
            }
    MAX-ACCESS read-write
    STATUS     current
    DESCRIPTION
            ""
    ::= { lcsSetupVpnProposalsIpsecEntry 6 }

-- {COLUMN} 1.3.6.1.4.1.2356.11.2.19.4.12.1.7
lcsSetupVpnProposalsIpsecEntryIpcompAlg OBJECT-TYPE
    SYNTAX     INTEGER {
                  eNone (0),
                  eDeflate (2),
                  eLzs (3)
            }
    MAX-ACCESS read-write
    STATUS     current
    DESCRIPTION
            ""
    ::= { lcsSetupVpnProposalsIpsecEntry 7 }

-- {COLUMN} 1.3.6.1.4.1.2356.11.2.19.4.12.1.8
lcsSetupVpnProposalsIpsecEntryLifetimeSec OBJECT-TYPE
    SYNTAX     Integer32 (0..2147483647)
    MAX-ACCESS read-write
    STATUS     current
    DESCRIPTION
            ""
    ::= { lcsSetupVpnProposalsIpsecEntry 8 }

-- {COLUMN} 1.3.6.1.4.1.2356.11.2.19.4.12.1.9
lcsSetupVpnProposalsIpsecEntryLifetimeKb OBJECT-TYPE
    SYNTAX     Integer32 (0..2147483647)
    MAX-ACCESS read-write
    STATUS     current
    DESCRIPTION
            ""
    ::= { lcsSetupVpnProposalsIpsecEntry 9 }

-- {NODE} 1.3.6.1.4.1.2356.11.2.19.5
lcsSetupVpnCertificatesAndKeys OBJECT IDENTIFIER ::= { lcsSetupVpn 5 }

-- {TABLE} 1.3.6.1.4.1.2356.11.2.19.5.3
lcsSetupVpnCertificatesAndKeysIkeKeysTable OBJECT-TYPE
    SYNTAX     SEQUENCE OF LcsSetupVpnCertificatesAndKeysIkeKeysEntry
    MAX-ACCESS not-accessible
    STATUS     current
    DESCRIPTION
            ""
    ::= { lcsSetupVpnCertificatesAndKeys 3 }

-- {ROW} 1.3.6.1.4.1.2356.11.2.19.5.3.1
lcsSetupVpnCertificatesAndKeysIkeKeysEntry OBJECT-TYPE
    SYNTAX     LcsSetupVpnCertificatesAndKeysIkeKeysEntry
    MAX-ACCESS not-accessible
    STATUS     current
    DESCRIPTION
            ""
    INDEX {
            lcsSetupVpnCertificatesAndKeysIkeKeysEntryName
          }
    ::= { lcsSetupVpnCertificatesAndKeysIkeKeysTable 1 }

LcsSetupVpnCertificatesAndKeysIkeKeysEntry ::= SEQUENCE {
            lcsSetupVpnCertificatesAndKeysIkeKeysEntryName DisplayString,
            lcsSetupVpnCertificatesAndKeysIkeKeysEntryRemoteIdentity DisplayString,
            lcsSetupVpnCertificatesAndKeysIkeKeysEntrySharedSec DisplayString,
            lcsSetupVpnCertificatesAndKeysIkeKeysEntrySharedSecFile DisplayString,
            lcsSetupVpnCertificatesAndKeysIkeKeysEntryRemoteIdType INTEGER,
            lcsSetupVpnCertificatesAndKeysIkeKeysEntryLocalIdType INTEGER,
            lcsSetupVpnCertificatesAndKeysIkeKeysEntryLocalIdentity DisplayString
    }

-- {COLUMN} 1.3.6.1.4.1.2356.11.2.19.5.3.1.1
lcsSetupVpnCertificatesAndKeysIkeKeysEntryName OBJECT-TYPE
    SYNTAX     DisplayString (SIZE(0..16))
    MAX-ACCESS read-write
    STATUS     current
    DESCRIPTION
            ""
    ::= { lcsSetupVpnCertificatesAndKeysIkeKeysEntry 1 }

-- {COLUMN} 1.3.6.1.4.1.2356.11.2.19.5.3.1.2
lcsSetupVpnCertificatesAndKeysIkeKeysEntryRemoteIdentity OBJECT-TYPE
    SYNTAX     DisplayString (SIZE(0..254))
    MAX-ACCESS read-write
    STATUS     current
    DESCRIPTION
            ""
    ::= { lcsSetupVpnCertificatesAndKeysIkeKeysEntry 2 }

-- {COLUMN} 1.3.6.1.4.1.2356.11.2.19.5.3.1.3
lcsSetupVpnCertificatesAndKeysIkeKeysEntrySharedSec OBJECT-TYPE
    SYNTAX     DisplayString (SIZE(0..64))
    MAX-ACCESS read-write
    STATUS     current
    DESCRIPTION
            ""
    ::= { lcsSetupVpnCertificatesAndKeysIkeKeysEntry 3 }

-- {COLUMN} 1.3.6.1.4.1.2356.11.2.19.5.3.1.4
lcsSetupVpnCertificatesAndKeysIkeKeysEntrySharedSecFile OBJECT-TYPE
    SYNTAX     DisplayString (SIZE(0..20))
    MAX-ACCESS read-write
    STATUS     current
    DESCRIPTION
            ""
    ::= { lcsSetupVpnCertificatesAndKeysIkeKeysEntry 4 }

-- {COLUMN} 1.3.6.1.4.1.2356.11.2.19.5.3.1.5
lcsSetupVpnCertificatesAndKeysIkeKeysEntryRemoteIdType OBJECT-TYPE
    SYNTAX     INTEGER {
                  eNoIdentity (0),
                  eIpAddress (1),
                  eDomainName (2),
                  eEmailAddress (3),
                  eIpv6Address (5),
                  eDistinguishedName (9),
                  eKeyId (11)
            }
    MAX-ACCESS read-write
    STATUS     current
    DESCRIPTION
            ""
    ::= { lcsSetupVpnCertificatesAndKeysIkeKeysEntry 5 }

-- {COLUMN} 1.3.6.1.4.1.2356.11.2.19.5.3.1.6
lcsSetupVpnCertificatesAndKeysIkeKeysEntryLocalIdType OBJECT-TYPE
    SYNTAX     INTEGER {
                  eNoIdentity (0),
                  eIpAddress (1),
                  eDomainName (2),
                  eEmailAddress (3),
                  eIpv6Address (5),
                  eDistinguishedName (9),
                  eKeyId (11)
            }
    MAX-ACCESS read-write
    STATUS     current
    DESCRIPTION
            ""
    ::= { lcsSetupVpnCertificatesAndKeysIkeKeysEntry 6 }

-- {COLUMN} 1.3.6.1.4.1.2356.11.2.19.5.3.1.7
lcsSetupVpnCertificatesAndKeysIkeKeysEntryLocalIdentity OBJECT-TYPE
    SYNTAX     DisplayString (SIZE(0..254))
    MAX-ACCESS read-write
    STATUS     current
    DESCRIPTION
            ""
    ::= { lcsSetupVpnCertificatesAndKeysIkeKeysEntry 7 }

-- {TABLE} 1.3.6.1.4.1.2356.11.2.19.7
lcsSetupVpnLayerTable OBJECT-TYPE
    SYNTAX     SEQUENCE OF LcsSetupVpnLayerEntry
    MAX-ACCESS not-accessible
    STATUS     current
    DESCRIPTION
            ""
    ::= { lcsSetupVpn 7 }

-- {ROW} 1.3.6.1.4.1.2356.11.2.19.7.1
lcsSetupVpnLayerEntry OBJECT-TYPE
    SYNTAX     LcsSetupVpnLayerEntry
    MAX-ACCESS not-accessible
    STATUS     current
    DESCRIPTION
            ""
    INDEX {
            lcsSetupVpnLayerEntryName
          }
    ::= { lcsSetupVpnLayerTable 1 }

LcsSetupVpnLayerEntry ::= SEQUENCE {
            lcsSetupVpnLayerEntryName DisplayString,
            lcsSetupVpnLayerEntryPfsGrp INTEGER,
            lcsSetupVpnLayerEntryIkeGrp INTEGER,
            lcsSetupVpnLayerEntryIkePropList DisplayString,
            lcsSetupVpnLayerEntryIpsecPropList DisplayString,
            lcsSetupVpnLayerEntryIkeKey DisplayString
    }

-- {COLUMN} 1.3.6.1.4.1.2356.11.2.19.7.1.1
lcsSetupVpnLayerEntryName OBJECT-TYPE
    SYNTAX     DisplayString (SIZE(0..16))
    MAX-ACCESS read-write
    STATUS     current
    DESCRIPTION
            ""
    ::= { lcsSetupVpnLayerEntry 1 }

-- {COLUMN} 1.3.6.1.4.1.2356.11.2.19.7.1.3
lcsSetupVpnLayerEntryPfsGrp OBJECT-TYPE
    SYNTAX     INTEGER {
                  e0 (0),
                  e1 (1),
                  e2 (2),
                  e5 (5),
                  e14 (14),
                  e15 (15),
                  e16 (16)
            }
    MAX-ACCESS read-write
    STATUS     current
    DESCRIPTION
            ""
    ::= { lcsSetupVpnLayerEntry 3 }

-- {COLUMN} 1.3.6.1.4.1.2356.11.2.19.7.1.4
lcsSetupVpnLayerEntryIkeGrp OBJECT-TYPE
    SYNTAX     INTEGER {
                  e1 (1),
                  e2 (2),
                  e5 (5),
                  e14 (14),
                  e15 (15),
                  e16 (16)
            }
    MAX-ACCESS read-write
    STATUS     current
    DESCRIPTION
            ""
    ::= { lcsSetupVpnLayerEntry 4 }

-- {COLUMN} 1.3.6.1.4.1.2356.11.2.19.7.1.5
lcsSetupVpnLayerEntryIkePropList OBJECT-TYPE
    SYNTAX     DisplayString (SIZE(0..17))
    MAX-ACCESS read-write
    STATUS     current
    DESCRIPTION
            ""
    ::= { lcsSetupVpnLayerEntry 5 }

-- {COLUMN} 1.3.6.1.4.1.2356.11.2.19.7.1.6
lcsSetupVpnLayerEntryIpsecPropList OBJECT-TYPE
    SYNTAX     DisplayString (SIZE(0..17))
    MAX-ACCESS read-write
    STATUS     current
    DESCRIPTION
            ""
    ::= { lcsSetupVpnLayerEntry 6 }

-- {COLUMN} 1.3.6.1.4.1.2356.11.2.19.7.1.7
lcsSetupVpnLayerEntryIkeKey OBJECT-TYPE
    SYNTAX     DisplayString (SIZE(0..16))
    MAX-ACCESS read-write
    STATUS     current
    DESCRIPTION
            ""
    ::= { lcsSetupVpnLayerEntry 7 }

-- {SCALAR} 1.3.6.1.4.1.2356.11.2.19.8
lcsSetupVpnOperating OBJECT-TYPE
    SYNTAX     INTEGER {
                  eNo (0),
                  eYes (1),
                  eExclusive (3)
            }
    MAX-ACCESS read-write
    STATUS     current
    DESCRIPTION
            ""
    ::= { lcsSetupVpn 8 }

-- {TABLE} 1.3.6.1.4.1.2356.11.2.19.9
lcsSetupVpnVpnPeersTable OBJECT-TYPE
    SYNTAX     SEQUENCE OF LcsSetupVpnVpnPeersEntry
    MAX-ACCESS not-accessible
    STATUS     current
    DESCRIPTION
            ""
    ::= { lcsSetupVpn 9 }

-- {ROW} 1.3.6.1.4.1.2356.11.2.19.9.1
lcsSetupVpnVpnPeersEntry OBJECT-TYPE
    SYNTAX     LcsSetupVpnVpnPeersEntry
    MAX-ACCESS not-accessible
    STATUS     current
    DESCRIPTION
            ""
    INDEX {
            lcsSetupVpnVpnPeersEntryPeer
          }
    ::= { lcsSetupVpnVpnPeersTable 1 }

LcsSetupVpnVpnPeersEntry ::= SEQUENCE {
            lcsSetupVpnVpnPeersEntryPeer DisplayString,
            lcsSetupVpnVpnPeersEntryExtranetAddress IpAddress,
            lcsSetupVpnVpnPeersEntryLayer DisplayString,
            lcsSetupVpnVpnPeersEntryDynamic INTEGER,
            lcsSetupVpnVpnPeersEntryShTime Integer32,
            lcsSetupVpnVpnPeersEntryIkeExchange INTEGER,
            lcsSetupVpnVpnPeersEntryRemoteGw DisplayString,
            lcsSetupVpnVpnPeersEntryRuleCreation INTEGER,
            lcsSetupVpnVpnPeersEntryDpdInactTimeout Integer32,
            lcsSetupVpnVpnPeersEntryIkeCfg INTEGER,
            lcsSetupVpnVpnPeersEntryXauth INTEGER,
            lcsSetupVpnVpnPeersEntrySslEncaps INTEGER,
            lcsSetupVpnVpnPeersEntryRtgTag Integer32,
            lcsSetupVpnVpnPeersEntryOcspCheck INTEGER,
            lcsSetupVpnVpnPeersEntryIpv4Rules DisplayString,
            lcsSetupVpnVpnPeersEntryIpv6Rules DisplayString,
            lcsSetupVpnVpnPeersEntryIpv4 DisplayString,
            lcsSetupVpnVpnPeersEntryIpv6 DisplayString
    }

-- {COLUMN} 1.3.6.1.4.1.2356.11.2.19.9.1.1
lcsSetupVpnVpnPeersEntryPeer OBJECT-TYPE
    SYNTAX     DisplayString (SIZE(0..16))
    MAX-ACCESS read-write
    STATUS     current
    DESCRIPTION
            ""
    ::= { lcsSetupVpnVpnPeersEntry 1 }

-- {COLUMN} 1.3.6.1.4.1.2356.11.2.19.9.1.2
lcsSetupVpnVpnPeersEntryExtranetAddress OBJECT-TYPE
    SYNTAX     IpAddress
    MAX-ACCESS read-write
    STATUS     current
    DESCRIPTION
            ""
    ::= { lcsSetupVpnVpnPeersEntry 2 }

-- {COLUMN} 1.3.6.1.4.1.2356.11.2.19.9.1.4
lcsSetupVpnVpnPeersEntryLayer OBJECT-TYPE
    SYNTAX     DisplayString (SIZE(0..16))
    MAX-ACCESS read-write
    STATUS     current
    DESCRIPTION
            ""
    ::= { lcsSetupVpnVpnPeersEntry 4 }

-- {COLUMN} 1.3.6.1.4.1.2356.11.2.19.9.1.5
lcsSetupVpnVpnPeersEntryDynamic OBJECT-TYPE
    SYNTAX     INTEGER {
                  eNo (0),
                  eBChannel (1),
                  eDChannel (2),
                  eIcmp (4),
                  eUdp (8)
            }
    MAX-ACCESS read-write
    STATUS     current
    DESCRIPTION
            ""
    ::= { lcsSetupVpnVpnPeersEntry 5 }

-- {COLUMN} 1.3.6.1.4.1.2356.11.2.19.9.1.6
lcsSetupVpnVpnPeersEntryShTime OBJECT-TYPE
    SYNTAX     Integer32 (0..65535)
    MAX-ACCESS read-write
    STATUS     current
    DESCRIPTION
            ""
    ::= { lcsSetupVpnVpnPeersEntry 6 }

-- {COLUMN} 1.3.6.1.4.1.2356.11.2.19.9.1.7
lcsSetupVpnVpnPeersEntryIkeExchange OBJECT-TYPE
    SYNTAX     INTEGER {
                  eMainMode (0),
                  eAggressiveMode (1)
            }
    MAX-ACCESS read-write
    STATUS     current
    DESCRIPTION
            ""
    ::= { lcsSetupVpnVpnPeersEntry 7 }

-- {COLUMN} 1.3.6.1.4.1.2356.11.2.19.9.1.8
lcsSetupVpnVpnPeersEntryRemoteGw OBJECT-TYPE
    SYNTAX     DisplayString (SIZE(0..63))
    MAX-ACCESS read-write
    STATUS     current
    DESCRIPTION
            ""
    ::= { lcsSetupVpnVpnPeersEntry 8 }

-- {COLUMN} 1.3.6.1.4.1.2356.11.2.19.9.1.9
lcsSetupVpnVpnPeersEntryRuleCreation OBJECT-TYPE
    SYNTAX     INTEGER {
                  eAuto (0),
                  eManually (1),
                  eOff (2)
            }
    MAX-ACCESS read-write
    STATUS     current
    DESCRIPTION
            ""
    ::= { lcsSetupVpnVpnPeersEntry 9 }

-- {COLUMN} 1.3.6.1.4.1.2356.11.2.19.9.1.10
lcsSetupVpnVpnPeersEntryDpdInactTimeout OBJECT-TYPE
    SYNTAX     Integer32 (0..2147483647)
    MAX-ACCESS read-write
    STATUS     current
    DESCRIPTION
            ""
    ::= { lcsSetupVpnVpnPeersEntry 10 }

-- {COLUMN} 1.3.6.1.4.1.2356.11.2.19.9.1.11
lcsSetupVpnVpnPeersEntryIkeCfg OBJECT-TYPE
    SYNTAX     INTEGER {
                  eOff (0),
                  eClient (1),
                  eServer (2)
            }
    MAX-ACCESS read-write
    STATUS     current
    DESCRIPTION
            ""
    ::= { lcsSetupVpnVpnPeersEntry 11 }

-- {COLUMN} 1.3.6.1.4.1.2356.11.2.19.9.1.12
lcsSetupVpnVpnPeersEntryXauth OBJECT-TYPE
    SYNTAX     INTEGER {
                  eOff (0),
                  eClient (1),
                  eServer (2)
            }
    MAX-ACCESS read-write
    STATUS     current
    DESCRIPTION
            ""
    ::= { lcsSetupVpnVpnPeersEntry 12 }

-- {COLUMN} 1.3.6.1.4.1.2356.11.2.19.9.1.13
lcsSetupVpnVpnPeersEntrySslEncaps OBJECT-TYPE
    SYNTAX     INTEGER {
                  eNo (0),
                  eYes (1)
            }
    MAX-ACCESS read-write
    STATUS     current
    DESCRIPTION
            ""
    ::= { lcsSetupVpnVpnPeersEntry 13 }

-- {COLUMN} 1.3.6.1.4.1.2356.11.2.19.9.1.15
lcsSetupVpnVpnPeersEntryRtgTag OBJECT-TYPE
    SYNTAX     Integer32 (0..65535)
    MAX-ACCESS read-write
    STATUS     current
    DESCRIPTION
            ""
    ::= { lcsSetupVpnVpnPeersEntry 15 }

-- {COLUMN} 1.3.6.1.4.1.2356.11.2.19.9.1.16
lcsSetupVpnVpnPeersEntryOcspCheck OBJECT-TYPE
    SYNTAX     INTEGER {
                  eNo (0),
                  eYes (1)
            }
    MAX-ACCESS read-write
    STATUS     current
    DESCRIPTION
            ""
    ::= { lcsSetupVpnVpnPeersEntry 16 }

-- {COLUMN} 1.3.6.1.4.1.2356.11.2.19.9.1.17
lcsSetupVpnVpnPeersEntryIpv4Rules OBJECT-TYPE
    SYNTAX     DisplayString (SIZE(0..63))
    MAX-ACCESS read-write
    STATUS     current
    DESCRIPTION
            "-- empty --"
    ::= { lcsSetupVpnVpnPeersEntry 17 }

-- {COLUMN} 1.3.6.1.4.1.2356.11.2.19.9.1.18
lcsSetupVpnVpnPeersEntryIpv6Rules OBJECT-TYPE
    SYNTAX     DisplayString (SIZE(0..63))
    MAX-ACCESS read-write
    STATUS     current
    DESCRIPTION
            "-- empty --"
    ::= { lcsSetupVpnVpnPeersEntry 18 }

-- {COLUMN} 1.3.6.1.4.1.2356.11.2.19.9.1.19
lcsSetupVpnVpnPeersEntryIpv4 OBJECT-TYPE
    SYNTAX     DisplayString (SIZE(0..16))
    MAX-ACCESS read-write
    STATUS     current
    DESCRIPTION
            "-- empty --"
    ::= { lcsSetupVpnVpnPeersEntry 19 }

-- {COLUMN} 1.3.6.1.4.1.2356.11.2.19.9.1.20
lcsSetupVpnVpnPeersEntryIpv6 OBJECT-TYPE
    SYNTAX     DisplayString (SIZE(0..16))
    MAX-ACCESS read-write
    STATUS     current
    DESCRIPTION
            "-- empty --"
    ::= { lcsSetupVpnVpnPeersEntry 20 }

-- {SCALAR} 1.3.6.1.4.1.2356.11.2.19.10
lcsSetupVpnAggrmodeProposalListDefault OBJECT-TYPE
    SYNTAX     DisplayString (SIZE(0..17))
    MAX-ACCESS read-write
    STATUS     current
    DESCRIPTION
            ""
    ::= { lcsSetupVpn 10 }

-- {SCALAR} 1.3.6.1.4.1.2356.11.2.19.11
lcsSetupVpnAggrmodeIkeGroupDefault OBJECT-TYPE
    SYNTAX     INTEGER {
                  e1 (1),
                  e2 (2),
                  e5 (5),
                  e14 (14),
                  e15 (15),
                  e16 (16)
            }
    MAX-ACCESS read-write
    STATUS     current
    DESCRIPTION
            ""
    ::= { lcsSetupVpn 11 }

-- {TABLE} 1.3.6.1.4.1.2356.11.2.19.12
lcsSetupVpnAdditionalGatewaysTable OBJECT-TYPE
    SYNTAX     SEQUENCE OF LcsSetupVpnAdditionalGatewaysEntry
    MAX-ACCESS not-accessible
    STATUS     current
    DESCRIPTION
            ""
    ::= { lcsSetupVpn 12 }

-- {ROW} 1.3.6.1.4.1.2356.11.2.19.12.1
lcsSetupVpnAdditionalGatewaysEntry OBJECT-TYPE
    SYNTAX     LcsSetupVpnAdditionalGatewaysEntry
    MAX-ACCESS not-accessible
    STATUS     current
    DESCRIPTION
            ""
    INDEX {
            lcsSetupVpnAdditionalGatewaysEntryPeer
          }
    ::= { lcsSetupVpnAdditionalGatewaysTable 1 }

LcsSetupVpnAdditionalGatewaysEntry ::= SEQUENCE {
            lcsSetupVpnAdditionalGatewaysEntryPeer DisplayString,
            lcsSetupVpnAdditionalGatewaysEntryGateway1 DisplayString,
            lcsSetupVpnAdditionalGatewaysEntryGateway2 DisplayString,
            lcsSetupVpnAdditionalGatewaysEntryGateway3 DisplayString,
            lcsSetupVpnAdditionalGatewaysEntryGateway4 DisplayString,
            lcsSetupVpnAdditionalGatewaysEntryGateway5 DisplayString,
            lcsSetupVpnAdditionalGatewaysEntryGateway6 DisplayString,
            lcsSetupVpnAdditionalGatewaysEntryGateway7 DisplayString,
            lcsSetupVpnAdditionalGatewaysEntryGateway8 DisplayString,
            lcsSetupVpnAdditionalGatewaysEntryBeginWith INTEGER,
            lcsSetupVpnAdditionalGatewaysEntryRtgTag1 Integer32,
            lcsSetupVpnAdditionalGatewaysEntryRtgTag2 Integer32,
            lcsSetupVpnAdditionalGatewaysEntryRtgTag3 Integer32,
            lcsSetupVpnAdditionalGatewaysEntryRtgTag4 Integer32,
            lcsSetupVpnAdditionalGatewaysEntryRtgTag5 Integer32,
            lcsSetupVpnAdditionalGatewaysEntryRtgTag6 Integer32,
            lcsSetupVpnAdditionalGatewaysEntryRtgTag7 Integer32,
            lcsSetupVpnAdditionalGatewaysEntryRtgTag8 Integer32,
            lcsSetupVpnAdditionalGatewaysEntryGateway9 DisplayString,
            lcsSetupVpnAdditionalGatewaysEntryGateway10 DisplayString,
            lcsSetupVpnAdditionalGatewaysEntryGateway11 DisplayString,
            lcsSetupVpnAdditionalGatewaysEntryGateway12 DisplayString,
            lcsSetupVpnAdditionalGatewaysEntryGateway13 DisplayString,
            lcsSetupVpnAdditionalGatewaysEntryGateway14 DisplayString,
            lcsSetupVpnAdditionalGatewaysEntryGateway15 DisplayString,
            lcsSetupVpnAdditionalGatewaysEntryGateway16 DisplayString,
            lcsSetupVpnAdditionalGatewaysEntryRtgTag9 Integer32,
            lcsSetupVpnAdditionalGatewaysEntryRtgTag10 Integer32,
            lcsSetupVpnAdditionalGatewaysEntryRtgTag11 Integer32,
            lcsSetupVpnAdditionalGatewaysEntryRtgTag12 Integer32,
            lcsSetupVpnAdditionalGatewaysEntryRtgTag13 Integer32,
            lcsSetupVpnAdditionalGatewaysEntryRtgTag14 Integer32,
            lcsSetupVpnAdditionalGatewaysEntryRtgTag15 Integer32,
            lcsSetupVpnAdditionalGatewaysEntryRtgTag16 Integer32,
            lcsSetupVpnAdditionalGatewaysEntryGateway17 DisplayString,
            lcsSetupVpnAdditionalGatewaysEntryRtgTag17 Integer32,
            lcsSetupVpnAdditionalGatewaysEntryGateway18 DisplayString,
            lcsSetupVpnAdditionalGatewaysEntryRtgTag18 Integer32,
            lcsSetupVpnAdditionalGatewaysEntryGateway19 DisplayString,
            lcsSetupVpnAdditionalGatewaysEntryRtgTag19 Integer32,
            lcsSetupVpnAdditionalGatewaysEntryGateway20 DisplayString,
            lcsSetupVpnAdditionalGatewaysEntryRtgTag20 Integer32,
            lcsSetupVpnAdditionalGatewaysEntryGateway21 DisplayString,
            lcsSetupVpnAdditionalGatewaysEntryRtgTag21 Integer32,
            lcsSetupVpnAdditionalGatewaysEntryGateway22 DisplayString,
            lcsSetupVpnAdditionalGatewaysEntryRtgTag22 Integer32,
            lcsSetupVpnAdditionalGatewaysEntryGateway23 DisplayString,
            lcsSetupVpnAdditionalGatewaysEntryRtgTag23 Integer32,
            lcsSetupVpnAdditionalGatewaysEntryGateway24 DisplayString,
            lcsSetupVpnAdditionalGatewaysEntryRtgTag24 Integer32,
            lcsSetupVpnAdditionalGatewaysEntryGateway25 DisplayString,
            lcsSetupVpnAdditionalGatewaysEntryRtgTag25 Integer32,
            lcsSetupVpnAdditionalGatewaysEntryGateway26 DisplayString,
            lcsSetupVpnAdditionalGatewaysEntryRtgTag26 Integer32,
            lcsSetupVpnAdditionalGatewaysEntryGateway27 DisplayString,
            lcsSetupVpnAdditionalGatewaysEntryRtgTag27 Integer32,
            lcsSetupVpnAdditionalGatewaysEntryGateway28 DisplayString,
            lcsSetupVpnAdditionalGatewaysEntryRtgTag28 Integer32,
            lcsSetupVpnAdditionalGatewaysEntryGateway29 DisplayString,
            lcsSetupVpnAdditionalGatewaysEntryRtgTag29 Integer32,
            lcsSetupVpnAdditionalGatewaysEntryGateway30 DisplayString,
            lcsSetupVpnAdditionalGatewaysEntryRtgTag30 Integer32,
            lcsSetupVpnAdditionalGatewaysEntryGateway31 DisplayString,
            lcsSetupVpnAdditionalGatewaysEntryRtgTag31 Integer32,
            lcsSetupVpnAdditionalGatewaysEntryGateway32 DisplayString,
            lcsSetupVpnAdditionalGatewaysEntryRtgTag32 Integer32,
            lcsSetupVpnAdditionalGatewaysEntryDefaultPrio Integer32
    }

-- {COLUMN} 1.3.6.1.4.1.2356.11.2.19.12.1.1
lcsSetupVpnAdditionalGatewaysEntryPeer OBJECT-TYPE
    SYNTAX     DisplayString (SIZE(0..16))
    MAX-ACCESS read-write
    STATUS     current
    DESCRIPTION
            ""
    ::= { lcsSetupVpnAdditionalGatewaysEntry 1 }

-- {COLUMN} 1.3.6.1.4.1.2356.11.2.19.12.1.2
lcsSetupVpnAdditionalGatewaysEntryGateway1 OBJECT-TYPE
    SYNTAX     DisplayString (SIZE(0..64))
    MAX-ACCESS read-write
    STATUS     current
    DESCRIPTION
            ""
    ::= { lcsSetupVpnAdditionalGatewaysEntry 2 }

-- {COLUMN} 1.3.6.1.4.1.2356.11.2.19.12.1.3
lcsSetupVpnAdditionalGatewaysEntryGateway2 OBJECT-TYPE
    SYNTAX     DisplayString (SIZE(0..64))
    MAX-ACCESS read-write
    STATUS     current
    DESCRIPTION
            ""
    ::= { lcsSetupVpnAdditionalGatewaysEntry 3 }

-- {COLUMN} 1.3.6.1.4.1.2356.11.2.19.12.1.4
lcsSetupVpnAdditionalGatewaysEntryGateway3 OBJECT-TYPE
    SYNTAX     DisplayString (SIZE(0..64))
    MAX-ACCESS read-write
    STATUS     current
    DESCRIPTION
            ""
    ::= { lcsSetupVpnAdditionalGatewaysEntry 4 }

-- {COLUMN} 1.3.6.1.4.1.2356.11.2.19.12.1.5
lcsSetupVpnAdditionalGatewaysEntryGateway4 OBJECT-TYPE
    SYNTAX     DisplayString (SIZE(0..64))
    MAX-ACCESS read-write
    STATUS     current
    DESCRIPTION
            ""
    ::= { lcsSetupVpnAdditionalGatewaysEntry 5 }

-- {COLUMN} 1.3.6.1.4.1.2356.11.2.19.12.1.6
lcsSetupVpnAdditionalGatewaysEntryGateway5 OBJECT-TYPE
    SYNTAX     DisplayString (SIZE(0..64))
    MAX-ACCESS read-write
    STATUS     current
    DESCRIPTION
            ""
    ::= { lcsSetupVpnAdditionalGatewaysEntry 6 }

-- {COLUMN} 1.3.6.1.4.1.2356.11.2.19.12.1.7
lcsSetupVpnAdditionalGatewaysEntryGateway6 OBJECT-TYPE
    SYNTAX     DisplayString (SIZE(0..64))
    MAX-ACCESS read-write
    STATUS     current
    DESCRIPTION
            ""
    ::= { lcsSetupVpnAdditionalGatewaysEntry 7 }

-- {COLUMN} 1.3.6.1.4.1.2356.11.2.19.12.1.8
lcsSetupVpnAdditionalGatewaysEntryGateway7 OBJECT-TYPE
    SYNTAX     DisplayString (SIZE(0..64))
    MAX-ACCESS read-write
    STATUS     current
    DESCRIPTION
            ""
    ::= { lcsSetupVpnAdditionalGatewaysEntry 8 }

-- {COLUMN} 1.3.6.1.4.1.2356.11.2.19.12.1.9
lcsSetupVpnAdditionalGatewaysEntryGateway8 OBJECT-TYPE
    SYNTAX     DisplayString (SIZE(0..64))
    MAX-ACCESS read-write
    STATUS     current
    DESCRIPTION
            ""
    ::= { lcsSetupVpnAdditionalGatewaysEntry 9 }

-- {COLUMN} 1.3.6.1.4.1.2356.11.2.19.12.1.10
lcsSetupVpnAdditionalGatewaysEntryBeginWith OBJECT-TYPE
    SYNTAX     INTEGER {
                  eLastUsed (0),
                  eFirst (1),
                  eRandom (2)
            }
    MAX-ACCESS read-write
    STATUS     current
    DESCRIPTION
            ""
    ::= { lcsSetupVpnAdditionalGatewaysEntry 10 }

-- {COLUMN} 1.3.6.1.4.1.2356.11.2.19.12.1.11
lcsSetupVpnAdditionalGatewaysEntryRtgTag1 OBJECT-TYPE
    SYNTAX     Integer32 (0..65535)
    MAX-ACCESS read-write
    STATUS     current
    DESCRIPTION
            ""
    ::= { lcsSetupVpnAdditionalGatewaysEntry 11 }

-- {COLUMN} 1.3.6.1.4.1.2356.11.2.19.12.1.12
lcsSetupVpnAdditionalGatewaysEntryRtgTag2 OBJECT-TYPE
    SYNTAX     Integer32 (0..65535)
    MAX-ACCESS read-write
    STATUS     current
    DESCRIPTION
            ""
    ::= { lcsSetupVpnAdditionalGatewaysEntry 12 }

-- {COLUMN} 1.3.6.1.4.1.2356.11.2.19.12.1.13
lcsSetupVpnAdditionalGatewaysEntryRtgTag3 OBJECT-TYPE
    SYNTAX     Integer32 (0..65535)
    MAX-ACCESS read-write
    STATUS     current
    DESCRIPTION
            ""
    ::= { lcsSetupVpnAdditionalGatewaysEntry 13 }

-- {COLUMN} 1.3.6.1.4.1.2356.11.2.19.12.1.14
lcsSetupVpnAdditionalGatewaysEntryRtgTag4 OBJECT-TYPE
    SYNTAX     Integer32 (0..65535)
    MAX-ACCESS read-write
    STATUS     current
    DESCRIPTION
            ""
    ::= { lcsSetupVpnAdditionalGatewaysEntry 14 }

-- {COLUMN} 1.3.6.1.4.1.2356.11.2.19.12.1.15
lcsSetupVpnAdditionalGatewaysEntryRtgTag5 OBJECT-TYPE
    SYNTAX     Integer32 (0..65535)
    MAX-ACCESS read-write
    STATUS     current
    DESCRIPTION
            ""
    ::= { lcsSetupVpnAdditionalGatewaysEntry 15 }

-- {COLUMN} 1.3.6.1.4.1.2356.11.2.19.12.1.16
lcsSetupVpnAdditionalGatewaysEntryRtgTag6 OBJECT-TYPE
    SYNTAX     Integer32 (0..65535)
    MAX-ACCESS read-write
    STATUS     current
    DESCRIPTION
            ""
    ::= { lcsSetupVpnAdditionalGatewaysEntry 16 }

-- {COLUMN} 1.3.6.1.4.1.2356.11.2.19.12.1.17
lcsSetupVpnAdditionalGatewaysEntryRtgTag7 OBJECT-TYPE
    SYNTAX     Integer32 (0..65535)
    MAX-ACCESS read-write
    STATUS     current
    DESCRIPTION
            ""
    ::= { lcsSetupVpnAdditionalGatewaysEntry 17 }

-- {COLUMN} 1.3.6.1.4.1.2356.11.2.19.12.1.18
lcsSetupVpnAdditionalGatewaysEntryRtgTag8 OBJECT-TYPE
    SYNTAX     Integer32 (0..65535)
    MAX-ACCESS read-write
    STATUS     current
    DESCRIPTION
            ""
    ::= { lcsSetupVpnAdditionalGatewaysEntry 18 }

-- {COLUMN} 1.3.6.1.4.1.2356.11.2.19.12.1.19
lcsSetupVpnAdditionalGatewaysEntryGateway9 OBJECT-TYPE
    SYNTAX     DisplayString (SIZE(0..64))
    MAX-ACCESS read-write
    STATUS     current
    DESCRIPTION
            ""
    ::= { lcsSetupVpnAdditionalGatewaysEntry 19 }

-- {COLUMN} 1.3.6.1.4.1.2356.11.2.19.12.1.20
lcsSetupVpnAdditionalGatewaysEntryGateway10 OBJECT-TYPE
    SYNTAX     DisplayString (SIZE(0..64))
    MAX-ACCESS read-write
    STATUS     current
    DESCRIPTION
            ""
    ::= { lcsSetupVpnAdditionalGatewaysEntry 20 }

-- {COLUMN} 1.3.6.1.4.1.2356.11.2.19.12.1.21
lcsSetupVpnAdditionalGatewaysEntryGateway11 OBJECT-TYPE
    SYNTAX     DisplayString (SIZE(0..64))
    MAX-ACCESS read-write
    STATUS     current
    DESCRIPTION
            ""
    ::= { lcsSetupVpnAdditionalGatewaysEntry 21 }

-- {COLUMN} 1.3.6.1.4.1.2356.11.2.19.12.1.22
lcsSetupVpnAdditionalGatewaysEntryGateway12 OBJECT-TYPE
    SYNTAX     DisplayString (SIZE(0..64))
    MAX-ACCESS read-write
    STATUS     current
    DESCRIPTION
            ""
    ::= { lcsSetupVpnAdditionalGatewaysEntry 22 }

-- {COLUMN} 1.3.6.1.4.1.2356.11.2.19.12.1.23
lcsSetupVpnAdditionalGatewaysEntryGateway13 OBJECT-TYPE
    SYNTAX     DisplayString (SIZE(0..64))
    MAX-ACCESS read-write
    STATUS     current
    DESCRIPTION
            ""
    ::= { lcsSetupVpnAdditionalGatewaysEntry 23 }

-- {COLUMN} 1.3.6.1.4.1.2356.11.2.19.12.1.24
lcsSetupVpnAdditionalGatewaysEntryGateway14 OBJECT-TYPE
    SYNTAX     DisplayString (SIZE(0..64))
    MAX-ACCESS read-write
    STATUS     current
    DESCRIPTION
            ""
    ::= { lcsSetupVpnAdditionalGatewaysEntry 24 }

-- {COLUMN} 1.3.6.1.4.1.2356.11.2.19.12.1.25
lcsSetupVpnAdditionalGatewaysEntryGateway15 OBJECT-TYPE
    SYNTAX     DisplayString (SIZE(0..64))
    MAX-ACCESS read-write
    STATUS     current
    DESCRIPTION
            ""
    ::= { lcsSetupVpnAdditionalGatewaysEntry 25 }

-- {COLUMN} 1.3.6.1.4.1.2356.11.2.19.12.1.26
lcsSetupVpnAdditionalGatewaysEntryGateway16 OBJECT-TYPE
    SYNTAX     DisplayString (SIZE(0..64))
    MAX-ACCESS read-write
    STATUS     current
    DESCRIPTION
            ""
    ::= { lcsSetupVpnAdditionalGatewaysEntry 26 }

-- {COLUMN} 1.3.6.1.4.1.2356.11.2.19.12.1.27
lcsSetupVpnAdditionalGatewaysEntryRtgTag9 OBJECT-TYPE
    SYNTAX     Integer32 (0..65535)
    MAX-ACCESS read-write
    STATUS     current
    DESCRIPTION
            ""
    ::= { lcsSetupVpnAdditionalGatewaysEntry 27 }

-- {COLUMN} 1.3.6.1.4.1.2356.11.2.19.12.1.28
lcsSetupVpnAdditionalGatewaysEntryRtgTag10 OBJECT-TYPE
    SYNTAX     Integer32 (0..65535)
    MAX-ACCESS read-write
    STATUS     current
    DESCRIPTION
            ""
    ::= { lcsSetupVpnAdditionalGatewaysEntry 28 }

-- {COLUMN} 1.3.6.1.4.1.2356.11.2.19.12.1.29
lcsSetupVpnAdditionalGatewaysEntryRtgTag11 OBJECT-TYPE
    SYNTAX     Integer32 (0..65535)
    MAX-ACCESS read-write
    STATUS     current
    DESCRIPTION
            ""
    ::= { lcsSetupVpnAdditionalGatewaysEntry 29 }

-- {COLUMN} 1.3.6.1.4.1.2356.11.2.19.12.1.30
lcsSetupVpnAdditionalGatewaysEntryRtgTag12 OBJECT-TYPE
    SYNTAX     Integer32 (0..65535)
    MAX-ACCESS read-write
    STATUS     current
    DESCRIPTION
            ""
    ::= { lcsSetupVpnAdditionalGatewaysEntry 30 }

-- {COLUMN} 1.3.6.1.4.1.2356.11.2.19.12.1.31
lcsSetupVpnAdditionalGatewaysEntryRtgTag13 OBJECT-TYPE
    SYNTAX     Integer32 (0..65535)
    MAX-ACCESS read-write
    STATUS     current
    DESCRIPTION
            ""
    ::= { lcsSetupVpnAdditionalGatewaysEntry 31 }

-- {COLUMN} 1.3.6.1.4.1.2356.11.2.19.12.1.32
lcsSetupVpnAdditionalGatewaysEntryRtgTag14 OBJECT-TYPE
    SYNTAX     Integer32 (0..65535)
    MAX-ACCESS read-write
    STATUS     current
    DESCRIPTION
            ""
    ::= { lcsSetupVpnAdditionalGatewaysEntry 32 }

-- {COLUMN} 1.3.6.1.4.1.2356.11.2.19.12.1.33
lcsSetupVpnAdditionalGatewaysEntryRtgTag15 OBJECT-TYPE
    SYNTAX     Integer32 (0..65535)
    MAX-ACCESS read-write
    STATUS     current
    DESCRIPTION
            ""
    ::= { lcsSetupVpnAdditionalGatewaysEntry 33 }

-- {COLUMN} 1.3.6.1.4.1.2356.11.2.19.12.1.34
lcsSetupVpnAdditionalGatewaysEntryRtgTag16 OBJECT-TYPE
    SYNTAX     Integer32 (0..65535)
    MAX-ACCESS read-write
    STATUS     current
    DESCRIPTION
            ""
    ::= { lcsSetupVpnAdditionalGatewaysEntry 34 }

-- {COLUMN} 1.3.6.1.4.1.2356.11.2.19.12.1.35
lcsSetupVpnAdditionalGatewaysEntryGateway17 OBJECT-TYPE
    SYNTAX     DisplayString (SIZE(0..64))
    MAX-ACCESS read-write
    STATUS     current
    DESCRIPTION
            ""
    ::= { lcsSetupVpnAdditionalGatewaysEntry 35 }

-- {COLUMN} 1.3.6.1.4.1.2356.11.2.19.12.1.36
lcsSetupVpnAdditionalGatewaysEntryRtgTag17 OBJECT-TYPE
    SYNTAX     Integer32 (0..65535)
    MAX-ACCESS read-write
    STATUS     current
    DESCRIPTION
            ""
    ::= { lcsSetupVpnAdditionalGatewaysEntry 36 }

-- {COLUMN} 1.3.6.1.4.1.2356.11.2.19.12.1.37
lcsSetupVpnAdditionalGatewaysEntryGateway18 OBJECT-TYPE
    SYNTAX     DisplayString (SIZE(0..64))
    MAX-ACCESS read-write
    STATUS     current
    DESCRIPTION
            ""
    ::= { lcsSetupVpnAdditionalGatewaysEntry 37 }

-- {COLUMN} 1.3.6.1.4.1.2356.11.2.19.12.1.38
lcsSetupVpnAdditionalGatewaysEntryRtgTag18 OBJECT-TYPE
    SYNTAX     Integer32 (0..65535)
    MAX-ACCESS read-write
    STATUS     current
    DESCRIPTION
            ""
    ::= { lcsSetupVpnAdditionalGatewaysEntry 38 }

-- {COLUMN} 1.3.6.1.4.1.2356.11.2.19.12.1.39
lcsSetupVpnAdditionalGatewaysEntryGateway19 OBJECT-TYPE
    SYNTAX     DisplayString (SIZE(0..64))
    MAX-ACCESS read-write
    STATUS     current
    DESCRIPTION
            ""
    ::= { lcsSetupVpnAdditionalGatewaysEntry 39 }

-- {COLUMN} 1.3.6.1.4.1.2356.11.2.19.12.1.40
lcsSetupVpnAdditionalGatewaysEntryRtgTag19 OBJECT-TYPE
    SYNTAX     Integer32 (0..65535)
    MAX-ACCESS read-write
    STATUS     current
    DESCRIPTION
            ""
    ::= { lcsSetupVpnAdditionalGatewaysEntry 40 }

-- {COLUMN} 1.3.6.1.4.1.2356.11.2.19.12.1.41
lcsSetupVpnAdditionalGatewaysEntryGateway20 OBJECT-TYPE
    SYNTAX     DisplayString (SIZE(0..64))
    MAX-ACCESS read-write
    STATUS     current
    DESCRIPTION
            ""
    ::= { lcsSetupVpnAdditionalGatewaysEntry 41 }

-- {COLUMN} 1.3.6.1.4.1.2356.11.2.19.12.1.42
lcsSetupVpnAdditionalGatewaysEntryRtgTag20 OBJECT-TYPE
    SYNTAX     Integer32 (0..65535)
    MAX-ACCESS read-write
    STATUS     current
    DESCRIPTION
            ""
    ::= { lcsSetupVpnAdditionalGatewaysEntry 42 }

-- {COLUMN} 1.3.6.1.4.1.2356.11.2.19.12.1.43
lcsSetupVpnAdditionalGatewaysEntryGateway21 OBJECT-TYPE
    SYNTAX     DisplayString (SIZE(0..64))
    MAX-ACCESS read-write
    STATUS     current
    DESCRIPTION
            ""
    ::= { lcsSetupVpnAdditionalGatewaysEntry 43 }

-- {COLUMN} 1.3.6.1.4.1.2356.11.2.19.12.1.44
lcsSetupVpnAdditionalGatewaysEntryRtgTag21 OBJECT-TYPE
    SYNTAX     Integer32 (0..65535)
    MAX-ACCESS read-write
    STATUS     current
    DESCRIPTION
            ""
    ::= { lcsSetupVpnAdditionalGatewaysEntry 44 }

-- {COLUMN} 1.3.6.1.4.1.2356.11.2.19.12.1.45
lcsSetupVpnAdditionalGatewaysEntryGateway22 OBJECT-TYPE
    SYNTAX     DisplayString (SIZE(0..64))
    MAX-ACCESS read-write
    STATUS     current
    DESCRIPTION
            ""
    ::= { lcsSetupVpnAdditionalGatewaysEntry 45 }

-- {COLUMN} 1.3.6.1.4.1.2356.11.2.19.12.1.46
lcsSetupVpnAdditionalGatewaysEntryRtgTag22 OBJECT-TYPE
    SYNTAX     Integer32 (0..65535)
    MAX-ACCESS read-write
    STATUS     current
    DESCRIPTION
            ""
    ::= { lcsSetupVpnAdditionalGatewaysEntry 46 }

-- {COLUMN} 1.3.6.1.4.1.2356.11.2.19.12.1.47
lcsSetupVpnAdditionalGatewaysEntryGateway23 OBJECT-TYPE
    SYNTAX     DisplayString (SIZE(0..64))
    MAX-ACCESS read-write
    STATUS     current
    DESCRIPTION
            ""
    ::= { lcsSetupVpnAdditionalGatewaysEntry 47 }

-- {COLUMN} 1.3.6.1.4.1.2356.11.2.19.12.1.48
lcsSetupVpnAdditionalGatewaysEntryRtgTag23 OBJECT-TYPE
    SYNTAX     Integer32 (0..65535)
    MAX-ACCESS read-write
    STATUS     current
    DESCRIPTION
            ""
    ::= { lcsSetupVpnAdditionalGatewaysEntry 48 }

-- {COLUMN} 1.3.6.1.4.1.2356.11.2.19.12.1.49
lcsSetupVpnAdditionalGatewaysEntryGateway24 OBJECT-TYPE
    SYNTAX     DisplayString (SIZE(0..64))
    MAX-ACCESS read-write
    STATUS     current
    DESCRIPTION
            ""
    ::= { lcsSetupVpnAdditionalGatewaysEntry 49 }

-- {COLUMN} 1.3.6.1.4.1.2356.11.2.19.12.1.50
lcsSetupVpnAdditionalGatewaysEntryRtgTag24 OBJECT-TYPE
    SYNTAX     Integer32 (0..65535)
    MAX-ACCESS read-write
    STATUS     current
    DESCRIPTION
            ""
    ::= { lcsSetupVpnAdditionalGatewaysEntry 50 }

-- {COLUMN} 1.3.6.1.4.1.2356.11.2.19.12.1.51
lcsSetupVpnAdditionalGatewaysEntryGateway25 OBJECT-TYPE
    SYNTAX     DisplayString (SIZE(0..64))
    MAX-ACCESS read-write
    STATUS     current
    DESCRIPTION
            ""
    ::= { lcsSetupVpnAdditionalGatewaysEntry 51 }

-- {COLUMN} 1.3.6.1.4.1.2356.11.2.19.12.1.52
lcsSetupVpnAdditionalGatewaysEntryRtgTag25 OBJECT-TYPE
    SYNTAX     Integer32 (0..65535)
    MAX-ACCESS read-write
    STATUS     current
    DESCRIPTION
            ""
    ::= { lcsSetupVpnAdditionalGatewaysEntry 52 }

-- {COLUMN} 1.3.6.1.4.1.2356.11.2.19.12.1.53
lcsSetupVpnAdditionalGatewaysEntryGateway26 OBJECT-TYPE
    SYNTAX     DisplayString (SIZE(0..64))
    MAX-ACCESS read-write
    STATUS     current
    DESCRIPTION
            ""
    ::= { lcsSetupVpnAdditionalGatewaysEntry 53 }

-- {COLUMN} 1.3.6.1.4.1.2356.11.2.19.12.1.54
lcsSetupVpnAdditionalGatewaysEntryRtgTag26 OBJECT-TYPE
    SYNTAX     Integer32 (0..65535)
    MAX-ACCESS read-write
    STATUS     current
    DESCRIPTION
            ""
    ::= { lcsSetupVpnAdditionalGatewaysEntry 54 }

-- {COLUMN} 1.3.6.1.4.1.2356.11.2.19.12.1.55
lcsSetupVpnAdditionalGatewaysEntryGateway27 OBJECT-TYPE
    SYNTAX     DisplayString (SIZE(0..64))
    MAX-ACCESS read-write
    STATUS     current
    DESCRIPTION
            ""
    ::= { lcsSetupVpnAdditionalGatewaysEntry 55 }

-- {COLUMN} 1.3.6.1.4.1.2356.11.2.19.12.1.56
lcsSetupVpnAdditionalGatewaysEntryRtgTag27 OBJECT-TYPE
    SYNTAX     Integer32 (0..65535)
    MAX-ACCESS read-write
    STATUS     current
    DESCRIPTION
            ""
    ::= { lcsSetupVpnAdditionalGatewaysEntry 56 }

-- {COLUMN} 1.3.6.1.4.1.2356.11.2.19.12.1.57
lcsSetupVpnAdditionalGatewaysEntryGateway28 OBJECT-TYPE
    SYNTAX     DisplayString (SIZE(0..64))
    MAX-ACCESS read-write
    STATUS     current
    DESCRIPTION
            ""
    ::= { lcsSetupVpnAdditionalGatewaysEntry 57 }

-- {COLUMN} 1.3.6.1.4.1.2356.11.2.19.12.1.58
lcsSetupVpnAdditionalGatewaysEntryRtgTag28 OBJECT-TYPE
    SYNTAX     Integer32 (0..65535)
    MAX-ACCESS read-write
    STATUS     current
    DESCRIPTION
            ""
    ::= { lcsSetupVpnAdditionalGatewaysEntry 58 }

-- {COLUMN} 1.3.6.1.4.1.2356.11.2.19.12.1.59
lcsSetupVpnAdditionalGatewaysEntryGateway29 OBJECT-TYPE
    SYNTAX     DisplayString (SIZE(0..64))
    MAX-ACCESS read-write
    STATUS     current
    DESCRIPTION
            ""
    ::= { lcsSetupVpnAdditionalGatewaysEntry 59 }

-- {COLUMN} 1.3.6.1.4.1.2356.11.2.19.12.1.60
lcsSetupVpnAdditionalGatewaysEntryRtgTag29 OBJECT-TYPE
    SYNTAX     Integer32 (0..65535)
    MAX-ACCESS read-write
    STATUS     current
    DESCRIPTION
            ""
    ::= { lcsSetupVpnAdditionalGatewaysEntry 60 }

-- {COLUMN} 1.3.6.1.4.1.2356.11.2.19.12.1.61
lcsSetupVpnAdditionalGatewaysEntryGateway30 OBJECT-TYPE
    SYNTAX     DisplayString (SIZE(0..64))
    MAX-ACCESS read-write
    STATUS     current
    DESCRIPTION
            ""
    ::= { lcsSetupVpnAdditionalGatewaysEntry 61 }

-- {COLUMN} 1.3.6.1.4.1.2356.11.2.19.12.1.62
lcsSetupVpnAdditionalGatewaysEntryRtgTag30 OBJECT-TYPE
    SYNTAX     Integer32 (0..65535)
    MAX-ACCESS read-write
    STATUS     current
    DESCRIPTION
            ""
    ::= { lcsSetupVpnAdditionalGatewaysEntry 62 }

-- {COLUMN} 1.3.6.1.4.1.2356.11.2.19.12.1.63
lcsSetupVpnAdditionalGatewaysEntryGateway31 OBJECT-TYPE
    SYNTAX     DisplayString (SIZE(0..64))
    MAX-ACCESS read-write
    STATUS     current
    DESCRIPTION
            ""
    ::= { lcsSetupVpnAdditionalGatewaysEntry 63 }

-- {COLUMN} 1.3.6.1.4.1.2356.11.2.19.12.1.64
lcsSetupVpnAdditionalGatewaysEntryRtgTag31 OBJECT-TYPE
    SYNTAX     Integer32 (0..65535)
    MAX-ACCESS read-write
    STATUS     current
    DESCRIPTION
            ""
    ::= { lcsSetupVpnAdditionalGatewaysEntry 64 }

-- {COLUMN} 1.3.6.1.4.1.2356.11.2.19.12.1.65
lcsSetupVpnAdditionalGatewaysEntryGateway32 OBJECT-TYPE
    SYNTAX     DisplayString (SIZE(0..64))
    MAX-ACCESS read-write
    STATUS     current
    DESCRIPTION
            ""
    ::= { lcsSetupVpnAdditionalGatewaysEntry 65 }

-- {COLUMN} 1.3.6.1.4.1.2356.11.2.19.12.1.66
lcsSetupVpnAdditionalGatewaysEntryRtgTag32 OBJECT-TYPE
    SYNTAX     Integer32 (0..65535)
    MAX-ACCESS read-write
    STATUS     current
    DESCRIPTION
            ""
    ::= { lcsSetupVpnAdditionalGatewaysEntry 66 }

-- {COLUMN} 1.3.6.1.4.1.2356.11.2.19.12.1.67
lcsSetupVpnAdditionalGatewaysEntryDefaultPrio OBJECT-TYPE
    SYNTAX     Integer32 (0..65535)
    MAX-ACCESS read-write
    STATUS     current
    DESCRIPTION
            "-- empty --"
    ::= { lcsSetupVpnAdditionalGatewaysEntry 67 }

-- {SCALAR} 1.3.6.1.4.1.2356.11.2.19.13
lcsSetupVpnMainmodeProposalListDefault OBJECT-TYPE
    SYNTAX     DisplayString (SIZE(0..17))
    MAX-ACCESS read-write
    STATUS     current
    DESCRIPTION
            ""
    ::= { lcsSetupVpn 13 }

-- {SCALAR} 1.3.6.1.4.1.2356.11.2.19.14
lcsSetupVpnMainmodeIkeGroupDefault OBJECT-TYPE
    SYNTAX     INTEGER {
                  e1 (1),
                  e2 (2),
                  e5 (5),
                  e14 (14),
                  e15 (15),
                  e16 (16)
            }
    MAX-ACCESS read-write
    STATUS     current
    DESCRIPTION
            ""
    ::= { lcsSetupVpn 14 }

-- {SCALAR} 1.3.6.1.4.1.2356.11.2.19.15
lcsSetupVpnLegacyDynVpnLcos50xSupport OBJECT-TYPE
    SYNTAX     INTEGER {
                  eNo (0),
                  eYes (1)
            }
    MAX-ACCESS read-write
    STATUS     current
    DESCRIPTION
            ""
    ::= { lcsSetupVpn 15 }

-- {SCALAR} 1.3.6.1.4.1.2356.11.2.19.16
lcsSetupVpnNatTOperating OBJECT-TYPE
    SYNTAX     INTEGER {
                  eNo (0),
                  eYes (1)
            }
    MAX-ACCESS read-write
    STATUS     current
    DESCRIPTION
            ""
    ::= { lcsSetupVpn 16 }

-- {SCALAR} 1.3.6.1.4.1.2356.11.2.19.17
lcsSetupVpnSimpleCertRasOperating OBJECT-TYPE
    SYNTAX     INTEGER {
                  eNo (0),
                  eYes (1)
            }
    MAX-ACCESS read-write
    STATUS     current
    DESCRIPTION
            ""
    ::= { lcsSetupVpn 17 }

-- {SCALAR} 1.3.6.1.4.1.2356.11.2.19.19
lcsSetupVpnQuickmodeProposalListDefault OBJECT-TYPE
    SYNTAX     DisplayString (SIZE(0..17))
    MAX-ACCESS read-write
    STATUS     current
    DESCRIPTION
            ""
    ::= { lcsSetupVpn 19 }

-- {SCALAR} 1.3.6.1.4.1.2356.11.2.19.20
lcsSetupVpnQuickmodePfsGroupDefault OBJECT-TYPE
    SYNTAX     INTEGER {
                  e0 (0),
                  e1 (1),
                  e2 (2),
                  e5 (5),
                  e14 (14),
                  e15 (15),
                  e16 (16)
            }
    MAX-ACCESS read-write
    STATUS     current
    DESCRIPTION
            ""
    ::= { lcsSetupVpn 20 }

-- {SCALAR} 1.3.6.1.4.1.2356.11.2.19.21
lcsSetupVpnQuickmodeShortholdTimeDefault OBJECT-TYPE
    SYNTAX     Integer32 (0..65535)
    MAX-ACCESS read-write
    STATUS     current
    DESCRIPTION
            ""
    ::= { lcsSetupVpn 21 }

-- {SCALAR} 1.3.6.1.4.1.2356.11.2.19.22
lcsSetupVpnAllowRemoteNetworkSelection OBJECT-TYPE
    SYNTAX     INTEGER {
                  eNo (0),
                  eYes (1)
            }
    MAX-ACCESS read-write
    STATUS     current
    DESCRIPTION
            ""
    ::= { lcsSetupVpn 22 }

-- {SCALAR} 1.3.6.1.4.1.2356.11.2.19.23
lcsSetupVpnEstablishSasCollectively OBJECT-TYPE
    SYNTAX     INTEGER {
                  eNo (0),
                  eYes (1),
                  eOnlyWithKeepalive (2)
            }
    MAX-ACCESS read-write
    STATUS     current
    DESCRIPTION
            ""
    ::= { lcsSetupVpn 23 }

-- {SCALAR} 1.3.6.1.4.1.2356.11.2.19.24
lcsSetupVpnMaxConcurrentConnections OBJECT-TYPE
    SYNTAX     Integer32 (0..2147483647)
    MAX-ACCESS read-write
    STATUS     current
    DESCRIPTION
            ""
    ::= { lcsSetupVpn 24 }

-- {SCALAR} 1.3.6.1.4.1.2356.11.2.19.25
lcsSetupVpnFlexibleIdComparison OBJECT-TYPE
    SYNTAX     INTEGER {
                  eNo (0),
                  eYes (1)
            }
    MAX-ACCESS read-write
    STATUS     current
    DESCRIPTION
            ""
    ::= { lcsSetupVpn 25 }

-- {SCALAR} 1.3.6.1.4.1.2356.11.2.19.26
lcsSetupVpnNatTPortForRekeying OBJECT-TYPE
    SYNTAX     INTEGER {
                  eNo (0),
                  eYes (1)
            }
    MAX-ACCESS read-write
    STATUS     current
    DESCRIPTION
            ""
    ::= { lcsSetupVpn 26 }

-- {SCALAR} 1.3.6.1.4.1.2356.11.2.19.27
lcsSetupVpnSslEncapsAllowed OBJECT-TYPE
    SYNTAX     INTEGER {
                  eNo (0),
                  eYes (1)
            }
    MAX-ACCESS read-write
    STATUS     current
    DESCRIPTION
            ""
    ::= { lcsSetupVpn 27 }

-- {NODE} 1.3.6.1.4.1.2356.11.2.19.28
lcsSetupVpnMyvpn OBJECT IDENTIFIER ::= { lcsSetupVpn 28 }

-- {SCALAR} 1.3.6.1.4.1.2356.11.2.19.28.1
lcsSetupVpnMyvpnOperating OBJECT-TYPE
    SYNTAX     INTEGER {
                  eNo (0),
                  eYes (1)
            }
    MAX-ACCESS read-write
    STATUS     current
    DESCRIPTION
            "-- empty --"
    ::= { lcsSetupVpnMyvpn 1 }

-- {SCALAR} 1.3.6.1.4.1.2356.11.2.19.28.2
lcsSetupVpnMyvpnPinLength OBJECT-TYPE
    SYNTAX     Integer32 (0..255)
    MAX-ACCESS read-write
    STATUS     current
    DESCRIPTION
            "-- empty --"
    ::= { lcsSetupVpnMyvpn 2 }

-- {SCALAR} 1.3.6.1.4.1.2356.11.2.19.28.3
lcsSetupVpnMyvpnDeviceHostname OBJECT-TYPE
    SYNTAX     DisplayString (SIZE(0..31))
    MAX-ACCESS read-write
    STATUS     current
    DESCRIPTION
            "-- empty --"
    ::= { lcsSetupVpnMyvpn 3 }

-- {TABLE} 1.3.6.1.4.1.2356.11.2.19.28.4
lcsSetupVpnMyvpnMappingTable OBJECT-TYPE
    SYNTAX     SEQUENCE OF LcsSetupVpnMyvpnMappingEntry
    MAX-ACCESS not-accessible
    STATUS     current
    DESCRIPTION
            "-- empty --"
    ::= { lcsSetupVpnMyvpn 4 }

-- {ROW} 1.3.6.1.4.1.2356.11.2.19.28.4.1
lcsSetupVpnMyvpnMappingEntry OBJECT-TYPE
    SYNTAX     LcsSetupVpnMyvpnMappingEntry
    MAX-ACCESS not-accessible
    STATUS     current
    DESCRIPTION
            ""
    INDEX {
            lcsSetupVpnMyvpnMappingEntryPin
          }
    ::= { lcsSetupVpnMyvpnMappingTable 1 }

LcsSetupVpnMyvpnMappingEntry ::= SEQUENCE {
            lcsSetupVpnMyvpnMappingEntryPin DisplayString,
            lcsSetupVpnMyvpnMappingEntryVpnProfile DisplayString,
            lcsSetupVpnMyvpnMappingEntryActive INTEGER
    }

-- {COLUMN} 1.3.6.1.4.1.2356.11.2.19.28.4.1.1
lcsSetupVpnMyvpnMappingEntryPin OBJECT-TYPE
    SYNTAX     DisplayString (SIZE(0..12))
    MAX-ACCESS read-write
    STATUS     current
    DESCRIPTION
            "-- empty --"
    ::= { lcsSetupVpnMyvpnMappingEntry 1 }

-- {COLUMN} 1.3.6.1.4.1.2356.11.2.19.28.4.1.2
lcsSetupVpnMyvpnMappingEntryVpnProfile OBJECT-TYPE
    SYNTAX     DisplayString (SIZE(0..16))
    MAX-ACCESS read-write
    STATUS     current
    DESCRIPTION
            "-- empty --"
    ::= { lcsSetupVpnMyvpnMappingEntry 2 }

-- {COLUMN} 1.3.6.1.4.1.2356.11.2.19.28.4.1.3
lcsSetupVpnMyvpnMappingEntryActive OBJECT-TYPE
    SYNTAX     INTEGER {
                  eNo (0),
                  eYes (1)
            }
    MAX-ACCESS read-write
    STATUS     current
    DESCRIPTION
            "-- empty --"
    ::= { lcsSetupVpnMyvpnMappingEntry 3 }

-- {SCALAR} 1.3.6.1.4.1.2356.11.2.19.28.5
lcsSetupVpnMyvpnReEnableLogin OBJECT-TYPE
    SYNTAX     DisplayString
    MAX-ACCESS read-write
    STATUS     current
    DESCRIPTION
            "-- empty --"
    ::= { lcsSetupVpnMyvpn 5 }

-- {SCALAR} 1.3.6.1.4.1.2356.11.2.19.28.6
lcsSetupVpnMyvpnEMailNotification OBJECT-TYPE
    SYNTAX     INTEGER {
                  eNo (0),
                  eYes (1)
            }
    MAX-ACCESS read-write
    STATUS     current
    DESCRIPTION
            "-- empty --"
    ::= { lcsSetupVpnMyvpn 6 }

-- {SCALAR} 1.3.6.1.4.1.2356.11.2.19.28.7
lcsSetupVpnMyvpnEMailAddress OBJECT-TYPE
    SYNTAX     DisplayString (SIZE(0..63))
    MAX-ACCESS read-write
    STATUS     current
    DESCRIPTION
            "-- empty --"
    ::= { lcsSetupVpnMyvpn 7 }

-- {SCALAR} 1.3.6.1.4.1.2356.11.2.19.28.8
lcsSetupVpnMyvpnSyslog OBJECT-TYPE
    SYNTAX     INTEGER {
                  eNo (0),
                  eYes (1)
            }
    MAX-ACCESS read-write
    STATUS     current
    DESCRIPTION
            "-- empty --"
    ::= { lcsSetupVpnMyvpn 8 }

-- {SCALAR} 1.3.6.1.4.1.2356.11.2.19.28.9
lcsSetupVpnMyvpnRemoteGateway OBJECT-TYPE
    SYNTAX     DisplayString (SIZE(0..63))
    MAX-ACCESS read-write
    STATUS     current
    DESCRIPTION
            "-- empty --"
    ::= { lcsSetupVpnMyvpn 9 }

-- {SCALAR} 1.3.6.1.4.1.2356.11.2.19.28.10
lcsSetupVpnMyvpnErrorCountForLoginBlock OBJECT-TYPE
    SYNTAX     Integer32 (0..2147483647)
    MAX-ACCESS read-write
    STATUS     current
    DESCRIPTION
            "-- empty --"
    ::= { lcsSetupVpnMyvpn 10 }

-- {SCALAR} 1.3.6.1.4.1.2356.11.2.19.28.11
lcsSetupVpnMyvpnAllowAccessFromWan OBJECT-TYPE
    SYNTAX     INTEGER {
                  eNo (0),
                  eYes (1)
            }
    MAX-ACCESS read-write
    STATUS     current
    DESCRIPTION
            "-- empty --"
    ::= { lcsSetupVpnMyvpn 11 }

-- {SCALAR} 1.3.6.1.4.1.2356.11.2.19.30
lcsSetupVpnAntiReplayWindowSize OBJECT-TYPE
    SYNTAX     Integer32 (0..65535)
    MAX-ACCESS read-write
    STATUS     current
    DESCRIPTION
            "-- empty --"
    ::= { lcsSetupVpn 30 }

-- {SCALAR} 1.3.6.1.4.1.2356.11.2.19.31
lcsSetupVpnMainmodeIkeGroupDefaultNew OBJECT-TYPE
    SYNTAX     INTEGER {
                  e1 (1),
                  e2 (2),
                  e5 (5),
                  e14 (14)
            }
    MAX-ACCESS read-write
    STATUS     current
    DESCRIPTION
            ""
    ::= { lcsSetupVpn 31 }

-- {SCALAR} 1.3.6.1.4.1.2356.11.2.19.32
lcsSetupVpnAggrmodeIkeGroupDefaultNew OBJECT-TYPE
    SYNTAX     INTEGER {
                  e1 (1),
                  e2 (2),
                  e5 (5),
                  e14 (14)
            }
    MAX-ACCESS read-write
    STATUS     current
    DESCRIPTION
            ""
    ::= { lcsSetupVpn 32 }

-- {SCALAR} 1.3.6.1.4.1.2356.11.2.19.33
lcsSetupVpnQuickmodePfsGroupDefaultNew OBJECT-TYPE
    SYNTAX     INTEGER {
                  e0 (0),
                  e1 (1),
                  e2 (2),
                  e5 (5),
                  e14 (14)
            }
    MAX-ACCESS read-write
    STATUS     current
    DESCRIPTION
            ""
    ::= { lcsSetupVpn 33 }

-- {NODE} 1.3.6.1.4.1.2356.11.2.19.35
lcsSetupVpnNetworks OBJECT IDENTIFIER ::= { lcsSetupVpn 35 }

-- {TABLE} 1.3.6.1.4.1.2356.11.2.19.35.1
lcsSetupVpnNetworksIpv4RulesTable OBJECT-TYPE
    SYNTAX     SEQUENCE OF LcsSetupVpnNetworksIpv4RulesEntry
    MAX-ACCESS not-accessible
    STATUS     current
    DESCRIPTION
            "-- empty --"
    ::= { lcsSetupVpnNetworks 1 }

-- {ROW} 1.3.6.1.4.1.2356.11.2.19.35.1.1
lcsSetupVpnNetworksIpv4RulesEntry OBJECT-TYPE
    SYNTAX     LcsSetupVpnNetworksIpv4RulesEntry
    MAX-ACCESS not-accessible
    STATUS     current
    DESCRIPTION
            ""
    INDEX {
            lcsSetupVpnNetworksIpv4RulesEntryName
          }
    ::= { lcsSetupVpnNetworksIpv4RulesTable 1 }

LcsSetupVpnNetworksIpv4RulesEntry ::= SEQUENCE {
            lcsSetupVpnNetworksIpv4RulesEntryName DisplayString,
            lcsSetupVpnNetworksIpv4RulesEntryLocalNetworks DisplayString,
            lcsSetupVpnNetworksIpv4RulesEntryRemoteNetworks DisplayString
    }

-- {COLUMN} 1.3.6.1.4.1.2356.11.2.19.35.1.1.1
lcsSetupVpnNetworksIpv4RulesEntryName OBJECT-TYPE
    SYNTAX     DisplayString (SIZE(0..31))
    MAX-ACCESS read-write
    STATUS     current
    DESCRIPTION
            "-- empty --"
    ::= { lcsSetupVpnNetworksIpv4RulesEntry 1 }

-- {COLUMN} 1.3.6.1.4.1.2356.11.2.19.35.1.1.2
lcsSetupVpnNetworksIpv4RulesEntryLocalNetworks OBJECT-TYPE
    SYNTAX     DisplayString (SIZE(0..127))
    MAX-ACCESS read-write
    STATUS     current
    DESCRIPTION
            "-- empty --"
    ::= { lcsSetupVpnNetworksIpv4RulesEntry 2 }

-- {COLUMN} 1.3.6.1.4.1.2356.11.2.19.35.1.1.3
lcsSetupVpnNetworksIpv4RulesEntryRemoteNetworks OBJECT-TYPE
    SYNTAX     DisplayString (SIZE(0..127))
    MAX-ACCESS read-write
    STATUS     current
    DESCRIPTION
            "-- empty --"
    ::= { lcsSetupVpnNetworksIpv4RulesEntry 3 }

-- {TABLE} 1.3.6.1.4.1.2356.11.2.19.35.2
lcsSetupVpnNetworksIpv4RuleListsTable OBJECT-TYPE
    SYNTAX     SEQUENCE OF LcsSetupVpnNetworksIpv4RuleListsEntry
    MAX-ACCESS not-accessible
    STATUS     current
    DESCRIPTION
            "-- empty --"
    ::= { lcsSetupVpnNetworks 2 }

-- {ROW} 1.3.6.1.4.1.2356.11.2.19.35.2.1
lcsSetupVpnNetworksIpv4RuleListsEntry OBJECT-TYPE
    SYNTAX     LcsSetupVpnNetworksIpv4RuleListsEntry
    MAX-ACCESS not-accessible
    STATUS     current
    DESCRIPTION
            ""
    INDEX {
            lcsSetupVpnNetworksIpv4RuleListsEntryName
          }
    ::= { lcsSetupVpnNetworksIpv4RuleListsTable 1 }

LcsSetupVpnNetworksIpv4RuleListsEntry ::= SEQUENCE {
            lcsSetupVpnNetworksIpv4RuleListsEntryName DisplayString,
            lcsSetupVpnNetworksIpv4RuleListsEntryRules DisplayString
    }

-- {COLUMN} 1.3.6.1.4.1.2356.11.2.19.35.2.1.1
lcsSetupVpnNetworksIpv4RuleListsEntryName OBJECT-TYPE
    SYNTAX     DisplayString (SIZE(0..31))
    MAX-ACCESS read-write
    STATUS     current
    DESCRIPTION
            "-- empty --"
    ::= { lcsSetupVpnNetworksIpv4RuleListsEntry 1 }

-- {COLUMN} 1.3.6.1.4.1.2356.11.2.19.35.2.1.2
lcsSetupVpnNetworksIpv4RuleListsEntryRules OBJECT-TYPE
    SYNTAX     DisplayString (SIZE(0..127))
    MAX-ACCESS read-write
    STATUS     current
    DESCRIPTION
            "-- empty --"
    ::= { lcsSetupVpnNetworksIpv4RuleListsEntry 2 }

-- {TABLE} 1.3.6.1.4.1.2356.11.2.19.35.3
lcsSetupVpnNetworksIpv6RulesTable OBJECT-TYPE
    SYNTAX     SEQUENCE OF LcsSetupVpnNetworksIpv6RulesEntry
    MAX-ACCESS not-accessible
    STATUS     current
    DESCRIPTION
            "-- empty --"
    ::= { lcsSetupVpnNetworks 3 }

-- {ROW} 1.3.6.1.4.1.2356.11.2.19.35.3.1
lcsSetupVpnNetworksIpv6RulesEntry OBJECT-TYPE
    SYNTAX     LcsSetupVpnNetworksIpv6RulesEntry
    MAX-ACCESS not-accessible
    STATUS     current
    DESCRIPTION
            ""
    INDEX {
            lcsSetupVpnNetworksIpv6RulesEntryName
          }
    ::= { lcsSetupVpnNetworksIpv6RulesTable 1 }

LcsSetupVpnNetworksIpv6RulesEntry ::= SEQUENCE {
            lcsSetupVpnNetworksIpv6RulesEntryName DisplayString,
            lcsSetupVpnNetworksIpv6RulesEntryLocalNetworks DisplayString,
            lcsSetupVpnNetworksIpv6RulesEntryRemoteNetworks DisplayString
    }

-- {COLUMN} 1.3.6.1.4.1.2356.11.2.19.35.3.1.1
lcsSetupVpnNetworksIpv6RulesEntryName OBJECT-TYPE
    SYNTAX     DisplayString (SIZE(0..31))
    MAX-ACCESS read-write
    STATUS     current
    DESCRIPTION
            "-- empty --"
    ::= { lcsSetupVpnNetworksIpv6RulesEntry 1 }

-- {COLUMN} 1.3.6.1.4.1.2356.11.2.19.35.3.1.2
lcsSetupVpnNetworksIpv6RulesEntryLocalNetworks OBJECT-TYPE
    SYNTAX     DisplayString (SIZE(0..127))
    MAX-ACCESS read-write
    STATUS     current
    DESCRIPTION
            "-- empty --"
    ::= { lcsSetupVpnNetworksIpv6RulesEntry 2 }

-- {COLUMN} 1.3.6.1.4.1.2356.11.2.19.35.3.1.3
lcsSetupVpnNetworksIpv6RulesEntryRemoteNetworks OBJECT-TYPE
    SYNTAX     DisplayString (SIZE(0..127))
    MAX-ACCESS read-write
    STATUS     current
    DESCRIPTION
            "-- empty --"
    ::= { lcsSetupVpnNetworksIpv6RulesEntry 3 }

-- {TABLE} 1.3.6.1.4.1.2356.11.2.19.35.4
lcsSetupVpnNetworksIpv6RuleListsTable OBJECT-TYPE
    SYNTAX     SEQUENCE OF LcsSetupVpnNetworksIpv6RuleListsEntry
    MAX-ACCESS not-accessible
    STATUS     current
    DESCRIPTION
            "-- empty --"
    ::= { lcsSetupVpnNetworks 4 }

-- {ROW} 1.3.6.1.4.1.2356.11.2.19.35.4.1
lcsSetupVpnNetworksIpv6RuleListsEntry OBJECT-TYPE
    SYNTAX     LcsSetupVpnNetworksIpv6RuleListsEntry
    MAX-ACCESS not-accessible
    STATUS     current
    DESCRIPTION
            ""
    INDEX {
            lcsSetupVpnNetworksIpv6RuleListsEntryName
          }
    ::= { lcsSetupVpnNetworksIpv6RuleListsTable 1 }

LcsSetupVpnNetworksIpv6RuleListsEntry ::= SEQUENCE {
            lcsSetupVpnNetworksIpv6RuleListsEntryName DisplayString,
            lcsSetupVpnNetworksIpv6RuleListsEntryRules DisplayString
    }

-- {COLUMN} 1.3.6.1.4.1.2356.11.2.19.35.4.1.1
lcsSetupVpnNetworksIpv6RuleListsEntryName OBJECT-TYPE
    SYNTAX     DisplayString (SIZE(0..31))
    MAX-ACCESS read-write
    STATUS     current
    DESCRIPTION
            "-- empty --"
    ::= { lcsSetupVpnNetworksIpv6RuleListsEntry 1 }

-- {COLUMN} 1.3.6.1.4.1.2356.11.2.19.35.4.1.2
lcsSetupVpnNetworksIpv6RuleListsEntryRules OBJECT-TYPE
    SYNTAX     DisplayString (SIZE(0..127))
    MAX-ACCESS read-write
    STATUS     current
    DESCRIPTION
            "-- empty --"
    ::= { lcsSetupVpnNetworksIpv6RuleListsEntry 2 }

-- {NODE} 1.3.6.1.4.1.2356.11.2.19.36
lcsSetupVpnIkev2 OBJECT IDENTIFIER ::= { lcsSetupVpn 36 }

-- {TABLE} 1.3.6.1.4.1.2356.11.2.19.36.1
lcsSetupVpnIkev2PeersTable OBJECT-TYPE
    SYNTAX     SEQUENCE OF LcsSetupVpnIkev2PeersEntry
    MAX-ACCESS not-accessible
    STATUS     current
    DESCRIPTION
            "-- empty --"
    ::= { lcsSetupVpnIkev2 1 }

-- {ROW} 1.3.6.1.4.1.2356.11.2.19.36.1.1
lcsSetupVpnIkev2PeersEntry OBJECT-TYPE
    SYNTAX     LcsSetupVpnIkev2PeersEntry
    MAX-ACCESS not-accessible
    STATUS     current
    DESCRIPTION
            ""
    INDEX {
            lcsSetupVpnIkev2PeersEntryPeer
          }
    ::= { lcsSetupVpnIkev2PeersTable 1 }

LcsSetupVpnIkev2PeersEntry ::= SEQUENCE {
            lcsSetupVpnIkev2PeersEntryPeer DisplayString,
            lcsSetupVpnIkev2PeersEntryActive INTEGER,
            lcsSetupVpnIkev2PeersEntryShTime Integer32,
            lcsSetupVpnIkev2PeersEntryRemoteGateway DisplayString,
            lcsSetupVpnIkev2PeersEntryRtgTag Integer32,
            lcsSetupVpnIkev2PeersEntryEncryption DisplayString,
            lcsSetupVpnIkev2PeersEntryAuthentication DisplayString,
            lcsSetupVpnIkev2PeersEntryGeneral DisplayString,
            lcsSetupVpnIkev2PeersEntryLifetimes DisplayString,
            lcsSetupVpnIkev2PeersEntryIkeCfg INTEGER,
            lcsSetupVpnIkev2PeersEntryRuleCreation INTEGER,
            lcsSetupVpnIkev2PeersEntryIpv4Rules DisplayString,
            lcsSetupVpnIkev2PeersEntryIpv6Rules DisplayString,
            lcsSetupVpnIkev2PeersEntryRouting DisplayString,
            lcsSetupVpnIkev2PeersEntryRadiusAuthorization DisplayString,
            lcsSetupVpnIkev2PeersEntryRadiusAccounting DisplayString,
            lcsSetupVpnIkev2PeersEntryComment DisplayString,
            lcsSetupVpnIkev2PeersEntryIpv4CfgPool DisplayString,
            lcsSetupVpnIkev2PeersEntryIpv6CfgPool DisplayString,
            lcsSetupVpnIkev2PeersEntryIpv4 DisplayString,
            lcsSetupVpnIkev2PeersEntryIpv6 DisplayString,
            lcsSetupVpnIkev2PeersEntrySplitDnsProfile DisplayString,
            lcsSetupVpnIkev2PeersEntryHsvpn DisplayString,
            lcsSetupVpnIkev2PeersEntryCfgClientProfile DisplayString
    }

-- {COLUMN} 1.3.6.1.4.1.2356.11.2.19.36.1.1.1
lcsSetupVpnIkev2PeersEntryPeer OBJECT-TYPE
    SYNTAX     DisplayString (SIZE(0..16))
    MAX-ACCESS read-write
    STATUS     current
    DESCRIPTION
            "-- empty --"
    ::= { lcsSetupVpnIkev2PeersEntry 1 }

-- {COLUMN} 1.3.6.1.4.1.2356.11.2.19.36.1.1.2
lcsSetupVpnIkev2PeersEntryActive OBJECT-TYPE
    SYNTAX     INTEGER {
                  eNo (0),
                  eYes (1)
            }
    MAX-ACCESS read-write
    STATUS     current
    DESCRIPTION
            "-- empty --"
    ::= { lcsSetupVpnIkev2PeersEntry 2 }

-- {COLUMN} 1.3.6.1.4.1.2356.11.2.19.36.1.1.3
lcsSetupVpnIkev2PeersEntryShTime OBJECT-TYPE
    SYNTAX     Integer32 (0..2147483647)
    MAX-ACCESS read-write
    STATUS     current
    DESCRIPTION
            "-- empty --"
    ::= { lcsSetupVpnIkev2PeersEntry 3 }

-- {COLUMN} 1.3.6.1.4.1.2356.11.2.19.36.1.1.4
lcsSetupVpnIkev2PeersEntryRemoteGateway OBJECT-TYPE
    SYNTAX     DisplayString (SIZE(0..64))
    MAX-ACCESS read-write
    STATUS     current
    DESCRIPTION
            "-- empty --"
    ::= { lcsSetupVpnIkev2PeersEntry 4 }

-- {COLUMN} 1.3.6.1.4.1.2356.11.2.19.36.1.1.5
lcsSetupVpnIkev2PeersEntryRtgTag OBJECT-TYPE
    SYNTAX     Integer32 (0..65535)
    MAX-ACCESS read-write
    STATUS     current
    DESCRIPTION
            "-- empty --"
    ::= { lcsSetupVpnIkev2PeersEntry 5 }

-- {COLUMN} 1.3.6.1.4.1.2356.11.2.19.36.1.1.6
lcsSetupVpnIkev2PeersEntryEncryption OBJECT-TYPE
    SYNTAX     DisplayString (SIZE(0..16))
    MAX-ACCESS read-write
    STATUS     current
    DESCRIPTION
            "-- empty --"
    ::= { lcsSetupVpnIkev2PeersEntry 6 }

-- {COLUMN} 1.3.6.1.4.1.2356.11.2.19.36.1.1.7
lcsSetupVpnIkev2PeersEntryAuthentication OBJECT-TYPE
    SYNTAX     DisplayString (SIZE(0..16))
    MAX-ACCESS read-write
    STATUS     current
    DESCRIPTION
            "-- empty --"
    ::= { lcsSetupVpnIkev2PeersEntry 7 }

-- {COLUMN} 1.3.6.1.4.1.2356.11.2.19.36.1.1.8
lcsSetupVpnIkev2PeersEntryGeneral OBJECT-TYPE
    SYNTAX     DisplayString (SIZE(0..16))
    MAX-ACCESS read-write
    STATUS     current
    DESCRIPTION
            "-- empty --"
    ::= { lcsSetupVpnIkev2PeersEntry 8 }

-- {COLUMN} 1.3.6.1.4.1.2356.11.2.19.36.1.1.9
lcsSetupVpnIkev2PeersEntryLifetimes OBJECT-TYPE
    SYNTAX     DisplayString (SIZE(0..16))
    MAX-ACCESS read-write
    STATUS     current
    DESCRIPTION
            "-- empty --"
    ::= { lcsSetupVpnIkev2PeersEntry 9 }

-- {COLUMN} 1.3.6.1.4.1.2356.11.2.19.36.1.1.10
lcsSetupVpnIkev2PeersEntryIkeCfg OBJECT-TYPE
    SYNTAX     INTEGER {
                  eOff (0),
                  eClient (1),
                  eServer (2)
            }
    MAX-ACCESS read-write
    STATUS     current
    DESCRIPTION
            "-- empty --"
    ::= { lcsSetupVpnIkev2PeersEntry 10 }

-- {COLUMN} 1.3.6.1.4.1.2356.11.2.19.36.1.1.11
lcsSetupVpnIkev2PeersEntryRuleCreation OBJECT-TYPE
    SYNTAX     INTEGER {
                  eAuto (0),
                  eManually (1)
            }
    MAX-ACCESS read-write
    STATUS     current
    DESCRIPTION
            "-- empty --"
    ::= { lcsSetupVpnIkev2PeersEntry 11 }

-- {COLUMN} 1.3.6.1.4.1.2356.11.2.19.36.1.1.12
lcsSetupVpnIkev2PeersEntryIpv4Rules OBJECT-TYPE
    SYNTAX     DisplayString (SIZE(0..63))
    MAX-ACCESS read-write
    STATUS     current
    DESCRIPTION
            "-- empty --"
    ::= { lcsSetupVpnIkev2PeersEntry 12 }

-- {COLUMN} 1.3.6.1.4.1.2356.11.2.19.36.1.1.13
lcsSetupVpnIkev2PeersEntryIpv6Rules OBJECT-TYPE
    SYNTAX     DisplayString (SIZE(0..63))
    MAX-ACCESS read-write
    STATUS     current
    DESCRIPTION
            "-- empty --"
    ::= { lcsSetupVpnIkev2PeersEntry 13 }

-- {COLUMN} 1.3.6.1.4.1.2356.11.2.19.36.1.1.14
lcsSetupVpnIkev2PeersEntryRouting OBJECT-TYPE
    SYNTAX     DisplayString (SIZE(0..31))
    MAX-ACCESS read-write
    STATUS     current
    DESCRIPTION
            "-- empty --"
    ::= { lcsSetupVpnIkev2PeersEntry 14 }

-- {COLUMN} 1.3.6.1.4.1.2356.11.2.19.36.1.1.15
lcsSetupVpnIkev2PeersEntryRadiusAuthorization OBJECT-TYPE
    SYNTAX     DisplayString (SIZE(0..31))
    MAX-ACCESS read-write
    STATUS     current
    DESCRIPTION
            "-- empty --"
    ::= { lcsSetupVpnIkev2PeersEntry 15 }

-- {COLUMN} 1.3.6.1.4.1.2356.11.2.19.36.1.1.16
lcsSetupVpnIkev2PeersEntryRadiusAccounting OBJECT-TYPE
    SYNTAX     DisplayString (SIZE(0..31))
    MAX-ACCESS read-write
    STATUS     current
    DESCRIPTION
            "-- empty --"
    ::= { lcsSetupVpnIkev2PeersEntry 16 }

-- {COLUMN} 1.3.6.1.4.1.2356.11.2.19.36.1.1.17
lcsSetupVpnIkev2PeersEntryComment OBJECT-TYPE
    SYNTAX     DisplayString (SIZE(0..63))
    MAX-ACCESS read-write
    STATUS     current
    DESCRIPTION
            "-- empty --"
    ::= { lcsSetupVpnIkev2PeersEntry 17 }

-- {COLUMN} 1.3.6.1.4.1.2356.11.2.19.36.1.1.18
lcsSetupVpnIkev2PeersEntryIpv4CfgPool OBJECT-TYPE
    SYNTAX     DisplayString (SIZE(0..16))
    MAX-ACCESS read-write
    STATUS     current
    DESCRIPTION
            "-- empty --"
    ::= { lcsSetupVpnIkev2PeersEntry 18 }

-- {COLUMN} 1.3.6.1.4.1.2356.11.2.19.36.1.1.19
lcsSetupVpnIkev2PeersEntryIpv6CfgPool OBJECT-TYPE
    SYNTAX     DisplayString (SIZE(0..16))
    MAX-ACCESS read-write
    STATUS     current
    DESCRIPTION
            "-- empty --"
    ::= { lcsSetupVpnIkev2PeersEntry 19 }

-- {COLUMN} 1.3.6.1.4.1.2356.11.2.19.36.1.1.20
lcsSetupVpnIkev2PeersEntryIpv4 OBJECT-TYPE
    SYNTAX     DisplayString (SIZE(0..16))
    MAX-ACCESS read-write
    STATUS     current
    DESCRIPTION
            "-- empty --"
    ::= { lcsSetupVpnIkev2PeersEntry 20 }

-- {COLUMN} 1.3.6.1.4.1.2356.11.2.19.36.1.1.21
lcsSetupVpnIkev2PeersEntryIpv6 OBJECT-TYPE
    SYNTAX     DisplayString (SIZE(0..16))
    MAX-ACCESS read-write
    STATUS     current
    DESCRIPTION
            "-- empty --"
    ::= { lcsSetupVpnIkev2PeersEntry 21 }

-- {COLUMN} 1.3.6.1.4.1.2356.11.2.19.36.1.1.22
lcsSetupVpnIkev2PeersEntrySplitDnsProfile OBJECT-TYPE
    SYNTAX     DisplayString (SIZE(0..16))
    MAX-ACCESS read-write
    STATUS     current
    DESCRIPTION
            "-- empty --"
    ::= { lcsSetupVpnIkev2PeersEntry 22 }

-- {COLUMN} 1.3.6.1.4.1.2356.11.2.19.36.1.1.23
lcsSetupVpnIkev2PeersEntryHsvpn OBJECT-TYPE
    SYNTAX     DisplayString (SIZE(0..16))
    MAX-ACCESS read-write
    STATUS     current
    DESCRIPTION
            "-- empty --"
    ::= { lcsSetupVpnIkev2PeersEntry 23 }

-- {COLUMN} 1.3.6.1.4.1.2356.11.2.19.36.1.1.24
lcsSetupVpnIkev2PeersEntryCfgClientProfile OBJECT-TYPE
    SYNTAX     DisplayString (SIZE(0..16))
    MAX-ACCESS read-write
    STATUS     current
    DESCRIPTION
            "-- empty --"
    ::= { lcsSetupVpnIkev2PeersEntry 24 }

-- {TABLE} 1.3.6.1.4.1.2356.11.2.19.36.2
lcsSetupVpnIkev2EncryptionTable OBJECT-TYPE
    SYNTAX     SEQUENCE OF LcsSetupVpnIkev2EncryptionEntry
    MAX-ACCESS not-accessible
    STATUS     current
    DESCRIPTION
            "-- empty --"
    ::= { lcsSetupVpnIkev2 2 }

-- {ROW} 1.3.6.1.4.1.2356.11.2.19.36.2.1
lcsSetupVpnIkev2EncryptionEntry OBJECT-TYPE
    SYNTAX     LcsSetupVpnIkev2EncryptionEntry
    MAX-ACCESS not-accessible
    STATUS     current
    DESCRIPTION
            ""
    INDEX {
            lcsSetupVpnIkev2EncryptionEntryName
          }
    ::= { lcsSetupVpnIkev2EncryptionTable 1 }

LcsSetupVpnIkev2EncryptionEntry ::= SEQUENCE {
            lcsSetupVpnIkev2EncryptionEntryName DisplayString,
            lcsSetupVpnIkev2EncryptionEntryDhGroups BITS,
            lcsSetupVpnIkev2EncryptionEntryPfs INTEGER,
            lcsSetupVpnIkev2EncryptionEntryIkeSaCipherList BITS,
            lcsSetupVpnIkev2EncryptionEntryIkeSaIntegAlgList BITS,
            lcsSetupVpnIkev2EncryptionEntryChildSaCipherList BITS,
            lcsSetupVpnIkev2EncryptionEntryChildSaIntegAlgList BITS
    }

-- {COLUMN} 1.3.6.1.4.1.2356.11.2.19.36.2.1.1
lcsSetupVpnIkev2EncryptionEntryName OBJECT-TYPE
    SYNTAX     DisplayString (SIZE(0..16))
    MAX-ACCESS read-write
    STATUS     current
    DESCRIPTION
            "-- empty --"
    ::= { lcsSetupVpnIkev2EncryptionEntry 1 }

-- {COLUMN} 1.3.6.1.4.1.2356.11.2.19.36.2.1.2
lcsSetupVpnIkev2EncryptionEntryDhGroups OBJECT-TYPE
    SYNTAX     BITS {
                  eDh32 (19),
                  eDh31 (20),
                  eDh19 (21),
                  eDh20 (22),
                  eDh21 (23),
                  eDh28 (24),
                  eDh29 (25),
                  eDh30 (26),
                  eDh2 (27),
                  eDh5 (28),
                  eDh14 (29),
                  eDh15 (30),
                  eDh16 (31)
            }
    MAX-ACCESS read-write
    STATUS     current
    DESCRIPTION
            "-- empty --"
    ::= { lcsSetupVpnIkev2EncryptionEntry 2 }

-- {COLUMN} 1.3.6.1.4.1.2356.11.2.19.36.2.1.3
lcsSetupVpnIkev2EncryptionEntryPfs OBJECT-TYPE
    SYNTAX     INTEGER {
                  eNo (0),
                  eYes (1)
            }
    MAX-ACCESS read-write
    STATUS     current
    DESCRIPTION
            "-- empty --"
    ::= { lcsSetupVpnIkev2EncryptionEntry 3 }

-- {COLUMN} 1.3.6.1.4.1.2356.11.2.19.36.2.1.4
lcsSetupVpnIkev2EncryptionEntryIkeSaCipherList OBJECT-TYPE
    SYNTAX     BITS {
                  eChacha20Poly1305 (24),
                  eAesGcm128 (25),
                  eAesGcm192 (26),
                  eAesGcm256 (27),
                  e3des (28),
                  eAesCbc128 (29),
                  eAesCbc192 (30),
                  eAesCbc256 (31)
            }
    MAX-ACCESS read-write
    STATUS     current
    DESCRIPTION
            "-- empty --"
    ::= { lcsSetupVpnIkev2EncryptionEntry 4 }

-- {COLUMN} 1.3.6.1.4.1.2356.11.2.19.36.2.1.5
lcsSetupVpnIkev2EncryptionEntryIkeSaIntegAlgList OBJECT-TYPE
    SYNTAX     BITS {
                  eMd5 (27),
                  eSha1 (28),
                  eSha256 (29),
                  eSha384 (30),
                  eSha512 (31)
            }
    MAX-ACCESS read-write
    STATUS     current
    DESCRIPTION
            "-- empty --"
    ::= { lcsSetupVpnIkev2EncryptionEntry 5 }

-- {COLUMN} 1.3.6.1.4.1.2356.11.2.19.36.2.1.6
lcsSetupVpnIkev2EncryptionEntryChildSaCipherList OBJECT-TYPE
    SYNTAX     BITS {
                  eChacha20Poly1305 (24),
                  eAesGcm128 (25),
                  eAesGcm192 (26),
                  eAesGcm256 (27),
                  e3des (28),
                  eAesCbc128 (29),
                  eAesCbc192 (30),
                  eAesCbc256 (31)
            }
    MAX-ACCESS read-write
    STATUS     current
    DESCRIPTION
            "-- empty --"
    ::= { lcsSetupVpnIkev2EncryptionEntry 6 }

-- {COLUMN} 1.3.6.1.4.1.2356.11.2.19.36.2.1.7
lcsSetupVpnIkev2EncryptionEntryChildSaIntegAlgList OBJECT-TYPE
    SYNTAX     BITS {
                  eMd5 (27),
                  eSha1 (28),
                  eSha256 (29),
                  eSha384 (30),
                  eSha512 (31)
            }
    MAX-ACCESS read-write
    STATUS     current
    DESCRIPTION
            "-- empty --"
    ::= { lcsSetupVpnIkev2EncryptionEntry 7 }

-- {NODE} 1.3.6.1.4.1.2356.11.2.19.36.3
lcsSetupVpnIkev2Auth OBJECT IDENTIFIER ::= { lcsSetupVpnIkev2 3 }

-- {TABLE} 1.3.6.1.4.1.2356.11.2.19.36.3.1
lcsSetupVpnIkev2AuthParameterTable OBJECT-TYPE
    SYNTAX     SEQUENCE OF LcsSetupVpnIkev2AuthParameterEntry
    MAX-ACCESS not-accessible
    STATUS     current
    DESCRIPTION
            "-- empty --"
    ::= { lcsSetupVpnIkev2Auth 1 }

-- {ROW} 1.3.6.1.4.1.2356.11.2.19.36.3.1.1
lcsSetupVpnIkev2AuthParameterEntry OBJECT-TYPE
    SYNTAX     LcsSetupVpnIkev2AuthParameterEntry
    MAX-ACCESS not-accessible
    STATUS     current
    DESCRIPTION
            ""
    INDEX {
            lcsSetupVpnIkev2AuthParameterEntryName
          }
    ::= { lcsSetupVpnIkev2AuthParameterTable 1 }

LcsSetupVpnIkev2AuthParameterEntry ::= SEQUENCE {
            lcsSetupVpnIkev2AuthParameterEntryName DisplayString,
            lcsSetupVpnIkev2AuthParameterEntryLocalAuth INTEGER,
            lcsSetupVpnIkev2AuthParameterEntryLocalIdType INTEGER,
            lcsSetupVpnIkev2AuthParameterEntryLocalId DisplayString,
            lcsSetupVpnIkev2AuthParameterEntryLocalPassword DisplayString,
            lcsSetupVpnIkev2AuthParameterEntryRemoteAuth INTEGER,
            lcsSetupVpnIkev2AuthParameterEntryRemoteIdType INTEGER,
            lcsSetupVpnIkev2AuthParameterEntryRemoteId DisplayString,
            lcsSetupVpnIkev2AuthParameterEntryRemotePassword DisplayString,
            lcsSetupVpnIkev2AuthParameterEntryAdditRemoteIdList DisplayString,
            lcsSetupVpnIkev2AuthParameterEntryLocalCertificate DisplayString,
            lcsSetupVpnIkev2AuthParameterEntryRemoteCertIdCheck INTEGER,
            lcsSetupVpnIkev2AuthParameterEntryLocalDigSigProfile DisplayString,
            lcsSetupVpnIkev2AuthParameterEntryRemoteDigSigProfile DisplayString,
            lcsSetupVpnIkev2AuthParameterEntryOcspCheck INTEGER,
            lcsSetupVpnIkev2AuthParameterEntryRemoteEapProfile DisplayString
    }

-- {COLUMN} 1.3.6.1.4.1.2356.11.2.19.36.3.1.1.1
lcsSetupVpnIkev2AuthParameterEntryName OBJECT-TYPE
    SYNTAX     DisplayString (SIZE(0..16))
    MAX-ACCESS read-write
    STATUS     current
    DESCRIPTION
            "-- empty --"
    ::= { lcsSetupVpnIkev2AuthParameterEntry 1 }

-- {COLUMN} 1.3.6.1.4.1.2356.11.2.19.36.3.1.1.2
lcsSetupVpnIkev2AuthParameterEntryLocalAuth OBJECT-TYPE
    SYNTAX     INTEGER {
                  eRsaSignature (1),
                  ePsk (2),
                  eEcdsa256 (9),
                  eEcdsa384 (10),
                  eEcdsa521 (11),
                  eDigitalSignature (14)
            }
    MAX-ACCESS read-write
    STATUS     current
    DESCRIPTION
            "-- empty --"
    ::= { lcsSetupVpnIkev2AuthParameterEntry 2 }

-- {COLUMN} 1.3.6.1.4.1.2356.11.2.19.36.3.1.1.3
lcsSetupVpnIkev2AuthParameterEntryLocalIdType OBJECT-TYPE
    SYNTAX     INTEGER {
                  eNoIdentity (0),
                  eIpAddress (1),
                  eDomainName (2),
                  eEmailAddress (3),
                  eIpv6Address (5),
                  eDistinguishedName (9),
                  eKeyId (11)
            }
    MAX-ACCESS read-write
    STATUS     current
    DESCRIPTION
            "-- empty --"
    ::= { lcsSetupVpnIkev2AuthParameterEntry 3 }

-- {COLUMN} 1.3.6.1.4.1.2356.11.2.19.36.3.1.1.4
lcsSetupVpnIkev2AuthParameterEntryLocalId OBJECT-TYPE
    SYNTAX     DisplayString (SIZE(0..254))
    MAX-ACCESS read-write
    STATUS     current
    DESCRIPTION
            "-- empty --"
    ::= { lcsSetupVpnIkev2AuthParameterEntry 4 }

-- {COLUMN} 1.3.6.1.4.1.2356.11.2.19.36.3.1.1.5
lcsSetupVpnIkev2AuthParameterEntryLocalPassword OBJECT-TYPE
    SYNTAX     DisplayString (SIZE(0..64))
    MAX-ACCESS read-write
    STATUS     current
    DESCRIPTION
            "-- empty --"
    ::= { lcsSetupVpnIkev2AuthParameterEntry 5 }

-- {COLUMN} 1.3.6.1.4.1.2356.11.2.19.36.3.1.1.6
lcsSetupVpnIkev2AuthParameterEntryRemoteAuth OBJECT-TYPE
    SYNTAX     INTEGER {
                  eRsaSignature (1),
                  ePsk (2),
                  eEcdsa256 (9),
                  eEcdsa384 (10),
                  eEcdsa521 (11),
                  eDigitalSignature (14),
                  eEap (201)
            }
    MAX-ACCESS read-write
    STATUS     current
    DESCRIPTION
            "-- empty --"
    ::= { lcsSetupVpnIkev2AuthParameterEntry 6 }

-- {COLUMN} 1.3.6.1.4.1.2356.11.2.19.36.3.1.1.7
lcsSetupVpnIkev2AuthParameterEntryRemoteIdType OBJECT-TYPE
    SYNTAX     INTEGER {
                  eNoIdentity (0),
                  eIpAddress (1),
                  eDomainName (2),
                  eEmailAddress (3),
                  eIpv6Address (5),
                  eDistinguishedName (9),
                  eKeyId (11)
            }
    MAX-ACCESS read-write
    STATUS     current
    DESCRIPTION
            "-- empty --"
    ::= { lcsSetupVpnIkev2AuthParameterEntry 7 }

-- {COLUMN} 1.3.6.1.4.1.2356.11.2.19.36.3.1.1.8
lcsSetupVpnIkev2AuthParameterEntryRemoteId OBJECT-TYPE
    SYNTAX     DisplayString (SIZE(0..254))
    MAX-ACCESS read-write
    STATUS     current
    DESCRIPTION
            "-- empty --"
    ::= { lcsSetupVpnIkev2AuthParameterEntry 8 }

-- {COLUMN} 1.3.6.1.4.1.2356.11.2.19.36.3.1.1.9
lcsSetupVpnIkev2AuthParameterEntryRemotePassword OBJECT-TYPE
    SYNTAX     DisplayString (SIZE(0..64))
    MAX-ACCESS read-write
    STATUS     current
    DESCRIPTION
            "-- empty --"
    ::= { lcsSetupVpnIkev2AuthParameterEntry 9 }

-- {COLUMN} 1.3.6.1.4.1.2356.11.2.19.36.3.1.1.10
lcsSetupVpnIkev2AuthParameterEntryAdditRemoteIdList OBJECT-TYPE
    SYNTAX     DisplayString (SIZE(0..16))
    MAX-ACCESS read-write
    STATUS     current
    DESCRIPTION
            "-- empty --"
    ::= { lcsSetupVpnIkev2AuthParameterEntry 10 }

-- {COLUMN} 1.3.6.1.4.1.2356.11.2.19.36.3.1.1.11
lcsSetupVpnIkev2AuthParameterEntryLocalCertificate OBJECT-TYPE
    SYNTAX     DisplayString (SIZE(0..254))
    MAX-ACCESS read-write
    STATUS     current
    DESCRIPTION
            "-- empty --"
    ::= { lcsSetupVpnIkev2AuthParameterEntry 11 }

-- {COLUMN} 1.3.6.1.4.1.2356.11.2.19.36.3.1.1.12
lcsSetupVpnIkev2AuthParameterEntryRemoteCertIdCheck OBJECT-TYPE
    SYNTAX     INTEGER {
                  eNo (0),
                  eYes (1)
            }
    MAX-ACCESS read-write
    STATUS     current
    DESCRIPTION
            "-- empty --"
    ::= { lcsSetupVpnIkev2AuthParameterEntry 12 }

-- {COLUMN} 1.3.6.1.4.1.2356.11.2.19.36.3.1.1.13
lcsSetupVpnIkev2AuthParameterEntryLocalDigSigProfile OBJECT-TYPE
    SYNTAX     DisplayString (SIZE(0..20))
    MAX-ACCESS read-write
    STATUS     current
    DESCRIPTION
            "-- empty --"
    ::= { lcsSetupVpnIkev2AuthParameterEntry 13 }

-- {COLUMN} 1.3.6.1.4.1.2356.11.2.19.36.3.1.1.14
lcsSetupVpnIkev2AuthParameterEntryRemoteDigSigProfile OBJECT-TYPE
    SYNTAX     DisplayString (SIZE(0..20))
    MAX-ACCESS read-write
    STATUS     current
    DESCRIPTION
            "-- empty --"
    ::= { lcsSetupVpnIkev2AuthParameterEntry 14 }

-- {COLUMN} 1.3.6.1.4.1.2356.11.2.19.36.3.1.1.15
lcsSetupVpnIkev2AuthParameterEntryOcspCheck OBJECT-TYPE
    SYNTAX     INTEGER {
                  eNo (0),
                  eYes (1)
            }
    MAX-ACCESS read-write
    STATUS     current
    DESCRIPTION
            "-- empty --"
    ::= { lcsSetupVpnIkev2AuthParameterEntry 15 }

-- {COLUMN} 1.3.6.1.4.1.2356.11.2.19.36.3.1.1.16
lcsSetupVpnIkev2AuthParameterEntryRemoteEapProfile OBJECT-TYPE
    SYNTAX     DisplayString (SIZE(0..16))
    MAX-ACCESS read-write
    STATUS     current
    DESCRIPTION
            "-- empty --"
    ::= { lcsSetupVpnIkev2AuthParameterEntry 16 }

-- {TABLE} 1.3.6.1.4.1.2356.11.2.19.36.3.2
lcsSetupVpnIkev2AuthAdditRemoteIdListTable OBJECT-TYPE
    SYNTAX     SEQUENCE OF LcsSetupVpnIkev2AuthAdditRemoteIdListEntry
    MAX-ACCESS not-accessible
    STATUS     current
    DESCRIPTION
            "-- empty --"
    ::= { lcsSetupVpnIkev2Auth 2 }

-- {ROW} 1.3.6.1.4.1.2356.11.2.19.36.3.2.1
lcsSetupVpnIkev2AuthAdditRemoteIdListEntry OBJECT-TYPE
    SYNTAX     LcsSetupVpnIkev2AuthAdditRemoteIdListEntry
    MAX-ACCESS not-accessible
    STATUS     current
    DESCRIPTION
            ""
    INDEX {
            lcsSetupVpnIkev2AuthAdditRemoteIdListEntryName
          }
    ::= { lcsSetupVpnIkev2AuthAdditRemoteIdListTable 1 }

LcsSetupVpnIkev2AuthAdditRemoteIdListEntry ::= SEQUENCE {
            lcsSetupVpnIkev2AuthAdditRemoteIdListEntryName DisplayString,
            lcsSetupVpnIkev2AuthAdditRemoteIdListEntryAdditRemoteIds DisplayString
    }

-- {COLUMN} 1.3.6.1.4.1.2356.11.2.19.36.3.2.1.1
lcsSetupVpnIkev2AuthAdditRemoteIdListEntryName OBJECT-TYPE
    SYNTAX     DisplayString (SIZE(0..20))
    MAX-ACCESS read-write
    STATUS     current
    DESCRIPTION
            "-- empty --"
    ::= { lcsSetupVpnIkev2AuthAdditRemoteIdListEntry 1 }

-- {COLUMN} 1.3.6.1.4.1.2356.11.2.19.36.3.2.1.2
lcsSetupVpnIkev2AuthAdditRemoteIdListEntryAdditRemoteIds OBJECT-TYPE
    SYNTAX     DisplayString (SIZE(0..254))
    MAX-ACCESS read-write
    STATUS     current
    DESCRIPTION
            "-- empty --"
    ::= { lcsSetupVpnIkev2AuthAdditRemoteIdListEntry 2 }

-- {TABLE} 1.3.6.1.4.1.2356.11.2.19.36.3.3
lcsSetupVpnIkev2AuthAdditRemoteIdsTable OBJECT-TYPE
    SYNTAX     SEQUENCE OF LcsSetupVpnIkev2AuthAdditRemoteIdsEntry
    MAX-ACCESS not-accessible
    STATUS     current
    DESCRIPTION
            "-- empty --"
    ::= { lcsSetupVpnIkev2Auth 3 }

-- {ROW} 1.3.6.1.4.1.2356.11.2.19.36.3.3.1
lcsSetupVpnIkev2AuthAdditRemoteIdsEntry OBJECT-TYPE
    SYNTAX     LcsSetupVpnIkev2AuthAdditRemoteIdsEntry
    MAX-ACCESS not-accessible
    STATUS     current
    DESCRIPTION
            ""
    INDEX {
            lcsSetupVpnIkev2AuthAdditRemoteIdsEntryName
          }
    ::= { lcsSetupVpnIkev2AuthAdditRemoteIdsTable 1 }

LcsSetupVpnIkev2AuthAdditRemoteIdsEntry ::= SEQUENCE {
            lcsSetupVpnIkev2AuthAdditRemoteIdsEntryName DisplayString,
            lcsSetupVpnIkev2AuthAdditRemoteIdsEntryRemoteAuth INTEGER,
            lcsSetupVpnIkev2AuthAdditRemoteIdsEntryRemoteIdType INTEGER,
            lcsSetupVpnIkev2AuthAdditRemoteIdsEntryRemoteId DisplayString,
            lcsSetupVpnIkev2AuthAdditRemoteIdsEntryRemotePassword DisplayString,
            lcsSetupVpnIkev2AuthAdditRemoteIdsEntryRemoteCertIdCheck INTEGER,
            lcsSetupVpnIkev2AuthAdditRemoteIdsEntryOcspCheck INTEGER,
            lcsSetupVpnIkev2AuthAdditRemoteIdsEntryRemoteDigSigProfile DisplayString,
            lcsSetupVpnIkev2AuthAdditRemoteIdsEntryRemoteEapProfile DisplayString
    }

-- {COLUMN} 1.3.6.1.4.1.2356.11.2.19.36.3.3.1.1
lcsSetupVpnIkev2AuthAdditRemoteIdsEntryName OBJECT-TYPE
    SYNTAX     DisplayString (SIZE(0..20))
    MAX-ACCESS read-write
    STATUS     current
    DESCRIPTION
            "-- empty --"
    ::= { lcsSetupVpnIkev2AuthAdditRemoteIdsEntry 1 }

-- {COLUMN} 1.3.6.1.4.1.2356.11.2.19.36.3.3.1.2
lcsSetupVpnIkev2AuthAdditRemoteIdsEntryRemoteAuth OBJECT-TYPE
    SYNTAX     INTEGER {
                  eRsaSignature (1),
                  ePsk (2),
                  eEcdsa256 (9),
                  eEcdsa384 (10),
                  eEcdsa521 (11),
                  eDigitalSignature (14),
                  eEap (201)
            }
    MAX-ACCESS read-write
    STATUS     current
    DESCRIPTION
            "-- empty --"
    ::= { lcsSetupVpnIkev2AuthAdditRemoteIdsEntry 2 }

-- {COLUMN} 1.3.6.1.4.1.2356.11.2.19.36.3.3.1.3
lcsSetupVpnIkev2AuthAdditRemoteIdsEntryRemoteIdType OBJECT-TYPE
    SYNTAX     INTEGER {
                  eNoIdentity (0),
                  eIpAddress (1),
                  eDomainName (2),
                  eEmailAddress (3),
                  eIpv6Address (5),
                  eDistinguishedName (9),
                  eKeyId (11)
            }
    MAX-ACCESS read-write
    STATUS     current
    DESCRIPTION
            "-- empty --"
    ::= { lcsSetupVpnIkev2AuthAdditRemoteIdsEntry 3 }

-- {COLUMN} 1.3.6.1.4.1.2356.11.2.19.36.3.3.1.4
lcsSetupVpnIkev2AuthAdditRemoteIdsEntryRemoteId OBJECT-TYPE
    SYNTAX     DisplayString (SIZE(0..254))
    MAX-ACCESS read-write
    STATUS     current
    DESCRIPTION
            "-- empty --"
    ::= { lcsSetupVpnIkev2AuthAdditRemoteIdsEntry 4 }

-- {COLUMN} 1.3.6.1.4.1.2356.11.2.19.36.3.3.1.5
lcsSetupVpnIkev2AuthAdditRemoteIdsEntryRemotePassword OBJECT-TYPE
    SYNTAX     DisplayString (SIZE(0..64))
    MAX-ACCESS read-write
    STATUS     current
    DESCRIPTION
            "-- empty --"
    ::= { lcsSetupVpnIkev2AuthAdditRemoteIdsEntry 5 }

-- {COLUMN} 1.3.6.1.4.1.2356.11.2.19.36.3.3.1.6
lcsSetupVpnIkev2AuthAdditRemoteIdsEntryRemoteCertIdCheck OBJECT-TYPE
    SYNTAX     INTEGER {
                  eNo (0),
                  eYes (1)
            }
    MAX-ACCESS read-write
    STATUS     current
    DESCRIPTION
            "-- empty --"
    ::= { lcsSetupVpnIkev2AuthAdditRemoteIdsEntry 6 }

-- {COLUMN} 1.3.6.1.4.1.2356.11.2.19.36.3.3.1.7
lcsSetupVpnIkev2AuthAdditRemoteIdsEntryOcspCheck OBJECT-TYPE
    SYNTAX     INTEGER {
                  eNo (0),
                  eYes (1)
            }
    MAX-ACCESS read-write
    STATUS     current
    DESCRIPTION
            "-- empty --"
    ::= { lcsSetupVpnIkev2AuthAdditRemoteIdsEntry 7 }

-- {COLUMN} 1.3.6.1.4.1.2356.11.2.19.36.3.3.1.8
lcsSetupVpnIkev2AuthAdditRemoteIdsEntryRemoteDigSigProfile OBJECT-TYPE
    SYNTAX     DisplayString (SIZE(0..20))
    MAX-ACCESS read-write
    STATUS     current
    DESCRIPTION
            "-- empty --"
    ::= { lcsSetupVpnIkev2AuthAdditRemoteIdsEntry 8 }

-- {COLUMN} 1.3.6.1.4.1.2356.11.2.19.36.3.3.1.9
lcsSetupVpnIkev2AuthAdditRemoteIdsEntryRemoteEapProfile OBJECT-TYPE
    SYNTAX     DisplayString (SIZE(0..16))
    MAX-ACCESS read-write
    STATUS     current
    DESCRIPTION
            "-- empty --"
    ::= { lcsSetupVpnIkev2AuthAdditRemoteIdsEntry 9 }

-- {TABLE} 1.3.6.1.4.1.2356.11.2.19.36.3.4
lcsSetupVpnIkev2AuthDigitalSignatureProfilesTable OBJECT-TYPE
    SYNTAX     SEQUENCE OF LcsSetupVpnIkev2AuthDigitalSignatureProfilesEntry
    MAX-ACCESS not-accessible
    STATUS     current
    DESCRIPTION
            "-- empty --"
    ::= { lcsSetupVpnIkev2Auth 4 }

-- {ROW} 1.3.6.1.4.1.2356.11.2.19.36.3.4.1
lcsSetupVpnIkev2AuthDigitalSignatureProfilesEntry OBJECT-TYPE
    SYNTAX     LcsSetupVpnIkev2AuthDigitalSignatureProfilesEntry
    MAX-ACCESS not-accessible
    STATUS     current
    DESCRIPTION
            ""
    INDEX {
            lcsSetupVpnIkev2AuthDigitalSignatureProfilesEntryName
          }
    ::= { lcsSetupVpnIkev2AuthDigitalSignatureProfilesTable 1 }

LcsSetupVpnIkev2AuthDigitalSignatureProfilesEntry ::= SEQUENCE {
            lcsSetupVpnIkev2AuthDigitalSignatureProfilesEntryName DisplayString,
            lcsSetupVpnIkev2AuthDigitalSignatureProfilesEntryAuthMethod INTEGER,
            lcsSetupVpnIkev2AuthDigitalSignatureProfilesEntryHashAlgorithms BITS
    }

-- {COLUMN} 1.3.6.1.4.1.2356.11.2.19.36.3.4.1.1
lcsSetupVpnIkev2AuthDigitalSignatureProfilesEntryName OBJECT-TYPE
    SYNTAX     DisplayString (SIZE(0..20))
    MAX-ACCESS read-write
    STATUS     current
    DESCRIPTION
            "-- empty --"
    ::= { lcsSetupVpnIkev2AuthDigitalSignatureProfilesEntry 1 }

-- {COLUMN} 1.3.6.1.4.1.2356.11.2.19.36.3.4.1.2
lcsSetupVpnIkev2AuthDigitalSignatureProfilesEntryAuthMethod OBJECT-TYPE
    SYNTAX     INTEGER {
                  eRsassaPss (1),
                  eRsassaPkcs1V15 (2),
                  eEcdsa (4),
                  eEddsa25519 (8),
                  eEddsa448 (16)
            }
    MAX-ACCESS read-write
    STATUS     current
    DESCRIPTION
            "-- empty --"
    ::= { lcsSetupVpnIkev2AuthDigitalSignatureProfilesEntry 2 }

-- {COLUMN} 1.3.6.1.4.1.2356.11.2.19.36.3.4.1.3
lcsSetupVpnIkev2AuthDigitalSignatureProfilesEntryHashAlgorithms OBJECT-TYPE
    SYNTAX     BITS {
                  eIdentity (3),
                  eSha1 (4),
                  eSha256 (5),
                  eSha384 (6),
                  eSha512 (7)
            }
    MAX-ACCESS read-write
    STATUS     current
    DESCRIPTION
            "-- empty --"
    ::= { lcsSetupVpnIkev2AuthDigitalSignatureProfilesEntry 3 }

-- {TABLE} 1.3.6.1.4.1.2356.11.2.19.36.3.5
lcsSetupVpnIkev2AuthEapProfilesTable OBJECT-TYPE
    SYNTAX     SEQUENCE OF LcsSetupVpnIkev2AuthEapProfilesEntry
    MAX-ACCESS not-accessible
    STATUS     current
    DESCRIPTION
            "-- empty --"
    ::= { lcsSetupVpnIkev2Auth 5 }

-- {ROW} 1.3.6.1.4.1.2356.11.2.19.36.3.5.1
lcsSetupVpnIkev2AuthEapProfilesEntry OBJECT-TYPE
    SYNTAX     LcsSetupVpnIkev2AuthEapProfilesEntry
    MAX-ACCESS not-accessible
    STATUS     current
    DESCRIPTION
            ""
    INDEX {
            lcsSetupVpnIkev2AuthEapProfilesEntryName
          }
    ::= { lcsSetupVpnIkev2AuthEapProfilesTable 1 }

LcsSetupVpnIkev2AuthEapProfilesEntry ::= SEQUENCE {
            lcsSetupVpnIkev2AuthEapProfilesEntryName DisplayString,
            lcsSetupVpnIkev2AuthEapProfilesEntryEapOnlyAuthentication INTEGER
    }

-- {COLUMN} 1.3.6.1.4.1.2356.11.2.19.36.3.5.1.1
lcsSetupVpnIkev2AuthEapProfilesEntryName OBJECT-TYPE
    SYNTAX     DisplayString (SIZE(0..16))
    MAX-ACCESS read-write
    STATUS     current
    DESCRIPTION
            "-- empty --"
    ::= { lcsSetupVpnIkev2AuthEapProfilesEntry 1 }

-- {COLUMN} 1.3.6.1.4.1.2356.11.2.19.36.3.5.1.4
lcsSetupVpnIkev2AuthEapProfilesEntryEapOnlyAuthentication OBJECT-TYPE
    SYNTAX     INTEGER {
                  eNo (0),
                  eYes (1)
            }
    MAX-ACCESS read-write
    STATUS     current
    DESCRIPTION
            "-- empty --"
    ::= { lcsSetupVpnIkev2AuthEapProfilesEntry 4 }

-- {TABLE} 1.3.6.1.4.1.2356.11.2.19.36.4
lcsSetupVpnIkev2GeneralTable OBJECT-TYPE
    SYNTAX     SEQUENCE OF LcsSetupVpnIkev2GeneralEntry
    MAX-ACCESS not-accessible
    STATUS     current
    DESCRIPTION
            "-- empty --"
    ::= { lcsSetupVpnIkev2 4 }

-- {ROW} 1.3.6.1.4.1.2356.11.2.19.36.4.1
lcsSetupVpnIkev2GeneralEntry OBJECT-TYPE
    SYNTAX     LcsSetupVpnIkev2GeneralEntry
    MAX-ACCESS not-accessible
    STATUS     current
    DESCRIPTION
            ""
    INDEX {
            lcsSetupVpnIkev2GeneralEntryName
          }
    ::= { lcsSetupVpnIkev2GeneralTable 1 }

LcsSetupVpnIkev2GeneralEntry ::= SEQUENCE {
            lcsSetupVpnIkev2GeneralEntryName DisplayString,
            lcsSetupVpnIkev2GeneralEntryDpdInactTimeout Integer32,
            lcsSetupVpnIkev2GeneralEntrySslEncaps INTEGER,
            lcsSetupVpnIkev2GeneralEntryIpcomp INTEGER,
            lcsSetupVpnIkev2GeneralEntryEncapsMode INTEGER,
            lcsSetupVpnIkev2GeneralEntryEncapsulation INTEGER,
            lcsSetupVpnIkev2GeneralEntryDestinationPort Integer32
    }

-- {COLUMN} 1.3.6.1.4.1.2356.11.2.19.36.4.1.1
lcsSetupVpnIkev2GeneralEntryName OBJECT-TYPE
    SYNTAX     DisplayString (SIZE(0..16))
    MAX-ACCESS read-write
    STATUS     current
    DESCRIPTION
            "-- empty --"
    ::= { lcsSetupVpnIkev2GeneralEntry 1 }

-- {COLUMN} 1.3.6.1.4.1.2356.11.2.19.36.4.1.2
lcsSetupVpnIkev2GeneralEntryDpdInactTimeout OBJECT-TYPE
    SYNTAX     Integer32 (0..2147483647)
    MAX-ACCESS read-write
    STATUS     current
    DESCRIPTION
            "-- empty --"
    ::= { lcsSetupVpnIkev2GeneralEntry 2 }

-- {COLUMN} 1.3.6.1.4.1.2356.11.2.19.36.4.1.4
lcsSetupVpnIkev2GeneralEntrySslEncaps OBJECT-TYPE
    SYNTAX     INTEGER {
                  eNo (0),
                  eYes (1)
            }
    MAX-ACCESS read-write
    STATUS     current
    DESCRIPTION
            "-- empty --"
    ::= { lcsSetupVpnIkev2GeneralEntry 4 }

-- {COLUMN} 1.3.6.1.4.1.2356.11.2.19.36.4.1.5
lcsSetupVpnIkev2GeneralEntryIpcomp OBJECT-TYPE
    SYNTAX     INTEGER {
                  eNo (0),
                  eYes (1)
            }
    MAX-ACCESS read-write
    STATUS     current
    DESCRIPTION
            "-- empty --"
    ::= { lcsSetupVpnIkev2GeneralEntry 5 }

-- {COLUMN} 1.3.6.1.4.1.2356.11.2.19.36.4.1.6
lcsSetupVpnIkev2GeneralEntryEncapsMode OBJECT-TYPE
    SYNTAX     INTEGER {
                  eTunnel (1)
            }
    MAX-ACCESS read-write
    STATUS     current
    DESCRIPTION
            "-- empty --"
    ::= { lcsSetupVpnIkev2GeneralEntry 6 }

-- {COLUMN} 1.3.6.1.4.1.2356.11.2.19.36.4.1.7
lcsSetupVpnIkev2GeneralEntryEncapsulation OBJECT-TYPE
    SYNTAX     INTEGER {
                  eNone (0),
                  eUdp (1),
                  eSsl (2)
            }
    MAX-ACCESS read-write
    STATUS     current
    DESCRIPTION
            "-- empty --"
    ::= { lcsSetupVpnIkev2GeneralEntry 7 }

-- {COLUMN} 1.3.6.1.4.1.2356.11.2.19.36.4.1.8
lcsSetupVpnIkev2GeneralEntryDestinationPort OBJECT-TYPE
    SYNTAX     Integer32 (0..65535)
    MAX-ACCESS read-write
    STATUS     current
    DESCRIPTION
            "-- empty --"
    ::= { lcsSetupVpnIkev2GeneralEntry 8 }

-- {TABLE} 1.3.6.1.4.1.2356.11.2.19.36.5
lcsSetupVpnIkev2LifetimesTable OBJECT-TYPE
    SYNTAX     SEQUENCE OF LcsSetupVpnIkev2LifetimesEntry
    MAX-ACCESS not-accessible
    STATUS     current
    DESCRIPTION
            "-- empty --"
    ::= { lcsSetupVpnIkev2 5 }

-- {ROW} 1.3.6.1.4.1.2356.11.2.19.36.5.1
lcsSetupVpnIkev2LifetimesEntry OBJECT-TYPE
    SYNTAX     LcsSetupVpnIkev2LifetimesEntry
    MAX-ACCESS not-accessible
    STATUS     current
    DESCRIPTION
            ""
    INDEX {
            lcsSetupVpnIkev2LifetimesEntryName
          }
    ::= { lcsSetupVpnIkev2LifetimesTable 1 }

LcsSetupVpnIkev2LifetimesEntry ::= SEQUENCE {
            lcsSetupVpnIkev2LifetimesEntryName DisplayString,
            lcsSetupVpnIkev2LifetimesEntryIkeSaSec Integer32,
            lcsSetupVpnIkev2LifetimesEntryIkeSaKb Integer32,
            lcsSetupVpnIkev2LifetimesEntryChildSaSec Integer32,
            lcsSetupVpnIkev2LifetimesEntryChildSaKb Integer32
    }

-- {COLUMN} 1.3.6.1.4.1.2356.11.2.19.36.5.1.1
lcsSetupVpnIkev2LifetimesEntryName OBJECT-TYPE
    SYNTAX     DisplayString (SIZE(0..16))
    MAX-ACCESS read-write
    STATUS     current
    DESCRIPTION
            "-- empty --"
    ::= { lcsSetupVpnIkev2LifetimesEntry 1 }

-- {COLUMN} 1.3.6.1.4.1.2356.11.2.19.36.5.1.2
lcsSetupVpnIkev2LifetimesEntryIkeSaSec OBJECT-TYPE
    SYNTAX     Integer32 (0..2147483647)
    MAX-ACCESS read-write
    STATUS     current
    DESCRIPTION
            "-- empty --"
    ::= { lcsSetupVpnIkev2LifetimesEntry 2 }

-- {COLUMN} 1.3.6.1.4.1.2356.11.2.19.36.5.1.3
lcsSetupVpnIkev2LifetimesEntryIkeSaKb OBJECT-TYPE
    SYNTAX     Integer32 (0..2147483647)
    MAX-ACCESS read-write
    STATUS     current
    DESCRIPTION
            "-- empty --"
    ::= { lcsSetupVpnIkev2LifetimesEntry 3 }

-- {COLUMN} 1.3.6.1.4.1.2356.11.2.19.36.5.1.4
lcsSetupVpnIkev2LifetimesEntryChildSaSec OBJECT-TYPE
    SYNTAX     Integer32 (0..2147483647)
    MAX-ACCESS read-write
    STATUS     current
    DESCRIPTION
            "-- empty --"
    ::= { lcsSetupVpnIkev2LifetimesEntry 4 }

-- {COLUMN} 1.3.6.1.4.1.2356.11.2.19.36.5.1.5
lcsSetupVpnIkev2LifetimesEntryChildSaKb OBJECT-TYPE
    SYNTAX     Integer32 (0..2147483647)
    MAX-ACCESS read-write
    STATUS     current
    DESCRIPTION
            "-- empty --"
    ::= { lcsSetupVpnIkev2LifetimesEntry 5 }

-- {NODE} 1.3.6.1.4.1.2356.11.2.19.36.6
lcsSetupVpnIkev2Routing OBJECT IDENTIFIER ::= { lcsSetupVpnIkev2 6 }

-- {TABLE} 1.3.6.1.4.1.2356.11.2.19.36.6.1
lcsSetupVpnIkev2RoutingIpv4Table OBJECT-TYPE
    SYNTAX     SEQUENCE OF LcsSetupVpnIkev2RoutingIpv4Entry
    MAX-ACCESS not-accessible
    STATUS     current
    DESCRIPTION
            "-- empty --"
    ::= { lcsSetupVpnIkev2Routing 1 }

-- {ROW} 1.3.6.1.4.1.2356.11.2.19.36.6.1.1
lcsSetupVpnIkev2RoutingIpv4Entry OBJECT-TYPE
    SYNTAX     LcsSetupVpnIkev2RoutingIpv4Entry
    MAX-ACCESS not-accessible
    STATUS     current
    DESCRIPTION
            ""
    INDEX {
            lcsSetupVpnIkev2RoutingIpv4EntryName,
            lcsSetupVpnIkev2RoutingIpv4EntryNetworks
          }
    ::= { lcsSetupVpnIkev2RoutingIpv4Table 1 }

LcsSetupVpnIkev2RoutingIpv4Entry ::= SEQUENCE {
            lcsSetupVpnIkev2RoutingIpv4EntryName DisplayString,
            lcsSetupVpnIkev2RoutingIpv4EntryNetworks DisplayString,
            lcsSetupVpnIkev2RoutingIpv4EntrySendIkeCfgAddr INTEGER
    }

-- {COLUMN} 1.3.6.1.4.1.2356.11.2.19.36.6.1.1.1
lcsSetupVpnIkev2RoutingIpv4EntryName OBJECT-TYPE
    SYNTAX     DisplayString (SIZE(0..31))
    MAX-ACCESS read-write
    STATUS     current
    DESCRIPTION
            "-- empty --"
    ::= { lcsSetupVpnIkev2RoutingIpv4Entry 1 }

-- {COLUMN} 1.3.6.1.4.1.2356.11.2.19.36.6.1.1.2
lcsSetupVpnIkev2RoutingIpv4EntryNetworks OBJECT-TYPE
    SYNTAX     DisplayString (SIZE(0..254))
    MAX-ACCESS read-write
    STATUS     current
    DESCRIPTION
            "-- empty --"
    ::= { lcsSetupVpnIkev2RoutingIpv4Entry 2 }

-- {COLUMN} 1.3.6.1.4.1.2356.11.2.19.36.6.1.1.3
lcsSetupVpnIkev2RoutingIpv4EntrySendIkeCfgAddr OBJECT-TYPE
    SYNTAX     INTEGER {
                  eNo (0),
                  eYes (1)
            }
    MAX-ACCESS read-write
    STATUS     current
    DESCRIPTION
            "-- empty --"
    ::= { lcsSetupVpnIkev2RoutingIpv4Entry 3 }

-- {TABLE} 1.3.6.1.4.1.2356.11.2.19.36.6.2
lcsSetupVpnIkev2RoutingIpv6Table OBJECT-TYPE
    SYNTAX     SEQUENCE OF LcsSetupVpnIkev2RoutingIpv6Entry
    MAX-ACCESS not-accessible
    STATUS     current
    DESCRIPTION
            "-- empty --"
    ::= { lcsSetupVpnIkev2Routing 2 }

-- {ROW} 1.3.6.1.4.1.2356.11.2.19.36.6.2.1
lcsSetupVpnIkev2RoutingIpv6Entry OBJECT-TYPE
    SYNTAX     LcsSetupVpnIkev2RoutingIpv6Entry
    MAX-ACCESS not-accessible
    STATUS     current
    DESCRIPTION
            ""
    INDEX {
            lcsSetupVpnIkev2RoutingIpv6EntryName,
            lcsSetupVpnIkev2RoutingIpv6EntryNetworks
          }
    ::= { lcsSetupVpnIkev2RoutingIpv6Table 1 }

LcsSetupVpnIkev2RoutingIpv6Entry ::= SEQUENCE {
            lcsSetupVpnIkev2RoutingIpv6EntryName DisplayString,
            lcsSetupVpnIkev2RoutingIpv6EntryNetworks DisplayString,
            lcsSetupVpnIkev2RoutingIpv6EntrySendIkeCfgAddr INTEGER
    }

-- {COLUMN} 1.3.6.1.4.1.2356.11.2.19.36.6.2.1.1
lcsSetupVpnIkev2RoutingIpv6EntryName OBJECT-TYPE
    SYNTAX     DisplayString (SIZE(0..31))
    MAX-ACCESS read-write
    STATUS     current
    DESCRIPTION
            "-- empty --"
    ::= { lcsSetupVpnIkev2RoutingIpv6Entry 1 }

-- {COLUMN} 1.3.6.1.4.1.2356.11.2.19.36.6.2.1.2
lcsSetupVpnIkev2RoutingIpv6EntryNetworks OBJECT-TYPE
    SYNTAX     DisplayString (SIZE(0..254))
    MAX-ACCESS read-write
    STATUS     current
    DESCRIPTION
            "-- empty --"
    ::= { lcsSetupVpnIkev2RoutingIpv6Entry 2 }

-- {COLUMN} 1.3.6.1.4.1.2356.11.2.19.36.6.2.1.3
lcsSetupVpnIkev2RoutingIpv6EntrySendIkeCfgAddr OBJECT-TYPE
    SYNTAX     INTEGER {
                  eNo (0),
                  eYes (1)
            }
    MAX-ACCESS read-write
    STATUS     current
    DESCRIPTION
            "-- empty --"
    ::= { lcsSetupVpnIkev2RoutingIpv6Entry 3 }

-- {NODE} 1.3.6.1.4.1.2356.11.2.19.36.7
lcsSetupVpnIkev2IkeCfg OBJECT IDENTIFIER ::= { lcsSetupVpnIkev2 7 }

-- {TABLE} 1.3.6.1.4.1.2356.11.2.19.36.7.1
lcsSetupVpnIkev2IkeCfgIpv4Table OBJECT-TYPE
    SYNTAX     SEQUENCE OF LcsSetupVpnIkev2IkeCfgIpv4Entry
    MAX-ACCESS not-accessible
    STATUS     current
    DESCRIPTION
            "-- empty --"
    ::= { lcsSetupVpnIkev2IkeCfg 1 }

-- {ROW} 1.3.6.1.4.1.2356.11.2.19.36.7.1.1
lcsSetupVpnIkev2IkeCfgIpv4Entry OBJECT-TYPE
    SYNTAX     LcsSetupVpnIkev2IkeCfgIpv4Entry
    MAX-ACCESS not-accessible
    STATUS     current
    DESCRIPTION
            ""
    INDEX {
            lcsSetupVpnIkev2IkeCfgIpv4EntryName
          }
    ::= { lcsSetupVpnIkev2IkeCfgIpv4Table 1 }

LcsSetupVpnIkev2IkeCfgIpv4Entry ::= SEQUENCE {
            lcsSetupVpnIkev2IkeCfgIpv4EntryName DisplayString,
            lcsSetupVpnIkev2IkeCfgIpv4EntryStartAddressPool DisplayString,
            lcsSetupVpnIkev2IkeCfgIpv4EntryEndAddressPool DisplayString,
            lcsSetupVpnIkev2IkeCfgIpv4EntryPrimaryDns DisplayString,
            lcsSetupVpnIkev2IkeCfgIpv4EntrySecondaryDns DisplayString
    }

-- {COLUMN} 1.3.6.1.4.1.2356.11.2.19.36.7.1.1.1
lcsSetupVpnIkev2IkeCfgIpv4EntryName OBJECT-TYPE
    SYNTAX     DisplayString (SIZE(0..16))
    MAX-ACCESS read-write
    STATUS     current
    DESCRIPTION
            "-- empty --"
    ::= { lcsSetupVpnIkev2IkeCfgIpv4Entry 1 }

-- {COLUMN} 1.3.6.1.4.1.2356.11.2.19.36.7.1.1.2
lcsSetupVpnIkev2IkeCfgIpv4EntryStartAddressPool OBJECT-TYPE
    SYNTAX     DisplayString (SIZE(0..15))
    MAX-ACCESS read-write
    STATUS     current
    DESCRIPTION
            "-- empty --"
    ::= { lcsSetupVpnIkev2IkeCfgIpv4Entry 2 }

-- {COLUMN} 1.3.6.1.4.1.2356.11.2.19.36.7.1.1.3
lcsSetupVpnIkev2IkeCfgIpv4EntryEndAddressPool OBJECT-TYPE
    SYNTAX     DisplayString (SIZE(0..15))
    MAX-ACCESS read-write
    STATUS     current
    DESCRIPTION
            "-- empty --"
    ::= { lcsSetupVpnIkev2IkeCfgIpv4Entry 3 }

-- {COLUMN} 1.3.6.1.4.1.2356.11.2.19.36.7.1.1.4
lcsSetupVpnIkev2IkeCfgIpv4EntryPrimaryDns OBJECT-TYPE
    SYNTAX     DisplayString (SIZE(0..15))
    MAX-ACCESS read-write
    STATUS     current
    DESCRIPTION
            "-- empty --"
    ::= { lcsSetupVpnIkev2IkeCfgIpv4Entry 4 }

-- {COLUMN} 1.3.6.1.4.1.2356.11.2.19.36.7.1.1.5
lcsSetupVpnIkev2IkeCfgIpv4EntrySecondaryDns OBJECT-TYPE
    SYNTAX     DisplayString (SIZE(0..15))
    MAX-ACCESS read-write
    STATUS     current
    DESCRIPTION
            "-- empty --"
    ::= { lcsSetupVpnIkev2IkeCfgIpv4Entry 5 }

-- {TABLE} 1.3.6.1.4.1.2356.11.2.19.36.7.2
lcsSetupVpnIkev2IkeCfgIpv6Table OBJECT-TYPE
    SYNTAX     SEQUENCE OF LcsSetupVpnIkev2IkeCfgIpv6Entry
    MAX-ACCESS not-accessible
    STATUS     current
    DESCRIPTION
            "-- empty --"
    ::= { lcsSetupVpnIkev2IkeCfg 2 }

-- {ROW} 1.3.6.1.4.1.2356.11.2.19.36.7.2.1
lcsSetupVpnIkev2IkeCfgIpv6Entry OBJECT-TYPE
    SYNTAX     LcsSetupVpnIkev2IkeCfgIpv6Entry
    MAX-ACCESS not-accessible
    STATUS     current
    DESCRIPTION
            ""
    INDEX {
            lcsSetupVpnIkev2IkeCfgIpv6EntryName
          }
    ::= { lcsSetupVpnIkev2IkeCfgIpv6Table 1 }

LcsSetupVpnIkev2IkeCfgIpv6Entry ::= SEQUENCE {
            lcsSetupVpnIkev2IkeCfgIpv6EntryName DisplayString,
            lcsSetupVpnIkev2IkeCfgIpv6EntryStartAddressPool DisplayString,
            lcsSetupVpnIkev2IkeCfgIpv6EntryEndAddressPool DisplayString,
            lcsSetupVpnIkev2IkeCfgIpv6EntryPrimaryDns DisplayString,
            lcsSetupVpnIkev2IkeCfgIpv6EntrySecondaryDns DisplayString,
            lcsSetupVpnIkev2IkeCfgIpv6EntryPdSource DisplayString
    }

-- {COLUMN} 1.3.6.1.4.1.2356.11.2.19.36.7.2.1.1
lcsSetupVpnIkev2IkeCfgIpv6EntryName OBJECT-TYPE
    SYNTAX     DisplayString (SIZE(0..16))
    MAX-ACCESS read-write
    STATUS     current
    DESCRIPTION
            "-- empty --"
    ::= { lcsSetupVpnIkev2IkeCfgIpv6Entry 1 }

-- {COLUMN} 1.3.6.1.4.1.2356.11.2.19.36.7.2.1.2
lcsSetupVpnIkev2IkeCfgIpv6EntryStartAddressPool OBJECT-TYPE
    SYNTAX     DisplayString (SIZE(0..39))
    MAX-ACCESS read-write
    STATUS     current
    DESCRIPTION
            "-- empty --"
    ::= { lcsSetupVpnIkev2IkeCfgIpv6Entry 2 }

-- {COLUMN} 1.3.6.1.4.1.2356.11.2.19.36.7.2.1.3
lcsSetupVpnIkev2IkeCfgIpv6EntryEndAddressPool OBJECT-TYPE
    SYNTAX     DisplayString (SIZE(0..39))
    MAX-ACCESS read-write
    STATUS     current
    DESCRIPTION
            "-- empty --"
    ::= { lcsSetupVpnIkev2IkeCfgIpv6Entry 3 }

-- {COLUMN} 1.3.6.1.4.1.2356.11.2.19.36.7.2.1.4
lcsSetupVpnIkev2IkeCfgIpv6EntryPrimaryDns OBJECT-TYPE
    SYNTAX     DisplayString (SIZE(0..39))
    MAX-ACCESS read-write
    STATUS     current
    DESCRIPTION
            "-- empty --"
    ::= { lcsSetupVpnIkev2IkeCfgIpv6Entry 4 }

-- {COLUMN} 1.3.6.1.4.1.2356.11.2.19.36.7.2.1.5
lcsSetupVpnIkev2IkeCfgIpv6EntrySecondaryDns OBJECT-TYPE
    SYNTAX     DisplayString (SIZE(0..39))
    MAX-ACCESS read-write
    STATUS     current
    DESCRIPTION
            "-- empty --"
    ::= { lcsSetupVpnIkev2IkeCfgIpv6Entry 5 }

-- {COLUMN} 1.3.6.1.4.1.2356.11.2.19.36.7.2.1.6
lcsSetupVpnIkev2IkeCfgIpv6EntryPdSource OBJECT-TYPE
    SYNTAX     DisplayString (SIZE(0..16))
    MAX-ACCESS read-write
    STATUS     current
    DESCRIPTION
            "-- empty --"
    ::= { lcsSetupVpnIkev2IkeCfgIpv6Entry 6 }

-- {NODE} 1.3.6.1.4.1.2356.11.2.19.36.7.3
lcsSetupVpnIkev2IkeCfgSplitDns OBJECT IDENTIFIER ::= { lcsSetupVpnIkev2IkeCfg 3 }

-- {TABLE} 1.3.6.1.4.1.2356.11.2.19.36.7.3.1
lcsSetupVpnIkev2IkeCfgSplitDnsDomainListsTable OBJECT-TYPE
    SYNTAX     SEQUENCE OF LcsSetupVpnIkev2IkeCfgSplitDnsDomainListsEntry
    MAX-ACCESS not-accessible
    STATUS     current
    DESCRIPTION
            "-- empty --"
    ::= { lcsSetupVpnIkev2IkeCfgSplitDns 1 }

-- {ROW} 1.3.6.1.4.1.2356.11.2.19.36.7.3.1.1
lcsSetupVpnIkev2IkeCfgSplitDnsDomainListsEntry OBJECT-TYPE
    SYNTAX     LcsSetupVpnIkev2IkeCfgSplitDnsDomainListsEntry
    MAX-ACCESS not-accessible
    STATUS     current
    DESCRIPTION
            ""
    INDEX {
            lcsSetupVpnIkev2IkeCfgSplitDnsDomainListsEntryDomainList,
            lcsSetupVpnIkev2IkeCfgSplitDnsDomainListsEntryDomainName
          }
    ::= { lcsSetupVpnIkev2IkeCfgSplitDnsDomainListsTable 1 }

LcsSetupVpnIkev2IkeCfgSplitDnsDomainListsEntry ::= SEQUENCE {
            lcsSetupVpnIkev2IkeCfgSplitDnsDomainListsEntryDomainList DisplayString,
            lcsSetupVpnIkev2IkeCfgSplitDnsDomainListsEntryDomainName DisplayString
    }

-- {COLUMN} 1.3.6.1.4.1.2356.11.2.19.36.7.3.1.1.1
lcsSetupVpnIkev2IkeCfgSplitDnsDomainListsEntryDomainList OBJECT-TYPE
    SYNTAX     DisplayString (SIZE(0..16))
    MAX-ACCESS read-write
    STATUS     current
    DESCRIPTION
            "-- empty --"
    ::= { lcsSetupVpnIkev2IkeCfgSplitDnsDomainListsEntry 1 }

-- {COLUMN} 1.3.6.1.4.1.2356.11.2.19.36.7.3.1.1.2
lcsSetupVpnIkev2IkeCfgSplitDnsDomainListsEntryDomainName OBJECT-TYPE
    SYNTAX     DisplayString (SIZE(0..64))
    MAX-ACCESS read-write
    STATUS     current
    DESCRIPTION
            "-- empty --"
    ::= { lcsSetupVpnIkev2IkeCfgSplitDnsDomainListsEntry 2 }

-- {TABLE} 1.3.6.1.4.1.2356.11.2.19.36.7.3.4
lcsSetupVpnIkev2IkeCfgSplitDnsProfilesTable OBJECT-TYPE
    SYNTAX     SEQUENCE OF LcsSetupVpnIkev2IkeCfgSplitDnsProfilesEntry
    MAX-ACCESS not-accessible
    STATUS     current
    DESCRIPTION
            "-- empty --"
    ::= { lcsSetupVpnIkev2IkeCfgSplitDns 4 }

-- {ROW} 1.3.6.1.4.1.2356.11.2.19.36.7.3.4.1
lcsSetupVpnIkev2IkeCfgSplitDnsProfilesEntry OBJECT-TYPE
    SYNTAX     LcsSetupVpnIkev2IkeCfgSplitDnsProfilesEntry
    MAX-ACCESS not-accessible
    STATUS     current
    DESCRIPTION
            ""
    INDEX {
            lcsSetupVpnIkev2IkeCfgSplitDnsProfilesEntryName
          }
    ::= { lcsSetupVpnIkev2IkeCfgSplitDnsProfilesTable 1 }

LcsSetupVpnIkev2IkeCfgSplitDnsProfilesEntry ::= SEQUENCE {
            lcsSetupVpnIkev2IkeCfgSplitDnsProfilesEntryName DisplayString,
            lcsSetupVpnIkev2IkeCfgSplitDnsProfilesEntrySendDnsForwardings INTEGER,
            lcsSetupVpnIkev2IkeCfgSplitDnsProfilesEntrySendLocalDomain INTEGER,
            lcsSetupVpnIkev2IkeCfgSplitDnsProfilesEntryDomainList DisplayString
    }

-- {COLUMN} 1.3.6.1.4.1.2356.11.2.19.36.7.3.4.1.1
lcsSetupVpnIkev2IkeCfgSplitDnsProfilesEntryName OBJECT-TYPE
    SYNTAX     DisplayString (SIZE(0..16))
    MAX-ACCESS read-write
    STATUS     current
    DESCRIPTION
            "-- empty --"
    ::= { lcsSetupVpnIkev2IkeCfgSplitDnsProfilesEntry 1 }

-- {COLUMN} 1.3.6.1.4.1.2356.11.2.19.36.7.3.4.1.2
lcsSetupVpnIkev2IkeCfgSplitDnsProfilesEntrySendDnsForwardings OBJECT-TYPE
    SYNTAX     INTEGER {
                  eNo (0),
                  eYes (1)
            }
    MAX-ACCESS read-write
    STATUS     current
    DESCRIPTION
            "-- empty --"
    ::= { lcsSetupVpnIkev2IkeCfgSplitDnsProfilesEntry 2 }

-- {COLUMN} 1.3.6.1.4.1.2356.11.2.19.36.7.3.4.1.3
lcsSetupVpnIkev2IkeCfgSplitDnsProfilesEntrySendLocalDomain OBJECT-TYPE
    SYNTAX     INTEGER {
                  eNo (0),
                  eYes (1)
            }
    MAX-ACCESS read-write
    STATUS     current
    DESCRIPTION
            "-- empty --"
    ::= { lcsSetupVpnIkev2IkeCfgSplitDnsProfilesEntry 3 }

-- {COLUMN} 1.3.6.1.4.1.2356.11.2.19.36.7.3.4.1.4
lcsSetupVpnIkev2IkeCfgSplitDnsProfilesEntryDomainList OBJECT-TYPE
    SYNTAX     DisplayString (SIZE(0..16))
    MAX-ACCESS read-write
    STATUS     current
    DESCRIPTION
            "-- empty --"
    ::= { lcsSetupVpnIkev2IkeCfgSplitDnsProfilesEntry 4 }

-- {TABLE} 1.3.6.1.4.1.2356.11.2.19.36.7.4
lcsSetupVpnIkev2IkeCfgClientProfileTable OBJECT-TYPE
    SYNTAX     SEQUENCE OF LcsSetupVpnIkev2IkeCfgClientProfileEntry
    MAX-ACCESS not-accessible
    STATUS     current
    DESCRIPTION
            "-- empty --"
    ::= { lcsSetupVpnIkev2IkeCfg 4 }

-- {ROW} 1.3.6.1.4.1.2356.11.2.19.36.7.4.1
lcsSetupVpnIkev2IkeCfgClientProfileEntry OBJECT-TYPE
    SYNTAX     LcsSetupVpnIkev2IkeCfgClientProfileEntry
    MAX-ACCESS not-accessible
    STATUS     current
    DESCRIPTION
            ""
    INDEX {
            lcsSetupVpnIkev2IkeCfgClientProfileEntryName
          }
    ::= { lcsSetupVpnIkev2IkeCfgClientProfileTable 1 }

LcsSetupVpnIkev2IkeCfgClientProfileEntry ::= SEQUENCE {
            lcsSetupVpnIkev2IkeCfgClientProfileEntryName DisplayString,
            lcsSetupVpnIkev2IkeCfgClientProfileEntryRequestAddress BITS
    }

-- {COLUMN} 1.3.6.1.4.1.2356.11.2.19.36.7.4.1.1
lcsSetupVpnIkev2IkeCfgClientProfileEntryName OBJECT-TYPE
    SYNTAX     DisplayString (SIZE(0..16))
    MAX-ACCESS read-write
    STATUS     current
    DESCRIPTION
            "-- empty --"
    ::= { lcsSetupVpnIkev2IkeCfgClientProfileEntry 1 }

-- {COLUMN} 1.3.6.1.4.1.2356.11.2.19.36.7.4.1.2
lcsSetupVpnIkev2IkeCfgClientProfileEntryRequestAddress OBJECT-TYPE
    SYNTAX     BITS {
                  eIpv6 (30),
                  eIpv4 (31)
            }
    MAX-ACCESS read-write
    STATUS     current
    DESCRIPTION
            "-- empty --"
    ::= { lcsSetupVpnIkev2IkeCfgClientProfileEntry 2 }

-- {SCALAR} 1.3.6.1.4.1.2356.11.2.19.36.8
lcsSetupVpnIkev2Mtu OBJECT-TYPE
    SYNTAX     Integer32 (0..65535)
    MAX-ACCESS read-write
    STATUS     current
    DESCRIPTION
            "-- empty --"
    ::= { lcsSetupVpnIkev2 8 }

-- {NODE} 1.3.6.1.4.1.2356.11.2.19.36.9
lcsSetupVpnIkev2Radius OBJECT IDENTIFIER ::= { lcsSetupVpnIkev2 9 }

-- {NODE} 1.3.6.1.4.1.2356.11.2.19.36.9.1
lcsSetupVpnIkev2RadiusAuthorization OBJECT IDENTIFIER ::= { lcsSetupVpnIkev2Radius 1 }

-- {TABLE} 1.3.6.1.4.1.2356.11.2.19.36.9.1.1
lcsSetupVpnIkev2RadiusAuthorizationServerTable OBJECT-TYPE
    SYNTAX     SEQUENCE OF LcsSetupVpnIkev2RadiusAuthorizationServerEntry
    MAX-ACCESS not-accessible
    STATUS     current
    DESCRIPTION
            "-- empty --"
    ::= { lcsSetupVpnIkev2RadiusAuthorization 1 }

-- {ROW} 1.3.6.1.4.1.2356.11.2.19.36.9.1.1.1
lcsSetupVpnIkev2RadiusAuthorizationServerEntry OBJECT-TYPE
    SYNTAX     LcsSetupVpnIkev2RadiusAuthorizationServerEntry
    MAX-ACCESS not-accessible
    STATUS     current
    DESCRIPTION
            ""
    INDEX {
            lcsSetupVpnIkev2RadiusAuthorizationServerEntryName
          }
    ::= { lcsSetupVpnIkev2RadiusAuthorizationServerTable 1 }

LcsSetupVpnIkev2RadiusAuthorizationServerEntry ::= SEQUENCE {
            lcsSetupVpnIkev2RadiusAuthorizationServerEntryName DisplayString,
            lcsSetupVpnIkev2RadiusAuthorizationServerEntryServerHostname DisplayString,
            lcsSetupVpnIkev2RadiusAuthorizationServerEntryPort Integer32,
            lcsSetupVpnIkev2RadiusAuthorizationServerEntrySecret DisplayString,
            lcsSetupVpnIkev2RadiusAuthorizationServerEntryProtocol INTEGER,
            lcsSetupVpnIkev2RadiusAuthorizationServerEntryLoopbackAddress DisplayString,
            lcsSetupVpnIkev2RadiusAuthorizationServerEntryAttributeValues DisplayString,
            lcsSetupVpnIkev2RadiusAuthorizationServerEntryBackup DisplayString,
            lcsSetupVpnIkev2RadiusAuthorizationServerEntryCoaActive INTEGER
    }

-- {COLUMN} 1.3.6.1.4.1.2356.11.2.19.36.9.1.1.1.1
lcsSetupVpnIkev2RadiusAuthorizationServerEntryName OBJECT-TYPE
    SYNTAX     DisplayString (SIZE(0..31))
    MAX-ACCESS read-write
    STATUS     current
    DESCRIPTION
            "-- empty --"
    ::= { lcsSetupVpnIkev2RadiusAuthorizationServerEntry 1 }

-- {COLUMN} 1.3.6.1.4.1.2356.11.2.19.36.9.1.1.1.2
lcsSetupVpnIkev2RadiusAuthorizationServerEntryServerHostname OBJECT-TYPE
    SYNTAX     DisplayString (SIZE(0..64))
    MAX-ACCESS read-write
    STATUS     current
    DESCRIPTION
            "-- empty --"
    ::= { lcsSetupVpnIkev2RadiusAuthorizationServerEntry 2 }

-- {COLUMN} 1.3.6.1.4.1.2356.11.2.19.36.9.1.1.1.3
lcsSetupVpnIkev2RadiusAuthorizationServerEntryPort OBJECT-TYPE
    SYNTAX     Integer32 (0..65535)
    MAX-ACCESS read-write
    STATUS     current
    DESCRIPTION
            "-- empty --"
    ::= { lcsSetupVpnIkev2RadiusAuthorizationServerEntry 3 }

-- {COLUMN} 1.3.6.1.4.1.2356.11.2.19.36.9.1.1.1.4
lcsSetupVpnIkev2RadiusAuthorizationServerEntrySecret OBJECT-TYPE
    SYNTAX     DisplayString (SIZE(0..64))
    MAX-ACCESS read-write
    STATUS     current
    DESCRIPTION
            "-- empty --"
    ::= { lcsSetupVpnIkev2RadiusAuthorizationServerEntry 4 }

-- {COLUMN} 1.3.6.1.4.1.2356.11.2.19.36.9.1.1.1.6
lcsSetupVpnIkev2RadiusAuthorizationServerEntryProtocol OBJECT-TYPE
    SYNTAX     INTEGER {
                  eRadius (0),
                  eRadsec (1)
            }
    MAX-ACCESS read-write
    STATUS     current
    DESCRIPTION
            "-- empty --"
    ::= { lcsSetupVpnIkev2RadiusAuthorizationServerEntry 6 }

-- {COLUMN} 1.3.6.1.4.1.2356.11.2.19.36.9.1.1.1.7
lcsSetupVpnIkev2RadiusAuthorizationServerEntryLoopbackAddress OBJECT-TYPE
    SYNTAX     DisplayString (SIZE(0..16))
    MAX-ACCESS read-write
    STATUS     current
    DESCRIPTION
            "-- empty --"
    ::= { lcsSetupVpnIkev2RadiusAuthorizationServerEntry 7 }

-- {COLUMN} 1.3.6.1.4.1.2356.11.2.19.36.9.1.1.1.8
lcsSetupVpnIkev2RadiusAuthorizationServerEntryAttributeValues OBJECT-TYPE
    SYNTAX     DisplayString (SIZE(0..251))
    MAX-ACCESS read-write
    STATUS     current
    DESCRIPTION
            "-- empty --"
    ::= { lcsSetupVpnIkev2RadiusAuthorizationServerEntry 8 }

-- {COLUMN} 1.3.6.1.4.1.2356.11.2.19.36.9.1.1.1.9
lcsSetupVpnIkev2RadiusAuthorizationServerEntryBackup OBJECT-TYPE
    SYNTAX     DisplayString (SIZE(0..31))
    MAX-ACCESS read-write
    STATUS     current
    DESCRIPTION
            "-- empty --"
    ::= { lcsSetupVpnIkev2RadiusAuthorizationServerEntry 9 }

-- {COLUMN} 1.3.6.1.4.1.2356.11.2.19.36.9.1.1.1.10
lcsSetupVpnIkev2RadiusAuthorizationServerEntryCoaActive OBJECT-TYPE
    SYNTAX     INTEGER {
                  eNo (0),
                  eYes (1)
            }
    MAX-ACCESS read-write
    STATUS     current
    DESCRIPTION
            "-- empty --"
    ::= { lcsSetupVpnIkev2RadiusAuthorizationServerEntry 10 }

-- {SCALAR} 1.3.6.1.4.1.2356.11.2.19.36.9.1.2
lcsSetupVpnIkev2RadiusAuthorizationPassword OBJECT-TYPE
    SYNTAX     DisplayString (SIZE(0..64))
    MAX-ACCESS read-write
    STATUS     current
    DESCRIPTION
            "-- empty --"
    ::= { lcsSetupVpnIkev2RadiusAuthorization 2 }

-- {NODE} 1.3.6.1.4.1.2356.11.2.19.36.9.2
lcsSetupVpnIkev2RadiusAccounting OBJECT IDENTIFIER ::= { lcsSetupVpnIkev2Radius 2 }

-- {TABLE} 1.3.6.1.4.1.2356.11.2.19.36.9.2.1
lcsSetupVpnIkev2RadiusAccountingServerTable OBJECT-TYPE
    SYNTAX     SEQUENCE OF LcsSetupVpnIkev2RadiusAccountingServerEntry
    MAX-ACCESS not-accessible
    STATUS     current
    DESCRIPTION
            "-- empty --"
    ::= { lcsSetupVpnIkev2RadiusAccounting 1 }

-- {ROW} 1.3.6.1.4.1.2356.11.2.19.36.9.2.1.1
lcsSetupVpnIkev2RadiusAccountingServerEntry OBJECT-TYPE
    SYNTAX     LcsSetupVpnIkev2RadiusAccountingServerEntry
    MAX-ACCESS not-accessible
    STATUS     current
    DESCRIPTION
            ""
    INDEX {
            lcsSetupVpnIkev2RadiusAccountingServerEntryName
          }
    ::= { lcsSetupVpnIkev2RadiusAccountingServerTable 1 }

LcsSetupVpnIkev2RadiusAccountingServerEntry ::= SEQUENCE {
            lcsSetupVpnIkev2RadiusAccountingServerEntryName DisplayString,
            lcsSetupVpnIkev2RadiusAccountingServerEntryServerHostname DisplayString,
            lcsSetupVpnIkev2RadiusAccountingServerEntryPort Integer32,
            lcsSetupVpnIkev2RadiusAccountingServerEntrySecret DisplayString,
            lcsSetupVpnIkev2RadiusAccountingServerEntryProtocol INTEGER,
            lcsSetupVpnIkev2RadiusAccountingServerEntryLoopbackAddress DisplayString,
            lcsSetupVpnIkev2RadiusAccountingServerEntryAttributeValues DisplayString,
            lcsSetupVpnIkev2RadiusAccountingServerEntryBackup DisplayString
    }

-- {COLUMN} 1.3.6.1.4.1.2356.11.2.19.36.9.2.1.1.1
lcsSetupVpnIkev2RadiusAccountingServerEntryName OBJECT-TYPE
    SYNTAX     DisplayString (SIZE(0..31))
    MAX-ACCESS read-write
    STATUS     current
    DESCRIPTION
            "-- empty --"
    ::= { lcsSetupVpnIkev2RadiusAccountingServerEntry 1 }

-- {COLUMN} 1.3.6.1.4.1.2356.11.2.19.36.9.2.1.1.2
lcsSetupVpnIkev2RadiusAccountingServerEntryServerHostname OBJECT-TYPE
    SYNTAX     DisplayString (SIZE(0..64))
    MAX-ACCESS read-write
    STATUS     current
    DESCRIPTION
            "-- empty --"
    ::= { lcsSetupVpnIkev2RadiusAccountingServerEntry 2 }

-- {COLUMN} 1.3.6.1.4.1.2356.11.2.19.36.9.2.1.1.3
lcsSetupVpnIkev2RadiusAccountingServerEntryPort OBJECT-TYPE
    SYNTAX     Integer32 (0..65535)
    MAX-ACCESS read-write
    STATUS     current
    DESCRIPTION
            "-- empty --"
    ::= { lcsSetupVpnIkev2RadiusAccountingServerEntry 3 }

-- {COLUMN} 1.3.6.1.4.1.2356.11.2.19.36.9.2.1.1.4
lcsSetupVpnIkev2RadiusAccountingServerEntrySecret OBJECT-TYPE
    SYNTAX     DisplayString (SIZE(0..64))
    MAX-ACCESS read-write
    STATUS     current
    DESCRIPTION
            "-- empty --"
    ::= { lcsSetupVpnIkev2RadiusAccountingServerEntry 4 }

-- {COLUMN} 1.3.6.1.4.1.2356.11.2.19.36.9.2.1.1.5
lcsSetupVpnIkev2RadiusAccountingServerEntryProtocol OBJECT-TYPE
    SYNTAX     INTEGER {
                  eRadius (0),
                  eRadsec (1)
            }
    MAX-ACCESS read-write
    STATUS     current
    DESCRIPTION
            "-- empty --"
    ::= { lcsSetupVpnIkev2RadiusAccountingServerEntry 5 }

-- {COLUMN} 1.3.6.1.4.1.2356.11.2.19.36.9.2.1.1.6
lcsSetupVpnIkev2RadiusAccountingServerEntryLoopbackAddress OBJECT-TYPE
    SYNTAX     DisplayString (SIZE(0..16))
    MAX-ACCESS read-write
    STATUS     current
    DESCRIPTION
            "-- empty --"
    ::= { lcsSetupVpnIkev2RadiusAccountingServerEntry 6 }

-- {COLUMN} 1.3.6.1.4.1.2356.11.2.19.36.9.2.1.1.7
lcsSetupVpnIkev2RadiusAccountingServerEntryAttributeValues OBJECT-TYPE
    SYNTAX     DisplayString (SIZE(0..251))
    MAX-ACCESS read-write
    STATUS     current
    DESCRIPTION
            "-- empty --"
    ::= { lcsSetupVpnIkev2RadiusAccountingServerEntry 7 }

-- {COLUMN} 1.3.6.1.4.1.2356.11.2.19.36.9.2.1.1.8
lcsSetupVpnIkev2RadiusAccountingServerEntryBackup OBJECT-TYPE
    SYNTAX     DisplayString (SIZE(0..31))
    MAX-ACCESS read-write
    STATUS     current
    DESCRIPTION
            "-- empty --"
    ::= { lcsSetupVpnIkev2RadiusAccountingServerEntry 8 }

-- {SCALAR} 1.3.6.1.4.1.2356.11.2.19.36.9.2.2
lcsSetupVpnIkev2RadiusAccountingInterimInterval OBJECT-TYPE
    SYNTAX     Integer32 (0..2147483647)
    MAX-ACCESS read-write
    STATUS     current
    DESCRIPTION
            "-- empty --"
    ::= { lcsSetupVpnIkev2RadiusAccounting 2 }

-- {SCALAR} 1.3.6.1.4.1.2356.11.2.19.36.10
lcsSetupVpnIkev2CreateRoutesForRasSas OBJECT-TYPE
    SYNTAX     INTEGER {
                  eNo (0),
                  eYes (1)
            }
    MAX-ACCESS read-write
    STATUS     current
    DESCRIPTION
            "-- empty --"
    ::= { lcsSetupVpnIkev2 10 }

-- {TABLE} 1.3.6.1.4.1.2356.11.2.19.36.11
lcsSetupVpnIkev2ExtendedParametersTable OBJECT-TYPE
    SYNTAX     SEQUENCE OF LcsSetupVpnIkev2ExtendedParametersEntry
    MAX-ACCESS not-accessible
    STATUS     current
    DESCRIPTION
            "-- empty --"
    ::= { lcsSetupVpnIkev2 11 }

-- {ROW} 1.3.6.1.4.1.2356.11.2.19.36.11.1
lcsSetupVpnIkev2ExtendedParametersEntry OBJECT-TYPE
    SYNTAX     LcsSetupVpnIkev2ExtendedParametersEntry
    MAX-ACCESS not-accessible
    STATUS     current
    DESCRIPTION
            ""
    INDEX {
            lcsSetupVpnIkev2ExtendedParametersEntryName
          }
    ::= { lcsSetupVpnIkev2ExtendedParametersTable 1 }

LcsSetupVpnIkev2ExtendedParametersEntry ::= SEQUENCE {
            lcsSetupVpnIkev2ExtendedParametersEntryName DisplayString,
            lcsSetupVpnIkev2ExtendedParametersEntryPrfAsSigHash INTEGER
    }

-- {COLUMN} 1.3.6.1.4.1.2356.11.2.19.36.11.1.1
lcsSetupVpnIkev2ExtendedParametersEntryName OBJECT-TYPE
    SYNTAX     DisplayString (SIZE(0..16))
    MAX-ACCESS read-write
    STATUS     current
    DESCRIPTION
            "-- empty --"
    ::= { lcsSetupVpnIkev2ExtendedParametersEntry 1 }

-- {COLUMN} 1.3.6.1.4.1.2356.11.2.19.36.11.1.2
lcsSetupVpnIkev2ExtendedParametersEntryPrfAsSigHash OBJECT-TYPE
    SYNTAX     INTEGER {
                  eNo (0),
                  eYes (1)
            }
    MAX-ACCESS read-write
    STATUS     current
    DESCRIPTION
            "-- empty --"
    ::= { lcsSetupVpnIkev2ExtendedParametersEntry 2 }

-- {SCALAR} 1.3.6.1.4.1.2356.11.2.19.36.12
lcsSetupVpnIkev2CookieChallenge OBJECT-TYPE
    SYNTAX     INTEGER {
                  eOff (0),
                  eAlways (1)
            }
    MAX-ACCESS read-write
    STATUS     current
    DESCRIPTION
            "-- empty --"
    ::= { lcsSetupVpnIkev2 12 }

-- {TABLE} 1.3.6.1.4.1.2356.11.2.19.36.13
lcsSetupVpnIkev2TunnelGroupsTable OBJECT-TYPE
    SYNTAX     SEQUENCE OF LcsSetupVpnIkev2TunnelGroupsEntry
    MAX-ACCESS not-accessible
    STATUS     current
    DESCRIPTION
            "-- empty --"
    ::= { lcsSetupVpnIkev2 13 }

-- {ROW} 1.3.6.1.4.1.2356.11.2.19.36.13.1
lcsSetupVpnIkev2TunnelGroupsEntry OBJECT-TYPE
    SYNTAX     LcsSetupVpnIkev2TunnelGroupsEntry
    MAX-ACCESS not-accessible
    STATUS     current
    DESCRIPTION
            ""
    INDEX {
            lcsSetupVpnIkev2TunnelGroupsEntryGroupName
          }
    ::= { lcsSetupVpnIkev2TunnelGroupsTable 1 }

LcsSetupVpnIkev2TunnelGroupsEntry ::= SEQUENCE {
            lcsSetupVpnIkev2TunnelGroupsEntryGroupName DisplayString,
            lcsSetupVpnIkev2TunnelGroupsEntryPeer1 DisplayString,
            lcsSetupVpnIkev2TunnelGroupsEntryPeer2 DisplayString,
            lcsSetupVpnIkev2TunnelGroupsEntryPeer3 DisplayString,
            lcsSetupVpnIkev2TunnelGroupsEntryPeer4 DisplayString
    }

-- {COLUMN} 1.3.6.1.4.1.2356.11.2.19.36.13.1.1
lcsSetupVpnIkev2TunnelGroupsEntryGroupName OBJECT-TYPE
    SYNTAX     DisplayString (SIZE(0..16))
    MAX-ACCESS read-write
    STATUS     current
    DESCRIPTION
            "-- empty --"
    ::= { lcsSetupVpnIkev2TunnelGroupsEntry 1 }

-- {COLUMN} 1.3.6.1.4.1.2356.11.2.19.36.13.1.2
lcsSetupVpnIkev2TunnelGroupsEntryPeer1 OBJECT-TYPE
    SYNTAX     DisplayString (SIZE(0..16))
    MAX-ACCESS read-write
    STATUS     current
    DESCRIPTION
            "-- empty --"
    ::= { lcsSetupVpnIkev2TunnelGroupsEntry 2 }

-- {COLUMN} 1.3.6.1.4.1.2356.11.2.19.36.13.1.3
lcsSetupVpnIkev2TunnelGroupsEntryPeer2 OBJECT-TYPE
    SYNTAX     DisplayString (SIZE(0..16))
    MAX-ACCESS read-write
    STATUS     current
    DESCRIPTION
            "-- empty --"
    ::= { lcsSetupVpnIkev2TunnelGroupsEntry 3 }

-- {COLUMN} 1.3.6.1.4.1.2356.11.2.19.36.13.1.4
lcsSetupVpnIkev2TunnelGroupsEntryPeer3 OBJECT-TYPE
    SYNTAX     DisplayString (SIZE(0..16))
    MAX-ACCESS read-write
    STATUS     current
    DESCRIPTION
            "-- empty --"
    ::= { lcsSetupVpnIkev2TunnelGroupsEntry 4 }

-- {COLUMN} 1.3.6.1.4.1.2356.11.2.19.36.13.1.5
lcsSetupVpnIkev2TunnelGroupsEntryPeer4 OBJECT-TYPE
    SYNTAX     DisplayString (SIZE(0..16))
    MAX-ACCESS read-write
    STATUS     current
    DESCRIPTION
            "-- empty --"
    ::= { lcsSetupVpnIkev2TunnelGroupsEntry 5 }

-- {SCALAR} 1.3.6.1.4.1.2356.11.2.19.36.14
lcsSetupVpnIkev2EnforcePreSharedKeyRules OBJECT-TYPE
    SYNTAX     INTEGER {
                  eNo (0),
                  eYes (1)
            }
    MAX-ACCESS read-write
    STATUS     current
    DESCRIPTION
            "-- empty --"
    ::= { lcsSetupVpnIkev2 14 }

-- {TABLE} 1.3.6.1.4.1.2356.11.2.19.36.15
lcsSetupVpnIkev2HsvpnProfilesTable OBJECT-TYPE
    SYNTAX     SEQUENCE OF LcsSetupVpnIkev2HsvpnProfilesEntry
    MAX-ACCESS not-accessible
    STATUS     current
    DESCRIPTION
            "-- empty --"
    ::= { lcsSetupVpnIkev2 15 }

-- {ROW} 1.3.6.1.4.1.2356.11.2.19.36.15.1
lcsSetupVpnIkev2HsvpnProfilesEntry OBJECT-TYPE
    SYNTAX     LcsSetupVpnIkev2HsvpnProfilesEntry
    MAX-ACCESS not-accessible
    STATUS     current
    DESCRIPTION
            ""
    INDEX {
            lcsSetupVpnIkev2HsvpnProfilesEntryName
          }
    ::= { lcsSetupVpnIkev2HsvpnProfilesTable 1 }

LcsSetupVpnIkev2HsvpnProfilesEntry ::= SEQUENCE {
            lcsSetupVpnIkev2HsvpnProfilesEntryName DisplayString,
            lcsSetupVpnIkev2HsvpnProfilesEntryRtgTagList DisplayString
    }

-- {COLUMN} 1.3.6.1.4.1.2356.11.2.19.36.15.1.1
lcsSetupVpnIkev2HsvpnProfilesEntryName OBJECT-TYPE
    SYNTAX     DisplayString (SIZE(0..16))
    MAX-ACCESS read-write
    STATUS     current
    DESCRIPTION
            "-- empty --"
    ::= { lcsSetupVpnIkev2HsvpnProfilesEntry 1 }

-- {COLUMN} 1.3.6.1.4.1.2356.11.2.19.36.15.1.2
lcsSetupVpnIkev2HsvpnProfilesEntryRtgTagList OBJECT-TYPE
    SYNTAX     DisplayString (SIZE(0..16))
    MAX-ACCESS read-write
    STATUS     current
    DESCRIPTION
            "-- empty --"
    ::= { lcsSetupVpnIkev2HsvpnProfilesEntry 2 }

-- {NODE} 1.3.6.1.4.1.2356.11.2.19.50
lcsSetupVpnLoadBalancer OBJECT IDENTIFIER ::= { lcsSetupVpn 50 }

-- {SCALAR} 1.3.6.1.4.1.2356.11.2.19.50.1
lcsSetupVpnLoadBalancerOperating OBJECT-TYPE
    SYNTAX     INTEGER {
                  eNo (0),
                  eYes (1)
            }
    MAX-ACCESS read-write
    STATUS     current
    DESCRIPTION
            "-- empty --"
    ::= { lcsSetupVpnLoadBalancer 1 }

-- {TABLE} 1.3.6.1.4.1.2356.11.2.19.50.2
lcsSetupVpnLoadBalancerInstancesTable OBJECT-TYPE
    SYNTAX     SEQUENCE OF LcsSetupVpnLoadBalancerInstancesEntry
    MAX-ACCESS not-accessible
    STATUS     current
    DESCRIPTION
            "-- empty --"
    ::= { lcsSetupVpnLoadBalancer 2 }

-- {ROW} 1.3.6.1.4.1.2356.11.2.19.50.2.1
lcsSetupVpnLoadBalancerInstancesEntry OBJECT-TYPE
    SYNTAX     LcsSetupVpnLoadBalancerInstancesEntry
    MAX-ACCESS not-accessible
    STATUS     current
    DESCRIPTION
            ""
    INDEX {
            lcsSetupVpnLoadBalancerInstancesEntryVrrpId
          }
    ::= { lcsSetupVpnLoadBalancerInstancesTable 1 }

LcsSetupVpnLoadBalancerInstancesEntry ::= SEQUENCE {
            lcsSetupVpnLoadBalancerInstancesEntryVrrpId Integer32,
            lcsSetupVpnLoadBalancerInstancesEntryLocalIpv4RedirectTarget DisplayString,
            lcsSetupVpnLoadBalancerInstancesEntryLocalIpv6RedirectTarget DisplayString,
            lcsSetupVpnLoadBalancerInstancesEntryMessageProfile DisplayString,
            lcsSetupVpnLoadBalancerInstancesEntryRedirectMode INTEGER,
            lcsSetupVpnLoadBalancerInstancesEntryRedirectDestinations INTEGER,
            lcsSetupVpnLoadBalancerInstancesEntryComment DisplayString
    }

-- {COLUMN} 1.3.6.1.4.1.2356.11.2.19.50.2.1.1
lcsSetupVpnLoadBalancerInstancesEntryVrrpId OBJECT-TYPE
    SYNTAX     Integer32 (0..255)
    MAX-ACCESS read-write
    STATUS     current
    DESCRIPTION
            "-- empty --"
    ::= { lcsSetupVpnLoadBalancerInstancesEntry 1 }

-- {COLUMN} 1.3.6.1.4.1.2356.11.2.19.50.2.1.2
lcsSetupVpnLoadBalancerInstancesEntryLocalIpv4RedirectTarget OBJECT-TYPE
    SYNTAX     DisplayString (SIZE(0..63))
    MAX-ACCESS read-write
    STATUS     current
    DESCRIPTION
            "-- empty --"
    ::= { lcsSetupVpnLoadBalancerInstancesEntry 2 }

-- {COLUMN} 1.3.6.1.4.1.2356.11.2.19.50.2.1.3
lcsSetupVpnLoadBalancerInstancesEntryLocalIpv6RedirectTarget OBJECT-TYPE
    SYNTAX     DisplayString (SIZE(0..63))
    MAX-ACCESS read-write
    STATUS     current
    DESCRIPTION
            "-- empty --"
    ::= { lcsSetupVpnLoadBalancerInstancesEntry 3 }

-- {COLUMN} 1.3.6.1.4.1.2356.11.2.19.50.2.1.4
lcsSetupVpnLoadBalancerInstancesEntryMessageProfile OBJECT-TYPE
    SYNTAX     DisplayString (SIZE(0..16))
    MAX-ACCESS read-write
    STATUS     current
    DESCRIPTION
            "-- empty --"
    ::= { lcsSetupVpnLoadBalancerInstancesEntry 4 }

-- {COLUMN} 1.3.6.1.4.1.2356.11.2.19.50.2.1.5
lcsSetupVpnLoadBalancerInstancesEntryRedirectMode OBJECT-TYPE
    SYNTAX     INTEGER {
                  eIkev2Init (1),
                  eIkev2Auth (2)
            }
    MAX-ACCESS read-write
    STATUS     current
    DESCRIPTION
            "-- empty --"
    ::= { lcsSetupVpnLoadBalancerInstancesEntry 5 }

-- {COLUMN} 1.3.6.1.4.1.2356.11.2.19.50.2.1.6
lcsSetupVpnLoadBalancerInstancesEntryRedirectDestinations OBJECT-TYPE
    SYNTAX     INTEGER {
                  eRemoteOnly (1),
                  eLocalOrRemote (2)
            }
    MAX-ACCESS read-write
    STATUS     current
    DESCRIPTION
            "-- empty --"
    ::= { lcsSetupVpnLoadBalancerInstancesEntry 6 }

-- {COLUMN} 1.3.6.1.4.1.2356.11.2.19.50.2.1.7
lcsSetupVpnLoadBalancerInstancesEntryComment OBJECT-TYPE
    SYNTAX     DisplayString (SIZE(0..63))
    MAX-ACCESS read-write
    STATUS     current
    DESCRIPTION
            "-- empty --"
    ::= { lcsSetupVpnLoadBalancerInstancesEntry 7 }

-- {TABLE} 1.3.6.1.4.1.2356.11.2.19.50.3
lcsSetupVpnLoadBalancerMessageProfilesTable OBJECT-TYPE
    SYNTAX     SEQUENCE OF LcsSetupVpnLoadBalancerMessageProfilesEntry
    MAX-ACCESS not-accessible
    STATUS     current
    DESCRIPTION
            "-- empty --"
    ::= { lcsSetupVpnLoadBalancer 3 }

-- {ROW} 1.3.6.1.4.1.2356.11.2.19.50.3.1
lcsSetupVpnLoadBalancerMessageProfilesEntry OBJECT-TYPE
    SYNTAX     LcsSetupVpnLoadBalancerMessageProfilesEntry
    MAX-ACCESS not-accessible
    STATUS     current
    DESCRIPTION
            ""
    INDEX {
            lcsSetupVpnLoadBalancerMessageProfilesEntryProfileName
          }
    ::= { lcsSetupVpnLoadBalancerMessageProfilesTable 1 }

LcsSetupVpnLoadBalancerMessageProfilesEntry ::= SEQUENCE {
            lcsSetupVpnLoadBalancerMessageProfilesEntryProfileName DisplayString,
            lcsSetupVpnLoadBalancerMessageProfilesEntryInterface DisplayString,
            lcsSetupVpnLoadBalancerMessageProfilesEntryAddress DisplayString,
            lcsSetupVpnLoadBalancerMessageProfilesEntryPort Integer32,
            lcsSetupVpnLoadBalancerMessageProfilesEntryInterval Integer32,
            lcsSetupVpnLoadBalancerMessageProfilesEntryHoldtime Integer32,
            lcsSetupVpnLoadBalancerMessageProfilesEntryReplayWindow Integer32,
            lcsSetupVpnLoadBalancerMessageProfilesEntryMaxTimeSkew Integer32,
            lcsSetupVpnLoadBalancerMessageProfilesEntrySecret DisplayString,
            lcsSetupVpnLoadBalancerMessageProfilesEntryCipher INTEGER,
            lcsSetupVpnLoadBalancerMessageProfilesEntryHmac INTEGER,
            lcsSetupVpnLoadBalancerMessageProfilesEntryComment DisplayString
    }

-- {COLUMN} 1.3.6.1.4.1.2356.11.2.19.50.3.1.1
lcsSetupVpnLoadBalancerMessageProfilesEntryProfileName OBJECT-TYPE
    SYNTAX     DisplayString (SIZE(0..16))
    MAX-ACCESS read-write
    STATUS     current
    DESCRIPTION
            "-- empty --"
    ::= { lcsSetupVpnLoadBalancerMessageProfilesEntry 1 }

-- {COLUMN} 1.3.6.1.4.1.2356.11.2.19.50.3.1.2
lcsSetupVpnLoadBalancerMessageProfilesEntryInterface OBJECT-TYPE
    SYNTAX     DisplayString (SIZE(0..16))
    MAX-ACCESS read-write
    STATUS     current
    DESCRIPTION
            "-- empty --"
    ::= { lcsSetupVpnLoadBalancerMessageProfilesEntry 2 }

-- {COLUMN} 1.3.6.1.4.1.2356.11.2.19.50.3.1.3
lcsSetupVpnLoadBalancerMessageProfilesEntryAddress OBJECT-TYPE
    SYNTAX     DisplayString (SIZE(0..15))
    MAX-ACCESS read-write
    STATUS     current
    DESCRIPTION
            "-- empty --"
    ::= { lcsSetupVpnLoadBalancerMessageProfilesEntry 3 }

-- {COLUMN} 1.3.6.1.4.1.2356.11.2.19.50.3.1.4
lcsSetupVpnLoadBalancerMessageProfilesEntryPort OBJECT-TYPE
    SYNTAX     Integer32 (0..65535)
    MAX-ACCESS read-write
    STATUS     current
    DESCRIPTION
            "-- empty --"
    ::= { lcsSetupVpnLoadBalancerMessageProfilesEntry 4 }

-- {COLUMN} 1.3.6.1.4.1.2356.11.2.19.50.3.1.5
lcsSetupVpnLoadBalancerMessageProfilesEntryInterval OBJECT-TYPE
    SYNTAX     Integer32 (0..65535)
    MAX-ACCESS read-write
    STATUS     current
    DESCRIPTION
            "-- empty --"
    ::= { lcsSetupVpnLoadBalancerMessageProfilesEntry 5 }

-- {COLUMN} 1.3.6.1.4.1.2356.11.2.19.50.3.1.6
lcsSetupVpnLoadBalancerMessageProfilesEntryHoldtime OBJECT-TYPE
    SYNTAX     Integer32 (0..65535)
    MAX-ACCESS read-write
    STATUS     current
    DESCRIPTION
            "-- empty --"
    ::= { lcsSetupVpnLoadBalancerMessageProfilesEntry 6 }

-- {COLUMN} 1.3.6.1.4.1.2356.11.2.19.50.3.1.7
lcsSetupVpnLoadBalancerMessageProfilesEntryReplayWindow OBJECT-TYPE
    SYNTAX     Integer32 (0..255)
    MAX-ACCESS read-write
    STATUS     current
    DESCRIPTION
            "-- empty --"
    ::= { lcsSetupVpnLoadBalancerMessageProfilesEntry 7 }

-- {COLUMN} 1.3.6.1.4.1.2356.11.2.19.50.3.1.8
lcsSetupVpnLoadBalancerMessageProfilesEntryMaxTimeSkew OBJECT-TYPE
    SYNTAX     Integer32 (0..255)
    MAX-ACCESS read-write
    STATUS     current
    DESCRIPTION
            "-- empty --"
    ::= { lcsSetupVpnLoadBalancerMessageProfilesEntry 8 }

-- {COLUMN} 1.3.6.1.4.1.2356.11.2.19.50.3.1.9
lcsSetupVpnLoadBalancerMessageProfilesEntrySecret OBJECT-TYPE
    SYNTAX     DisplayString (SIZE(0..32))
    MAX-ACCESS read-write
    STATUS     current
    DESCRIPTION
            "-- empty --"
    ::= { lcsSetupVpnLoadBalancerMessageProfilesEntry 9 }

-- {COLUMN} 1.3.6.1.4.1.2356.11.2.19.50.3.1.10
lcsSetupVpnLoadBalancerMessageProfilesEntryCipher OBJECT-TYPE
    SYNTAX     INTEGER {
                  eNone (0),
                  eAes128Gcm (1),
                  eAes192Gcm (2),
                  eAes256Gcm (3)
            }
    MAX-ACCESS read-write
    STATUS     current
    DESCRIPTION
            "-- empty --"
    ::= { lcsSetupVpnLoadBalancerMessageProfilesEntry 10 }

-- {COLUMN} 1.3.6.1.4.1.2356.11.2.19.50.3.1.11
lcsSetupVpnLoadBalancerMessageProfilesEntryHmac OBJECT-TYPE
    SYNTAX     INTEGER {
                  eNone (0),
                  e96Bits (1),
                  e128Bits (2)
            }
    MAX-ACCESS read-write
    STATUS     current
    DESCRIPTION
            "-- empty --"
    ::= { lcsSetupVpnLoadBalancerMessageProfilesEntry 11 }

-- {COLUMN} 1.3.6.1.4.1.2356.11.2.19.50.3.1.12
lcsSetupVpnLoadBalancerMessageProfilesEntryComment OBJECT-TYPE
    SYNTAX     DisplayString (SIZE(0..63))
    MAX-ACCESS read-write
    STATUS     current
    DESCRIPTION
            "-- empty --"
    ::= { lcsSetupVpnLoadBalancerMessageProfilesEntry 12 }

-- {SCALAR} 1.3.6.1.4.1.2356.11.2.19.50.4
lcsSetupVpnLoadBalancerRedirectToRemotePeers OBJECT-TYPE
    SYNTAX     DisplayString
    MAX-ACCESS read-write
    STATUS     current
    DESCRIPTION
            "-- empty --"
    ::= { lcsSetupVpnLoadBalancer 4 }

-- {NODE} 1.3.6.1.4.1.2356.11.2.19.64
lcsSetupVpnOcspClient OBJECT IDENTIFIER ::= { lcsSetupVpn 64 }

-- {SCALAR} 1.3.6.1.4.1.2356.11.2.19.64.1
lcsSetupVpnOcspClientActive OBJECT-TYPE
    SYNTAX     INTEGER {
                  eNo (0),
                  eYes (1)
            }
    MAX-ACCESS read-write
    STATUS     current
    DESCRIPTION
            ""
    ::= { lcsSetupVpnOcspClient 1 }

-- {TABLE} 1.3.6.1.4.1.2356.11.2.19.65
lcsSetupVpnGatewayGroupsTable OBJECT-TYPE
    SYNTAX     SEQUENCE OF LcsSetupVpnGatewayGroupsEntry
    MAX-ACCESS not-accessible
    STATUS     current
    DESCRIPTION
            "-- empty --"
    ::= { lcsSetupVpn 65 }

-- {ROW} 1.3.6.1.4.1.2356.11.2.19.65.1
lcsSetupVpnGatewayGroupsEntry OBJECT-TYPE
    SYNTAX     LcsSetupVpnGatewayGroupsEntry
    MAX-ACCESS not-accessible
    STATUS     current
    DESCRIPTION
            ""
    INDEX {
            lcsSetupVpnGatewayGroupsEntryGroupName
          }
    ::= { lcsSetupVpnGatewayGroupsTable 1 }

LcsSetupVpnGatewayGroupsEntry ::= SEQUENCE {
            lcsSetupVpnGatewayGroupsEntryGroupName DisplayString,
            lcsSetupVpnGatewayGroupsEntryPriority Integer32,
            lcsSetupVpnGatewayGroupsEntryBeginWith INTEGER,
            lcsSetupVpnGatewayGroupsEntryComment DisplayString
    }

-- {COLUMN} 1.3.6.1.4.1.2356.11.2.19.65.1.1
lcsSetupVpnGatewayGroupsEntryGroupName OBJECT-TYPE
    SYNTAX     DisplayString (SIZE(0..24))
    MAX-ACCESS read-write
    STATUS     current
    DESCRIPTION
            "-- empty --"
    ::= { lcsSetupVpnGatewayGroupsEntry 1 }

-- {COLUMN} 1.3.6.1.4.1.2356.11.2.19.65.1.2
lcsSetupVpnGatewayGroupsEntryPriority OBJECT-TYPE
    SYNTAX     Integer32 (0..65535)
    MAX-ACCESS read-write
    STATUS     current
    DESCRIPTION
            "-- empty --"
    ::= { lcsSetupVpnGatewayGroupsEntry 2 }

-- {COLUMN} 1.3.6.1.4.1.2356.11.2.19.65.1.3
lcsSetupVpnGatewayGroupsEntryBeginWith OBJECT-TYPE
    SYNTAX     INTEGER {
                  eLastUsed (0),
                  eFirst (1),
                  eRandom (2)
            }
    MAX-ACCESS read-write
    STATUS     current
    DESCRIPTION
            "-- empty --"
    ::= { lcsSetupVpnGatewayGroupsEntry 3 }

-- {COLUMN} 1.3.6.1.4.1.2356.11.2.19.65.1.4
lcsSetupVpnGatewayGroupsEntryComment OBJECT-TYPE
    SYNTAX     DisplayString (SIZE(0..64))
    MAX-ACCESS read-write
    STATUS     current
    DESCRIPTION
            "-- empty --"
    ::= { lcsSetupVpnGatewayGroupsEntry 4 }

-- {TABLE} 1.3.6.1.4.1.2356.11.2.19.66
lcsSetupVpnGatewayMappingsTable OBJECT-TYPE
    SYNTAX     SEQUENCE OF LcsSetupVpnGatewayMappingsEntry
    MAX-ACCESS not-accessible
    STATUS     current
    DESCRIPTION
            "-- empty --"
    ::= { lcsSetupVpn 66 }

-- {ROW} 1.3.6.1.4.1.2356.11.2.19.66.1
lcsSetupVpnGatewayMappingsEntry OBJECT-TYPE
    SYNTAX     LcsSetupVpnGatewayMappingsEntry
    MAX-ACCESS not-accessible
    STATUS     current
    DESCRIPTION
            ""
    INDEX {
            lcsSetupVpnGatewayMappingsEntryGroupName,
            lcsSetupVpnGatewayMappingsEntryGateway
          }
    ::= { lcsSetupVpnGatewayMappingsTable 1 }

LcsSetupVpnGatewayMappingsEntry ::= SEQUENCE {
            lcsSetupVpnGatewayMappingsEntryGroupName DisplayString,
            lcsSetupVpnGatewayMappingsEntryGateway DisplayString,
            lcsSetupVpnGatewayMappingsEntryRtgTag Integer32,
            lcsSetupVpnGatewayMappingsEntryComment DisplayString
    }

-- {COLUMN} 1.3.6.1.4.1.2356.11.2.19.66.1.1
lcsSetupVpnGatewayMappingsEntryGroupName OBJECT-TYPE
    SYNTAX     DisplayString (SIZE(0..24))
    MAX-ACCESS read-write
    STATUS     current
    DESCRIPTION
            "-- empty --"
    ::= { lcsSetupVpnGatewayMappingsEntry 1 }

-- {COLUMN} 1.3.6.1.4.1.2356.11.2.19.66.1.2
lcsSetupVpnGatewayMappingsEntryGateway OBJECT-TYPE
    SYNTAX     DisplayString (SIZE(0..64))
    MAX-ACCESS read-write
    STATUS     current
    DESCRIPTION
            "-- empty --"
    ::= { lcsSetupVpnGatewayMappingsEntry 2 }

-- {COLUMN} 1.3.6.1.4.1.2356.11.2.19.66.1.3
lcsSetupVpnGatewayMappingsEntryRtgTag OBJECT-TYPE
    SYNTAX     Integer32 (0..65535)
    MAX-ACCESS read-write
    STATUS     current
    DESCRIPTION
            "-- empty --"
    ::= { lcsSetupVpnGatewayMappingsEntry 3 }

-- {COLUMN} 1.3.6.1.4.1.2356.11.2.19.66.1.4
lcsSetupVpnGatewayMappingsEntryComment OBJECT-TYPE
    SYNTAX     DisplayString (SIZE(0..64))
    MAX-ACCESS read-write
    STATUS     current
    DESCRIPTION
            "-- empty --"
    ::= { lcsSetupVpnGatewayMappingsEntry 4 }

-- {NODE} 1.3.6.1.4.1.2356.11.2.20
lcsSetupLanBridge OBJECT IDENTIFIER ::= { lcsSetup 20 }

-- {SCALAR} 1.3.6.1.4.1.2356.11.2.20.1
lcsSetupLanBridgeProtocolVersion OBJECT-TYPE
    SYNTAX     INTEGER {
                  eNo (0),
                  eYes (1)
            }
    MAX-ACCESS read-write
    STATUS     current
    DESCRIPTION
            ""
    ::= { lcsSetupLanBridge 1 }

-- {SCALAR} 1.3.6.1.4.1.2356.11.2.20.2
lcsSetupLanBridgeBridgePriority OBJECT-TYPE
    SYNTAX     Integer32 (0..65535)
    MAX-ACCESS read-write
    STATUS     current
    DESCRIPTION
            ""
    ::= { lcsSetupLanBridge 2 }

-- {TABLE} 1.3.6.1.4.1.2356.11.2.20.4
lcsSetupLanBridgeEncapsulationTableTable OBJECT-TYPE
    SYNTAX     SEQUENCE OF LcsSetupLanBridgeEncapsulationTableEntry
    MAX-ACCESS not-accessible
    STATUS     current
    DESCRIPTION
            ""
    ::= { lcsSetupLanBridge 4 }

-- {ROW} 1.3.6.1.4.1.2356.11.2.20.4.1
lcsSetupLanBridgeEncapsulationTableEntry OBJECT-TYPE
    SYNTAX     LcsSetupLanBridgeEncapsulationTableEntry
    MAX-ACCESS not-accessible
    STATUS     current
    DESCRIPTION
            ""
    INDEX {
            lcsSetupLanBridgeEncapsulationTableEntryProtocol
          }
    ::= { lcsSetupLanBridgeEncapsulationTableTable 1 }

LcsSetupLanBridgeEncapsulationTableEntry ::= SEQUENCE {
            lcsSetupLanBridgeEncapsulationTableEntryProtocol Integer32,
            lcsSetupLanBridgeEncapsulationTableEntryEncapsulation INTEGER
    }

-- {COLUMN} 1.3.6.1.4.1.2356.11.2.20.4.1.1
lcsSetupLanBridgeEncapsulationTableEntryProtocol OBJECT-TYPE
    SYNTAX     Integer32 (0..65535)
    MAX-ACCESS read-write
    STATUS     current
    DESCRIPTION
            ""
    ::= { lcsSetupLanBridgeEncapsulationTableEntry 1 }

-- {COLUMN} 1.3.6.1.4.1.2356.11.2.20.4.1.2
lcsSetupLanBridgeEncapsulationTableEntryEncapsulation OBJECT-TYPE
    SYNTAX     INTEGER {
                  eEthIi (0),
                  eSnap (1)
            }
    MAX-ACCESS read-write
    STATUS     current
    DESCRIPTION
            ""
    ::= { lcsSetupLanBridgeEncapsulationTableEntry 2 }

-- {SCALAR} 1.3.6.1.4.1.2356.11.2.20.5
lcsSetupLanBridgeMaxAge OBJECT-TYPE
    SYNTAX     Integer32 (0..65535)
    MAX-ACCESS read-write
    STATUS     current
    DESCRIPTION
            ""
    ::= { lcsSetupLanBridge 5 }

-- {SCALAR} 1.3.6.1.4.1.2356.11.2.20.6
lcsSetupLanBridgeHelloTime OBJECT-TYPE
    SYNTAX     Integer32 (0..65535)
    MAX-ACCESS read-write
    STATUS     current
    DESCRIPTION
            ""
    ::= { lcsSetupLanBridge 6 }

-- {SCALAR} 1.3.6.1.4.1.2356.11.2.20.7
lcsSetupLanBridgeForwardDelay OBJECT-TYPE
    SYNTAX     Integer32 (0..65535)
    MAX-ACCESS read-write
    STATUS     current
    DESCRIPTION
            ""
    ::= { lcsSetupLanBridge 7 }

-- {SCALAR} 1.3.6.1.4.1.2356.11.2.20.8
lcsSetupLanBridgeIsolatedMode OBJECT-TYPE
    SYNTAX     INTEGER {
                  eNo (0),
                  eYes (1)
            }
    MAX-ACCESS read-write
    STATUS     current
    DESCRIPTION
            ""
    ::= { lcsSetupLanBridge 8 }

-- {TABLE} 1.3.6.1.4.1.2356.11.2.20.10
lcsSetupLanBridgeProtocolTableTable OBJECT-TYPE
    SYNTAX     SEQUENCE OF LcsSetupLanBridgeProtocolTableEntry
    MAX-ACCESS not-accessible
    STATUS     current
    DESCRIPTION
            ""
    ::= { lcsSetupLanBridge 10 }

-- {ROW} 1.3.6.1.4.1.2356.11.2.20.10.1
lcsSetupLanBridgeProtocolTableEntry OBJECT-TYPE
    SYNTAX     LcsSetupLanBridgeProtocolTableEntry
    MAX-ACCESS not-accessible
    STATUS     current
    DESCRIPTION
            ""
    INDEX {
            lcsSetupLanBridgeProtocolTableEntryName
          }
    ::= { lcsSetupLanBridgeProtocolTableTable 1 }

LcsSetupLanBridgeProtocolTableEntry ::= SEQUENCE {
            lcsSetupLanBridgeProtocolTableEntryName DisplayString,
            lcsSetupLanBridgeProtocolTableEntryProtocol DisplayString,
            lcsSetupLanBridgeProtocolTableEntrySubProtocol Integer32,
            lcsSetupLanBridgeProtocolTableEntryPort Integer32,
            lcsSetupLanBridgeProtocolTableEntryPortEnd Integer32,
            lcsSetupLanBridgeProtocolTableEntryIfcList DisplayString,
            lcsSetupLanBridgeProtocolTableEntryAction INTEGER,
            lcsSetupLanBridgeProtocolTableEntryRedirectIpAddress IpAddress,
            lcsSetupLanBridgeProtocolTableEntryDestMacAddr MacAddress,
            lcsSetupLanBridgeProtocolTableEntryIpNetwork IpAddress,
            lcsSetupLanBridgeProtocolTableEntryIpNetmask IpAddress,
            lcsSetupLanBridgeProtocolTableEntryDhcpSrcMac INTEGER
    }

-- {COLUMN} 1.3.6.1.4.1.2356.11.2.20.10.1.1
lcsSetupLanBridgeProtocolTableEntryName OBJECT-TYPE
    SYNTAX     DisplayString (SIZE(0..15))
    MAX-ACCESS read-write
    STATUS     current
    DESCRIPTION
            ""
    ::= { lcsSetupLanBridgeProtocolTableEntry 1 }

-- {COLUMN} 1.3.6.1.4.1.2356.11.2.20.10.1.2
lcsSetupLanBridgeProtocolTableEntryProtocol OBJECT-TYPE
    SYNTAX     DisplayString (SIZE(0..4))
    MAX-ACCESS read-write
    STATUS     current
    DESCRIPTION
            ""
    ::= { lcsSetupLanBridgeProtocolTableEntry 2 }

-- {COLUMN} 1.3.6.1.4.1.2356.11.2.20.10.1.3
lcsSetupLanBridgeProtocolTableEntrySubProtocol OBJECT-TYPE
    SYNTAX     Integer32 (0..65535)
    MAX-ACCESS read-write
    STATUS     current
    DESCRIPTION
            ""
    ::= { lcsSetupLanBridgeProtocolTableEntry 3 }

-- {COLUMN} 1.3.6.1.4.1.2356.11.2.20.10.1.4
lcsSetupLanBridgeProtocolTableEntryPort OBJECT-TYPE
    SYNTAX     Integer32 (0..65535)
    MAX-ACCESS read-write
    STATUS     current
    DESCRIPTION
            ""
    ::= { lcsSetupLanBridgeProtocolTableEntry 4 }

-- {COLUMN} 1.3.6.1.4.1.2356.11.2.20.10.1.5
lcsSetupLanBridgeProtocolTableEntryPortEnd OBJECT-TYPE
    SYNTAX     Integer32 (0..65535)
    MAX-ACCESS read-write
    STATUS     current
    DESCRIPTION
            ""
    ::= { lcsSetupLanBridgeProtocolTableEntry 5 }

-- {COLUMN} 1.3.6.1.4.1.2356.11.2.20.10.1.6
lcsSetupLanBridgeProtocolTableEntryIfcList OBJECT-TYPE
    SYNTAX     DisplayString (SIZE(0..251))
    MAX-ACCESS read-write
    STATUS     current
    DESCRIPTION
            ""
    ::= { lcsSetupLanBridgeProtocolTableEntry 6 }

-- {COLUMN} 1.3.6.1.4.1.2356.11.2.20.10.1.7
lcsSetupLanBridgeProtocolTableEntryAction OBJECT-TYPE
    SYNTAX     INTEGER {
                  eDrop (0),
                  ePass (1),
                  eRedirect (2)
            }
    MAX-ACCESS read-write
    STATUS     current
    DESCRIPTION
            ""
    ::= { lcsSetupLanBridgeProtocolTableEntry 7 }

-- {COLUMN} 1.3.6.1.4.1.2356.11.2.20.10.1.8
lcsSetupLanBridgeProtocolTableEntryRedirectIpAddress OBJECT-TYPE
    SYNTAX     IpAddress
    MAX-ACCESS read-write
    STATUS     current
    DESCRIPTION
            ""
    ::= { lcsSetupLanBridgeProtocolTableEntry 8 }

-- {COLUMN} 1.3.6.1.4.1.2356.11.2.20.10.1.9
lcsSetupLanBridgeProtocolTableEntryDestMacAddr OBJECT-TYPE
    SYNTAX     MacAddress
    MAX-ACCESS read-write
    STATUS     current
    DESCRIPTION
            ""
    ::= { lcsSetupLanBridgeProtocolTableEntry 9 }

-- {COLUMN} 1.3.6.1.4.1.2356.11.2.20.10.1.10
lcsSetupLanBridgeProtocolTableEntryIpNetwork OBJECT-TYPE
    SYNTAX     IpAddress
    MAX-ACCESS read-write
    STATUS     current
    DESCRIPTION
            ""
    ::= { lcsSetupLanBridgeProtocolTableEntry 10 }

-- {COLUMN} 1.3.6.1.4.1.2356.11.2.20.10.1.11
lcsSetupLanBridgeProtocolTableEntryIpNetmask OBJECT-TYPE
    SYNTAX     IpAddress
    MAX-ACCESS read-write
    STATUS     current
    DESCRIPTION
            ""
    ::= { lcsSetupLanBridgeProtocolTableEntry 11 }

-- {COLUMN} 1.3.6.1.4.1.2356.11.2.20.10.1.12
lcsSetupLanBridgeProtocolTableEntryDhcpSrcMac OBJECT-TYPE
    SYNTAX     INTEGER {
                  eIrrelevant (0),
                  eNo (1),
                  eYes (2)
            }
    MAX-ACCESS read-write
    STATUS     current
    DESCRIPTION
            ""
    ::= { lcsSetupLanBridgeProtocolTableEntry 12 }

-- {TABLE} 1.3.6.1.4.1.2356.11.2.20.11
lcsSetupLanBridgePortDataTable OBJECT-TYPE
    SYNTAX     SEQUENCE OF LcsSetupLanBridgePortDataEntry
    MAX-ACCESS not-accessible
    STATUS     current
    DESCRIPTION
            ""
    ::= { lcsSetupLanBridge 11 }

-- {ROW} 1.3.6.1.4.1.2356.11.2.20.11.1
lcsSetupLanBridgePortDataEntry OBJECT-TYPE
    SYNTAX     LcsSetupLanBridgePortDataEntry
    MAX-ACCESS not-accessible
    STATUS     current
    DESCRIPTION
            ""
    INDEX {
            lcsSetupLanBridgePortDataEntryPort
          }
    ::= { lcsSetupLanBridgePortDataTable 1 }

LcsSetupLanBridgePortDataEntry ::= SEQUENCE {
            lcsSetupLanBridgePortDataEntryPort DisplayString,
            lcsSetupLanBridgePortDataEntryActive INTEGER,
            lcsSetupLanBridgePortDataEntryBridgeGroup INTEGER,
            lcsSetupLanBridgePortDataEntryDhcpLimit Integer32,
            lcsSetupLanBridgePortDataEntryPointToPointPort INTEGER,
            lcsSetupLanBridgePortDataEntryPrivateMode INTEGER
    }

-- {COLUMN} 1.3.6.1.4.1.2356.11.2.20.11.1.2
lcsSetupLanBridgePortDataEntryPort OBJECT-TYPE
    SYNTAX     DisplayString (SIZE(0..18))
    MAX-ACCESS read-only
    STATUS     current
    DESCRIPTION
            ""
    ::= { lcsSetupLanBridgePortDataEntry 2 }

-- {COLUMN} 1.3.6.1.4.1.2356.11.2.20.11.1.3
lcsSetupLanBridgePortDataEntryActive OBJECT-TYPE
    SYNTAX     INTEGER {
                  eNo (0),
                  eYes (1)
            }
    MAX-ACCESS read-write
    STATUS     current
    DESCRIPTION
            ""
    ::= { lcsSetupLanBridgePortDataEntry 3 }

-- {COLUMN} 1.3.6.1.4.1.2356.11.2.20.11.1.5
lcsSetupLanBridgePortDataEntryBridgeGroup OBJECT-TYPE
    SYNTAX     INTEGER {
                  eBrg1 (0),
                  eBrg2 (1),
                  eBrg3 (2),
                  eBrg4 (3),
                  eBrg5 (4),
                  eBrg6 (5),
                  eBrg7 (6),
                  eBrg8 (7),
                  eNone (255)
            }
    MAX-ACCESS read-write
    STATUS     current
    DESCRIPTION
            ""
    ::= { lcsSetupLanBridgePortDataEntry 5 }

-- {COLUMN} 1.3.6.1.4.1.2356.11.2.20.11.1.6
lcsSetupLanBridgePortDataEntryDhcpLimit OBJECT-TYPE
    SYNTAX     Integer32 (0..255)
    MAX-ACCESS read-write
    STATUS     current
    DESCRIPTION
            ""
    ::= { lcsSetupLanBridgePortDataEntry 6 }

-- {COLUMN} 1.3.6.1.4.1.2356.11.2.20.11.1.7
lcsSetupLanBridgePortDataEntryPointToPointPort OBJECT-TYPE
    SYNTAX     INTEGER {
                  eAuto (0),
                  eForceTrue (1),
                  eForceFalse (2)
            }
    MAX-ACCESS read-write
    STATUS     current
    DESCRIPTION
            ""
    ::= { lcsSetupLanBridgePortDataEntry 7 }

-- {COLUMN} 1.3.6.1.4.1.2356.11.2.20.11.1.9
lcsSetupLanBridgePortDataEntryPrivateMode OBJECT-TYPE
    SYNTAX     INTEGER {
                  eNo (0),
                  eYes (1)
            }
    MAX-ACCESS read-write
    STATUS     current
    DESCRIPTION
            "-- empty --"
    ::= { lcsSetupLanBridgePortDataEntry 9 }

-- {SCALAR} 1.3.6.1.4.1.2356.11.2.20.12
lcsSetupLanBridgeAgingTime OBJECT-TYPE
    SYNTAX     Integer32 (0..2147483647)
    MAX-ACCESS read-write
    STATUS     current
    DESCRIPTION
            ""
    ::= { lcsSetupLanBridge 12 }

-- {TABLE} 1.3.6.1.4.1.2356.11.2.20.13
lcsSetupLanBridgePriorityMappingTable OBJECT-TYPE
    SYNTAX     SEQUENCE OF LcsSetupLanBridgePriorityMappingEntry
    MAX-ACCESS not-accessible
    STATUS     current
    DESCRIPTION
            ""
    ::= { lcsSetupLanBridge 13 }

-- {ROW} 1.3.6.1.4.1.2356.11.2.20.13.1
lcsSetupLanBridgePriorityMappingEntry OBJECT-TYPE
    SYNTAX     LcsSetupLanBridgePriorityMappingEntry
    MAX-ACCESS not-accessible
    STATUS     current
    DESCRIPTION
            ""
    INDEX {
            lcsSetupLanBridgePriorityMappingEntryName
          }
    ::= { lcsSetupLanBridgePriorityMappingTable 1 }

LcsSetupLanBridgePriorityMappingEntry ::= SEQUENCE {
            lcsSetupLanBridgePriorityMappingEntryName DisplayString,
            lcsSetupLanBridgePriorityMappingEntryDscpValue Integer32,
            lcsSetupLanBridgePriorityMappingEntryPriority INTEGER
    }

-- {COLUMN} 1.3.6.1.4.1.2356.11.2.20.13.1.1
lcsSetupLanBridgePriorityMappingEntryName OBJECT-TYPE
    SYNTAX     DisplayString (SIZE(0..16))
    MAX-ACCESS read-write
    STATUS     current
    DESCRIPTION
            ""
    ::= { lcsSetupLanBridgePriorityMappingEntry 1 }

-- {COLUMN} 1.3.6.1.4.1.2356.11.2.20.13.1.2
lcsSetupLanBridgePriorityMappingEntryDscpValue OBJECT-TYPE
    SYNTAX     Integer32 (0..255)
    MAX-ACCESS read-write
    STATUS     current
    DESCRIPTION
            ""
    ::= { lcsSetupLanBridgePriorityMappingEntry 2 }

-- {COLUMN} 1.3.6.1.4.1.2356.11.2.20.13.1.3
lcsSetupLanBridgePriorityMappingEntryPriority OBJECT-TYPE
    SYNTAX     INTEGER {
                  eBestEffort (0),
                  eBackground (1),
                  eTwo (2),
                  eExcellentEffort (3),
                  eControlledLatency (4),
                  eVideo (5),
                  eVoice (6),
                  eNetworkControl (7)
            }
    MAX-ACCESS read-write
    STATUS     current
    DESCRIPTION
            ""
    ::= { lcsSetupLanBridgePriorityMappingEntry 3 }

-- {NODE} 1.3.6.1.4.1.2356.11.2.20.20
lcsSetupLanBridgeSpanningTree OBJECT IDENTIFIER ::= { lcsSetupLanBridge 20 }

-- {SCALAR} 1.3.6.1.4.1.2356.11.2.20.20.1
lcsSetupLanBridgeSpanningTreeOperating OBJECT-TYPE
    SYNTAX     INTEGER {
                  eNo (0),
                  eYes (1)
            }
    MAX-ACCESS read-write
    STATUS     current
    DESCRIPTION
            ""
    ::= { lcsSetupLanBridgeSpanningTree 1 }

-- {SCALAR} 1.3.6.1.4.1.2356.11.2.20.20.2
lcsSetupLanBridgeSpanningTreeBridgePriority OBJECT-TYPE
    SYNTAX     Integer32 (0..65535)
    MAX-ACCESS read-write
    STATUS     current
    DESCRIPTION
            ""
    ::= { lcsSetupLanBridgeSpanningTree 2 }

-- {SCALAR} 1.3.6.1.4.1.2356.11.2.20.20.5
lcsSetupLanBridgeSpanningTreeMaxAge OBJECT-TYPE
    SYNTAX     Integer32 (0..65535)
    MAX-ACCESS read-write
    STATUS     current
    DESCRIPTION
            ""
    ::= { lcsSetupLanBridgeSpanningTree 5 }

-- {SCALAR} 1.3.6.1.4.1.2356.11.2.20.20.6
lcsSetupLanBridgeSpanningTreeHelloTime OBJECT-TYPE
    SYNTAX     Integer32 (0..65535)
    MAX-ACCESS read-write
    STATUS     current
    DESCRIPTION
            ""
    ::= { lcsSetupLanBridgeSpanningTree 6 }

-- {SCALAR} 1.3.6.1.4.1.2356.11.2.20.20.7
lcsSetupLanBridgeSpanningTreeForwardDelay OBJECT-TYPE
    SYNTAX     Integer32 (0..65535)
    MAX-ACCESS read-write
    STATUS     current
    DESCRIPTION
            ""
    ::= { lcsSetupLanBridgeSpanningTree 7 }

-- {TABLE} 1.3.6.1.4.1.2356.11.2.20.20.11
lcsSetupLanBridgeSpanningTreePortDataTable OBJECT-TYPE
    SYNTAX     SEQUENCE OF LcsSetupLanBridgeSpanningTreePortDataEntry
    MAX-ACCESS not-accessible
    STATUS     current
    DESCRIPTION
            ""
    ::= { lcsSetupLanBridgeSpanningTree 11 }

-- {ROW} 1.3.6.1.4.1.2356.11.2.20.20.11.1
lcsSetupLanBridgeSpanningTreePortDataEntry OBJECT-TYPE
    SYNTAX     LcsSetupLanBridgeSpanningTreePortDataEntry
    MAX-ACCESS not-accessible
    STATUS     current
    DESCRIPTION
            ""
    INDEX {
            lcsSetupLanBridgeSpanningTreePortDataEntryPort
          }
    ::= { lcsSetupLanBridgeSpanningTreePortDataTable 1 }

LcsSetupLanBridgeSpanningTreePortDataEntry ::= SEQUENCE {
            lcsSetupLanBridgeSpanningTreePortDataEntryPort DisplayString,
            lcsSetupLanBridgeSpanningTreePortDataEntryPriority Integer32,
            lcsSetupLanBridgeSpanningTreePortDataEntryEdgePort INTEGER,
            lcsSetupLanBridgeSpanningTreePortDataEntryPathCostOverride Integer32
    }

-- {COLUMN} 1.3.6.1.4.1.2356.11.2.20.20.11.1.2
lcsSetupLanBridgeSpanningTreePortDataEntryPort OBJECT-TYPE
    SYNTAX     DisplayString (SIZE(0..18))
    MAX-ACCESS read-only
    STATUS     current
    DESCRIPTION
            ""
    ::= { lcsSetupLanBridgeSpanningTreePortDataEntry 2 }

-- {COLUMN} 1.3.6.1.4.1.2356.11.2.20.20.11.1.4
lcsSetupLanBridgeSpanningTreePortDataEntryPriority OBJECT-TYPE
    SYNTAX     Integer32 (0..255)
    MAX-ACCESS read-write
    STATUS     current
    DESCRIPTION
            ""
    ::= { lcsSetupLanBridgeSpanningTreePortDataEntry 4 }

-- {COLUMN} 1.3.6.1.4.1.2356.11.2.20.20.11.1.6
lcsSetupLanBridgeSpanningTreePortDataEntryEdgePort OBJECT-TYPE
    SYNTAX     INTEGER {
                  eNo (0),
                  eYes (1)
            }
    MAX-ACCESS read-write
    STATUS     current
    DESCRIPTION
            ""
    ::= { lcsSetupLanBridgeSpanningTreePortDataEntry 6 }

-- {COLUMN} 1.3.6.1.4.1.2356.11.2.20.20.11.1.7
lcsSetupLanBridgeSpanningTreePortDataEntryPathCostOverride OBJECT-TYPE
    SYNTAX     Integer32 (0..2147483647)
    MAX-ACCESS read-write
    STATUS     current
    DESCRIPTION
            ""
    ::= { lcsSetupLanBridgeSpanningTreePortDataEntry 7 }

-- {SCALAR} 1.3.6.1.4.1.2356.11.2.20.20.12
lcsSetupLanBridgeSpanningTreeProtocolVersion OBJECT-TYPE
    SYNTAX     INTEGER {
                  eClassic (0),
                  eRapid (1)
            }
    MAX-ACCESS read-write
    STATUS     current
    DESCRIPTION
            ""
    ::= { lcsSetupLanBridgeSpanningTree 12 }

-- {SCALAR} 1.3.6.1.4.1.2356.11.2.20.20.13
lcsSetupLanBridgeSpanningTreeTransmitHoldCount OBJECT-TYPE
    SYNTAX     Integer32 (0..255)
    MAX-ACCESS read-write
    STATUS     current
    DESCRIPTION
            ""
    ::= { lcsSetupLanBridgeSpanningTree 13 }

-- {SCALAR} 1.3.6.1.4.1.2356.11.2.20.20.14
lcsSetupLanBridgeSpanningTreePathCostComputation OBJECT-TYPE
    SYNTAX     INTEGER {
                  eClassic (0),
                  eRapid (1)
            }
    MAX-ACCESS read-write
    STATUS     current
    DESCRIPTION
            ""
    ::= { lcsSetupLanBridgeSpanningTree 14 }

-- {NODE} 1.3.6.1.4.1.2356.11.2.20.30
lcsSetupLanBridgeIgmpSnooping OBJECT IDENTIFIER ::= { lcsSetupLanBridge 30 }

-- {SCALAR} 1.3.6.1.4.1.2356.11.2.20.30.1
lcsSetupLanBridgeIgmpSnoopingOperating OBJECT-TYPE
    SYNTAX     INTEGER {
                  eNo (0),
                  eYes (1),
                  eAuto (2)
            }
    MAX-ACCESS read-write
    STATUS     current
    DESCRIPTION
            ""
    ::= { lcsSetupLanBridgeIgmpSnooping 1 }

-- {TABLE} 1.3.6.1.4.1.2356.11.2.20.30.2
lcsSetupLanBridgeIgmpSnoopingPortSettingsTable OBJECT-TYPE
    SYNTAX     SEQUENCE OF LcsSetupLanBridgeIgmpSnoopingPortSettingsEntry
    MAX-ACCESS not-accessible
    STATUS     current
    DESCRIPTION
            ""
    ::= { lcsSetupLanBridgeIgmpSnooping 2 }

-- {ROW} 1.3.6.1.4.1.2356.11.2.20.30.2.1
lcsSetupLanBridgeIgmpSnoopingPortSettingsEntry OBJECT-TYPE
    SYNTAX     LcsSetupLanBridgeIgmpSnoopingPortSettingsEntry
    MAX-ACCESS not-accessible
    STATUS     current
    DESCRIPTION
            ""
    INDEX {
            lcsSetupLanBridgeIgmpSnoopingPortSettingsEntryPort
          }
    ::= { lcsSetupLanBridgeIgmpSnoopingPortSettingsTable 1 }

LcsSetupLanBridgeIgmpSnoopingPortSettingsEntry ::= SEQUENCE {
            lcsSetupLanBridgeIgmpSnoopingPortSettingsEntryPort DisplayString,
            lcsSetupLanBridgeIgmpSnoopingPortSettingsEntryRouterPort INTEGER
    }

-- {COLUMN} 1.3.6.1.4.1.2356.11.2.20.30.2.1.1
lcsSetupLanBridgeIgmpSnoopingPortSettingsEntryPort OBJECT-TYPE
    SYNTAX     DisplayString (SIZE(0..18))
    MAX-ACCESS read-write
    STATUS     current
    DESCRIPTION
            ""
    ::= { lcsSetupLanBridgeIgmpSnoopingPortSettingsEntry 1 }

-- {COLUMN} 1.3.6.1.4.1.2356.11.2.20.30.2.1.2
lcsSetupLanBridgeIgmpSnoopingPortSettingsEntryRouterPort OBJECT-TYPE
    SYNTAX     INTEGER {
                  eNo (0),
                  eAuto (1),
                  eYes (2)
            }
    MAX-ACCESS read-write
    STATUS     current
    DESCRIPTION
            ""
    ::= { lcsSetupLanBridgeIgmpSnoopingPortSettingsEntry 2 }

-- {SCALAR} 1.3.6.1.4.1.2356.11.2.20.30.3
lcsSetupLanBridgeIgmpSnoopingUnregisteredDataPacketHandling OBJECT-TYPE
    SYNTAX     INTEGER {
                  eRouterPortsOnly (0),
                  eFlood (1),
                  eDiscard (2)
            }
    MAX-ACCESS read-write
    STATUS     current
    DESCRIPTION
            ""
    ::= { lcsSetupLanBridgeIgmpSnooping 3 }

-- {TABLE} 1.3.6.1.4.1.2356.11.2.20.30.4
lcsSetupLanBridgeIgmpSnoopingSimulatedQueriersTable OBJECT-TYPE
    SYNTAX     SEQUENCE OF LcsSetupLanBridgeIgmpSnoopingSimulatedQueriersEntry
    MAX-ACCESS not-accessible
    STATUS     current
    DESCRIPTION
            ""
    ::= { lcsSetupLanBridgeIgmpSnooping 4 }

-- {ROW} 1.3.6.1.4.1.2356.11.2.20.30.4.1
lcsSetupLanBridgeIgmpSnoopingSimulatedQueriersEntry OBJECT-TYPE
    SYNTAX     LcsSetupLanBridgeIgmpSnoopingSimulatedQueriersEntry
    MAX-ACCESS not-accessible
    STATUS     current
    DESCRIPTION
            ""
    INDEX {
            lcsSetupLanBridgeIgmpSnoopingSimulatedQueriersEntryName
          }
    ::= { lcsSetupLanBridgeIgmpSnoopingSimulatedQueriersTable 1 }

LcsSetupLanBridgeIgmpSnoopingSimulatedQueriersEntry ::= SEQUENCE {
            lcsSetupLanBridgeIgmpSnoopingSimulatedQueriersEntryName DisplayString,
            lcsSetupLanBridgeIgmpSnoopingSimulatedQueriersEntryOperating INTEGER,
            lcsSetupLanBridgeIgmpSnoopingSimulatedQueriersEntryBridgeGroup INTEGER,
            lcsSetupLanBridgeIgmpSnoopingSimulatedQueriersEntryVlanId Integer32
    }

-- {COLUMN} 1.3.6.1.4.1.2356.11.2.20.30.4.1.1
lcsSetupLanBridgeIgmpSnoopingSimulatedQueriersEntryName OBJECT-TYPE
    SYNTAX     DisplayString (SIZE(0..8))
    MAX-ACCESS read-write
    STATUS     current
    DESCRIPTION
            ""
    ::= { lcsSetupLanBridgeIgmpSnoopingSimulatedQueriersEntry 1 }

-- {COLUMN} 1.3.6.1.4.1.2356.11.2.20.30.4.1.2
lcsSetupLanBridgeIgmpSnoopingSimulatedQueriersEntryOperating OBJECT-TYPE
    SYNTAX     INTEGER {
                  eNo (0),
                  eYes (1)
            }
    MAX-ACCESS read-write
    STATUS     current
    DESCRIPTION
            ""
    ::= { lcsSetupLanBridgeIgmpSnoopingSimulatedQueriersEntry 2 }

-- {COLUMN} 1.3.6.1.4.1.2356.11.2.20.30.4.1.3
lcsSetupLanBridgeIgmpSnoopingSimulatedQueriersEntryBridgeGroup OBJECT-TYPE
    SYNTAX     INTEGER {
                  eBrg1 (0),
                  eBrg2 (1),
                  eBrg3 (2),
                  eBrg4 (3),
                  eBrg5 (4),
                  eBrg6 (5),
                  eBrg7 (6),
                  eBrg8 (7),
                  eNone (255)
            }
    MAX-ACCESS read-write
    STATUS     current
    DESCRIPTION
            ""
    ::= { lcsSetupLanBridgeIgmpSnoopingSimulatedQueriersEntry 3 }

-- {COLUMN} 1.3.6.1.4.1.2356.11.2.20.30.4.1.4
lcsSetupLanBridgeIgmpSnoopingSimulatedQueriersEntryVlanId OBJECT-TYPE
    SYNTAX     Integer32 (0..65535)
    MAX-ACCESS read-write
    STATUS     current
    DESCRIPTION
            ""
    ::= { lcsSetupLanBridgeIgmpSnoopingSimulatedQueriersEntry 4 }

-- {SCALAR} 1.3.6.1.4.1.2356.11.2.20.30.5
lcsSetupLanBridgeIgmpSnoopingQueryInterval OBJECT-TYPE
    SYNTAX     Integer32 (0..2147483647)
    MAX-ACCESS read-write
    STATUS     current
    DESCRIPTION
            ""
    ::= { lcsSetupLanBridgeIgmpSnooping 5 }

-- {SCALAR} 1.3.6.1.4.1.2356.11.2.20.30.6
lcsSetupLanBridgeIgmpSnoopingQueryResponseInterval OBJECT-TYPE
    SYNTAX     Integer32 (0..2147483647)
    MAX-ACCESS read-write
    STATUS     current
    DESCRIPTION
            ""
    ::= { lcsSetupLanBridgeIgmpSnooping 6 }

-- {SCALAR} 1.3.6.1.4.1.2356.11.2.20.30.7
lcsSetupLanBridgeIgmpSnoopingRobustness OBJECT-TYPE
    SYNTAX     Integer32 (0..2147483647)
    MAX-ACCESS read-write
    STATUS     current
    DESCRIPTION
            ""
    ::= { lcsSetupLanBridgeIgmpSnooping 7 }

-- {TABLE} 1.3.6.1.4.1.2356.11.2.20.30.8
lcsSetupLanBridgeIgmpSnoopingStaticMembersTable OBJECT-TYPE
    SYNTAX     SEQUENCE OF LcsSetupLanBridgeIgmpSnoopingStaticMembersEntry
    MAX-ACCESS not-accessible
    STATUS     current
    DESCRIPTION
            ""
    ::= { lcsSetupLanBridgeIgmpSnooping 8 }

-- {ROW} 1.3.6.1.4.1.2356.11.2.20.30.8.1
lcsSetupLanBridgeIgmpSnoopingStaticMembersEntry OBJECT-TYPE
    SYNTAX     LcsSetupLanBridgeIgmpSnoopingStaticMembersEntry
    MAX-ACCESS not-accessible
    STATUS     current
    DESCRIPTION
            ""
    INDEX {
            lcsSetupLanBridgeIgmpSnoopingStaticMembersEntryAddress,
            lcsSetupLanBridgeIgmpSnoopingStaticMembersEntryVlanId
          }
    ::= { lcsSetupLanBridgeIgmpSnoopingStaticMembersTable 1 }

LcsSetupLanBridgeIgmpSnoopingStaticMembersEntry ::= SEQUENCE {
            lcsSetupLanBridgeIgmpSnoopingStaticMembersEntryAddress IpAddress,
            lcsSetupLanBridgeIgmpSnoopingStaticMembersEntryStaticMembers DisplayString,
            lcsSetupLanBridgeIgmpSnoopingStaticMembersEntryVlanId Integer32,
            lcsSetupLanBridgeIgmpSnoopingStaticMembersEntryAllowLearning INTEGER
    }

-- {COLUMN} 1.3.6.1.4.1.2356.11.2.20.30.8.1.1
lcsSetupLanBridgeIgmpSnoopingStaticMembersEntryAddress OBJECT-TYPE
    SYNTAX     IpAddress
    MAX-ACCESS read-write
    STATUS     current
    DESCRIPTION
            ""
    ::= { lcsSetupLanBridgeIgmpSnoopingStaticMembersEntry 1 }

-- {COLUMN} 1.3.6.1.4.1.2356.11.2.20.30.8.1.2
lcsSetupLanBridgeIgmpSnoopingStaticMembersEntryStaticMembers OBJECT-TYPE
    SYNTAX     DisplayString (SIZE(0..251))
    MAX-ACCESS read-write
    STATUS     current
    DESCRIPTION
            ""
    ::= { lcsSetupLanBridgeIgmpSnoopingStaticMembersEntry 2 }

-- {COLUMN} 1.3.6.1.4.1.2356.11.2.20.30.8.1.3
lcsSetupLanBridgeIgmpSnoopingStaticMembersEntryVlanId OBJECT-TYPE
    SYNTAX     Integer32 (0..65535)
    MAX-ACCESS read-write
    STATUS     current
    DESCRIPTION
            ""
    ::= { lcsSetupLanBridgeIgmpSnoopingStaticMembersEntry 3 }

-- {COLUMN} 1.3.6.1.4.1.2356.11.2.20.30.8.1.4
lcsSetupLanBridgeIgmpSnoopingStaticMembersEntryAllowLearning OBJECT-TYPE
    SYNTAX     INTEGER {
                  eYes (0),
                  eNo (1)
            }
    MAX-ACCESS read-write
    STATUS     current
    DESCRIPTION
            ""
    ::= { lcsSetupLanBridgeIgmpSnoopingStaticMembersEntry 4 }

-- {SCALAR} 1.3.6.1.4.1.2356.11.2.20.30.9
lcsSetupLanBridgeIgmpSnoopingAdvertiseInterval OBJECT-TYPE
    SYNTAX     Integer32 (0..255)
    MAX-ACCESS read-write
    STATUS     current
    DESCRIPTION
            ""
    ::= { lcsSetupLanBridgeIgmpSnooping 9 }

-- {TABLE} 1.3.6.1.4.1.2356.11.2.20.40
lcsSetupLanBridgeDhcpSnoopingTable OBJECT-TYPE
    SYNTAX     SEQUENCE OF LcsSetupLanBridgeDhcpSnoopingEntry
    MAX-ACCESS not-accessible
    STATUS     current
    DESCRIPTION
            "-- empty --"
    ::= { lcsSetupLanBridge 40 }

-- {ROW} 1.3.6.1.4.1.2356.11.2.20.40.1
lcsSetupLanBridgeDhcpSnoopingEntry OBJECT-TYPE
    SYNTAX     LcsSetupLanBridgeDhcpSnoopingEntry
    MAX-ACCESS not-accessible
    STATUS     current
    DESCRIPTION
            ""
    INDEX {
            lcsSetupLanBridgeDhcpSnoopingEntryPort
          }
    ::= { lcsSetupLanBridgeDhcpSnoopingTable 1 }

LcsSetupLanBridgeDhcpSnoopingEntry ::= SEQUENCE {
            lcsSetupLanBridgeDhcpSnoopingEntryPort DisplayString,
            lcsSetupLanBridgeDhcpSnoopingEntryAddAgentInfo INTEGER,
            lcsSetupLanBridgeDhcpSnoopingEntryTreatExistingAgentInfo INTEGER,
            lcsSetupLanBridgeDhcpSnoopingEntryRemoteId DisplayString,
            lcsSetupLanBridgeDhcpSnoopingEntryCircuitId DisplayString
    }

-- {COLUMN} 1.3.6.1.4.1.2356.11.2.20.40.1.1
lcsSetupLanBridgeDhcpSnoopingEntryPort OBJECT-TYPE
    SYNTAX     DisplayString (SIZE(0..18))
    MAX-ACCESS read-only
    STATUS     current
    DESCRIPTION
            "-- empty --"
    ::= { lcsSetupLanBridgeDhcpSnoopingEntry 1 }

-- {COLUMN} 1.3.6.1.4.1.2356.11.2.20.40.1.2
lcsSetupLanBridgeDhcpSnoopingEntryAddAgentInfo OBJECT-TYPE
    SYNTAX     INTEGER {
                  eNo (0),
                  eYes (1)
            }
    MAX-ACCESS read-write
    STATUS     current
    DESCRIPTION
            "-- empty --"
    ::= { lcsSetupLanBridgeDhcpSnoopingEntry 2 }

-- {COLUMN} 1.3.6.1.4.1.2356.11.2.20.40.1.3
lcsSetupLanBridgeDhcpSnoopingEntryTreatExistingAgentInfo OBJECT-TYPE
    SYNTAX     INTEGER {
                  eKeep (0),
                  eReplace (1),
                  eDiscard (2)
            }
    MAX-ACCESS read-write
    STATUS     current
    DESCRIPTION
            "-- empty --"
    ::= { lcsSetupLanBridgeDhcpSnoopingEntry 3 }

-- {COLUMN} 1.3.6.1.4.1.2356.11.2.20.40.1.4
lcsSetupLanBridgeDhcpSnoopingEntryRemoteId OBJECT-TYPE
    SYNTAX     DisplayString (SIZE(0..30))
    MAX-ACCESS read-write
    STATUS     current
    DESCRIPTION
            "-- empty --"
    ::= { lcsSetupLanBridgeDhcpSnoopingEntry 4 }

-- {COLUMN} 1.3.6.1.4.1.2356.11.2.20.40.1.5
lcsSetupLanBridgeDhcpSnoopingEntryCircuitId OBJECT-TYPE
    SYNTAX     DisplayString (SIZE(0..30))
    MAX-ACCESS read-write
    STATUS     current
    DESCRIPTION
            "-- empty --"
    ::= { lcsSetupLanBridgeDhcpSnoopingEntry 5 }

-- {TABLE} 1.3.6.1.4.1.2356.11.2.20.41
lcsSetupLanBridgeDhcpv6SnoopingTable OBJECT-TYPE
    SYNTAX     SEQUENCE OF LcsSetupLanBridgeDhcpv6SnoopingEntry
    MAX-ACCESS not-accessible
    STATUS     current
    DESCRIPTION
            "-- empty --"
    ::= { lcsSetupLanBridge 41 }

-- {ROW} 1.3.6.1.4.1.2356.11.2.20.41.1
lcsSetupLanBridgeDhcpv6SnoopingEntry OBJECT-TYPE
    SYNTAX     LcsSetupLanBridgeDhcpv6SnoopingEntry
    MAX-ACCESS not-accessible
    STATUS     current
    DESCRIPTION
            ""
    INDEX {
            lcsSetupLanBridgeDhcpv6SnoopingEntryPort
          }
    ::= { lcsSetupLanBridgeDhcpv6SnoopingTable 1 }

LcsSetupLanBridgeDhcpv6SnoopingEntry ::= SEQUENCE {
            lcsSetupLanBridgeDhcpv6SnoopingEntryPort DisplayString,
            lcsSetupLanBridgeDhcpv6SnoopingEntryOrientation INTEGER,
            lcsSetupLanBridgeDhcpv6SnoopingEntryType INTEGER,
            lcsSetupLanBridgeDhcpv6SnoopingEntryRemoteId DisplayString,
            lcsSetupLanBridgeDhcpv6SnoopingEntryInterfaceId DisplayString,
            lcsSetupLanBridgeDhcpv6SnoopingEntryServerAddress DisplayString
    }

-- {COLUMN} 1.3.6.1.4.1.2356.11.2.20.41.1.1
lcsSetupLanBridgeDhcpv6SnoopingEntryPort OBJECT-TYPE
    SYNTAX     DisplayString (SIZE(0..18))
    MAX-ACCESS read-only
    STATUS     current
    DESCRIPTION
            "-- empty --"
    ::= { lcsSetupLanBridgeDhcpv6SnoopingEntry 1 }

-- {COLUMN} 1.3.6.1.4.1.2356.11.2.20.41.1.2
lcsSetupLanBridgeDhcpv6SnoopingEntryOrientation OBJECT-TYPE
    SYNTAX     INTEGER {
                  eNetworkFacing (0),
                  eClientFacing (1)
            }
    MAX-ACCESS read-write
    STATUS     current
    DESCRIPTION
            "-- empty --"
    ::= { lcsSetupLanBridgeDhcpv6SnoopingEntry 2 }

-- {COLUMN} 1.3.6.1.4.1.2356.11.2.20.41.1.3
lcsSetupLanBridgeDhcpv6SnoopingEntryType OBJECT-TYPE
    SYNTAX     INTEGER {
                  eTrusted (0),
                  eUntrusted (1)
            }
    MAX-ACCESS read-write
    STATUS     current
    DESCRIPTION
            "-- empty --"
    ::= { lcsSetupLanBridgeDhcpv6SnoopingEntry 3 }

-- {COLUMN} 1.3.6.1.4.1.2356.11.2.20.41.1.4
lcsSetupLanBridgeDhcpv6SnoopingEntryRemoteId OBJECT-TYPE
    SYNTAX     DisplayString (SIZE(0..30))
    MAX-ACCESS read-write
    STATUS     current
    DESCRIPTION
            "-- empty --"
    ::= { lcsSetupLanBridgeDhcpv6SnoopingEntry 4 }

-- {COLUMN} 1.3.6.1.4.1.2356.11.2.20.41.1.5
lcsSetupLanBridgeDhcpv6SnoopingEntryInterfaceId OBJECT-TYPE
    SYNTAX     DisplayString (SIZE(0..30))
    MAX-ACCESS read-write
    STATUS     current
    DESCRIPTION
            "-- empty --"
    ::= { lcsSetupLanBridgeDhcpv6SnoopingEntry 5 }

-- {COLUMN} 1.3.6.1.4.1.2356.11.2.20.41.1.6
lcsSetupLanBridgeDhcpv6SnoopingEntryServerAddress OBJECT-TYPE
    SYNTAX     DisplayString (SIZE(0..39))
    MAX-ACCESS read-write
    STATUS     current
    DESCRIPTION
            "-- empty --"
    ::= { lcsSetupLanBridgeDhcpv6SnoopingEntry 6 }

-- {TABLE} 1.3.6.1.4.1.2356.11.2.20.42
lcsSetupLanBridgeRaSnoopingTable OBJECT-TYPE
    SYNTAX     SEQUENCE OF LcsSetupLanBridgeRaSnoopingEntry
    MAX-ACCESS not-accessible
    STATUS     current
    DESCRIPTION
            "-- empty --"
    ::= { lcsSetupLanBridge 42 }

-- {ROW} 1.3.6.1.4.1.2356.11.2.20.42.1
lcsSetupLanBridgeRaSnoopingEntry OBJECT-TYPE
    SYNTAX     LcsSetupLanBridgeRaSnoopingEntry
    MAX-ACCESS not-accessible
    STATUS     current
    DESCRIPTION
            ""
    INDEX {
            lcsSetupLanBridgeRaSnoopingEntryPort
          }
    ::= { lcsSetupLanBridgeRaSnoopingTable 1 }

LcsSetupLanBridgeRaSnoopingEntry ::= SEQUENCE {
            lcsSetupLanBridgeRaSnoopingEntryPort DisplayString,
            lcsSetupLanBridgeRaSnoopingEntryType INTEGER,
            lcsSetupLanBridgeRaSnoopingEntryRouterAddress DisplayString
    }

-- {COLUMN} 1.3.6.1.4.1.2356.11.2.20.42.1.1
lcsSetupLanBridgeRaSnoopingEntryPort OBJECT-TYPE
    SYNTAX     DisplayString (SIZE(0..18))
    MAX-ACCESS read-only
    STATUS     current
    DESCRIPTION
            "-- empty --"
    ::= { lcsSetupLanBridgeRaSnoopingEntry 1 }

-- {COLUMN} 1.3.6.1.4.1.2356.11.2.20.42.1.3
lcsSetupLanBridgeRaSnoopingEntryType OBJECT-TYPE
    SYNTAX     INTEGER {
                  eRouter (0),
                  eClient (1)
            }
    MAX-ACCESS read-write
    STATUS     current
    DESCRIPTION
            "-- empty --"
    ::= { lcsSetupLanBridgeRaSnoopingEntry 3 }

-- {COLUMN} 1.3.6.1.4.1.2356.11.2.20.42.1.4
lcsSetupLanBridgeRaSnoopingEntryRouterAddress OBJECT-TYPE
    SYNTAX     DisplayString (SIZE(0..39))
    MAX-ACCESS read-write
    STATUS     current
    DESCRIPTION
            "-- empty --"
    ::= { lcsSetupLanBridgeRaSnoopingEntry 4 }

-- {TABLE} 1.3.6.1.4.1.2356.11.2.20.43
lcsSetupLanBridgePppoeSnoopingTable OBJECT-TYPE
    SYNTAX     SEQUENCE OF LcsSetupLanBridgePppoeSnoopingEntry
    MAX-ACCESS not-accessible
    STATUS     current
    DESCRIPTION
            "-- empty --"
    ::= { lcsSetupLanBridge 43 }

-- {ROW} 1.3.6.1.4.1.2356.11.2.20.43.1
lcsSetupLanBridgePppoeSnoopingEntry OBJECT-TYPE
    SYNTAX     LcsSetupLanBridgePppoeSnoopingEntry
    MAX-ACCESS not-accessible
    STATUS     current
    DESCRIPTION
            ""
    INDEX {
            lcsSetupLanBridgePppoeSnoopingEntryPort
          }
    ::= { lcsSetupLanBridgePppoeSnoopingTable 1 }

LcsSetupLanBridgePppoeSnoopingEntry ::= SEQUENCE {
            lcsSetupLanBridgePppoeSnoopingEntryPort DisplayString,
            lcsSetupLanBridgePppoeSnoopingEntryAddAgentInfo INTEGER,
            lcsSetupLanBridgePppoeSnoopingEntryRemoteId DisplayString,
            lcsSetupLanBridgePppoeSnoopingEntryCircuitId DisplayString,
            lcsSetupLanBridgePppoeSnoopingEntryDiscardServerPackets INTEGER
    }

-- {COLUMN} 1.3.6.1.4.1.2356.11.2.20.43.1.1
lcsSetupLanBridgePppoeSnoopingEntryPort OBJECT-TYPE
    SYNTAX     DisplayString (SIZE(0..18))
    MAX-ACCESS read-only
    STATUS     current
    DESCRIPTION
            "-- empty --"
    ::= { lcsSetupLanBridgePppoeSnoopingEntry 1 }

-- {COLUMN} 1.3.6.1.4.1.2356.11.2.20.43.1.2
lcsSetupLanBridgePppoeSnoopingEntryAddAgentInfo OBJECT-TYPE
    SYNTAX     INTEGER {
                  eNo (0),
                  eYes (1)
            }
    MAX-ACCESS read-write
    STATUS     current
    DESCRIPTION
            "-- empty --"
    ::= { lcsSetupLanBridgePppoeSnoopingEntry 2 }

-- {COLUMN} 1.3.6.1.4.1.2356.11.2.20.43.1.3
lcsSetupLanBridgePppoeSnoopingEntryRemoteId OBJECT-TYPE
    SYNTAX     DisplayString (SIZE(0..30))
    MAX-ACCESS read-write
    STATUS     current
    DESCRIPTION
            "-- empty --"
    ::= { lcsSetupLanBridgePppoeSnoopingEntry 3 }

-- {COLUMN} 1.3.6.1.4.1.2356.11.2.20.43.1.4
lcsSetupLanBridgePppoeSnoopingEntryCircuitId OBJECT-TYPE
    SYNTAX     DisplayString (SIZE(0..30))
    MAX-ACCESS read-write
    STATUS     current
    DESCRIPTION
            "-- empty --"
    ::= { lcsSetupLanBridgePppoeSnoopingEntry 4 }

-- {COLUMN} 1.3.6.1.4.1.2356.11.2.20.43.1.5
lcsSetupLanBridgePppoeSnoopingEntryDiscardServerPackets OBJECT-TYPE
    SYNTAX     INTEGER {
                  eNo (0),
                  eYes (1)
            }
    MAX-ACCESS read-write
    STATUS     current
    DESCRIPTION
            "-- empty --"
    ::= { lcsSetupLanBridgePppoeSnoopingEntry 5 }

-- {NODE} 1.3.6.1.4.1.2356.11.2.21
lcsSetupHttp OBJECT IDENTIFIER ::= { lcsSetup 21 }

-- {SCALAR} 1.3.6.1.4.1.2356.11.2.21.1
lcsSetupHttpDocumentRoot OBJECT-TYPE
    SYNTAX     DisplayString (SIZE(0..99))
    MAX-ACCESS read-write
    STATUS     current
    DESCRIPTION
            ""
    ::= { lcsSetupHttp 1 }

-- {SCALAR} 1.3.6.1.4.1.2356.11.2.21.2
lcsSetupHttpUseCss OBJECT-TYPE
    SYNTAX     INTEGER {
                  eNo (0),
                  eYes (1)
            }
    MAX-ACCESS read-write
    STATUS     current
    DESCRIPTION
            ""
    ::= { lcsSetupHttp 2 }

-- {SCALAR} 1.3.6.1.4.1.2356.11.2.21.3
lcsSetupHttpFontFamily OBJECT-TYPE
    SYNTAX     DisplayString (SIZE(0..39))
    MAX-ACCESS read-write
    STATUS     current
    DESCRIPTION
            ""
    ::= { lcsSetupHttp 3 }

-- {SCALAR} 1.3.6.1.4.1.2356.11.2.21.5
lcsSetupHttpPageHeaders OBJECT-TYPE
    SYNTAX     INTEGER {
                  eImages (0),
                  eTexts (1)
            }
    MAX-ACCESS read-write
    STATUS     current
    DESCRIPTION
            ""
    ::= { lcsSetupHttp 5 }

-- {SCALAR} 1.3.6.1.4.1.2356.11.2.21.6
lcsSetupHttpErrorPageStyle OBJECT-TYPE
    SYNTAX     INTEGER {
                  eStandard (0),
                  eNifty (1)
            }
    MAX-ACCESS read-write
    STATUS     current
    DESCRIPTION
            ""
    ::= { lcsSetupHttp 6 }

-- {SCALAR} 1.3.6.1.4.1.2356.11.2.21.7
lcsSetupHttpPort OBJECT-TYPE
    SYNTAX     Integer32 (0..65535)
    MAX-ACCESS read-write
    STATUS     current
    DESCRIPTION
            ""
    ::= { lcsSetupHttp 7 }

-- {SCALAR} 1.3.6.1.4.1.2356.11.2.21.8
lcsSetupHttpSslPort OBJECT-TYPE
    SYNTAX     Integer32 (0..65535)
    MAX-ACCESS read-write
    STATUS     current
    DESCRIPTION
            ""
    ::= { lcsSetupHttp 8 }

-- {SCALAR} 1.3.6.1.4.1.2356.11.2.21.9
lcsSetupHttpMaxTunnelConnections OBJECT-TYPE
    SYNTAX     Integer32 (0..255)
    MAX-ACCESS read-write
    STATUS     current
    DESCRIPTION
            ""
    ::= { lcsSetupHttp 9 }

-- {SCALAR} 1.3.6.1.4.1.2356.11.2.21.10
lcsSetupHttpTunnelIdleTimeout OBJECT-TYPE
    SYNTAX     Integer32 (0..2147483647)
    MAX-ACCESS read-write
    STATUS     current
    DESCRIPTION
            ""
    ::= { lcsSetupHttp 10 }

-- {SCALAR} 1.3.6.1.4.1.2356.11.2.21.11
lcsSetupHttpSessionTimeout OBJECT-TYPE
    SYNTAX     Integer32 (0..2147483647)
    MAX-ACCESS read-write
    STATUS     current
    DESCRIPTION
            ""
    ::= { lcsSetupHttp 11 }

-- {SCALAR} 1.3.6.1.4.1.2356.11.2.21.13
lcsSetupHttpStandardDesign OBJECT-TYPE
    SYNTAX     INTEGER {
                  eNormalDesign (0),
                  eDesignForSmallResolutions (1),
                  eDesignWithHighContrast (2)
            }
    MAX-ACCESS read-write
    STATUS     current
    DESCRIPTION
            ""
    ::= { lcsSetupHttp 13 }

-- {TABLE} 1.3.6.1.4.1.2356.11.2.21.14
lcsSetupHttpShowDeviceInformationTable OBJECT-TYPE
    SYNTAX     SEQUENCE OF LcsSetupHttpShowDeviceInformationEntry
    MAX-ACCESS not-accessible
    STATUS     current
    DESCRIPTION
            ""
    ::= { lcsSetupHttp 14 }

-- {ROW} 1.3.6.1.4.1.2356.11.2.21.14.1
lcsSetupHttpShowDeviceInformationEntry OBJECT-TYPE
    SYNTAX     LcsSetupHttpShowDeviceInformationEntry
    MAX-ACCESS not-accessible
    STATUS     current
    DESCRIPTION
            ""
    INDEX {
            lcsSetupHttpShowDeviceInformationEntryDeviceInformation
          }
    ::= { lcsSetupHttpShowDeviceInformationTable 1 }

LcsSetupHttpShowDeviceInformationEntry ::= SEQUENCE {
            lcsSetupHttpShowDeviceInformationEntryDeviceInformation INTEGER,
            lcsSetupHttpShowDeviceInformationEntryPosition Integer32
    }

-- {COLUMN} 1.3.6.1.4.1.2356.11.2.21.14.1.1
lcsSetupHttpShowDeviceInformationEntryDeviceInformation OBJECT-TYPE
    SYNTAX     INTEGER {
                  eCpu (1),
                  eMemory (2),
                  eWlan (3),
                  eP2pConnections (4),
                  eEthernetPorts (5),
                  eTroughputEthernet (6),
                  eMobileModemInterface (7),
                  eRouter (8),
                  eFirewall (9),
                  eDhcp (10),
                  eDns (11),
                  eVpn (12),
                  eAdsl (13),
                  eIsdn (14),
                  eDSLDSLoL (15),
                  eScepCa (16),
                  eWlanController (17),
                  eTime (18),
                  eIpv4Addresses (19),
                  eOperatingTime (20),
                  eVdsl (21),
                  eConnections (22),
                  eIpv6Addresses (23),
                  eIpv6Prefixes (24),
                  eDhcpv6Client (25),
                  eDhcpv6Server (26),
                  eTr069 (28),
                  eVoiceCallManager (29),
                  eLicenseStatus (30),
                  eSysteminfo (31),
                  eFirmware (32)
            }
    MAX-ACCESS read-write
    STATUS     current
    DESCRIPTION
            ""
    ::= { lcsSetupHttpShowDeviceInformationEntry 1 }

-- {COLUMN} 1.3.6.1.4.1.2356.11.2.21.14.1.2
lcsSetupHttpShowDeviceInformationEntryPosition OBJECT-TYPE
    SYNTAX     Integer32 (0..2147483647)
    MAX-ACCESS read-write
    STATUS     current
    DESCRIPTION
            ""
    ::= { lcsSetupHttpShowDeviceInformationEntry 2 }

-- {SCALAR} 1.3.6.1.4.1.2356.11.2.21.15
lcsSetupHttpHttpCompression OBJECT-TYPE
    SYNTAX     INTEGER {
                  eActivated (0),
                  eOnlyForWan (1),
                  eDeactivated (2)
            }
    MAX-ACCESS read-write
    STATUS     current
    DESCRIPTION
            ""
    ::= { lcsSetupHttp 15 }

-- {TABLE} 1.3.6.1.4.1.2356.11.2.21.16
lcsSetupHttpKeepServerPortsOpenTable OBJECT-TYPE
    SYNTAX     SEQUENCE OF LcsSetupHttpKeepServerPortsOpenEntry
    MAX-ACCESS not-accessible
    STATUS     current
    DESCRIPTION
            ""
    ::= { lcsSetupHttp 16 }

-- {ROW} 1.3.6.1.4.1.2356.11.2.21.16.1
lcsSetupHttpKeepServerPortsOpenEntry OBJECT-TYPE
    SYNTAX     LcsSetupHttpKeepServerPortsOpenEntry
    MAX-ACCESS not-accessible
    STATUS     current
    DESCRIPTION
            ""
    INDEX {
            lcsSetupHttpKeepServerPortsOpenEntryIfc
          }
    ::= { lcsSetupHttpKeepServerPortsOpenTable 1 }

LcsSetupHttpKeepServerPortsOpenEntry ::= SEQUENCE {
            lcsSetupHttpKeepServerPortsOpenEntryIfc INTEGER,
            lcsSetupHttpKeepServerPortsOpenEntryKeepServerPortsOpen INTEGER
    }

-- {COLUMN} 1.3.6.1.4.1.2356.11.2.21.16.1.1
lcsSetupHttpKeepServerPortsOpenEntryIfc OBJECT-TYPE
    SYNTAX     INTEGER {
                  eLan (1),
                  eWan (2),
                  eWlan (4)
            }
    MAX-ACCESS read-only
    STATUS     current
    DESCRIPTION
            ""
    ::= { lcsSetupHttpKeepServerPortsOpenEntry 1 }

-- {COLUMN} 1.3.6.1.4.1.2356.11.2.21.16.1.2
lcsSetupHttpKeepServerPortsOpenEntryKeepServerPortsOpen OBJECT-TYPE
    SYNTAX     INTEGER {
                  eAutomatic (0),
                  eEnabled (1),
                  eDisabled (2)
            }
    MAX-ACCESS read-write
    STATUS     current
    DESCRIPTION
            ""
    ::= { lcsSetupHttpKeepServerPortsOpenEntry 2 }

-- {SCALAR} 1.3.6.1.4.1.2356.11.2.21.17
lcsSetupHttpUseUserProvidedCertificate OBJECT-TYPE
    SYNTAX     INTEGER {
                  eNo (0),
                  eYes (1)
            }
    MAX-ACCESS read-write
    STATUS     current
    DESCRIPTION
            ""
    ::= { lcsSetupHttp 17 }

-- {SCALAR} 1.3.6.1.4.1.2356.11.2.21.18
lcsSetupHttpSslVersions OBJECT-TYPE
    SYNTAX     BITS {
                  eTlsv12 (4),
                  eTlsv11 (5),
                  eTlsv1 (6),
                  eSslv3 (7)
            }
    MAX-ACCESS read-write
    STATUS     current
    DESCRIPTION
            "-- empty --"
    ::= { lcsSetupHttp 18 }

-- {NODE} 1.3.6.1.4.1.2356.11.2.21.20
lcsSetupHttpRolloutWizard OBJECT IDENTIFIER ::= { lcsSetupHttp 20 }

-- {SCALAR} 1.3.6.1.4.1.2356.11.2.21.20.1
lcsSetupHttpRolloutWizardOperating OBJECT-TYPE
    SYNTAX     INTEGER {
                  eNo (0),
                  eYes (1)
            }
    MAX-ACCESS read-write
    STATUS     current
    DESCRIPTION
            ""
    ::= { lcsSetupHttpRolloutWizard 1 }

-- {SCALAR} 1.3.6.1.4.1.2356.11.2.21.20.2
lcsSetupHttpRolloutWizardTitle OBJECT-TYPE
    SYNTAX     DisplayString (SIZE(0..50))
    MAX-ACCESS read-write
    STATUS     current
    DESCRIPTION
            ""
    ::= { lcsSetupHttpRolloutWizard 2 }

-- {TABLE} 1.3.6.1.4.1.2356.11.2.21.20.3
lcsSetupHttpRolloutWizardVariablesTable OBJECT-TYPE
    SYNTAX     SEQUENCE OF LcsSetupHttpRolloutWizardVariablesEntry
    MAX-ACCESS not-accessible
    STATUS     current
    DESCRIPTION
            ""
    ::= { lcsSetupHttpRolloutWizard 3 }

-- {ROW} 1.3.6.1.4.1.2356.11.2.21.20.3.1
lcsSetupHttpRolloutWizardVariablesEntry OBJECT-TYPE
    SYNTAX     LcsSetupHttpRolloutWizardVariablesEntry
    MAX-ACCESS not-accessible
    STATUS     current
    DESCRIPTION
            ""
    INDEX {
            lcsSetupHttpRolloutWizardVariablesEntryIndex
          }
    ::= { lcsSetupHttpRolloutWizardVariablesTable 1 }

LcsSetupHttpRolloutWizardVariablesEntry ::= SEQUENCE {
            lcsSetupHttpRolloutWizardVariablesEntryIndex Integer32,
            lcsSetupHttpRolloutWizardVariablesEntryIdent DisplayString,
            lcsSetupHttpRolloutWizardVariablesEntryTitle DisplayString,
            lcsSetupHttpRolloutWizardVariablesEntryType INTEGER,
            lcsSetupHttpRolloutWizardVariablesEntryMinValue Integer32,
            lcsSetupHttpRolloutWizardVariablesEntryMaxValue Integer32,
            lcsSetupHttpRolloutWizardVariablesEntryDefaultValue DisplayString
    }

-- {COLUMN} 1.3.6.1.4.1.2356.11.2.21.20.3.1.1
lcsSetupHttpRolloutWizardVariablesEntryIndex OBJECT-TYPE
    SYNTAX     Integer32 (0..2147483647)
    MAX-ACCESS read-write
    STATUS     current
    DESCRIPTION
            ""
    ::= { lcsSetupHttpRolloutWizardVariablesEntry 1 }

-- {COLUMN} 1.3.6.1.4.1.2356.11.2.21.20.3.1.2
lcsSetupHttpRolloutWizardVariablesEntryIdent OBJECT-TYPE
    SYNTAX     DisplayString (SIZE(0..16))
    MAX-ACCESS read-write
    STATUS     current
    DESCRIPTION
            ""
    ::= { lcsSetupHttpRolloutWizardVariablesEntry 2 }

-- {COLUMN} 1.3.6.1.4.1.2356.11.2.21.20.3.1.3
lcsSetupHttpRolloutWizardVariablesEntryTitle OBJECT-TYPE
    SYNTAX     DisplayString (SIZE(0..40))
    MAX-ACCESS read-write
    STATUS     current
    DESCRIPTION
            ""
    ::= { lcsSetupHttpRolloutWizardVariablesEntry 3 }

-- {COLUMN} 1.3.6.1.4.1.2356.11.2.21.20.3.1.4
lcsSetupHttpRolloutWizardVariablesEntryType OBJECT-TYPE
    SYNTAX     INTEGER {
                  eLabel (0),
                  eInteger (1),
                  eString (2),
                  ePassword (3),
                  eCheckmark (4)
            }
    MAX-ACCESS read-write
    STATUS     current
    DESCRIPTION
            ""
    ::= { lcsSetupHttpRolloutWizardVariablesEntry 4 }

-- {COLUMN} 1.3.6.1.4.1.2356.11.2.21.20.3.1.5
lcsSetupHttpRolloutWizardVariablesEntryMinValue OBJECT-TYPE
    SYNTAX     Integer32 (0..2147483647)
    MAX-ACCESS read-write
    STATUS     current
    DESCRIPTION
            ""
    ::= { lcsSetupHttpRolloutWizardVariablesEntry 5 }

-- {COLUMN} 1.3.6.1.4.1.2356.11.2.21.20.3.1.6
lcsSetupHttpRolloutWizardVariablesEntryMaxValue OBJECT-TYPE
    SYNTAX     Integer32 (0..2147483647)
    MAX-ACCESS read-write
    STATUS     current
    DESCRIPTION
            ""
    ::= { lcsSetupHttpRolloutWizardVariablesEntry 6 }

-- {COLUMN} 1.3.6.1.4.1.2356.11.2.21.20.3.1.7
lcsSetupHttpRolloutWizardVariablesEntryDefaultValue OBJECT-TYPE
    SYNTAX     DisplayString (SIZE(0..30))
    MAX-ACCESS read-write
    STATUS     current
    DESCRIPTION
            ""
    ::= { lcsSetupHttpRolloutWizardVariablesEntry 7 }

-- {TABLE} 1.3.6.1.4.1.2356.11.2.21.20.4
lcsSetupHttpRolloutWizardActionsTable OBJECT-TYPE
    SYNTAX     SEQUENCE OF LcsSetupHttpRolloutWizardActionsEntry
    MAX-ACCESS not-accessible
    STATUS     current
    DESCRIPTION
            ""
    ::= { lcsSetupHttpRolloutWizard 4 }

-- {ROW} 1.3.6.1.4.1.2356.11.2.21.20.4.1
lcsSetupHttpRolloutWizardActionsEntry OBJECT-TYPE
    SYNTAX     LcsSetupHttpRolloutWizardActionsEntry
    MAX-ACCESS not-accessible
    STATUS     current
    DESCRIPTION
            ""
    INDEX {
            lcsSetupHttpRolloutWizardActionsEntryIndex
          }
    ::= { lcsSetupHttpRolloutWizardActionsTable 1 }

LcsSetupHttpRolloutWizardActionsEntry ::= SEQUENCE {
            lcsSetupHttpRolloutWizardActionsEntryIndex Integer32,
            lcsSetupHttpRolloutWizardActionsEntryAction DisplayString,
            lcsSetupHttpRolloutWizardActionsEntryDescription DisplayString
    }

-- {COLUMN} 1.3.6.1.4.1.2356.11.2.21.20.4.1.1
lcsSetupHttpRolloutWizardActionsEntryIndex OBJECT-TYPE
    SYNTAX     Integer32 (0..2147483647)
    MAX-ACCESS read-write
    STATUS     current
    DESCRIPTION
            ""
    ::= { lcsSetupHttpRolloutWizardActionsEntry 1 }

-- {COLUMN} 1.3.6.1.4.1.2356.11.2.21.20.4.1.2
lcsSetupHttpRolloutWizardActionsEntryAction OBJECT-TYPE
    SYNTAX     DisplayString (SIZE(0..251))
    MAX-ACCESS read-write
    STATUS     current
    DESCRIPTION
            ""
    ::= { lcsSetupHttpRolloutWizardActionsEntry 2 }

-- {COLUMN} 1.3.6.1.4.1.2356.11.2.21.20.4.1.3
lcsSetupHttpRolloutWizardActionsEntryDescription OBJECT-TYPE
    SYNTAX     DisplayString (SIZE(0..251))
    MAX-ACCESS read-write
    STATUS     current
    DESCRIPTION
            ""
    ::= { lcsSetupHttpRolloutWizardActionsEntry 3 }

-- {SCALAR} 1.3.6.1.4.1.2356.11.2.21.20.5
lcsSetupHttpRolloutWizardRenumberVariables OBJECT-TYPE
    SYNTAX     DisplayString
    MAX-ACCESS read-write
    STATUS     current
    DESCRIPTION
            ""
    ::= { lcsSetupHttpRolloutWizard 5 }

-- {SCALAR} 1.3.6.1.4.1.2356.11.2.21.20.6
lcsSetupHttpRolloutWizardRenumberActions OBJECT-TYPE
    SYNTAX     DisplayString
    MAX-ACCESS read-write
    STATUS     current
    DESCRIPTION
            ""
    ::= { lcsSetupHttpRolloutWizard 6 }

-- {SCALAR} 1.3.6.1.4.1.2356.11.2.21.20.7
lcsSetupHttpRolloutWizardDisplayConnectionStatusFor OBJECT-TYPE
    SYNTAX     BITS {
                  eNothing (0),
                  eDsl (28),
                  eVpn (29),
                  eIsdn (30)
            }
    MAX-ACCESS read-only
    STATUS     current
    DESCRIPTION
            ""
    ::= { lcsSetupHttpRolloutWizard 7 }

-- {SCALAR} 1.3.6.1.4.1.2356.11.2.21.20.8
lcsSetupHttpRolloutWizardUseExtraChecks OBJECT-TYPE
    SYNTAX     INTEGER {
                  eNo (0),
                  eYes (1)
            }
    MAX-ACCESS read-write
    STATUS     current
    DESCRIPTION
            ""
    ::= { lcsSetupHttpRolloutWizard 8 }

-- {TABLE} 1.3.6.1.4.1.2356.11.2.21.20.9
lcsSetupHttpRolloutWizardPresetsTable OBJECT-TYPE
    SYNTAX     SEQUENCE OF LcsSetupHttpRolloutWizardPresetsEntry
    MAX-ACCESS not-accessible
    STATUS     current
    DESCRIPTION
            "-- empty --"
    ::= { lcsSetupHttpRolloutWizard 9 }

-- {ROW} 1.3.6.1.4.1.2356.11.2.21.20.9.1
lcsSetupHttpRolloutWizardPresetsEntry OBJECT-TYPE
    SYNTAX     LcsSetupHttpRolloutWizardPresetsEntry
    MAX-ACCESS not-accessible
    STATUS     current
    DESCRIPTION
            ""
    INDEX {
            lcsSetupHttpRolloutWizardPresetsEntryName
          }
    ::= { lcsSetupHttpRolloutWizardPresetsTable 1 }

LcsSetupHttpRolloutWizardPresetsEntry ::= SEQUENCE {
            lcsSetupHttpRolloutWizardPresetsEntryName INTEGER,
            lcsSetupHttpRolloutWizardPresetsEntryPreset DisplayString,
            lcsSetupHttpRolloutWizardPresetsEntryUsePreset INTEGER
    }

-- {COLUMN} 1.3.6.1.4.1.2356.11.2.21.20.9.1.1
lcsSetupHttpRolloutWizardPresetsEntryName OBJECT-TYPE
    SYNTAX     INTEGER {
                  eRolloutHost (1),
                  eProtocol (2),
                  eUsername (3),
                  ePassword (4),
                  eProject (5),
                  eDeviceId (6),
                  eTan (8),
                  eSourceLoopbackAddress (10),
                  ePort (11),
                  eRolloutVariant (12),
                  eLmcDomain (13),
                  eLmcProject (14),
                  eLmcLocation (15),
                  eDeviceRole (16),
                  eDeviceRoleInputSet (17)
            }
    MAX-ACCESS read-only
    STATUS     current
    DESCRIPTION
            "-- empty --"
    ::= { lcsSetupHttpRolloutWizardPresetsEntry 1 }

-- {COLUMN} 1.3.6.1.4.1.2356.11.2.21.20.9.1.2
lcsSetupHttpRolloutWizardPresetsEntryPreset OBJECT-TYPE
    SYNTAX     DisplayString (SIZE(0..127))
    MAX-ACCESS read-write
    STATUS     current
    DESCRIPTION
            "-- empty --"
    ::= { lcsSetupHttpRolloutWizardPresetsEntry 2 }

-- {COLUMN} 1.3.6.1.4.1.2356.11.2.21.20.9.1.3
lcsSetupHttpRolloutWizardPresetsEntryUsePreset OBJECT-TYPE
    SYNTAX     INTEGER {
                  eNo (0),
                  eYes (1)
            }
    MAX-ACCESS read-write
    STATUS     current
    DESCRIPTION
            "-- empty --"
    ::= { lcsSetupHttpRolloutWizardPresetsEntry 3 }

-- {SCALAR} 1.3.6.1.4.1.2356.11.2.21.20.10
lcsSetupHttpRolloutWizardDeleteWizard OBJECT-TYPE
    SYNTAX     DisplayString
    MAX-ACCESS read-write
    STATUS     current
    DESCRIPTION
            "-- empty --"
    ::= { lcsSetupHttpRolloutWizard 10 }

-- {NODE} 1.3.6.1.4.1.2356.11.2.21.20.11
lcsSetupHttpRolloutWizardSslNew OBJECT IDENTIFIER ::= { lcsSetupHttpRolloutWizard 11 }

-- {SCALAR} 1.3.6.1.4.1.2356.11.2.21.20.11.1
lcsSetupHttpRolloutWizardSslNewVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupHttpRolloutWizardSslNew 1 }

-- {SCALAR} 1.3.6.1.4.1.2356.11.2.21.20.11.2
lcsSetupHttpRolloutWizardSslNewKeyexAlgorithms OBJECT-TYPE
    SYNTAX     BITS {
                  eEcdhe (27),
                  eDhe (29),
                  eRsa (31)
            }
    MAX-ACCESS read-write
    STATUS     current
    DESCRIPTION
            "-- empty --"
    ::= { lcsSetupHttpRolloutWizardSslNew 2 }

-- {SCALAR} 1.3.6.1.4.1.2356.11.2.21.20.11.3
lcsSetupHttpRolloutWizardSslNewCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupHttpRolloutWizardSslNew 3 }

-- {SCALAR} 1.3.6.1.4.1.2356.11.2.21.20.11.4
lcsSetupHttpRolloutWizardSslNewHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupHttpRolloutWizardSslNew 4 }

-- {SCALAR} 1.3.6.1.4.1.2356.11.2.21.20.11.5
lcsSetupHttpRolloutWizardSslNewPreferPfs OBJECT-TYPE
    SYNTAX     BITS {
                  eNo (0),
                  eYes (7)
            }
    MAX-ACCESS read-write
    STATUS     current
    DESCRIPTION
            "-- empty --"
    ::= { lcsSetupHttpRolloutWizardSslNew 5 }

-- {SCALAR} 1.3.6.1.4.1.2356.11.2.21.20.11.6
lcsSetupHttpRolloutWizardSslNewRenegotiations OBJECT-TYPE
    SYNTAX     INTEGER {
                  eForbidden (0),
                  eAllowed (1),
                  eIgnored (2)
            }
    MAX-ACCESS read-write
    STATUS     current
    DESCRIPTION
            "-- empty --"
    ::= { lcsSetupHttpRolloutWizardSslNew 6 }

-- {SCALAR} 1.3.6.1.4.1.2356.11.2.21.20.11.7
lcsSetupHttpRolloutWizardSslNewEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupHttpRolloutWizardSslNew 7 }

-- {SCALAR} 1.3.6.1.4.1.2356.11.2.21.20.11.21
lcsSetupHttpRolloutWizardSslNewSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupHttpRolloutWizardSslNew 21 }

-- {SCALAR} 1.3.6.1.4.1.2356.11.2.21.21
lcsSetupHttpMaxHttpJobCount OBJECT-TYPE
    SYNTAX     Integer32 (0..2147483647)
    MAX-ACCESS read-write
    STATUS     current
    DESCRIPTION
            "-- empty --"
    ::= { lcsSetupHttp 21 }

-- {SCALAR} 1.3.6.1.4.1.2356.11.2.21.22
lcsSetupHttpDisablePasswordAutocompletion OBJECT-TYPE
    SYNTAX     INTEGER {
                  eNo (0),
                  eYes (1)
            }
    MAX-ACCESS read-write
    STATUS     current
    DESCRIPTION
            "-- empty --"
    ::= { lcsSetupHttp 22 }

-- {TABLE} 1.3.6.1.4.1.2356.11.2.21.23
lcsSetupHttpUserDefinedWizardsTable OBJECT-TYPE
    SYNTAX     SEQUENCE OF LcsSetupHttpUserDefinedWizardsEntry
    MAX-ACCESS not-accessible
    STATUS     current
    DESCRIPTION
            "-- empty --"
    ::= { lcsSetupHttp 23 }

-- {ROW} 1.3.6.1.4.1.2356.11.2.21.23.1
lcsSetupHttpUserDefinedWizardsEntry OBJECT-TYPE
    SYNTAX     LcsSetupHttpUserDefinedWizardsEntry
    MAX-ACCESS not-accessible
    STATUS     current
    DESCRIPTION
            ""
    INDEX {
            lcsSetupHttpUserDefinedWizardsEntryWizard
          }
    ::= { lcsSetupHttpUserDefinedWizardsTable 1 }

LcsSetupHttpUserDefinedWizardsEntry ::= SEQUENCE {
            lcsSetupHttpUserDefinedWizardsEntryWizard Integer32,
            lcsSetupHttpUserDefinedWizardsEntryActive INTEGER,
            lcsSetupHttpUserDefinedWizardsEntryName DisplayString,
            lcsSetupHttpUserDefinedWizardsEntryUseExtraChecks INTEGER
    }

-- {COLUMN} 1.3.6.1.4.1.2356.11.2.21.23.1.1
lcsSetupHttpUserDefinedWizardsEntryWizard OBJECT-TYPE
    SYNTAX     Integer32 (0..255)
    MAX-ACCESS read-only
    STATUS     current
    DESCRIPTION
            "-- empty --"
    ::= { lcsSetupHttpUserDefinedWizardsEntry 1 }

-- {COLUMN} 1.3.6.1.4.1.2356.11.2.21.23.1.2
lcsSetupHttpUserDefinedWizardsEntryActive OBJECT-TYPE
    SYNTAX     INTEGER {
                  eNo (0),
                  eYes (1)
            }
    MAX-ACCESS read-write
    STATUS     current
    DESCRIPTION
            "-- empty --"
    ::= { lcsSetupHttpUserDefinedWizardsEntry 2 }

-- {COLUMN} 1.3.6.1.4.1.2356.11.2.21.23.1.3
lcsSetupHttpUserDefinedWizardsEntryName OBJECT-TYPE
    SYNTAX     DisplayString (SIZE(0..63))
    MAX-ACCESS read-write
    STATUS     current
    DESCRIPTION
            "-- empty --"
    ::= { lcsSetupHttpUserDefinedWizardsEntry 3 }

-- {COLUMN} 1.3.6.1.4.1.2356.11.2.21.23.1.4
lcsSetupHttpUserDefinedWizardsEntryUseExtraChecks OBJECT-TYPE
    SYNTAX     INTEGER {
                  eNo (0),
                  eYes (1)
            }
    MAX-ACCESS read-write
    STATUS     current
    DESCRIPTION
            "-- empty --"
    ::= { lcsSetupHttpUserDefinedWizardsEntry 4 }

-- {SCALAR} 1.3.6.1.4.1.2356.11.2.21.24
lcsSetupHttpAutomaticRedirectToHttps OBJECT-TYPE
    SYNTAX     INTEGER {
                  eNo (0),
                  eYes (1)
            }
    MAX-ACCESS read-write
    STATUS     current
    DESCRIPTION
            "-- empty --"
    ::= { lcsSetupHttp 24 }

-- {NODE} 1.3.6.1.4.1.2356.11.2.21.30
lcsSetupHttpFileServer OBJECT IDENTIFIER ::= { lcsSetupHttp 30 }

-- {SCALAR} 1.3.6.1.4.1.2356.11.2.21.30.1
lcsSetupHttpFileServerPublicSubdir OBJECT-TYPE
    SYNTAX     DisplayString (SIZE(0..64))
    MAX-ACCESS read-write
    STATUS     current
    DESCRIPTION
            ""
    ::= { lcsSetupHttpFileServer 1 }

-- {SCALAR} 1.3.6.1.4.1.2356.11.2.21.30.2
lcsSetupHttpFileServerOperating OBJECT-TYPE
    SYNTAX     INTEGER {
                  eNo (0),
                  eYes (1)
            }
    MAX-ACCESS read-write
    STATUS     current
    DESCRIPTION
            ""
    ::= { lcsSetupHttpFileServer 2 }

-- {NODE} 1.3.6.1.4.1.2356.11.2.21.40
lcsSetupHttpSslNew OBJECT IDENTIFIER ::= { lcsSetupHttp 40 }

-- {SCALAR} 1.3.6.1.4.1.2356.11.2.21.40.3
lcsSetupHttpSslNewVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupHttpSslNew 3 }

-- {SCALAR} 1.3.6.1.4.1.2356.11.2.21.40.4
lcsSetupHttpSslNewKeyexAlgorithms OBJECT-TYPE
    SYNTAX     BITS {
                  eEcdhe (27),
                  eDhe (29),
                  eRsa (31)
            }
    MAX-ACCESS read-write
    STATUS     current
    DESCRIPTION
            "-- empty --"
    ::= { lcsSetupHttpSslNew 4 }

-- {SCALAR} 1.3.6.1.4.1.2356.11.2.21.40.5
lcsSetupHttpSslNewCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupHttpSslNew 5 }

-- {SCALAR} 1.3.6.1.4.1.2356.11.2.21.40.6
lcsSetupHttpSslNewHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupHttpSslNew 6 }

-- {SCALAR} 1.3.6.1.4.1.2356.11.2.21.40.7
lcsSetupHttpSslNewPreferPfs OBJECT-TYPE
    SYNTAX     BITS {
                  eNo (0),
                  eYes (7)
            }
    MAX-ACCESS read-write
    STATUS     current
    DESCRIPTION
            "-- empty --"
    ::= { lcsSetupHttpSslNew 7 }

-- {SCALAR} 1.3.6.1.4.1.2356.11.2.21.40.8
lcsSetupHttpSslNewRenegotiations OBJECT-TYPE
    SYNTAX     INTEGER {
                  eForbidden (0),
                  eAllowed (1),
                  eIgnored (2)
            }
    MAX-ACCESS read-write
    STATUS     current
    DESCRIPTION
            "-- empty --"
    ::= { lcsSetupHttpSslNew 8 }

-- {SCALAR} 1.3.6.1.4.1.2356.11.2.21.40.9
lcsSetupHttpSslNewEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupHttpSslNew 9 }

-- {SCALAR} 1.3.6.1.4.1.2356.11.2.21.40.10
lcsSetupHttpSslNewPortNew OBJECT-TYPE
    SYNTAX     Integer32 (0..65535)
    MAX-ACCESS read-write
    STATUS     current
    DESCRIPTION
            "TCP port device is listening on for HTTPS"
    ::= { lcsSetupHttpSslNew 10 }

-- {SCALAR} 1.3.6.1.4.1.2356.11.2.21.40.11
lcsSetupHttpSslNewUseUserDefCert OBJECT-TYPE
    SYNTAX     INTEGER {
                  eNo (0),
                  eYes (1)
            }
    MAX-ACCESS read-write
    STATUS     current
    DESCRIPTION
            "use uploaded SSL certificate for HTTPS server"
    ::= { lcsSetupHttpSslNew 11 }

-- {SCALAR} 1.3.6.1.4.1.2356.11.2.21.40.12
lcsSetupHttpSslNewCloseDelayMs OBJECT-TYPE
    SYNTAX     Integer32 (0..2147483647)
    MAX-ACCESS read-write
    STATUS     current
    DESCRIPTION
            "-- empty --"
    ::= { lcsSetupHttpSslNew 12 }

-- {SCALAR} 1.3.6.1.4.1.2356.11.2.21.40.23
lcsSetupHttpSslNewSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupHttpSslNew 23 }

-- {NODE} 1.3.6.1.4.1.2356.11.2.22
lcsSetupSyslog OBJECT IDENTIFIER ::= { lcsSetup 22 }

-- {SCALAR} 1.3.6.1.4.1.2356.11.2.22.1
lcsSetupSyslogOperating OBJECT-TYPE
    SYNTAX     INTEGER {
                  eNo (0),
                  eYes (1)
            }
    MAX-ACCESS read-write
    STATUS     current
    DESCRIPTION
            ""
    ::= { lcsSetupSyslog 1 }

-- {TABLE} 1.3.6.1.4.1.2356.11.2.22.2
lcsSetupSyslogServerTable OBJECT-TYPE
    SYNTAX     SEQUENCE OF LcsSetupSyslogServerEntry
    MAX-ACCESS not-accessible
    STATUS     current
    DESCRIPTION
            ""
    ::= { lcsSetupSyslog 2 }

-- {ROW} 1.3.6.1.4.1.2356.11.2.22.2.1
lcsSetupSyslogServerEntry OBJECT-TYPE
    SYNTAX     LcsSetupSyslogServerEntry
    MAX-ACCESS not-accessible
    STATUS     current
    DESCRIPTION
            ""
    INDEX {
            lcsSetupSyslogServerEntryIdx
          }
    ::= { lcsSetupSyslogServerTable 1 }

LcsSetupSyslogServerEntry ::= SEQUENCE {
            lcsSetupSyslogServerEntryIdx DisplayString,
            lcsSetupSyslogServerEntryIpAddress IpAddress,
            lcsSetupSyslogServerEntrySource BITS,
            lcsSetupSyslogServerEntryLevel BITS,
            lcsSetupSyslogServerEntryLoopbackAddr DisplayString,
            lcsSetupSyslogServerEntryIpAddressDns DisplayString,
            lcsSetupSyslogServerEntryPort Integer32,
            lcsSetupSyslogServerEntryProtocol INTEGER,
            lcsSetupSyslogServerEntryFilterPolicy INTEGER,
            lcsSetupSyslogServerEntryFilterName DisplayString
    }

-- {COLUMN} 1.3.6.1.4.1.2356.11.2.22.2.1.1
lcsSetupSyslogServerEntryIdx OBJECT-TYPE
    SYNTAX     DisplayString (SIZE(0..4))
    MAX-ACCESS read-write
    STATUS     current
    DESCRIPTION
            ""
    ::= { lcsSetupSyslogServerEntry 1 }

-- {COLUMN} 1.3.6.1.4.1.2356.11.2.22.2.1.2
lcsSetupSyslogServerEntryIpAddress OBJECT-TYPE
    SYNTAX     IpAddress
    MAX-ACCESS read-write
    STATUS     current
    DESCRIPTION
            ""
    ::= { lcsSetupSyslogServerEntry 2 }

-- {COLUMN} 1.3.6.1.4.1.2356.11.2.22.2.1.3
lcsSetupSyslogServerEntrySource OBJECT-TYPE
    SYNTAX     BITS {
                  eRouter (0),
                  eAdministration (1),
                  eAccounting (2),
                  eConnections (3),
                  eConsoleLogin (4),
                  eSystemtime (5),
                  eLogin (6),
                  eSystem (7)
            }
    MAX-ACCESS read-write
    STATUS     current
    DESCRIPTION
            ""
    ::= { lcsSetupSyslogServerEntry 3 }

-- {COLUMN} 1.3.6.1.4.1.2356.11.2.22.2.1.4
lcsSetupSyslogServerEntryLevel OBJECT-TYPE
    SYNTAX     BITS {
                  eDebug (3),
                  eInfo (4),
                  eWarning (5),
                  eError (6),
                  eAlarm (7)
            }
    MAX-ACCESS read-write
    STATUS     current
    DESCRIPTION
            ""
    ::= { lcsSetupSyslogServerEntry 4 }

-- {COLUMN} 1.3.6.1.4.1.2356.11.2.22.2.1.6
lcsSetupSyslogServerEntryLoopbackAddr OBJECT-TYPE
    SYNTAX     DisplayString (SIZE(0..16))
    MAX-ACCESS read-write
    STATUS     current
    DESCRIPTION
            ""
    ::= { lcsSetupSyslogServerEntry 6 }

-- {COLUMN} 1.3.6.1.4.1.2356.11.2.22.2.1.7
lcsSetupSyslogServerEntryIpAddressDns OBJECT-TYPE
    SYNTAX     DisplayString (SIZE(0..64))
    MAX-ACCESS read-write
    STATUS     current
    DESCRIPTION
            ""
    ::= { lcsSetupSyslogServerEntry 7 }

-- {COLUMN} 1.3.6.1.4.1.2356.11.2.22.2.1.8
lcsSetupSyslogServerEntryPort OBJECT-TYPE
    SYNTAX     Integer32 (0..65535)
    MAX-ACCESS read-write
    STATUS     current
    DESCRIPTION
            "-- empty --"
    ::= { lcsSetupSyslogServerEntry 8 }

-- {COLUMN} 1.3.6.1.4.1.2356.11.2.22.2.1.9
lcsSetupSyslogServerEntryProtocol OBJECT-TYPE
    SYNTAX     INTEGER {
                  eUdp (0),
                  eTcp (1)
            }
    MAX-ACCESS read-write
    STATUS     current
    DESCRIPTION
            "-- empty --"
    ::= { lcsSetupSyslogServerEntry 9 }

-- {COLUMN} 1.3.6.1.4.1.2356.11.2.22.2.1.10
lcsSetupSyslogServerEntryFilterPolicy OBJECT-TYPE
    SYNTAX     INTEGER {
                  eAllow (0),
                  eDeny (1)
            }
    MAX-ACCESS read-write
    STATUS     current
    DESCRIPTION
            "-- empty --"
    ::= { lcsSetupSyslogServerEntry 10 }

-- {COLUMN} 1.3.6.1.4.1.2356.11.2.22.2.1.11
lcsSetupSyslogServerEntryFilterName OBJECT-TYPE
    SYNTAX     DisplayString (SIZE(0..32))
    MAX-ACCESS read-write
    STATUS     current
    DESCRIPTION
            "-- empty --"
    ::= { lcsSetupSyslogServerEntry 11 }

-- {TABLE} 1.3.6.1.4.1.2356.11.2.22.3
lcsSetupSyslogFacilityMapperTable OBJECT-TYPE
    SYNTAX     SEQUENCE OF LcsSetupSyslogFacilityMapperEntry
    MAX-ACCESS not-accessible
    STATUS     current
    DESCRIPTION
            ""
    ::= { lcsSetupSyslog 3 }

-- {ROW} 1.3.6.1.4.1.2356.11.2.22.3.1
lcsSetupSyslogFacilityMapperEntry OBJECT-TYPE
    SYNTAX     LcsSetupSyslogFacilityMapperEntry
    MAX-ACCESS not-accessible
    STATUS     current
    DESCRIPTION
            ""
    INDEX {
            lcsSetupSyslogFacilityMapperEntrySource
          }
    ::= { lcsSetupSyslogFacilityMapperTable 1 }

LcsSetupSyslogFacilityMapperEntry ::= SEQUENCE {
            lcsSetupSyslogFacilityMapperEntrySource INTEGER,
            lcsSetupSyslogFacilityMapperEntryFacility INTEGER
    }

-- {COLUMN} 1.3.6.1.4.1.2356.11.2.22.3.1.1
lcsSetupSyslogFacilityMapperEntrySource OBJECT-TYPE
    SYNTAX     INTEGER {
                  eSystem (1),
                  eLogin (2),
                  eSystemtime (4),
                  eConsoleLogin (8),
                  eConnections (16),
                  eAccounting (32),
                  eAdministration (64),
                  eRouter (128)
            }
    MAX-ACCESS read-only
    STATUS     current
    DESCRIPTION
            ""
    ::= { lcsSetupSyslogFacilityMapperEntry 1 }

-- {COLUMN} 1.3.6.1.4.1.2356.11.2.22.3.1.2
lcsSetupSyslogFacilityMapperEntryFacility OBJECT-TYPE
    SYNTAX     INTEGER {
                  eKern (0),
                  eUser (1),
                  eMail (2),
                  eDaemon (3),
                  eAuth (4),
                  eSyslog (5),
                  eLpr (6),
                  eNews (7),
                  eUucp (8),
                  eCron (9),
                  eAuthpriv (10),
                  eSystem0 (11),
                  eSystem1 (12),
                  eSystem2 (13),
                  eSystem3 (14),
                  eSystem4 (15),
                  eLocal0 (16),
                  eLocal1 (17),
                  eLocal2 (18),
                  eLocal3 (19),
                  eLocal4 (20),
                  eLocal5 (21),
                  eLocal6 (22),
                  eLocal7 (23)
            }
    MAX-ACCESS read-write
    STATUS     current
    DESCRIPTION
            ""
    ::= { lcsSetupSyslogFacilityMapperEntry 2 }

-- {SCALAR} 1.3.6.1.4.1.2356.11.2.22.4
lcsSetupSyslogPort OBJECT-TYPE
    SYNTAX     Integer32 (0..65535)
    MAX-ACCESS read-write
    STATUS     current
    DESCRIPTION
            ""
    ::= { lcsSetupSyslog 4 }

-- {SCALAR} 1.3.6.1.4.1.2356.11.2.22.5
lcsSetupSyslogMessagesTableOrder OBJECT-TYPE
    SYNTAX     INTEGER {
                  eOldestOnTop (0),
                  eNewestOnTop (1)
            }
    MAX-ACCESS read-write
    STATUS     current
    DESCRIPTION
            ""
    ::= { lcsSetupSyslog 5 }

-- {SCALAR} 1.3.6.1.4.1.2356.11.2.22.6
lcsSetupSyslogBackupIntervall OBJECT-TYPE
    SYNTAX     Integer32 (0..2147483647)
    MAX-ACCESS read-write
    STATUS     current
    DESCRIPTION
            "-- empty --"
    ::= { lcsSetupSyslog 6 }

-- {SCALAR} 1.3.6.1.4.1.2356.11.2.22.7
lcsSetupSyslogBackupActive OBJECT-TYPE
    SYNTAX     INTEGER {
                  eNo (0),
                  eYes (1)
            }
    MAX-ACCESS read-write
    STATUS     current
    DESCRIPTION
            "-- empty --"
    ::= { lcsSetupSyslog 7 }

-- {SCALAR} 1.3.6.1.4.1.2356.11.2.22.8
lcsSetupSyslogLogCliChanges OBJECT-TYPE
    SYNTAX     INTEGER {
                  eNo (0),
                  eYes (1)
            }
    MAX-ACCESS read-write
    STATUS     current
    DESCRIPTION
            "-- empty --"
    ::= { lcsSetupSyslog 8 }

-- {SCALAR} 1.3.6.1.4.1.2356.11.2.22.9
lcsSetupSyslogMaxMessageAgeHours OBJECT-TYPE
    SYNTAX     Integer32 (0..2147483647)
    MAX-ACCESS read-write
    STATUS     current
    DESCRIPTION
            "-- empty --"
    ::= { lcsSetupSyslog 9 }

-- {SCALAR} 1.3.6.1.4.1.2356.11.2.22.10
lcsSetupSyslogRemoveOldMessages OBJECT-TYPE
    SYNTAX     INTEGER {
                  eNo (0),
                  eYes (1)
            }
    MAX-ACCESS read-write
    STATUS     current
    DESCRIPTION
            "-- empty --"
    ::= { lcsSetupSyslog 10 }

-- {SCALAR} 1.3.6.1.4.1.2356.11.2.22.11
lcsSetupSyslogMaxAgeUnit OBJECT-TYPE
    SYNTAX     INTEGER {
                  eHour (0),
                  eDay (1),
                  eMonth (2)
            }
    MAX-ACCESS read-write
    STATUS     current
    DESCRIPTION
            "-- empty --"
    ::= { lcsSetupSyslog 11 }

-- {SCALAR} 1.3.6.1.4.1.2356.11.2.22.12
lcsSetupSyslogCriticalPrio OBJECT-TYPE
    SYNTAX     INTEGER {
                  eEmergency (0),
                  eAlarm (1),
                  eCritical (2),
                  eError (3),
                  eWarning (4),
                  eNotice (5),
                  eInfo (6),
                  eDebug (7)
            }
    MAX-ACCESS read-write
    STATUS     current
    DESCRIPTION
            "-- empty --"
    ::= { lcsSetupSyslog 12 }

-- {TABLE} 1.3.6.1.4.1.2356.11.2.22.13
lcsSetupSyslogFilterTable OBJECT-TYPE
    SYNTAX     SEQUENCE OF LcsSetupSyslogFilterEntry
    MAX-ACCESS not-accessible
    STATUS     current
    DESCRIPTION
            "-- empty --"
    ::= { lcsSetupSyslog 13 }

-- {ROW} 1.3.6.1.4.1.2356.11.2.22.13.1
lcsSetupSyslogFilterEntry OBJECT-TYPE
    SYNTAX     LcsSetupSyslogFilterEntry
    MAX-ACCESS not-accessible
    STATUS     current
    DESCRIPTION
            ""
    INDEX {
            lcsSetupSyslogFilterEntryIdx
          }
    ::= { lcsSetupSyslogFilterTable 1 }

LcsSetupSyslogFilterEntry ::= SEQUENCE {
            lcsSetupSyslogFilterEntryIdx DisplayString,
            lcsSetupSyslogFilterEntryFilterName DisplayString,
            lcsSetupSyslogFilterEntryMatchSource BITS,
            lcsSetupSyslogFilterEntryMatchLevel BITS,
            lcsSetupSyslogFilterEntryFilterRegex DisplayString,
            lcsSetupSyslogFilterEntrySetSource INTEGER,
            lcsSetupSyslogFilterEntrySetLevel INTEGER,
            lcsSetupSyslogFilterEntryFilterAction INTEGER
    }

-- {COLUMN} 1.3.6.1.4.1.2356.11.2.22.13.1.1
lcsSetupSyslogFilterEntryIdx OBJECT-TYPE
    SYNTAX     DisplayString (SIZE(0..4))
    MAX-ACCESS read-write
    STATUS     current
    DESCRIPTION
            "-- empty --"
    ::= { lcsSetupSyslogFilterEntry 1 }

-- {COLUMN} 1.3.6.1.4.1.2356.11.2.22.13.1.2
lcsSetupSyslogFilterEntryFilterName OBJECT-TYPE
    SYNTAX     DisplayString (SIZE(0..32))
    MAX-ACCESS read-write
    STATUS     current
    DESCRIPTION
            "-- empty --"
    ::= { lcsSetupSyslogFilterEntry 2 }

-- {COLUMN} 1.3.6.1.4.1.2356.11.2.22.13.1.3
lcsSetupSyslogFilterEntryMatchSource OBJECT-TYPE
    SYNTAX     BITS {
                  eRouter (0),
                  eAdministration (1),
                  eAccounting (2),
                  eConnections (3),
                  eConsoleLogin (4),
                  eSystemtime (5),
                  eLogin (6),
                  eSystem (7)
            }
    MAX-ACCESS read-write
    STATUS     current
    DESCRIPTION
            "-- empty --"
    ::= { lcsSetupSyslogFilterEntry 3 }

-- {COLUMN} 1.3.6.1.4.1.2356.11.2.22.13.1.4
lcsSetupSyslogFilterEntryMatchLevel OBJECT-TYPE
    SYNTAX     BITS {
                  eDebug (3),
                  eInfo (4),
                  eWarning (5),
                  eError (6),
                  eAlarm (7)
            }
    MAX-ACCESS read-write
    STATUS     current
    DESCRIPTION
            "-- empty --"
    ::= { lcsSetupSyslogFilterEntry 4 }

-- {COLUMN} 1.3.6.1.4.1.2356.11.2.22.13.1.5
lcsSetupSyslogFilterEntryFilterRegex OBJECT-TYPE
    SYNTAX     DisplayString (SIZE(0..128))
    MAX-ACCESS read-write
    STATUS     current
    DESCRIPTION
            "-- empty --"
    ::= { lcsSetupSyslogFilterEntry 5 }

-- {COLUMN} 1.3.6.1.4.1.2356.11.2.22.13.1.6
lcsSetupSyslogFilterEntrySetSource OBJECT-TYPE
    SYNTAX     INTEGER {
                  eNone (0),
                  eSystem (1),
                  eLogin (2),
                  eSystemtime (4),
                  eConsoleLogin (8),
                  eConnections (16),
                  eAccounting (32),
                  eAdministration (64),
                  eRouter (128)
            }
    MAX-ACCESS read-write
    STATUS     current
    DESCRIPTION
            "-- empty --"
    ::= { lcsSetupSyslogFilterEntry 6 }

-- {COLUMN} 1.3.6.1.4.1.2356.11.2.22.13.1.7
lcsSetupSyslogFilterEntrySetLevel OBJECT-TYPE
    SYNTAX     INTEGER {
                  eNone (0),
                  eAlarm (1),
                  eError (2),
                  eWarning (4),
                  eInfo (8),
                  eDebug (16)
            }
    MAX-ACCESS read-write
    STATUS     current
    DESCRIPTION
            "-- empty --"
    ::= { lcsSetupSyslogFilterEntry 7 }

-- {COLUMN} 1.3.6.1.4.1.2356.11.2.22.13.1.8
lcsSetupSyslogFilterEntryFilterAction OBJECT-TYPE
    SYNTAX     INTEGER {
                  eAllow (0),
                  eDeny (1)
            }
    MAX-ACCESS read-write
    STATUS     current
    DESCRIPTION
            "-- empty --"
    ::= { lcsSetupSyslogFilterEntry 8 }

-- {NODE} 1.3.6.1.4.1.2356.11.2.23
lcsSetupInterfaces OBJECT IDENTIFIER ::= { lcsSetup 23 }

-- {TABLE} 1.3.6.1.4.1.2356.11.2.23.1
lcsSetupInterfacesS0Table OBJECT-TYPE
    SYNTAX     SEQUENCE OF LcsSetupInterfacesS0Entry
    MAX-ACCESS not-accessible
    STATUS     current
    DESCRIPTION
            ""
    ::= { lcsSetupInterfaces 1 }

-- {ROW} 1.3.6.1.4.1.2356.11.2.23.1.1
lcsSetupInterfacesS0Entry OBJECT-TYPE
    SYNTAX     LcsSetupInterfacesS0Entry
    MAX-ACCESS not-accessible
    STATUS     current
    DESCRIPTION
            ""
    INDEX {
            lcsSetupInterfacesS0EntryIfc
          }
    ::= { lcsSetupInterfacesS0Table 1 }

LcsSetupInterfacesS0Entry ::= SEQUENCE {
            lcsSetupInterfacesS0EntryIfc INTEGER,
            lcsSetupInterfacesS0EntryProtocol INTEGER,
            lcsSetupInterfacesS0EntryLlBChan INTEGER,
            lcsSetupInterfacesS0EntryDialPrefix DisplayString,
            lcsSetupInterfacesS0EntryMaxInCalls INTEGER,
            lcsSetupInterfacesS0EntryMaxOutCalls INTEGER,
            lcsSetupInterfacesS0EntryTypeOfInterface Integer32,
            lcsSetupInterfacesS0EntryTermination INTEGER
    }

-- {COLUMN} 1.3.6.1.4.1.2356.11.2.23.1.1.1
lcsSetupInterfacesS0EntryIfc OBJECT-TYPE
    SYNTAX     INTEGER {
                  eS01 (257),
                  eS02 (258),
                  eModem (513),
                  eDsl1 (2049),
                  eDsl2 (2050),
                  eDsl3 (2051),
                  eDsl4 (2052),
                  eDsl5 (2053),
                  eAdsl (8193),
                  eVdsl (16385),
                  eVdsl2 (16386)
            }
    MAX-ACCESS read-only
    STATUS     current
    DESCRIPTION
            ""
    ::= { lcsSetupInterfacesS0Entry 1 }

-- {COLUMN} 1.3.6.1.4.1.2356.11.2.23.1.1.2
lcsSetupInterfacesS0EntryProtocol OBJECT-TYPE
    SYNTAX     INTEGER {
                  eNo (0),
                  eDss1 (1),
                  e1tr6 (2),
                  eP2pDss1 (4),
                  eGrp0 (16),
                  eAuto (255),
                  eNtP2pDss1 (16384),
                  eNtDss1 (32768),
                  eRevNtP2pDss1 (65536),
                  eRevNtDss1 (131072),
                  eClock (262144)
            }
    MAX-ACCESS read-write
    STATUS     current
    DESCRIPTION
            ""
    ::= { lcsSetupInterfacesS0Entry 2 }

-- {COLUMN} 1.3.6.1.4.1.2356.11.2.23.1.1.7
lcsSetupInterfacesS0EntryLlBChan OBJECT-TYPE
    SYNTAX     INTEGER {
                  eNone (0),
                  eB1 (1),
                  eB2 (2)
            }
    MAX-ACCESS read-write
    STATUS     current
    DESCRIPTION
            ""
    ::= { lcsSetupInterfacesS0Entry 7 }

-- {COLUMN} 1.3.6.1.4.1.2356.11.2.23.1.1.9
lcsSetupInterfacesS0EntryDialPrefix OBJECT-TYPE
    SYNTAX     DisplayString (SIZE(0..8))
    MAX-ACCESS read-write
    STATUS     current
    DESCRIPTION
            ""
    ::= { lcsSetupInterfacesS0Entry 9 }

-- {COLUMN} 1.3.6.1.4.1.2356.11.2.23.1.1.13
lcsSetupInterfacesS0EntryMaxInCalls OBJECT-TYPE
    SYNTAX     INTEGER {
                  eTwo (0),
                  eOne (1),
                  eZero (2)
            }
    MAX-ACCESS read-write
    STATUS     current
    DESCRIPTION
            ""
    ::= { lcsSetupInterfacesS0Entry 13 }

-- {COLUMN} 1.3.6.1.4.1.2356.11.2.23.1.1.14
lcsSetupInterfacesS0EntryMaxOutCalls OBJECT-TYPE
    SYNTAX     INTEGER {
                  eTwo (0),
                  eOne (1),
                  eZero (2)
            }
    MAX-ACCESS read-write
    STATUS     current
    DESCRIPTION
            ""
    ::= { lcsSetupInterfacesS0Entry 14 }

-- {COLUMN} 1.3.6.1.4.1.2356.11.2.23.1.1.15
lcsSetupInterfacesS0EntryTypeOfInterface OBJECT-TYPE
    SYNTAX     Integer32 (0..2147483647)
    MAX-ACCESS read-only
    STATUS     current
    DESCRIPTION
            ""
    ::= { lcsSetupInterfacesS0Entry 15 }

-- {COLUMN} 1.3.6.1.4.1.2356.11.2.23.1.1.27
lcsSetupInterfacesS0EntryTermination OBJECT-TYPE
    SYNTAX     INTEGER {
                  eNo (0),
                  eYes (1)
            }
    MAX-ACCESS read-write
    STATUS     current
    DESCRIPTION
            "-- empty --"
    ::= { lcsSetupInterfacesS0Entry 27 }

-- {TABLE} 1.3.6.1.4.1.2356.11.2.23.4
lcsSetupInterfacesDslTable OBJECT-TYPE
    SYNTAX     SEQUENCE OF LcsSetupInterfacesDslEntry
    MAX-ACCESS not-accessible
    STATUS     current
    DESCRIPTION
            ""
    ::= { lcsSetupInterfaces 4 }

-- {ROW} 1.3.6.1.4.1.2356.11.2.23.4.1
lcsSetupInterfacesDslEntry OBJECT-TYPE
    SYNTAX     LcsSetupInterfacesDslEntry
    MAX-ACCESS not-accessible
    STATUS     current
    DESCRIPTION
            ""
    INDEX {
            lcsSetupInterfacesDslEntryIfc
          }
    ::= { lcsSetupInterfacesDslTable 1 }

LcsSetupInterfacesDslEntry ::= SEQUENCE {
            lcsSetupInterfacesDslEntryIfc INTEGER,
            lcsSetupInterfacesDslEntryOperating INTEGER,
            lcsSetupInterfacesDslEntryConnector INTEGER,
            lcsSetupInterfacesDslEntryTypeOfInterface Integer32,
            lcsSetupInterfacesDslEntryUpstreamRate Integer32,
            lcsSetupInterfacesDslEntryExtOverhead Integer32,
            lcsSetupInterfacesDslEntryDownstreamRate Integer32,
            lcsSetupInterfacesDslEntryLanIfc INTEGER,
            lcsSetupInterfacesDslEntryVlanId Integer32
    }

-- {COLUMN} 1.3.6.1.4.1.2356.11.2.23.4.1.1
lcsSetupInterfacesDslEntryIfc OBJECT-TYPE
    SYNTAX     INTEGER {
                  eS01 (257),
                  eS02 (258),
                  eModem (513),
                  eDsl1 (2049),
                  eDsl2 (2050),
                  eDsl3 (2051),
                  eDsl4 (2052),
                  eDsl5 (2053),
                  eAdsl (8193),
                  eVdsl (16385),
                  eVdsl2 (16386)
            }
    MAX-ACCESS read-only
    STATUS     current
    DESCRIPTION
            ""
    ::= { lcsSetupInterfacesDslEntry 1 }

-- {COLUMN} 1.3.6.1.4.1.2356.11.2.23.4.1.2
lcsSetupInterfacesDslEntryOperating OBJECT-TYPE
    SYNTAX     INTEGER {
                  eNo (0),
                  eYes (16)
            }
    MAX-ACCESS read-write
    STATUS     current
    DESCRIPTION
            ""
    ::= { lcsSetupInterfacesDslEntry 2 }

-- {COLUMN} 1.3.6.1.4.1.2356.11.2.23.4.1.6
lcsSetupInterfacesDslEntryConnector OBJECT-TYPE
    SYNTAX     INTEGER {
                  eAuto (0),
                  eExclusive (1)
            }
    MAX-ACCESS read-write
    STATUS     current
    DESCRIPTION
            ""
    ::= { lcsSetupInterfacesDslEntry 6 }

-- {COLUMN} 1.3.6.1.4.1.2356.11.2.23.4.1.15
lcsSetupInterfacesDslEntryTypeOfInterface OBJECT-TYPE
    SYNTAX     Integer32 (0..2147483647)
    MAX-ACCESS read-only
    STATUS     current
    DESCRIPTION
            ""
    ::= { lcsSetupInterfacesDslEntry 15 }

-- {COLUMN} 1.3.6.1.4.1.2356.11.2.23.4.1.16
lcsSetupInterfacesDslEntryUpstreamRate OBJECT-TYPE
    SYNTAX     Integer32 (0..2147483647)
    MAX-ACCESS read-write
    STATUS     current
    DESCRIPTION
            ""
    ::= { lcsSetupInterfacesDslEntry 16 }

-- {COLUMN} 1.3.6.1.4.1.2356.11.2.23.4.1.17
lcsSetupInterfacesDslEntryExtOverhead OBJECT-TYPE
    SYNTAX     Integer32 (0..2147483647)
    MAX-ACCESS read-write
    STATUS     current
    DESCRIPTION
            ""
    ::= { lcsSetupInterfacesDslEntry 17 }

-- {COLUMN} 1.3.6.1.4.1.2356.11.2.23.4.1.18
lcsSetupInterfacesDslEntryDownstreamRate OBJECT-TYPE
    SYNTAX     Integer32 (0..2147483647)
    MAX-ACCESS read-write
    STATUS     current
    DESCRIPTION
            ""
    ::= { lcsSetupInterfacesDslEntry 18 }

-- {COLUMN} 1.3.6.1.4.1.2356.11.2.23.4.1.23
lcsSetupInterfacesDslEntryLanIfc OBJECT-TYPE
    SYNTAX     INTEGER {
                  eNone (0),
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eAny (65535)
            }
    MAX-ACCESS read-write
    STATUS     current
    DESCRIPTION
            ""
    ::= { lcsSetupInterfacesDslEntry 23 }

-- {COLUMN} 1.3.6.1.4.1.2356.11.2.23.4.1.24
lcsSetupInterfacesDslEntryVlanId OBJECT-TYPE
    SYNTAX     Integer32 (0..65535)
    MAX-ACCESS read-write
    STATUS     current
    DESCRIPTION
            "-- empty --"
    ::= { lcsSetupInterfacesDslEntry 24 }

-- {TABLE} 1.3.6.1.4.1.2356.11.2.23.6
lcsSetupInterfacesAdslTable OBJECT-TYPE
    SYNTAX     SEQUENCE OF LcsSetupInterfacesAdslEntry
    MAX-ACCESS not-accessible
    STATUS     current
    DESCRIPTION
            "-- empty --"
    ::= { lcsSetupInterfaces 6 }

-- {ROW} 1.3.6.1.4.1.2356.11.2.23.6.1
lcsSetupInterfacesAdslEntry OBJECT-TYPE
    SYNTAX     LcsSetupInterfacesAdslEntry
    MAX-ACCESS not-accessible
    STATUS     current
    DESCRIPTION
            ""
    INDEX {
            lcsSetupInterfacesAdslEntryIfc
          }
    ::= { lcsSetupInterfacesAdslTable 1 }

LcsSetupInterfacesAdslEntry ::= SEQUENCE {
            lcsSetupInterfacesAdslEntryIfc INTEGER,
            lcsSetupInterfacesAdslEntryProtocol INTEGER,
            lcsSetupInterfacesAdslEntryUpstreamRate Integer32,
            lcsSetupInterfacesAdslEntryDownstreamRate Integer32
    }

-- {COLUMN} 1.3.6.1.4.1.2356.11.2.23.6.1.1
lcsSetupInterfacesAdslEntryIfc OBJECT-TYPE
    SYNTAX     INTEGER {
                  eS01 (257),
                  eModem (513),
                  eDsl1 (2049),
                  eDsl2 (2050),
                  eDsl3 (2051),
                  eDsl4 (2052),
                  eAdsl (8193)
            }
    MAX-ACCESS read-only
    STATUS     current
    DESCRIPTION
            "-- empty --"
    ::= { lcsSetupInterfacesAdslEntry 1 }

-- {COLUMN} 1.3.6.1.4.1.2356.11.2.23.6.1.2
lcsSetupInterfacesAdslEntryProtocol OBJECT-TYPE
    SYNTAX     INTEGER {
                  eOff (0),
                  eAuto (8),
                  eAdsl1 (20),
                  eAdsl2 (21),
                  eAdsl2plus (22),
                  eAutoPOTS (520),
                  eAdsl1A (532),
                  eAdsl2A (533),
                  eAdsl2plusA (534),
                  eAdsl2M (543),
                  eAdsl2plusM (544),
                  eAdsl2I (545),
                  eAdsl2plusI (546),
                  eAdsl2L (549),
                  eAutoISDN (776),
                  eAdsl1B (788),
                  eAdsl2B (789),
                  eAdsl2plusB (790),
                  eAdsl2J (803),
                  eAdsl2plusJ (804)
            }
    MAX-ACCESS read-write
    STATUS     current
    DESCRIPTION
            "-- empty --"
    ::= { lcsSetupInterfacesAdslEntry 2 }

-- {COLUMN} 1.3.6.1.4.1.2356.11.2.23.6.1.16
lcsSetupInterfacesAdslEntryUpstreamRate OBJECT-TYPE
    SYNTAX     Integer32 (0..2147483647)
    MAX-ACCESS read-write
    STATUS     current
    DESCRIPTION
            "-- empty --"
    ::= { lcsSetupInterfacesAdslEntry 16 }

-- {COLUMN} 1.3.6.1.4.1.2356.11.2.23.6.1.18
lcsSetupInterfacesAdslEntryDownstreamRate OBJECT-TYPE
    SYNTAX     Integer32 (0..2147483647)
    MAX-ACCESS read-write
    STATUS     current
    DESCRIPTION
            "-- empty --"
    ::= { lcsSetupInterfacesAdslEntry 18 }

-- {TABLE} 1.3.6.1.4.1.2356.11.2.23.7
lcsSetupInterfacesModemMobileTable OBJECT-TYPE
    SYNTAX     SEQUENCE OF LcsSetupInterfacesModemMobileEntry
    MAX-ACCESS not-accessible
    STATUS     current
    DESCRIPTION
            ""
    ::= { lcsSetupInterfaces 7 }

-- {ROW} 1.3.6.1.4.1.2356.11.2.23.7.1
lcsSetupInterfacesModemMobileEntry OBJECT-TYPE
    SYNTAX     LcsSetupInterfacesModemMobileEntry
    MAX-ACCESS not-accessible
    STATUS     current
    DESCRIPTION
            ""
    INDEX {
            lcsSetupInterfacesModemMobileEntryIfc
          }
    ::= { lcsSetupInterfacesModemMobileTable 1 }

LcsSetupInterfacesModemMobileEntry ::= SEQUENCE {
            lcsSetupInterfacesModemMobileEntryIfc INTEGER,
            lcsSetupInterfacesModemMobileEntryOperating INTEGER,
            lcsSetupInterfacesModemMobileEntryTypeOfInterface Integer32,
            lcsSetupInterfacesModemMobileEntryDataRate INTEGER,
            lcsSetupInterfacesModemMobileEntryProfile DisplayString
    }

-- {COLUMN} 1.3.6.1.4.1.2356.11.2.23.7.1.1
lcsSetupInterfacesModemMobileEntryIfc OBJECT-TYPE
    SYNTAX     INTEGER {
                  eS01 (257),
                  eS02 (258),
                  eModem (513),
                  eDsl1 (2049),
                  eDsl2 (2050),
                  eDsl3 (2051),
                  eDsl4 (2052),
                  eDsl5 (2053),
                  eAdsl (8193),
                  eVdsl (16385),
                  eVdsl2 (16386)
            }
    MAX-ACCESS read-only
    STATUS     current
    DESCRIPTION
            ""
    ::= { lcsSetupInterfacesModemMobileEntry 1 }

-- {COLUMN} 1.3.6.1.4.1.2356.11.2.23.7.1.2
lcsSetupInterfacesModemMobileEntryOperating OBJECT-TYPE
    SYNTAX     INTEGER {
                  eNo (0),
                  eModem (1),
                  eWwan (2)
            }
    MAX-ACCESS read-write
    STATUS     current
    DESCRIPTION
            ""
    ::= { lcsSetupInterfacesModemMobileEntry 2 }

-- {COLUMN} 1.3.6.1.4.1.2356.11.2.23.7.1.15
lcsSetupInterfacesModemMobileEntryTypeOfInterface OBJECT-TYPE
    SYNTAX     Integer32 (0..2147483647)
    MAX-ACCESS read-only
    STATUS     current
    DESCRIPTION
            ""
    ::= { lcsSetupInterfacesModemMobileEntry 15 }

-- {COLUMN} 1.3.6.1.4.1.2356.11.2.23.7.1.21
lcsSetupInterfacesModemMobileEntryDataRate OBJECT-TYPE
    SYNTAX     INTEGER {
                  e19200 (19200),
                  e38400 (38400),
                  e57600 (57600),
                  e115200 (115200)
            }
    MAX-ACCESS read-write
    STATUS     current
    DESCRIPTION
            ""
    ::= { lcsSetupInterfacesModemMobileEntry 21 }

-- {COLUMN} 1.3.6.1.4.1.2356.11.2.23.7.1.22
lcsSetupInterfacesModemMobileEntryProfile OBJECT-TYPE
    SYNTAX     DisplayString (SIZE(0..16))
    MAX-ACCESS read-write
    STATUS     current
    DESCRIPTION
            ""
    ::= { lcsSetupInterfacesModemMobileEntry 22 }

-- {TABLE} 1.3.6.1.4.1.2356.11.2.23.8
lcsSetupInterfacesVdslTable OBJECT-TYPE
    SYNTAX     SEQUENCE OF LcsSetupInterfacesVdslEntry
    MAX-ACCESS not-accessible
    STATUS     current
    DESCRIPTION
            ""
    ::= { lcsSetupInterfaces 8 }

-- {ROW} 1.3.6.1.4.1.2356.11.2.23.8.1
lcsSetupInterfacesVdslEntry OBJECT-TYPE
    SYNTAX     LcsSetupInterfacesVdslEntry
    MAX-ACCESS not-accessible
    STATUS     current
    DESCRIPTION
            ""
    INDEX {
            lcsSetupInterfacesVdslEntryIfc
          }
    ::= { lcsSetupInterfacesVdslTable 1 }

LcsSetupInterfacesVdslEntry ::= SEQUENCE {
            lcsSetupInterfacesVdslEntryIfc INTEGER,
            lcsSetupInterfacesVdslEntryProtocol INTEGER,
            lcsSetupInterfacesVdslEntryUpstreamRate Integer32,
            lcsSetupInterfacesVdslEntryDownstreamRate Integer32,
            lcsSetupInterfacesVdslEntryHandshake INTEGER,
            lcsSetupInterfacesVdslEntryOptions BITS
    }

-- {COLUMN} 1.3.6.1.4.1.2356.11.2.23.8.1.1
lcsSetupInterfacesVdslEntryIfc OBJECT-TYPE
    SYNTAX     INTEGER {
                  eS01 (257),
                  eS02 (258),
                  eModem (513),
                  eDsl1 (2049),
                  eDsl2 (2050),
                  eDsl3 (2051),
                  eDsl4 (2052),
                  eDsl5 (2053),
                  eVdsl (16385),
                  eVdsl2 (16386)
            }
    MAX-ACCESS read-only
    STATUS     current
    DESCRIPTION
            ""
    ::= { lcsSetupInterfacesVdslEntry 1 }

-- {COLUMN} 1.3.6.1.4.1.2356.11.2.23.8.1.2
lcsSetupInterfacesVdslEntryProtocol OBJECT-TYPE
    SYNTAX     INTEGER {
                  eOff (0),
                  eAuto (8),
                  eAdsl1 (20),
                  eAdsl2 (21),
                  eAdsl2plus (22),
                  eAdsl2M (31),
                  eAdsl2plusM (32),
                  eAdsl2J (35),
                  eAdsl2plusJ (36),
                  eAdsl2L (37),
                  eVdsl (40),
                  eAdsl (41)
            }
    MAX-ACCESS read-write
    STATUS     current
    DESCRIPTION
            ""
    ::= { lcsSetupInterfacesVdslEntry 2 }

-- {COLUMN} 1.3.6.1.4.1.2356.11.2.23.8.1.16
lcsSetupInterfacesVdslEntryUpstreamRate OBJECT-TYPE
    SYNTAX     Integer32 (0..2147483647)
    MAX-ACCESS read-write
    STATUS     current
    DESCRIPTION
            "-- empty --"
    ::= { lcsSetupInterfacesVdslEntry 16 }

-- {COLUMN} 1.3.6.1.4.1.2356.11.2.23.8.1.18
lcsSetupInterfacesVdslEntryDownstreamRate OBJECT-TYPE
    SYNTAX     Integer32 (0..2147483647)
    MAX-ACCESS read-write
    STATUS     current
    DESCRIPTION
            "-- empty --"
    ::= { lcsSetupInterfacesVdslEntry 18 }

-- {COLUMN} 1.3.6.1.4.1.2356.11.2.23.8.1.25
lcsSetupInterfacesVdslEntryHandshake OBJECT-TYPE
    SYNTAX     INTEGER {
                  eChipsetDefault (0),
                  eV43IfNeeded (1),
                  eV43Enabled (2),
                  eV43Disabled (3)
            }
    MAX-ACCESS read-write
    STATUS     current
    DESCRIPTION
            "-- empty --"
    ::= { lcsSetupInterfacesVdslEntry 25 }

-- {COLUMN} 1.3.6.1.4.1.2356.11.2.23.8.1.28
lcsSetupInterfacesVdslEntryOptions OBJECT-TYPE
    SYNTAX     BITS {
                  eNoOptions (0),
                  eUsVn (14),
                  eUsRetx (15),
                  eDsVn (30),
                  eDsRetx (31)
            }
    MAX-ACCESS read-write
    STATUS     current
    DESCRIPTION
            "-- empty --"
    ::= { lcsSetupInterfacesVdslEntry 28 }

-- {SCALAR} 1.3.6.1.4.1.2356.11.2.23.18
lcsSetupInterfacesPermanentL1Activation OBJECT-TYPE
    SYNTAX     INTEGER {
                  eDisabled (0),
                  eSyncSourceOnly (1),
                  eAllTeInterfaces (2)
            }
    MAX-ACCESS read-write
    STATUS     current
    DESCRIPTION
            ""
    ::= { lcsSetupInterfaces 18 }

-- {SCALAR} 1.3.6.1.4.1.2356.11.2.23.19
lcsSetupInterfacesPcmSyncSource OBJECT-TYPE
    SYNTAX     INTEGER {
                  eAuto (0),
                  eS01 (1),
                  eS02 (2)
            }
    MAX-ACCESS read-write
    STATUS     current
    DESCRIPTION
            ""
    ::= { lcsSetupInterfaces 19 }

-- {NODE} 1.3.6.1.4.1.2356.11.2.23.20
lcsSetupInterfacesWlan OBJECT IDENTIFIER ::= { lcsSetupInterfaces 20 }

-- {TABLE} 1.3.6.1.4.1.2356.11.2.23.20.1
lcsSetupInterfacesWlanNetworkTable OBJECT-TYPE
    SYNTAX     SEQUENCE OF LcsSetupInterfacesWlanNetworkEntry
    MAX-ACCESS not-accessible
    STATUS     current
    DESCRIPTION
            ""
    ::= { lcsSetupInterfacesWlan 1 }

-- {ROW} 1.3.6.1.4.1.2356.11.2.23.20.1.1
lcsSetupInterfacesWlanNetworkEntry OBJECT-TYPE
    SYNTAX     LcsSetupInterfacesWlanNetworkEntry
    MAX-ACCESS not-accessible
    STATUS     current
    DESCRIPTION
            ""
    INDEX {
            lcsSetupInterfacesWlanNetworkEntryIfc
          }
    ::= { lcsSetupInterfacesWlanNetworkTable 1 }

LcsSetupInterfacesWlanNetworkEntry ::= SEQUENCE {
            lcsSetupInterfacesWlanNetworkEntryIfc INTEGER,
            lcsSetupInterfacesWlanNetworkEntryNetworkName DisplayString,
            lcsSetupInterfacesWlanNetworkEntryClosedNetwork INTEGER,
            lcsSetupInterfacesWlanNetworkEntryOperating INTEGER,
            lcsSetupInterfacesWlanNetworkEntryMacFilter INTEGER,
            lcsSetupInterfacesWlanNetworkEntryMaxStations Integer32,
            lcsSetupInterfacesWlanNetworkEntryClBrgSupport INTEGER,
            lcsSetupInterfacesWlanNetworkEntryRadiusAccounting INTEGER,
            lcsSetupInterfacesWlanNetworkEntryInterStationTraffic INTEGER,
            lcsSetupInterfacesWlanNetworkEntryApsd INTEGER,
            lcsSetupInterfacesWlanNetworkEntryAironetExtensions INTEGER,
            lcsSetupInterfacesWlanNetworkEntryMinClientStrength Integer32,
            lcsSetupInterfacesWlanNetworkEntryIncludeUuid INTEGER,
            lcsSetupInterfacesWlanNetworkEntryTransmitOnlyUnicasts INTEGER,
            lcsSetupInterfacesWlanNetworkEntryTxLimit Integer32,
            lcsSetupInterfacesWlanNetworkEntryRxLimit Integer32,
            lcsSetupInterfacesWlanNetworkEntryAccountingServer DisplayString,
            lcsSetupInterfacesWlanNetworkEntryLbsTracking INTEGER,
            lcsSetupInterfacesWlanNetworkEntryLbsTrackingList DisplayString,
            lcsSetupInterfacesWlanNetworkEntryPerClientTxLimit Integer32,
            lcsSetupInterfacesWlanNetworkEntryPerClientRxLimit Integer32,
            lcsSetupInterfacesWlanNetworkEntryAccountingStartCondition INTEGER,
            lcsSetupInterfacesWlanNetworkEntryDynAuth INTEGER,
            lcsSetupInterfacesWlanNetworkEntryDynVlanTrunkPorts DisplayString,
            lcsSetupInterfacesWlanNetworkEntryAssistedRoaming INTEGER,
            lcsSetupInterfacesWlanNetworkEntryTimeframe DisplayString,
            lcsSetupInterfacesWlanNetworkEntryMinClientDisassocStrength Integer32
    }

-- {COLUMN} 1.3.6.1.4.1.2356.11.2.23.20.1.1.1
lcsSetupInterfacesWlanNetworkEntryIfc OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-write
    STATUS     current
    DESCRIPTION
            ""
    ::= { lcsSetupInterfacesWlanNetworkEntry 1 }

-- {COLUMN} 1.3.6.1.4.1.2356.11.2.23.20.1.1.2
lcsSetupInterfacesWlanNetworkEntryNetworkName OBJECT-TYPE
    SYNTAX     DisplayString (SIZE(0..32))
    MAX-ACCESS read-write
    STATUS     current
    DESCRIPTION
            ""
    ::= { lcsSetupInterfacesWlanNetworkEntry 2 }

-- {COLUMN} 1.3.6.1.4.1.2356.11.2.23.20.1.1.4
lcsSetupInterfacesWlanNetworkEntryClosedNetwork OBJECT-TYPE
    SYNTAX     INTEGER {
                  eNo (0),
                  eYes (1),
                  eTightened (2)
            }
    MAX-ACCESS read-write
    STATUS     current
    DESCRIPTION
            ""
    ::= { lcsSetupInterfacesWlanNetworkEntry 4 }

-- {COLUMN} 1.3.6.1.4.1.2356.11.2.23.20.1.1.8
lcsSetupInterfacesWlanNetworkEntryOperating OBJECT-TYPE
    SYNTAX     INTEGER {
                  eYes (0),
                  eNo (1)
            }
    MAX-ACCESS read-write
    STATUS     current
    DESCRIPTION
            ""
    ::= { lcsSetupInterfacesWlanNetworkEntry 8 }

-- {COLUMN} 1.3.6.1.4.1.2356.11.2.23.20.1.1.9
lcsSetupInterfacesWlanNetworkEntryMacFilter OBJECT-TYPE
    SYNTAX     INTEGER {
                  eYes (0),
                  eNo (1),
                  eLocalOnly (2),
                  eRadiusOnly (3)
            }
    MAX-ACCESS read-write
    STATUS     current
    DESCRIPTION
            ""
    ::= { lcsSetupInterfacesWlanNetworkEntry 9 }

-- {COLUMN} 1.3.6.1.4.1.2356.11.2.23.20.1.1.10
lcsSetupInterfacesWlanNetworkEntryMaxStations OBJECT-TYPE
    SYNTAX     Integer32 (0..65535)
    MAX-ACCESS read-write
    STATUS     current
    DESCRIPTION
            ""
    ::= { lcsSetupInterfacesWlanNetworkEntry 10 }

-- {COLUMN} 1.3.6.1.4.1.2356.11.2.23.20.1.1.11
lcsSetupInterfacesWlanNetworkEntryClBrgSupport OBJECT-TYPE
    SYNTAX     INTEGER {
                  eNo (0),
                  eYes (1),
                  eExclusive (2)
            }
    MAX-ACCESS read-write
    STATUS     current
    DESCRIPTION
            ""
    ::= { lcsSetupInterfacesWlanNetworkEntry 11 }

-- {COLUMN} 1.3.6.1.4.1.2356.11.2.23.20.1.1.12
lcsSetupInterfacesWlanNetworkEntryRadiusAccounting OBJECT-TYPE
    SYNTAX     INTEGER {
                  eNo (0),
                  eYes (1)
            }
    MAX-ACCESS read-write
    STATUS     current
    DESCRIPTION
            ""
    ::= { lcsSetupInterfacesWlanNetworkEntry 12 }

-- {COLUMN} 1.3.6.1.4.1.2356.11.2.23.20.1.1.13
lcsSetupInterfacesWlanNetworkEntryInterStationTraffic OBJECT-TYPE
    SYNTAX     INTEGER {
                  eNo (0),
                  eYes (1),
                  eGloballyOff (2)
            }
    MAX-ACCESS read-write
    STATUS     current
    DESCRIPTION
            ""
    ::= { lcsSetupInterfacesWlanNetworkEntry 13 }

-- {COLUMN} 1.3.6.1.4.1.2356.11.2.23.20.1.1.14
lcsSetupInterfacesWlanNetworkEntryApsd OBJECT-TYPE
    SYNTAX     INTEGER {
                  eNo (0),
                  eYes (1)
            }
    MAX-ACCESS read-write
    STATUS     current
    DESCRIPTION
            ""
    ::= { lcsSetupInterfacesWlanNetworkEntry 14 }

-- {COLUMN} 1.3.6.1.4.1.2356.11.2.23.20.1.1.15
lcsSetupInterfacesWlanNetworkEntryAironetExtensions OBJECT-TYPE
    SYNTAX     INTEGER {
                  eNo (0),
                  eYes (1)
            }
    MAX-ACCESS read-write
    STATUS     current
    DESCRIPTION
            ""
    ::= { lcsSetupInterfacesWlanNetworkEntry 15 }

-- {COLUMN} 1.3.6.1.4.1.2356.11.2.23.20.1.1.16
lcsSetupInterfacesWlanNetworkEntryMinClientStrength OBJECT-TYPE
    SYNTAX     Integer32 (0..255)
    MAX-ACCESS read-write
    STATUS     current
    DESCRIPTION
            ""
    ::= { lcsSetupInterfacesWlanNetworkEntry 16 }

-- {COLUMN} 1.3.6.1.4.1.2356.11.2.23.20.1.1.17
lcsSetupInterfacesWlanNetworkEntryIncludeUuid OBJECT-TYPE
    SYNTAX     INTEGER {
                  eNo (0),
                  eYes (1)
            }
    MAX-ACCESS read-write
    STATUS     current
    DESCRIPTION
            "-- empty --"
    ::= { lcsSetupInterfacesWlanNetworkEntry 17 }

-- {COLUMN} 1.3.6.1.4.1.2356.11.2.23.20.1.1.19
lcsSetupInterfacesWlanNetworkEntryTransmitOnlyUnicasts OBJECT-TYPE
    SYNTAX     INTEGER {
                  eNo (0),
                  eYes (1)
            }
    MAX-ACCESS read-write
    STATUS     current
    DESCRIPTION
            "-- empty --"
    ::= { lcsSetupInterfacesWlanNetworkEntry 19 }

-- {COLUMN} 1.3.6.1.4.1.2356.11.2.23.20.1.1.20
lcsSetupInterfacesWlanNetworkEntryTxLimit OBJECT-TYPE
    SYNTAX     Integer32 (0..2147483647)
    MAX-ACCESS read-write
    STATUS     current
    DESCRIPTION
            "-- empty --"
    ::= { lcsSetupInterfacesWlanNetworkEntry 20 }

-- {COLUMN} 1.3.6.1.4.1.2356.11.2.23.20.1.1.21
lcsSetupInterfacesWlanNetworkEntryRxLimit OBJECT-TYPE
    SYNTAX     Integer32 (0..2147483647)
    MAX-ACCESS read-write
    STATUS     current
    DESCRIPTION
            "-- empty --"
    ::= { lcsSetupInterfacesWlanNetworkEntry 21 }

-- {COLUMN} 1.3.6.1.4.1.2356.11.2.23.20.1.1.22
lcsSetupInterfacesWlanNetworkEntryAccountingServer OBJECT-TYPE
    SYNTAX     DisplayString (SIZE(0..16))
    MAX-ACCESS read-write
    STATUS     current
    DESCRIPTION
            "-- empty --"
    ::= { lcsSetupInterfacesWlanNetworkEntry 22 }

-- {COLUMN} 1.3.6.1.4.1.2356.11.2.23.20.1.1.23
lcsSetupInterfacesWlanNetworkEntryLbsTracking OBJECT-TYPE
    SYNTAX     INTEGER {
                  eNo (0),
                  eYes (1)
            }
    MAX-ACCESS read-write
    STATUS     current
    DESCRIPTION
            "-- empty --"
    ::= { lcsSetupInterfacesWlanNetworkEntry 23 }

-- {COLUMN} 1.3.6.1.4.1.2356.11.2.23.20.1.1.24
lcsSetupInterfacesWlanNetworkEntryLbsTrackingList OBJECT-TYPE
    SYNTAX     DisplayString (SIZE(0..32))
    MAX-ACCESS read-write
    STATUS     current
    DESCRIPTION
            "-- empty --"
    ::= { lcsSetupInterfacesWlanNetworkEntry 24 }

-- {COLUMN} 1.3.6.1.4.1.2356.11.2.23.20.1.1.25
lcsSetupInterfacesWlanNetworkEntryPerClientTxLimit OBJECT-TYPE
    SYNTAX     Integer32 (0..2147483647)
    MAX-ACCESS read-write
    STATUS     current
    DESCRIPTION
            "-- empty --"
    ::= { lcsSetupInterfacesWlanNetworkEntry 25 }

-- {COLUMN} 1.3.6.1.4.1.2356.11.2.23.20.1.1.26
lcsSetupInterfacesWlanNetworkEntryPerClientRxLimit OBJECT-TYPE
    SYNTAX     Integer32 (0..2147483647)
    MAX-ACCESS read-write
    STATUS     current
    DESCRIPTION
            "-- empty --"
    ::= { lcsSetupInterfacesWlanNetworkEntry 26 }

-- {COLUMN} 1.3.6.1.4.1.2356.11.2.23.20.1.1.27
lcsSetupInterfacesWlanNetworkEntryAccountingStartCondition OBJECT-TYPE
    SYNTAX     INTEGER {
                  eNone (0),
                  eValidIpv4Address (1),
                  eValidIpv6Address (2),
                  eValidIpAddress (3)
            }
    MAX-ACCESS read-write
    STATUS     current
    DESCRIPTION
            "-- empty --"
    ::= { lcsSetupInterfacesWlanNetworkEntry 27 }

-- {COLUMN} 1.3.6.1.4.1.2356.11.2.23.20.1.1.28
lcsSetupInterfacesWlanNetworkEntryDynAuth OBJECT-TYPE
    SYNTAX     INTEGER {
                  eNo (0),
                  eYes (1)
            }
    MAX-ACCESS read-write
    STATUS     current
    DESCRIPTION
            "-- empty --"
    ::= { lcsSetupInterfacesWlanNetworkEntry 28 }

-- {COLUMN} 1.3.6.1.4.1.2356.11.2.23.20.1.1.29
lcsSetupInterfacesWlanNetworkEntryDynVlanTrunkPorts OBJECT-TYPE
    SYNTAX     DisplayString (SIZE(0..32))
    MAX-ACCESS read-write
    STATUS     current
    DESCRIPTION
            "-- empty --"
    ::= { lcsSetupInterfacesWlanNetworkEntry 29 }

-- {COLUMN} 1.3.6.1.4.1.2356.11.2.23.20.1.1.30
lcsSetupInterfacesWlanNetworkEntryAssistedRoaming OBJECT-TYPE
    SYNTAX     INTEGER {
                  eNo (0),
                  eYes (1)
            }
    MAX-ACCESS read-write
    STATUS     current
    DESCRIPTION
            "-- empty --"
    ::= { lcsSetupInterfacesWlanNetworkEntry 30 }

-- {COLUMN} 1.3.6.1.4.1.2356.11.2.23.20.1.1.31
lcsSetupInterfacesWlanNetworkEntryTimeframe OBJECT-TYPE
    SYNTAX     DisplayString (SIZE(0..31))
    MAX-ACCESS read-write
    STATUS     current
    DESCRIPTION
            "-- empty --"
    ::= { lcsSetupInterfacesWlanNetworkEntry 31 }

-- {COLUMN} 1.3.6.1.4.1.2356.11.2.23.20.1.1.32
lcsSetupInterfacesWlanNetworkEntryMinClientDisassocStrength OBJECT-TYPE
    SYNTAX     Integer32 (0..255)
    MAX-ACCESS read-write
    STATUS     current
    DESCRIPTION
            "-- empty --"
    ::= { lcsSetupInterfacesWlanNetworkEntry 32 }

-- {TABLE} 1.3.6.1.4.1.2356.11.2.23.20.2
lcsSetupInterfacesWlanTransmissionTable OBJECT-TYPE
    SYNTAX     SEQUENCE OF LcsSetupInterfacesWlanTransmissionEntry
    MAX-ACCESS not-accessible
    STATUS     current
    DESCRIPTION
            ""
    ::= { lcsSetupInterfacesWlan 2 }

-- {ROW} 1.3.6.1.4.1.2356.11.2.23.20.2.1
lcsSetupInterfacesWlanTransmissionEntry OBJECT-TYPE
    SYNTAX     LcsSetupInterfacesWlanTransmissionEntry
    MAX-ACCESS not-accessible
    STATUS     current
    DESCRIPTION
            ""
    INDEX {
            lcsSetupInterfacesWlanTransmissionEntryIfc
          }
    ::= { lcsSetupInterfacesWlanTransmissionTable 1 }

LcsSetupInterfacesWlanTransmissionEntry ::= SEQUENCE {
            lcsSetupInterfacesWlanTransmissionEntryIfc INTEGER,
            lcsSetupInterfacesWlanTransmissionEntryPacketSize Integer32,
            lcsSetupInterfacesWlanTransmissionEntryMinTxRate INTEGER,
            lcsSetupInterfacesWlanTransmissionEntryBasicRate INTEGER,
            lcsSetupInterfacesWlanTransmissionEntryRtsThreshold Integer32,
            lcsSetupInterfacesWlanTransmissionEntry11bPreamble INTEGER,
            lcsSetupInterfacesWlanTransmissionEntryMaxTxRate INTEGER,
            lcsSetupInterfacesWlanTransmissionEntryMinFragLen Integer32,
            lcsSetupInterfacesWlanTransmissionEntrySoftRetries Integer32,
            lcsSetupInterfacesWlanTransmissionEntryHardRetries Integer32,
            lcsSetupInterfacesWlanTransmissionEntryShortGuardInterval INTEGER,
            lcsSetupInterfacesWlanTransmissionEntryMaxSpatialStreams INTEGER,
            lcsSetupInterfacesWlanTransmissionEntrySendAggregates INTEGER,
            lcsSetupInterfacesWlanTransmissionEntryMinHtMcs INTEGER,
            lcsSetupInterfacesWlanTransmissionEntryMaxHtMcs INTEGER,
            lcsSetupInterfacesWlanTransmissionEntryMinSpatialStreams INTEGER,
            lcsSetupInterfacesWlanTransmissionEntryEapolRate INTEGER,
            lcsSetupInterfacesWlanTransmissionEntryMaxAggrPacketCount Integer32,
            lcsSetupInterfacesWlanTransmissionEntryProberspRetries Integer32,
            lcsSetupInterfacesWlanTransmissionEntryReceiveAggregates INTEGER,
            lcsSetupInterfacesWlanTransmissionEntryUseStbc INTEGER,
            lcsSetupInterfacesWlanTransmissionEntryUseLdpc INTEGER,
            lcsSetupInterfacesWlanTransmissionEntryConvertToUnicast BITS,
            lcsSetupInterfacesWlanTransmissionEntry11acBeamforming INTEGER,
            lcsSetupInterfacesWlanTransmissionEntryQosMapping INTEGER
    }

-- {COLUMN} 1.3.6.1.4.1.2356.11.2.23.20.2.1.1
lcsSetupInterfacesWlanTransmissionEntryIfc OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-write
    STATUS     current
    DESCRIPTION
            ""
    ::= { lcsSetupInterfacesWlanTransmissionEntry 1 }

-- {COLUMN} 1.3.6.1.4.1.2356.11.2.23.20.2.1.2
lcsSetupInterfacesWlanTransmissionEntryPacketSize OBJECT-TYPE
    SYNTAX     Integer32 (0..65535)
    MAX-ACCESS read-write
    STATUS     current
    DESCRIPTION
            ""
    ::= { lcsSetupInterfacesWlanTransmissionEntry 2 }

-- {COLUMN} 1.3.6.1.4.1.2356.11.2.23.20.2.1.3
lcsSetupInterfacesWlanTransmissionEntryMinTxRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-write
    STATUS     current
    DESCRIPTION
            ""
    ::= { lcsSetupInterfacesWlanTransmissionEntry 3 }

-- {COLUMN} 1.3.6.1.4.1.2356.11.2.23.20.2.1.4
lcsSetupInterfacesWlanTransmissionEntryBasicRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-write
    STATUS     current
    DESCRIPTION
            ""
    ::= { lcsSetupInterfacesWlanTransmissionEntry 4 }

-- {COLUMN} 1.3.6.1.4.1.2356.11.2.23.20.2.1.6
lcsSetupInterfacesWlanTransmissionEntryRtsThreshold OBJECT-TYPE
    SYNTAX     Integer32 (0..65535)
    MAX-ACCESS read-write
    STATUS     current
    DESCRIPTION
            ""
    ::= { lcsSetupInterfacesWlanTransmissionEntry 6 }

-- {COLUMN} 1.3.6.1.4.1.2356.11.2.23.20.2.1.7
lcsSetupInterfacesWlanTransmissionEntry11bPreamble OBJECT-TYPE
    SYNTAX     INTEGER {
                  eAuto (0),
                  eLong (1)
            }
    MAX-ACCESS read-write
    STATUS     current
    DESCRIPTION
            ""
    ::= { lcsSetupInterfacesWlanTransmissionEntry 7 }

-- {COLUMN} 1.3.6.1.4.1.2356.11.2.23.20.2.1.9
lcsSetupInterfacesWlanTransmissionEntryMaxTxRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-write
    STATUS     current
    DESCRIPTION
            ""
    ::= { lcsSetupInterfacesWlanTransmissionEntry 9 }

-- {COLUMN} 1.3.6.1.4.1.2356.11.2.23.20.2.1.10
lcsSetupInterfacesWlanTransmissionEntryMinFragLen OBJECT-TYPE
    SYNTAX     Integer32 (0..65535)
    MAX-ACCESS read-write
    STATUS     current
    DESCRIPTION
            ""
    ::= { lcsSetupInterfacesWlanTransmissionEntry 10 }

-- {COLUMN} 1.3.6.1.4.1.2356.11.2.23.20.2.1.11
lcsSetupInterfacesWlanTransmissionEntrySoftRetries OBJECT-TYPE
    SYNTAX     Integer32 (0..255)
    MAX-ACCESS read-write
    STATUS     current
    DESCRIPTION
            ""
    ::= { lcsSetupInterfacesWlanTransmissionEntry 11 }

-- {COLUMN} 1.3.6.1.4.1.2356.11.2.23.20.2.1.12
lcsSetupInterfacesWlanTransmissionEntryHardRetries OBJECT-TYPE
    SYNTAX     Integer32 (0..255)
    MAX-ACCESS read-write
    STATUS     current
    DESCRIPTION
            ""
    ::= { lcsSetupInterfacesWlanTransmissionEntry 12 }

-- {COLUMN} 1.3.6.1.4.1.2356.11.2.23.20.2.1.13
lcsSetupInterfacesWlanTransmissionEntryShortGuardInterval OBJECT-TYPE
    SYNTAX     INTEGER {
                  eAuto (0),
                  eNo (1)
            }
    MAX-ACCESS read-write
    STATUS     current
    DESCRIPTION
            ""
    ::= { lcsSetupInterfacesWlanTransmissionEntry 13 }

-- {COLUMN} 1.3.6.1.4.1.2356.11.2.23.20.2.1.14
lcsSetupInterfacesWlanTransmissionEntryMaxSpatialStreams OBJECT-TYPE
    SYNTAX     INTEGER {
                  eAuto (0),
                  eOne (1),
                  eTwo (2),
                  eThree (3),
                  eFour (4)
            }
    MAX-ACCESS read-write
    STATUS     current
    DESCRIPTION
            ""
    ::= { lcsSetupInterfacesWlanTransmissionEntry 14 }

-- {COLUMN} 1.3.6.1.4.1.2356.11.2.23.20.2.1.15
lcsSetupInterfacesWlanTransmissionEntrySendAggregates OBJECT-TYPE
    SYNTAX     INTEGER {
                  eNo (0),
                  eYes (1)
            }
    MAX-ACCESS read-write
    STATUS     current
    DESCRIPTION
            ""
    ::= { lcsSetupInterfacesWlanTransmissionEntry 15 }

-- {COLUMN} 1.3.6.1.4.1.2356.11.2.23.20.2.1.16
lcsSetupInterfacesWlanTransmissionEntryMinHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-write
    STATUS     current
    DESCRIPTION
            ""
    ::= { lcsSetupInterfacesWlanTransmissionEntry 16 }

-- {COLUMN} 1.3.6.1.4.1.2356.11.2.23.20.2.1.17
lcsSetupInterfacesWlanTransmissionEntryMaxHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-write
    STATUS     current
    DESCRIPTION
            ""
    ::= { lcsSetupInterfacesWlanTransmissionEntry 17 }

-- {COLUMN} 1.3.6.1.4.1.2356.11.2.23.20.2.1.18
lcsSetupInterfacesWlanTransmissionEntryMinSpatialStreams OBJECT-TYPE
    SYNTAX     INTEGER {
                  eAuto (0),
                  eOne (1),
                  eTwo (2),
                  eThree (3),
                  eFour (4)
            }
    MAX-ACCESS read-write
    STATUS     current
    DESCRIPTION
            ""
    ::= { lcsSetupInterfacesWlanTransmissionEntry 18 }

-- {COLUMN} 1.3.6.1.4.1.2356.11.2.23.20.2.1.19
lcsSetupInterfacesWlanTransmissionEntryEapolRate OBJECT-TYPE
    SYNTAX     INTEGER {
                  eLikeData (0),
                  e1M (1),
                  e2M (2),
                  e5M5 (4),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-write
    STATUS     current
    DESCRIPTION
            ""
    ::= { lcsSetupInterfacesWlanTransmissionEntry 19 }

-- {COLUMN} 1.3.6.1.4.1.2356.11.2.23.20.2.1.20
lcsSetupInterfacesWlanTransmissionEntryMaxAggrPacketCount OBJECT-TYPE
    SYNTAX     Integer32 (0..255)
    MAX-ACCESS read-write
    STATUS     current
    DESCRIPTION
            ""
    ::= { lcsSetupInterfacesWlanTransmissionEntry 20 }

-- {COLUMN} 1.3.6.1.4.1.2356.11.2.23.20.2.1.21
lcsSetupInterfacesWlanTransmissionEntryProberspRetries OBJECT-TYPE
    SYNTAX     Integer32 (0..255)
    MAX-ACCESS read-write
    STATUS     current
    DESCRIPTION
            ""
    ::= { lcsSetupInterfacesWlanTransmissionEntry 21 }

-- {COLUMN} 1.3.6.1.4.1.2356.11.2.23.20.2.1.22
lcsSetupInterfacesWlanTransmissionEntryReceiveAggregates OBJECT-TYPE
    SYNTAX     INTEGER {
                  eNo (0),
                  eYes (1)
            }
    MAX-ACCESS read-write
    STATUS     current
    DESCRIPTION
            ""
    ::= { lcsSetupInterfacesWlanTransmissionEntry 22 }

-- {COLUMN} 1.3.6.1.4.1.2356.11.2.23.20.2.1.23
lcsSetupInterfacesWlanTransmissionEntryUseStbc OBJECT-TYPE
    SYNTAX     INTEGER {
                  eNo (0),
                  eYes (1)
            }
    MAX-ACCESS read-write
    STATUS     current
    DESCRIPTION
            "-- empty --"
    ::= { lcsSetupInterfacesWlanTransmissionEntry 23 }

-- {COLUMN} 1.3.6.1.4.1.2356.11.2.23.20.2.1.24
lcsSetupInterfacesWlanTransmissionEntryUseLdpc OBJECT-TYPE
    SYNTAX     INTEGER {
                  eNo (0),
                  eYes (1)
            }
    MAX-ACCESS read-write
    STATUS     current
    DESCRIPTION
            "-- empty --"
    ::= { lcsSetupInterfacesWlanTransmissionEntry 24 }

-- {COLUMN} 1.3.6.1.4.1.2356.11.2.23.20.2.1.25
lcsSetupInterfacesWlanTransmissionEntryConvertToUnicast OBJECT-TYPE
    SYNTAX     BITS {
                  eMulticast (30),
                  eDhcp (31)
            }
    MAX-ACCESS read-write
    STATUS     current
    DESCRIPTION
            "-- empty --"
    ::= { lcsSetupInterfacesWlanTransmissionEntry 25 }

-- {COLUMN} 1.3.6.1.4.1.2356.11.2.23.20.2.1.26
lcsSetupInterfacesWlanTransmissionEntry11acBeamforming OBJECT-TYPE
    SYNTAX     INTEGER {
                  eAuto (0),
                  eNo (1),
                  eSuMimo (2),
                  eMuMimo (3)
            }
    MAX-ACCESS read-write
    STATUS     current
    DESCRIPTION
            "-- empty --"
    ::= { lcsSetupInterfacesWlanTransmissionEntry 26 }

-- {COLUMN} 1.3.6.1.4.1.2356.11.2.23.20.2.1.27
lcsSetupInterfacesWlanTransmissionEntryQosMapping OBJECT-TYPE
    SYNTAX     INTEGER {
                  eNo (0),
                  eYes (1)
            }
    MAX-ACCESS read-write
    STATUS     current
    DESCRIPTION
            "-- empty --"
    ::= { lcsSetupInterfacesWlanTransmissionEntry 27 }

-- {TABLE} 1.3.6.1.4.1.2356.11.2.23.20.3
lcsSetupInterfacesWlanEncryptionTable OBJECT-TYPE
    SYNTAX     SEQUENCE OF LcsSetupInterfacesWlanEncryptionEntry
    MAX-ACCESS not-accessible
    STATUS     current
    DESCRIPTION
            ""
    ::= { lcsSetupInterfacesWlan 3 }

-- {ROW} 1.3.6.1.4.1.2356.11.2.23.20.3.1
lcsSetupInterfacesWlanEncryptionEntry OBJECT-TYPE
    SYNTAX     LcsSetupInterfacesWlanEncryptionEntry
    MAX-ACCESS not-accessible
    STATUS     current
    DESCRIPTION
            ""
    INDEX {
            lcsSetupInterfacesWlanEncryptionEntryIfc
          }
    ::= { lcsSetupInterfacesWlanEncryptionTable 1 }

LcsSetupInterfacesWlanEncryptionEntry ::= SEQUENCE {
            lcsSetupInterfacesWlanEncryptionEntryIfc INTEGER,
            lcsSetupInterfacesWlanEncryptionEntryEncryption INTEGER,
            lcsSetupInterfacesWlanEncryptionEntryDefaultKey Integer32,
            lcsSetupInterfacesWlanEncryptionEntryMethod INTEGER,
            lcsSetupInterfacesWlanEncryptionEntryAuthentication INTEGER,
            lcsSetupInterfacesWlanEncryptionEntryKey DisplayString,
            lcsSetupInterfacesWlanEncryptionEntryWpaVersion INTEGER,
            lcsSetupInterfacesWlanEncryptionEntryClientEapMethod INTEGER,
            lcsSetupInterfacesWlanEncryptionEntryWpaRekeyingCycle Integer32,
            lcsSetupInterfacesWlanEncryptionEntryWpa1SessionKeytypes INTEGER,
            lcsSetupInterfacesWlanEncryptionEntryWpa2SessionKeytypes INTEGER,
            lcsSetupInterfacesWlanEncryptionEntryProtMgmtFrames INTEGER,
            lcsSetupInterfacesWlanEncryptionEntryPmkCaching INTEGER,
            lcsSetupInterfacesWlanEncryptionEntryPreAuthentication INTEGER,
            lcsSetupInterfacesWlanEncryptionEntryOkc INTEGER,
            lcsSetupInterfacesWlanEncryptionEntryWpa2KeyManagement BITS,
            lcsSetupInterfacesWlanEncryptionEntryPmkIappSecret DisplayString,
            lcsSetupInterfacesWlanEncryptionEntryRadiusProfile DisplayString,
            lcsSetupInterfacesWlanEncryptionEntryOWE-Groups BITS,
            lcsSetupInterfacesWlanEncryptionEntryOWE-Key-Lifetime Integer32,
            lcsSetupInterfacesWlanEncryptionEntrySaeGroups BITS,
            lcsSetupInterfacesWlanEncryptionEntryWpa23SessionKeytypes BITS,
            lcsSetupInterfacesWlanEncryptionEntryWpa8021xSecurityLevel INTEGER
    }

-- {COLUMN} 1.3.6.1.4.1.2356.11.2.23.20.3.1.1
lcsSetupInterfacesWlanEncryptionEntryIfc OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-write
    STATUS     current
    DESCRIPTION
            ""
    ::= { lcsSetupInterfacesWlanEncryptionEntry 1 }

-- {COLUMN} 1.3.6.1.4.1.2356.11.2.23.20.3.1.2
lcsSetupInterfacesWlanEncryptionEntryEncryption OBJECT-TYPE
    SYNTAX     INTEGER {
                  eNo (0),
                  eYes (2)
            }
    MAX-ACCESS read-write
    STATUS     current
    DESCRIPTION
            ""
    ::= { lcsSetupInterfacesWlanEncryptionEntry 2 }

-- {COLUMN} 1.3.6.1.4.1.2356.11.2.23.20.3.1.3
lcsSetupInterfacesWlanEncryptionEntryDefaultKey OBJECT-TYPE
    SYNTAX     Integer32 (0..255)
    MAX-ACCESS read-write
    STATUS     current
    DESCRIPTION
            ""
    ::= { lcsSetupInterfacesWlanEncryptionEntry 3 }

-- {COLUMN} 1.3.6.1.4.1.2356.11.2.23.20.3.1.4
lcsSetupInterfacesWlanEncryptionEntryMethod OBJECT-TYPE
    SYNTAX     INTEGER {
                  eWep40Bits (5),
                  eWep104Bits (13),
                  eWep128Bits (16),
                  e80211iWpaPsk (32),
                  e80211iWpa8021x (33),
                  eWep40Bits8021x (34),
                  eWep104Bits8021x (35),
                  eWep128Bits8021x (36),
                  eWPA-OWE (37),
                  eEnhancedOpenTransitional (38),
                  eOsen (39)
            }
    MAX-ACCESS read-write
    STATUS     current
    DESCRIPTION
            ""
    ::= { lcsSetupInterfacesWlanEncryptionEntry 4 }

-- {COLUMN} 1.3.6.1.4.1.2356.11.2.23.20.3.1.5
lcsSetupInterfacesWlanEncryptionEntryAuthentication OBJECT-TYPE
    SYNTAX     INTEGER {
                  eOpenSystem (0),
                  eSharedKey (1)
            }
    MAX-ACCESS read-write
    STATUS     current
    DESCRIPTION
            ""
    ::= { lcsSetupInterfacesWlanEncryptionEntry 5 }

-- {COLUMN} 1.3.6.1.4.1.2356.11.2.23.20.3.1.6
lcsSetupInterfacesWlanEncryptionEntryKey OBJECT-TYPE
    SYNTAX     DisplayString (SIZE(0..63))
    MAX-ACCESS read-write
    STATUS     current
    DESCRIPTION
            ""
    ::= { lcsSetupInterfacesWlanEncryptionEntry 6 }

-- {COLUMN} 1.3.6.1.4.1.2356.11.2.23.20.3.1.9
lcsSetupInterfacesWlanEncryptionEntryWpaVersion OBJECT-TYPE
    SYNTAX     INTEGER {
                  eWpa1 (2),
                  eWpa2 (4),
                  eWpa12 (6),
                  eWpa3 (8),
                  eWpa23 (12),
                  eWpa123 (14)
            }
    MAX-ACCESS read-write
    STATUS     current
    DESCRIPTION
            ""
    ::= { lcsSetupInterfacesWlanEncryptionEntry 9 }

-- {COLUMN} 1.3.6.1.4.1.2356.11.2.23.20.3.1.10
lcsSetupInterfacesWlanEncryptionEntryClientEapMethod OBJECT-TYPE
    SYNTAX     INTEGER {
                  eTls (3328),
                  eTtlsMd5 (5380),
                  eTtlsPap (5383),
                  eTtlsChap (5384),
                  eTtlsMschapv2 (5402),
                  eTtlsMschap (5567),
                  ePeapGtc (6406),
                  ePeapMschapv2 (6426),
                  eWfaUnauth (36096)
            }
    MAX-ACCESS read-write
    STATUS     current
    DESCRIPTION
            ""
    ::= { lcsSetupInterfacesWlanEncryptionEntry 10 }

-- {COLUMN} 1.3.6.1.4.1.2356.11.2.23.20.3.1.11
lcsSetupInterfacesWlanEncryptionEntryWpaRekeyingCycle OBJECT-TYPE
    SYNTAX     Integer32 (0..2147483647)
    MAX-ACCESS read-write
    STATUS     current
    DESCRIPTION
            ""
    ::= { lcsSetupInterfacesWlanEncryptionEntry 11 }

-- {COLUMN} 1.3.6.1.4.1.2356.11.2.23.20.3.1.12
lcsSetupInterfacesWlanEncryptionEntryWpa1SessionKeytypes OBJECT-TYPE
    SYNTAX     INTEGER {
                  eTkip (1),
                  eAes (2),
                  eTkipAes (3)
            }
    MAX-ACCESS read-write
    STATUS     current
    DESCRIPTION
            ""
    ::= { lcsSetupInterfacesWlanEncryptionEntry 12 }

-- {COLUMN} 1.3.6.1.4.1.2356.11.2.23.20.3.1.13
lcsSetupInterfacesWlanEncryptionEntryWpa2SessionKeytypes OBJECT-TYPE
    SYNTAX     INTEGER {
                  eTkip (1),
                  eAes (2),
                  eTkipAes (3)
            }
    MAX-ACCESS read-write
    STATUS     current
    DESCRIPTION
            ""
    ::= { lcsSetupInterfacesWlanEncryptionEntry 13 }

-- {COLUMN} 1.3.6.1.4.1.2356.11.2.23.20.3.1.14
lcsSetupInterfacesWlanEncryptionEntryProtMgmtFrames OBJECT-TYPE
    SYNTAX     INTEGER {
                  eNo (0),
                  eOptional (1),
                  eMandatory (2)
            }
    MAX-ACCESS read-write
    STATUS     current
    DESCRIPTION
            ""
    ::= { lcsSetupInterfacesWlanEncryptionEntry 14 }

-- {COLUMN} 1.3.6.1.4.1.2356.11.2.23.20.3.1.15
lcsSetupInterfacesWlanEncryptionEntryPmkCaching OBJECT-TYPE
    SYNTAX     INTEGER {
                  eNo (0),
                  eYes (1)
            }
    MAX-ACCESS read-write
    STATUS     current
    DESCRIPTION
            "-- empty --"
    ::= { lcsSetupInterfacesWlanEncryptionEntry 15 }

-- {COLUMN} 1.3.6.1.4.1.2356.11.2.23.20.3.1.16
lcsSetupInterfacesWlanEncryptionEntryPreAuthentication OBJECT-TYPE
    SYNTAX     INTEGER {
                  eNo (0),
                  eYes (1)
            }
    MAX-ACCESS read-write
    STATUS     current
    DESCRIPTION
            "-- empty --"
    ::= { lcsSetupInterfacesWlanEncryptionEntry 16 }

-- {COLUMN} 1.3.6.1.4.1.2356.11.2.23.20.3.1.17
lcsSetupInterfacesWlanEncryptionEntryOkc OBJECT-TYPE
    SYNTAX     INTEGER {
                  eNo (0),
                  eYes (1)
            }
    MAX-ACCESS read-write
    STATUS     current
    DESCRIPTION
            "-- empty --"
    ::= { lcsSetupInterfacesWlanEncryptionEntry 17 }

-- {COLUMN} 1.3.6.1.4.1.2356.11.2.23.20.3.1.19
lcsSetupInterfacesWlanEncryptionEntryWpa2KeyManagement OBJECT-TYPE
    SYNTAX     BITS {
                  eSha256 (5),
                  eFastRoaming (6),
                  eStandard (7)
            }
    MAX-ACCESS read-write
    STATUS     current
    DESCRIPTION
            "-- empty --"
    ::= { lcsSetupInterfacesWlanEncryptionEntry 19 }

-- {COLUMN} 1.3.6.1.4.1.2356.11.2.23.20.3.1.20
lcsSetupInterfacesWlanEncryptionEntryPmkIappSecret OBJECT-TYPE
    SYNTAX     DisplayString (SIZE(0..64))
    MAX-ACCESS read-write
    STATUS     current
    DESCRIPTION
            "-- empty --"
    ::= { lcsSetupInterfacesWlanEncryptionEntry 20 }

-- {COLUMN} 1.3.6.1.4.1.2356.11.2.23.20.3.1.21
lcsSetupInterfacesWlanEncryptionEntryRadiusProfile OBJECT-TYPE
    SYNTAX     DisplayString (SIZE(0..16))
    MAX-ACCESS read-write
    STATUS     current
    DESCRIPTION
            "-- empty --"
    ::= { lcsSetupInterfacesWlanEncryptionEntry 21 }

-- {COLUMN} 1.3.6.1.4.1.2356.11.2.23.20.3.1.22
lcsSetupInterfacesWlanEncryptionEntryOWE-Groups OBJECT-TYPE
    SYNTAX     BITS {
                  eSecp521r1 (10),
                  eSecp384r1 (11),
                  eSecp256r1 (12)
            }
    MAX-ACCESS read-write
    STATUS     current
    DESCRIPTION
            "OWE Finite Groups"
    ::= { lcsSetupInterfacesWlanEncryptionEntry 22 }

-- {COLUMN} 1.3.6.1.4.1.2356.11.2.23.20.3.1.23
lcsSetupInterfacesWlanEncryptionEntryOWE-Key-Lifetime OBJECT-TYPE
    SYNTAX     Integer32 (0..2147483647)
    MAX-ACCESS read-write
    STATUS     current
    DESCRIPTION
            ""
    ::= { lcsSetupInterfacesWlanEncryptionEntry 23 }

-- {COLUMN} 1.3.6.1.4.1.2356.11.2.23.20.3.1.26
lcsSetupInterfacesWlanEncryptionEntrySaeGroups OBJECT-TYPE
    SYNTAX     BITS {
                  eSecp521r1 (10),
                  eSecp384r1 (11),
                  eSecp256r1 (12)
            }
    MAX-ACCESS read-write
    STATUS     current
    DESCRIPTION
            "-- empty --"
    ::= { lcsSetupInterfacesWlanEncryptionEntry 26 }

-- {COLUMN} 1.3.6.1.4.1.2356.11.2.23.20.3.1.27
lcsSetupInterfacesWlanEncryptionEntryWpa23SessionKeytypes OBJECT-TYPE
    SYNTAX     BITS {
                  eAesGcmp256 (3),
                  eAesGcmp128 (4),
                  eAesCcmp256 (5),
                  eAesCcm (6),
                  eTkip (7)
            }
    MAX-ACCESS read-write
    STATUS     current
    DESCRIPTION
            "-- empty --"
    ::= { lcsSetupInterfacesWlanEncryptionEntry 27 }

-- {COLUMN} 1.3.6.1.4.1.2356.11.2.23.20.3.1.28
lcsSetupInterfacesWlanEncryptionEntryWpa8021xSecurityLevel OBJECT-TYPE
    SYNTAX     INTEGER {
                  eStandard (0),
                  eSuiteB128Bits (1),
                  eSuiteB192Bits (2)
            }
    MAX-ACCESS read-write
    STATUS     current
    DESCRIPTION
            "-- empty --"
    ::= { lcsSetupInterfacesWlanEncryptionEntry 28 }

-- {TABLE} 1.3.6.1.4.1.2356.11.2.23.20.4
lcsSetupInterfacesWlanGroupEncryptionKeysTable OBJECT-TYPE
    SYNTAX     SEQUENCE OF LcsSetupInterfacesWlanGroupEncryptionKeysEntry
    MAX-ACCESS not-accessible
    STATUS     current
    DESCRIPTION
            ""
    ::= { lcsSetupInterfacesWlan 4 }

-- {ROW} 1.3.6.1.4.1.2356.11.2.23.20.4.1
lcsSetupInterfacesWlanGroupEncryptionKeysEntry OBJECT-TYPE
    SYNTAX     LcsSetupInterfacesWlanGroupEncryptionKeysEntry
    MAX-ACCESS not-accessible
    STATUS     current
    DESCRIPTION
            ""
    INDEX {
            lcsSetupInterfacesWlanGroupEncryptionKeysEntryIfc
          }
    ::= { lcsSetupInterfacesWlanGroupEncryptionKeysTable 1 }

LcsSetupInterfacesWlanGroupEncryptionKeysEntry ::= SEQUENCE {
            lcsSetupInterfacesWlanGroupEncryptionKeysEntryIfc INTEGER,
            lcsSetupInterfacesWlanGroupEncryptionKeysEntryKey2 DisplayString,
            lcsSetupInterfacesWlanGroupEncryptionKeysEntryKey3 DisplayString,
            lcsSetupInterfacesWlanGroupEncryptionKeysEntryKey4 DisplayString,
            lcsSetupInterfacesWlanGroupEncryptionKeysEntryKeytype2 INTEGER,
            lcsSetupInterfacesWlanGroupEncryptionKeysEntryKeytype3 INTEGER,
            lcsSetupInterfacesWlanGroupEncryptionKeysEntryKeytype4 INTEGER
    }

-- {COLUMN} 1.3.6.1.4.1.2356.11.2.23.20.4.1.1
lcsSetupInterfacesWlanGroupEncryptionKeysEntryIfc OBJECT-TYPE
    SYNTAX     INTEGER {
                  eWlan1 (1),
                  eWlan2 (2)
            }
    MAX-ACCESS read-write
    STATUS     current
    DESCRIPTION
            ""
    ::= { lcsSetupInterfacesWlanGroupEncryptionKeysEntry 1 }

-- {COLUMN} 1.3.6.1.4.1.2356.11.2.23.20.4.1.3
lcsSetupInterfacesWlanGroupEncryptionKeysEntryKey2 OBJECT-TYPE
    SYNTAX     DisplayString (SIZE(0..63))
    MAX-ACCESS read-write
    STATUS     current
    DESCRIPTION
            ""
    ::= { lcsSetupInterfacesWlanGroupEncryptionKeysEntry 3 }

-- {COLUMN} 1.3.6.1.4.1.2356.11.2.23.20.4.1.4
lcsSetupInterfacesWlanGroupEncryptionKeysEntryKey3 OBJECT-TYPE
    SYNTAX     DisplayString (SIZE(0..63))
    MAX-ACCESS read-write
    STATUS     current
    DESCRIPTION
            ""
    ::= { lcsSetupInterfacesWlanGroupEncryptionKeysEntry 4 }

-- {COLUMN} 1.3.6.1.4.1.2356.11.2.23.20.4.1.5
lcsSetupInterfacesWlanGroupEncryptionKeysEntryKey4 OBJECT-TYPE
    SYNTAX     DisplayString (SIZE(0..63))
    MAX-ACCESS read-write
    STATUS     current
    DESCRIPTION
            ""
    ::= { lcsSetupInterfacesWlanGroupEncryptionKeysEntry 5 }

-- {COLUMN} 1.3.6.1.4.1.2356.11.2.23.20.4.1.7
lcsSetupInterfacesWlanGroupEncryptionKeysEntryKeytype2 OBJECT-TYPE
    SYNTAX     INTEGER {
                  eWep40Bits (5),
                  eWep104Bits (13),
                  eWep128Bits (16)
            }
    MAX-ACCESS read-write
    STATUS     current
    DESCRIPTION
            ""
    ::= { lcsSetupInterfacesWlanGroupEncryptionKeysEntry 7 }

-- {COLUMN} 1.3.6.1.4.1.2356.11.2.23.20.4.1.8
lcsSetupInterfacesWlanGroupEncryptionKeysEntryKeytype3 OBJECT-TYPE
    SYNTAX     INTEGER {
                  eWep40Bits (5),
                  eWep104Bits (13),
                  eWep128Bits (16)
            }
    MAX-ACCESS read-write
    STATUS     current
    DESCRIPTION
            ""
    ::= { lcsSetupInterfacesWlanGroupEncryptionKeysEntry 8 }

-- {COLUMN} 1.3.6.1.4.1.2356.11.2.23.20.4.1.9
lcsSetupInterfacesWlanGroupEncryptionKeysEntryKeytype4 OBJECT-TYPE
    SYNTAX     INTEGER {
                  eWep40Bits (5),
                  eWep104Bits (13),
                  eWep128Bits (16)
            }
    MAX-ACCESS read-write
    STATUS     current
    DESCRIPTION
            ""
    ::= { lcsSetupInterfacesWlanGroupEncryptionKeysEntry 9 }

-- {TABLE} 1.3.6.1.4.1.2356.11.2.23.20.5
lcsSetupInterfacesWlanIntpntSetTable OBJECT-TYPE
    SYNTAX     SEQUENCE OF LcsSetupInterfacesWlanIntpntSetEntry
    MAX-ACCESS not-accessible
    STATUS     current
    DESCRIPTION
            ""
    ::= { lcsSetupInterfacesWlan 5 }

-- {ROW} 1.3.6.1.4.1.2356.11.2.23.20.5.1
lcsSetupInterfacesWlanIntpntSetEntry OBJECT-TYPE
    SYNTAX     LcsSetupInterfacesWlanIntpntSetEntry
    MAX-ACCESS not-accessible
    STATUS     current
    DESCRIPTION
            ""
    INDEX {
            lcsSetupInterfacesWlanIntpntSetEntryIfc
          }
    ::= { lcsSetupInterfacesWlanIntpntSetTable 1 }

LcsSetupInterfacesWlanIntpntSetEntry ::= SEQUENCE {
            lcsSetupInterfacesWlanIntpntSetEntryIfc INTEGER,
            lcsSetupInterfacesWlanIntpntSetEntryEnable INTEGER,
            lcsSetupInterfacesWlanIntpntSetEntryIsolatedMode INTEGER,
            lcsSetupInterfacesWlanIntpntSetEntryChanSelScheme INTEGER,
            lcsSetupInterfacesWlanIntpntSetEntryLinkLossTimeout Integer32,
            lcsSetupInterfacesWlanIntpntSetEntryKeyHandshakeRole INTEGER,
            lcsSetupInterfacesWlanIntpntSetEntryLocalName DisplayString,
            lcsSetupInterfacesWlanIntpntSetEntryRemoteStatusReporting INTEGER,
            lcsSetupInterfacesWlanIntpntSetEntryNetworkName DisplayString
    }

-- {COLUMN} 1.3.6.1.4.1.2356.11.2.23.20.5.1.1
lcsSetupInterfacesWlanIntpntSetEntryIfc OBJECT-TYPE
    SYNTAX     INTEGER {
                  eWlan1 (1),
                  eWlan2 (2)
            }
    MAX-ACCESS read-write
    STATUS     current
    DESCRIPTION
            ""
    ::= { lcsSetupInterfacesWlanIntpntSetEntry 1 }

-- {COLUMN} 1.3.6.1.4.1.2356.11.2.23.20.5.1.2
lcsSetupInterfacesWlanIntpntSetEntryEnable OBJECT-TYPE
    SYNTAX     INTEGER {
                  eNo (0),
                  eYes (1),
                  eExclusive (2)
            }
    MAX-ACCESS read-write
    STATUS     current
    DESCRIPTION
            ""
    ::= { lcsSetupInterfacesWlanIntpntSetEntry 2 }

-- {COLUMN} 1.3.6.1.4.1.2356.11.2.23.20.5.1.9
lcsSetupInterfacesWlanIntpntSetEntryIsolatedMode OBJECT-TYPE
    SYNTAX     INTEGER {
                  eNo (0),
                  eYes (1)
            }
    MAX-ACCESS read-write
    STATUS     current
    DESCRIPTION
            ""
    ::= { lcsSetupInterfacesWlanIntpntSetEntry 9 }

-- {COLUMN} 1.3.6.1.4.1.2356.11.2.23.20.5.1.10
lcsSetupInterfacesWlanIntpntSetEntryChanSelScheme OBJECT-TYPE
    SYNTAX     INTEGER {
                  eMaster (0),
                  eSlave (1)
            }
    MAX-ACCESS read-write
    STATUS     current
    DESCRIPTION
            ""
    ::= { lcsSetupInterfacesWlanIntpntSetEntry 10 }

-- {COLUMN} 1.3.6.1.4.1.2356.11.2.23.20.5.1.11
lcsSetupInterfacesWlanIntpntSetEntryLinkLossTimeout OBJECT-TYPE
    SYNTAX     Integer32 (0..2147483647)
    MAX-ACCESS read-write
    STATUS     current
    DESCRIPTION
            ""
    ::= { lcsSetupInterfacesWlanIntpntSetEntry 11 }

-- {COLUMN} 1.3.6.1.4.1.2356.11.2.23.20.5.1.12
lcsSetupInterfacesWlanIntpntSetEntryKeyHandshakeRole OBJECT-TYPE
    SYNTAX     INTEGER {
                  eDefault (0),
                  eAuto (3)
            }
    MAX-ACCESS read-write
    STATUS     current
    DESCRIPTION
            ""
    ::= { lcsSetupInterfacesWlanIntpntSetEntry 12 }

-- {COLUMN} 1.3.6.1.4.1.2356.11.2.23.20.5.1.13
lcsSetupInterfacesWlanIntpntSetEntryLocalName OBJECT-TYPE
    SYNTAX     DisplayString (SIZE(0..24))
    MAX-ACCESS read-write
    STATUS     current
    DESCRIPTION
            ""
    ::= { lcsSetupInterfacesWlanIntpntSetEntry 13 }

-- {COLUMN} 1.3.6.1.4.1.2356.11.2.23.20.5.1.14
lcsSetupInterfacesWlanIntpntSetEntryRemoteStatusReporting OBJECT-TYPE
    SYNTAX     INTEGER {
                  eNo (0),
                  eYes (1)
            }
    MAX-ACCESS read-write
    STATUS     current
    DESCRIPTION
            "-- empty --"
    ::= { lcsSetupInterfacesWlanIntpntSetEntry 14 }

-- {COLUMN} 1.3.6.1.4.1.2356.11.2.23.20.5.1.15
lcsSetupInterfacesWlanIntpntSetEntryNetworkName OBJECT-TYPE
    SYNTAX     DisplayString (SIZE(0..32))
    MAX-ACCESS read-write
    STATUS     current
    DESCRIPTION
            "-- empty --"
    ::= { lcsSetupInterfacesWlanIntpntSetEntry 15 }

-- {TABLE} 1.3.6.1.4.1.2356.11.2.23.20.6
lcsSetupInterfacesWlanClientModesTable OBJECT-TYPE
    SYNTAX     SEQUENCE OF LcsSetupInterfacesWlanClientModesEntry
    MAX-ACCESS not-accessible
    STATUS     current
    DESCRIPTION
            ""
    ::= { lcsSetupInterfacesWlan 6 }

-- {ROW} 1.3.6.1.4.1.2356.11.2.23.20.6.1
lcsSetupInterfacesWlanClientModesEntry OBJECT-TYPE
    SYNTAX     LcsSetupInterfacesWlanClientModesEntry
    MAX-ACCESS not-accessible
    STATUS     current
    DESCRIPTION
            ""
    INDEX {
            lcsSetupInterfacesWlanClientModesEntryIfc
          }
    ::= { lcsSetupInterfacesWlanClientModesTable 1 }

LcsSetupInterfacesWlanClientModesEntry ::= SEQUENCE {
            lcsSetupInterfacesWlanClientModesEntryIfc INTEGER,
            lcsSetupInterfacesWlanClientModesEntryCreateIbss INTEGER,
            lcsSetupInterfacesWlanClientModesEntryConnectionKeepalive INTEGER,
            lcsSetupInterfacesWlanClientModesEntryNetworkTypes INTEGER,
            lcsSetupInterfacesWlanClientModesEntryScanBands INTEGER,
            lcsSetupInterfacesWlanClientModesEntryPreferredBss MacAddress,
            lcsSetupInterfacesWlanClientModesEntryAddressAdaption INTEGER,
            lcsSetupInterfacesWlanClientModesEntryClBrgSupport INTEGER,
            lcsSetupInterfacesWlanClientModesEntryTxLimit Integer32,
            lcsSetupInterfacesWlanClientModesEntryRxLimit Integer32,
            lcsSetupInterfacesWlanClientModesEntrySelectionPreference INTEGER,
            lcsSetupInterfacesWlanClientModesEntrySendDeauthUpon BITS
    }

-- {COLUMN} 1.3.6.1.4.1.2356.11.2.23.20.6.1.1
lcsSetupInterfacesWlanClientModesEntryIfc OBJECT-TYPE
    SYNTAX     INTEGER {
                  eWlan1 (1),
                  eWlan2 (2)
            }
    MAX-ACCESS read-write
    STATUS     current
    DESCRIPTION
            ""
    ::= { lcsSetupInterfacesWlanClientModesEntry 1 }

-- {COLUMN} 1.3.6.1.4.1.2356.11.2.23.20.6.1.2
lcsSetupInterfacesWlanClientModesEntryCreateIbss OBJECT-TYPE
    SYNTAX     INTEGER {
                  eNo (0),
                  eYes (1)
            }
    MAX-ACCESS read-write
    STATUS     current
    DESCRIPTION
            ""
    ::= { lcsSetupInterfacesWlanClientModesEntry 2 }

-- {COLUMN} 1.3.6.1.4.1.2356.11.2.23.20.6.1.3
lcsSetupInterfacesWlanClientModesEntryConnectionKeepalive OBJECT-TYPE
    SYNTAX     INTEGER {
                  eNo (0),
                  eYes (1)
            }
    MAX-ACCESS read-write
    STATUS     current
    DESCRIPTION
            ""
    ::= { lcsSetupInterfacesWlanClientModesEntry 3 }

-- {COLUMN} 1.3.6.1.4.1.2356.11.2.23.20.6.1.4
lcsSetupInterfacesWlanClientModesEntryNetworkTypes OBJECT-TYPE
    SYNTAX     INTEGER {
                  eAdhoc (2),
                  eInfrastructure (4),
                  eBoth (6)
            }
    MAX-ACCESS read-write
    STATUS     current
    DESCRIPTION
            ""
    ::= { lcsSetupInterfacesWlanClientModesEntry 4 }

-- {COLUMN} 1.3.6.1.4.1.2356.11.2.23.20.6.1.5
lcsSetupInterfacesWlanClientModesEntryScanBands OBJECT-TYPE
    SYNTAX     INTEGER {
                  e24ghz (1),
                  e5ghz (2),
                  e24ghz5ghz (3)
            }
    MAX-ACCESS read-write
    STATUS     current
    DESCRIPTION
            ""
    ::= { lcsSetupInterfacesWlanClientModesEntry 5 }

-- {COLUMN} 1.3.6.1.4.1.2356.11.2.23.20.6.1.6
lcsSetupInterfacesWlanClientModesEntryPreferredBss OBJECT-TYPE
    SYNTAX     MacAddress
    MAX-ACCESS read-write
    STATUS     current
    DESCRIPTION
            ""
    ::= { lcsSetupInterfacesWlanClientModesEntry 6 }

-- {COLUMN} 1.3.6.1.4.1.2356.11.2.23.20.6.1.7
lcsSetupInterfacesWlanClientModesEntryAddressAdaption OBJECT-TYPE
    SYNTAX     INTEGER {
                  eNo (0),
                  eYes (1)
            }
    MAX-ACCESS read-write
    STATUS     current
    DESCRIPTION
            ""
    ::= { lcsSetupInterfacesWlanClientModesEntry 7 }

-- {COLUMN} 1.3.6.1.4.1.2356.11.2.23.20.6.1.8
lcsSetupInterfacesWlanClientModesEntryClBrgSupport OBJECT-TYPE
    SYNTAX     INTEGER {
                  eNo (0),
                  eYes (1)
            }
    MAX-ACCESS read-write
    STATUS     current
    DESCRIPTION
            ""
    ::= { lcsSetupInterfacesWlanClientModesEntry 8 }

-- {COLUMN} 1.3.6.1.4.1.2356.11.2.23.20.6.1.9
lcsSetupInterfacesWlanClientModesEntryTxLimit OBJECT-TYPE
    SYNTAX     Integer32 (0..2147483647)
    MAX-ACCESS read-write
    STATUS     current
    DESCRIPTION
            ""
    ::= { lcsSetupInterfacesWlanClientModesEntry 9 }

-- {COLUMN} 1.3.6.1.4.1.2356.11.2.23.20.6.1.10
lcsSetupInterfacesWlanClientModesEntryRxLimit OBJECT-TYPE
    SYNTAX     Integer32 (0..2147483647)
    MAX-ACCESS read-write
    STATUS     current
    DESCRIPTION
            ""
    ::= { lcsSetupInterfacesWlanClientModesEntry 10 }

-- {COLUMN} 1.3.6.1.4.1.2356.11.2.23.20.6.1.12
lcsSetupInterfacesWlanClientModesEntrySelectionPreference OBJECT-TYPE
    SYNTAX     INTEGER {
                  eSignalStrength (0),
                  eProfile (1)
            }
    MAX-ACCESS read-write
    STATUS     current
    DESCRIPTION
            ""
    ::= { lcsSetupInterfacesWlanClientModesEntry 12 }

-- {COLUMN} 1.3.6.1.4.1.2356.11.2.23.20.6.1.13
lcsSetupInterfacesWlanClientModesEntrySendDeauthUpon OBJECT-TYPE
    SYNTAX     BITS {
                  eNever (0),
                  eAddressChange (30),
                  eDeactivation (31)
            }
    MAX-ACCESS read-write
    STATUS     current
    DESCRIPTION
            "-- empty --"
    ::= { lcsSetupInterfacesWlanClientModesEntry 13 }

-- {TABLE} 1.3.6.1.4.1.2356.11.2.23.20.7
lcsSetupInterfacesWlanOperationalTable OBJECT-TYPE
    SYNTAX     SEQUENCE OF LcsSetupInterfacesWlanOperationalEntry
    MAX-ACCESS not-accessible
    STATUS     current
    DESCRIPTION
            ""
    ::= { lcsSetupInterfacesWlan 7 }

-- {ROW} 1.3.6.1.4.1.2356.11.2.23.20.7.1
lcsSetupInterfacesWlanOperationalEntry OBJECT-TYPE
    SYNTAX     LcsSetupInterfacesWlanOperationalEntry
    MAX-ACCESS not-accessible
    STATUS     current
    DESCRIPTION
            ""
    INDEX {
            lcsSetupInterfacesWlanOperationalEntryIfc
          }
    ::= { lcsSetupInterfacesWlanOperationalTable 1 }

LcsSetupInterfacesWlanOperationalEntry ::= SEQUENCE {
            lcsSetupInterfacesWlanOperationalEntryIfc INTEGER,
            lcsSetupInterfacesWlanOperationalEntryOperating INTEGER,
            lcsSetupInterfacesWlanOperationalEntryOperationMode INTEGER,
            lcsSetupInterfacesWlanOperationalEntryLinkLedFunction INTEGER,
            lcsSetupInterfacesWlanOperationalEntryBrokenLinkDetection INTEGER
    }

-- {COLUMN} 1.3.6.1.4.1.2356.11.2.23.20.7.1.1
lcsSetupInterfacesWlanOperationalEntryIfc OBJECT-TYPE
    SYNTAX     INTEGER {
                  eWlan1 (1),
                  eWlan2 (2)
            }
    MAX-ACCESS read-write
    STATUS     current
    DESCRIPTION
            ""
    ::= { lcsSetupInterfacesWlanOperationalEntry 1 }

-- {COLUMN} 1.3.6.1.4.1.2356.11.2.23.20.7.1.2
lcsSetupInterfacesWlanOperationalEntryOperating OBJECT-TYPE
    SYNTAX     INTEGER {
                  eYes (0),
                  eNo (1)
            }
    MAX-ACCESS read-write
    STATUS     current
    DESCRIPTION
            ""
    ::= { lcsSetupInterfacesWlanOperationalEntry 2 }

-- {COLUMN} 1.3.6.1.4.1.2356.11.2.23.20.7.1.3
lcsSetupInterfacesWlanOperationalEntryOperationMode OBJECT-TYPE
    SYNTAX     INTEGER {
                  eStation (0),
                  eAccessPoint (1),
                  eManagedAp (4),
                  eProbe (5),
                  eScanner (7)
            }
    MAX-ACCESS read-write
    STATUS     current
    DESCRIPTION
            "lancom's description of operation mode"
    ::= { lcsSetupInterfacesWlanOperationalEntry 3 }

-- {COLUMN} 1.3.6.1.4.1.2356.11.2.23.20.7.1.4
lcsSetupInterfacesWlanOperationalEntryLinkLedFunction OBJECT-TYPE
    SYNTAX     INTEGER {
                  eNormal (0),
                  eClientModeStrength (1),
                  eP2p1Strength (8),
                  eP2p2Strength (9),
                  eP2p3Strength (10),
                  eP2p4Strength (11),
                  eP2p5Strength (12),
                  eP2p6Strength (13),
                  eP2p7Strength (14),
                  eP2p8Strength (15),
                  eP2p9Strength (16),
                  eP2p10Strength (17),
                  eP2p11Strength (18),
                  eP2p12Strength (19),
                  eP2p13Strength (20),
                  eP2p14Strength (21),
                  eP2p15Strength (22),
                  eP2p16Strength (23)
            }
    MAX-ACCESS read-write
    STATUS     current
    DESCRIPTION
            ""
    ::= { lcsSetupInterfacesWlanOperationalEntry 4 }

-- {COLUMN} 1.3.6.1.4.1.2356.11.2.23.20.7.1.5
lcsSetupInterfacesWlanOperationalEntryBrokenLinkDetection OBJECT-TYPE
    SYNTAX     INTEGER {
                  eNo (0),
                  eLan1 (1),
                  eLan2 (2),
                  eLan3 (3),
                  eLan4 (4)
            }
    MAX-ACCESS read-write
    STATUS     current
    DESCRIPTION
            ""
    ::= { lcsSetupInterfacesWlanOperationalEntry 5 }

-- {TABLE} 1.3.6.1.4.1.2356.11.2.23.20.8
lcsSetupInterfacesWlanRadioSettingsTable OBJECT-TYPE
    SYNTAX     SEQUENCE OF LcsSetupInterfacesWlanRadioSettingsEntry
    MAX-ACCESS not-accessible
    STATUS     current
    DESCRIPTION
            ""
    ::= { lcsSetupInterfacesWlan 8 }

-- {ROW} 1.3.6.1.4.1.2356.11.2.23.20.8.1
lcsSetupInterfacesWlanRadioSettingsEntry OBJECT-TYPE
    SYNTAX     LcsSetupInterfacesWlanRadioSettingsEntry
    MAX-ACCESS not-accessible
    STATUS     current
    DESCRIPTION
            ""
    INDEX {
            lcsSetupInterfacesWlanRadioSettingsEntryIfc
          }
    ::= { lcsSetupInterfacesWlanRadioSettingsTable 1 }

LcsSetupInterfacesWlanRadioSettingsEntry ::= SEQUENCE {
            lcsSetupInterfacesWlanRadioSettingsEntryIfc INTEGER,
            lcsSetupInterfacesWlanRadioSettingsEntryTxPowerReduction Integer32,
            lcsSetupInterfacesWlanRadioSettingsEntry5ghzMode INTEGER,
            lcsSetupInterfacesWlanRadioSettingsEntryMaximumDistance Integer32,
            lcsSetupInterfacesWlanRadioSettingsEntryRadioBand INTEGER,
            lcsSetupInterfacesWlanRadioSettingsEntrySubbands INTEGER,
            lcsSetupInterfacesWlanRadioSettingsEntryRadioChannel Integer32,
            lcsSetupInterfacesWlanRadioSettingsEntry24ghzMode INTEGER,
            lcsSetupInterfacesWlanRadioSettingsEntryApDensity INTEGER,
            lcsSetupInterfacesWlanRadioSettingsEntryAntennaGain Integer32,
            lcsSetupInterfacesWlanRadioSettingsEntryChannelList DisplayString,
            lcsSetupInterfacesWlanRadioSettingsEntryBackgroundScan Integer32,
            lcsSetupInterfacesWlanRadioSettingsEntryDfsRescanHours DisplayString,
            lcsSetupInterfacesWlanRadioSettingsEntryAllow40mhz INTEGER,
            lcsSetupInterfacesWlanRadioSettingsEntryAntennaMask INTEGER,
            lcsSetupInterfacesWlanRadioSettingsEntryBackgroundScanUnit INTEGER,
            lcsSetupInterfacesWlanRadioSettingsEntryChannelPairing INTEGER,
            lcsSetupInterfacesWlanRadioSettingsEntryPreferredDfsScheme INTEGER,
            lcsSetupInterfacesWlanRadioSettingsEntryCacDuration Integer32,
            lcsSetupInterfacesWlanRadioSettingsEntryForce40mhz INTEGER,
            lcsSetupInterfacesWlanRadioSettingsEntryAdaptiveNoiseImmunity INTEGER,
            lcsSetupInterfacesWlanRadioSettingsEntryMaxChannelBandwidth INTEGER,
            lcsSetupInterfacesWlanRadioSettingsEntryAllowPhyRestarts INTEGER,
            lcsSetupInterfacesWlanRadioSettingsEntryDfsRscFlClChan INTEGER,
            lcsSetupInterfacesWlanRadioSettingsEntryDfsRescanNumChannels Integer32,
            lcsSetupInterfacesWlanRadioSettingsEntryPreferred24Scheme INTEGER,
            lcsSetupInterfacesWlanRadioSettingsEntryIndoorOnlyOperation INTEGER,
            lcsSetupInterfacesWlanRadioSettingsEntryPowerSetting INTEGER,
            lcsSetupInterfacesWlanRadioSettingsEntryEirp Integer32,
            lcsSetupInterfacesWlanRadioSettingsEntryRxPacketSensReduction Integer32
    }

-- {COLUMN} 1.3.6.1.4.1.2356.11.2.23.20.8.1.1
lcsSetupInterfacesWlanRadioSettingsEntryIfc OBJECT-TYPE
    SYNTAX     INTEGER {
                  eWlan1 (1),
                  eWlan2 (2)
            }
    MAX-ACCESS read-write
    STATUS     current
    DESCRIPTION
            ""
    ::= { lcsSetupInterfacesWlanRadioSettingsEntry 1 }

-- {COLUMN} 1.3.6.1.4.1.2356.11.2.23.20.8.1.2
lcsSetupInterfacesWlanRadioSettingsEntryTxPowerReduction OBJECT-TYPE
    SYNTAX     Integer32 (0..255)
    MAX-ACCESS read-write
    STATUS     current
    DESCRIPTION
            ""
    ::= { lcsSetupInterfacesWlanRadioSettingsEntry 2 }

-- {COLUMN} 1.3.6.1.4.1.2356.11.2.23.20.8.1.3
lcsSetupInterfacesWlanRadioSettingsEntry5ghzMode OBJECT-TYPE
    SYNTAX     INTEGER {
                  eNormal (0),
                  e11anMixed (3),
                  eGreenfield (4),
                  e11anacMixed (7),
                  e11nacMixed (8),
                  e11acOnly (9),
                  eAuto (255)
            }
    MAX-ACCESS read-write
    STATUS     current
    DESCRIPTION
            ""
    ::= { lcsSetupInterfacesWlanRadioSettingsEntry 3 }

-- {COLUMN} 1.3.6.1.4.1.2356.11.2.23.20.8.1.4
lcsSetupInterfacesWlanRadioSettingsEntryMaximumDistance OBJECT-TYPE
    SYNTAX     Integer32 (0..65535)
    MAX-ACCESS read-write
    STATUS     current
    DESCRIPTION
            ""
    ::= { lcsSetupInterfacesWlanRadioSettingsEntry 4 }

-- {COLUMN} 1.3.6.1.4.1.2356.11.2.23.20.8.1.6
lcsSetupInterfacesWlanRadioSettingsEntryRadioBand OBJECT-TYPE
    SYNTAX     INTEGER {
                  e24ghz (1),
                  e5ghz (2)
            }
    MAX-ACCESS read-write
    STATUS     current
    DESCRIPTION
            ""
    ::= { lcsSetupInterfacesWlanRadioSettingsEntry 6 }

-- {COLUMN} 1.3.6.1.4.1.2356.11.2.23.20.8.1.7
lcsSetupInterfacesWlanRadioSettingsEntrySubbands OBJECT-TYPE
    SYNTAX     INTEGER {
                  eBand1 (1),
                  eBand2 (2),
                  eBand1Plus2 (3),
                  eBand3 (4),
                  eBand1Plus3 (5),
                  eBand2Plus3 (6),
                  eBand1Plus2Plus3 (7)
            }
    MAX-ACCESS read-write
    STATUS     current
    DESCRIPTION
            ""
    ::= { lcsSetupInterfacesWlanRadioSettingsEntry 7 }

-- {COLUMN} 1.3.6.1.4.1.2356.11.2.23.20.8.1.8
lcsSetupInterfacesWlanRadioSettingsEntryRadioChannel OBJECT-TYPE
    SYNTAX     Integer32 (0..255)
    MAX-ACCESS read-write
    STATUS     current
    DESCRIPTION
            ""
    ::= { lcsSetupInterfacesWlanRadioSettingsEntry 8 }

-- {COLUMN} 1.3.6.1.4.1.2356.11.2.23.20.8.1.9
lcsSetupInterfacesWlanRadioSettingsEntry24ghzMode OBJECT-TYPE
    SYNTAX     INTEGER {
                  e11bgMixed (0),
                  e11gOnly (1),
                  e11bOnly (2),
                  e2mMixed (3),
                  e11bgnMixed (5),
                  e2m11bgnMixed (6),
                  e11gnMixed (7),
                  eGreenfield (8),
                  eAuto (255)
            }
    MAX-ACCESS read-write
    STATUS     current
    DESCRIPTION
            ""
    ::= { lcsSetupInterfacesWlanRadioSettingsEntry 9 }

-- {COLUMN} 1.3.6.1.4.1.2356.11.2.23.20.8.1.10
lcsSetupInterfacesWlanRadioSettingsEntryApDensity OBJECT-TYPE
    SYNTAX     INTEGER {
                  eOff (0),
                  eLow (1),
                  eMedium (2),
                  eHigh (3),
                  eMinicell (4),
                  eMicrocell (5)
            }
    MAX-ACCESS read-write
    STATUS     current
    DESCRIPTION
            ""
    ::= { lcsSetupInterfacesWlanRadioSettingsEntry 10 }

-- {COLUMN} 1.3.6.1.4.1.2356.11.2.23.20.8.1.12
lcsSetupInterfacesWlanRadioSettingsEntryAntennaGain OBJECT-TYPE
    SYNTAX     Integer32 (-128..127)
    MAX-ACCESS read-write
    STATUS     current
    DESCRIPTION
            ""
    ::= { lcsSetupInterfacesWlanRadioSettingsEntry 12 }

-- {COLUMN} 1.3.6.1.4.1.2356.11.2.23.20.8.1.13
lcsSetupInterfacesWlanRadioSettingsEntryChannelList OBJECT-TYPE
    SYNTAX     DisplayString (SIZE(0..48))
    MAX-ACCESS read-write
    STATUS     current
    DESCRIPTION
            ""
    ::= { lcsSetupInterfacesWlanRadioSettingsEntry 13 }

-- {COLUMN} 1.3.6.1.4.1.2356.11.2.23.20.8.1.14
lcsSetupInterfacesWlanRadioSettingsEntryBackgroundScan OBJECT-TYPE
    SYNTAX     Integer32 (0..2147483647)
    MAX-ACCESS read-write
    STATUS     current
    DESCRIPTION
            ""
    ::= { lcsSetupInterfacesWlanRadioSettingsEntry 14 }

-- {COLUMN} 1.3.6.1.4.1.2356.11.2.23.20.8.1.15
lcsSetupInterfacesWlanRadioSettingsEntryDfsRescanHours OBJECT-TYPE
    SYNTAX     DisplayString (SIZE(0..30))
    MAX-ACCESS read-write
    STATUS     current
    DESCRIPTION
            ""
    ::= { lcsSetupInterfacesWlanRadioSettingsEntry 15 }

-- {COLUMN} 1.3.6.1.4.1.2356.11.2.23.20.8.1.16
lcsSetupInterfacesWlanRadioSettingsEntryAllow40mhz OBJECT-TYPE
    SYNTAX     INTEGER {
                  eAuto (0),
                  eNo (1)
            }
    MAX-ACCESS read-write
    STATUS     current
    DESCRIPTION
            ""
    ::= { lcsSetupInterfacesWlanRadioSettingsEntry 16 }

-- {COLUMN} 1.3.6.1.4.1.2356.11.2.23.20.8.1.17
lcsSetupInterfacesWlanRadioSettingsEntryAntennaMask OBJECT-TYPE
    SYNTAX     INTEGER {
                  eAuto (0),
                  eAntenna1 (1),
                  eAntenna1Plus2 (3),
                  eAntenna1Plus3 (5),
                  eAntenna1Plus2Plus3 (7),
                  eAntenna1Plus2Plus3Plus4 (15)
            }
    MAX-ACCESS read-write
    STATUS     current
    DESCRIPTION
            ""
    ::= { lcsSetupInterfacesWlanRadioSettingsEntry 17 }

-- {COLUMN} 1.3.6.1.4.1.2356.11.2.23.20.8.1.18
lcsSetupInterfacesWlanRadioSettingsEntryBackgroundScanUnit OBJECT-TYPE
    SYNTAX     INTEGER {
                  eSeconds (0),
                  eMilliseconds (1),
                  eMicroseconds (2),
                  eMinutes (3),
                  eHours (4),
                  eDays (5),
                  eWeeks (6),
                  eFortnights (7)
            }
    MAX-ACCESS read-write
    STATUS     current
    DESCRIPTION
            ""
    ::= { lcsSetupInterfacesWlanRadioSettingsEntry 18 }

-- {COLUMN} 1.3.6.1.4.1.2356.11.2.23.20.8.1.19
lcsSetupInterfacesWlanRadioSettingsEntryChannelPairing OBJECT-TYPE
    SYNTAX     INTEGER {
                  e11nCompliant (0),
                  eLegacyTurboFriendly (1)
            }
    MAX-ACCESS read-write
    STATUS     current
    DESCRIPTION
            ""
    ::= { lcsSetupInterfacesWlanRadioSettingsEntry 19 }

-- {COLUMN} 1.3.6.1.4.1.2356.11.2.23.20.8.1.20
lcsSetupInterfacesWlanRadioSettingsEntryPreferredDfsScheme OBJECT-TYPE
    SYNTAX     INTEGER {
                  eEn301893V13 (2),
                  eEn301893V15 (32),
                  eEn301893V16 (64),
                  eEn301893V17 (256),
                  eEn301893V21 (512)
            }
    MAX-ACCESS read-write
    STATUS     current
    DESCRIPTION
            ""
    ::= { lcsSetupInterfacesWlanRadioSettingsEntry 20 }

-- {COLUMN} 1.3.6.1.4.1.2356.11.2.23.20.8.1.21
lcsSetupInterfacesWlanRadioSettingsEntryCacDuration OBJECT-TYPE
    SYNTAX     Integer32 (0..2147483647)
    MAX-ACCESS read-write
    STATUS     current
    DESCRIPTION
            "-- empty --"
    ::= { lcsSetupInterfacesWlanRadioSettingsEntry 21 }

-- {COLUMN} 1.3.6.1.4.1.2356.11.2.23.20.8.1.22
lcsSetupInterfacesWlanRadioSettingsEntryForce40mhz OBJECT-TYPE
    SYNTAX     INTEGER {
                  eNo (0),
                  eYes (1)
            }
    MAX-ACCESS read-write
    STATUS     current
    DESCRIPTION
            "-- empty --"
    ::= { lcsSetupInterfacesWlanRadioSettingsEntry 22 }

-- {COLUMN} 1.3.6.1.4.1.2356.11.2.23.20.8.1.23
lcsSetupInterfacesWlanRadioSettingsEntryAdaptiveNoiseImmunity OBJECT-TYPE
    SYNTAX     INTEGER {
                  eNo (0),
                  eYes (1)
            }
    MAX-ACCESS read-write
    STATUS     current
    DESCRIPTION
            "-- empty --"
    ::= { lcsSetupInterfacesWlanRadioSettingsEntry 23 }

-- {COLUMN} 1.3.6.1.4.1.2356.11.2.23.20.8.1.24
lcsSetupInterfacesWlanRadioSettingsEntryMaxChannelBandwidth OBJECT-TYPE
    SYNTAX     INTEGER {
                  e20mhz (0),
                  e40mhz (1),
                  e80mhz (2),
                  e160mhz (3),
                  e80Plus80mhz (4),
                  eAuto (255)
            }
    MAX-ACCESS read-write
    STATUS     current
    DESCRIPTION
            "-- empty --"
    ::= { lcsSetupInterfacesWlanRadioSettingsEntry 24 }

-- {COLUMN} 1.3.6.1.4.1.2356.11.2.23.20.8.1.25
lcsSetupInterfacesWlanRadioSettingsEntryAllowPhyRestarts OBJECT-TYPE
    SYNTAX     INTEGER {
                  eNo (0),
                  eYes (1)
            }
    MAX-ACCESS read-write
    STATUS     current
    DESCRIPTION
            "-- empty --"
    ::= { lcsSetupInterfacesWlanRadioSettingsEntry 25 }

-- {COLUMN} 1.3.6.1.4.1.2356.11.2.23.20.8.1.26
lcsSetupInterfacesWlanRadioSettingsEntryDfsRscFlClChan OBJECT-TYPE
    SYNTAX     INTEGER {
                  eNo (0),
                  eYes (1)
            }
    MAX-ACCESS read-write
    STATUS     current
    DESCRIPTION
            ""
    ::= { lcsSetupInterfacesWlanRadioSettingsEntry 26 }

-- {COLUMN} 1.3.6.1.4.1.2356.11.2.23.20.8.1.27
lcsSetupInterfacesWlanRadioSettingsEntryDfsRescanNumChannels OBJECT-TYPE
    SYNTAX     Integer32 (0..2147483647)
    MAX-ACCESS read-write
    STATUS     current
    DESCRIPTION
            "-- empty --"
    ::= { lcsSetupInterfacesWlanRadioSettingsEntry 27 }

-- {COLUMN} 1.3.6.1.4.1.2356.11.2.23.20.8.1.28
lcsSetupInterfacesWlanRadioSettingsEntryPreferred24Scheme OBJECT-TYPE
    SYNTAX     INTEGER {
                  eEn300328V17 (1),
                  eEn300328V18 (2),
                  eEn300328V21 (4)
            }
    MAX-ACCESS read-write
    STATUS     current
    DESCRIPTION
            "-- empty --"
    ::= { lcsSetupInterfacesWlanRadioSettingsEntry 28 }

-- {COLUMN} 1.3.6.1.4.1.2356.11.2.23.20.8.1.29
lcsSetupInterfacesWlanRadioSettingsEntryIndoorOnlyOperation OBJECT-TYPE
    SYNTAX     INTEGER {
                  eNo (0),
                  eYes (1)
            }
    MAX-ACCESS read-write
    STATUS     current
    DESCRIPTION
            "-- empty --"
    ::= { lcsSetupInterfacesWlanRadioSettingsEntry 29 }

-- {COLUMN} 1.3.6.1.4.1.2356.11.2.23.20.8.1.33
lcsSetupInterfacesWlanRadioSettingsEntryPowerSetting OBJECT-TYPE
    SYNTAX     INTEGER {
                  eAutomatic (0),
                  eManual (1)
            }
    MAX-ACCESS read-write
    STATUS     current
    DESCRIPTION
            "-- empty --"
    ::= { lcsSetupInterfacesWlanRadioSettingsEntry 33 }

-- {COLUMN} 1.3.6.1.4.1.2356.11.2.23.20.8.1.34
lcsSetupInterfacesWlanRadioSettingsEntryEirp OBJECT-TYPE
    SYNTAX     Integer32 (-128..127)
    MAX-ACCESS read-write
    STATUS     current
    DESCRIPTION
            "-- empty --"
    ::= { lcsSetupInterfacesWlanRadioSettingsEntry 34 }

-- {COLUMN} 1.3.6.1.4.1.2356.11.2.23.20.8.1.35
lcsSetupInterfacesWlanRadioSettingsEntryRxPacketSensReduction OBJECT-TYPE
    SYNTAX     Integer32 (0..255)
    MAX-ACCESS read-write
    STATUS     current
    DESCRIPTION
            "-- empty --"
    ::= { lcsSetupInterfacesWlanRadioSettingsEntry 35 }

-- {TABLE} 1.3.6.1.4.1.2356.11.2.23.20.9
lcsSetupInterfacesWlanPerformanceTable OBJECT-TYPE
    SYNTAX     SEQUENCE OF LcsSetupInterfacesWlanPerformanceEntry
    MAX-ACCESS not-accessible
    STATUS     current
    DESCRIPTION
            ""
    ::= { lcsSetupInterfacesWlan 9 }

-- {ROW} 1.3.6.1.4.1.2356.11.2.23.20.9.1
lcsSetupInterfacesWlanPerformanceEntry OBJECT-TYPE
    SYNTAX     LcsSetupInterfacesWlanPerformanceEntry
    MAX-ACCESS not-accessible
    STATUS     current
    DESCRIPTION
            ""
    INDEX {
            lcsSetupInterfacesWlanPerformanceEntryIfc
          }
    ::= { lcsSetupInterfacesWlanPerformanceTable 1 }

LcsSetupInterfacesWlanPerformanceEntry ::= SEQUENCE {
            lcsSetupInterfacesWlanPerformanceEntryIfc INTEGER,
            lcsSetupInterfacesWlanPerformanceEntryTxBursting Integer32,
            lcsSetupInterfacesWlanPerformanceEntryQos INTEGER,
            lcsSetupInterfacesWlanPerformanceEntryAirtimeFairnessMode INTEGER
    }

-- {COLUMN} 1.3.6.1.4.1.2356.11.2.23.20.9.1.1
lcsSetupInterfacesWlanPerformanceEntryIfc OBJECT-TYPE
    SYNTAX     INTEGER {
                  eWlan1 (1),
                  eWlan2 (2)
            }
    MAX-ACCESS read-write
    STATUS     current
    DESCRIPTION
            ""
    ::= { lcsSetupInterfacesWlanPerformanceEntry 1 }

-- {COLUMN} 1.3.6.1.4.1.2356.11.2.23.20.9.1.2
lcsSetupInterfacesWlanPerformanceEntryTxBursting OBJECT-TYPE
    SYNTAX     Integer32 (0..65535)
    MAX-ACCESS read-write
    STATUS     current
    DESCRIPTION
            ""
    ::= { lcsSetupInterfacesWlanPerformanceEntry 2 }

-- {COLUMN} 1.3.6.1.4.1.2356.11.2.23.20.9.1.5
lcsSetupInterfacesWlanPerformanceEntryQos OBJECT-TYPE
    SYNTAX     INTEGER {
                  eNo (0),
                  eYes (1)
            }
    MAX-ACCESS read-write
    STATUS     current
    DESCRIPTION
            ""
    ::= { lcsSetupInterfacesWlanPerformanceEntry 5 }

-- {COLUMN} 1.3.6.1.4.1.2356.11.2.23.20.9.1.6
lcsSetupInterfacesWlanPerformanceEntryAirtimeFairnessMode OBJECT-TYPE
    SYNTAX     INTEGER {
                  eRoundRobin (0),
                  eEqualAirtime (1),
                  ePref11nAirtime (2),
                  eEqualVolume (3)
            }
    MAX-ACCESS read-write
    STATUS     current
    DESCRIPTION
            "-- empty --"
    ::= { lcsSetupInterfacesWlanPerformanceEntry 6 }

-- {TABLE} 1.3.6.1.4.1.2356.11.2.23.20.10
lcsSetupInterfacesWlanBeaconingTable OBJECT-TYPE
    SYNTAX     SEQUENCE OF LcsSetupInterfacesWlanBeaconingEntry
    MAX-ACCESS not-accessible
    STATUS     current
    DESCRIPTION
            ""
    ::= { lcsSetupInterfacesWlan 10 }

-- {ROW} 1.3.6.1.4.1.2356.11.2.23.20.10.1
lcsSetupInterfacesWlanBeaconingEntry OBJECT-TYPE
    SYNTAX     LcsSetupInterfacesWlanBeaconingEntry
    MAX-ACCESS not-accessible
    STATUS     current
    DESCRIPTION
            ""
    INDEX {
            lcsSetupInterfacesWlanBeaconingEntryIfc
          }
    ::= { lcsSetupInterfacesWlanBeaconingTable 1 }

LcsSetupInterfacesWlanBeaconingEntry ::= SEQUENCE {
            lcsSetupInterfacesWlanBeaconingEntryIfc INTEGER,
            lcsSetupInterfacesWlanBeaconingEntryBeaconPeriod Integer32,
            lcsSetupInterfacesWlanBeaconingEntryDtimPeriod Integer32,
            lcsSetupInterfacesWlanBeaconingEntryBeaconOrder INTEGER
    }

-- {COLUMN} 1.3.6.1.4.1.2356.11.2.23.20.10.1.1
lcsSetupInterfacesWlanBeaconingEntryIfc OBJECT-TYPE
    SYNTAX     INTEGER {
                  eWlan1 (1),
                  eWlan2 (2)
            }
    MAX-ACCESS read-write
    STATUS     current
    DESCRIPTION
            ""
    ::= { lcsSetupInterfacesWlanBeaconingEntry 1 }

-- {COLUMN} 1.3.6.1.4.1.2356.11.2.23.20.10.1.2
lcsSetupInterfacesWlanBeaconingEntryBeaconPeriod OBJECT-TYPE
    SYNTAX     Integer32 (0..65535)
    MAX-ACCESS read-write
    STATUS     current
    DESCRIPTION
            ""
    ::= { lcsSetupInterfacesWlanBeaconingEntry 2 }

-- {COLUMN} 1.3.6.1.4.1.2356.11.2.23.20.10.1.3
lcsSetupInterfacesWlanBeaconingEntryDtimPeriod OBJECT-TYPE
    SYNTAX     Integer32 (0..255)
    MAX-ACCESS read-write
    STATUS     current
    DESCRIPTION
            ""
    ::= { lcsSetupInterfacesWlanBeaconingEntry 3 }

-- {COLUMN} 1.3.6.1.4.1.2356.11.2.23.20.10.1.4
lcsSetupInterfacesWlanBeaconingEntryBeaconOrder OBJECT-TYPE
    SYNTAX     INTEGER {
                  eCyclic (0),
                  eStaggered (1),
                  eSimpleBurst (2)
            }
    MAX-ACCESS read-write
    STATUS     current
    DESCRIPTION
            ""
    ::= { lcsSetupInterfacesWlanBeaconingEntry 4 }

-- {TABLE} 1.3.6.1.4.1.2356.11.2.23.20.11
lcsSetupInterfacesWlanRoamingTable OBJECT-TYPE
    SYNTAX     SEQUENCE OF LcsSetupInterfacesWlanRoamingEntry
    MAX-ACCESS not-accessible
    STATUS     current
    DESCRIPTION
            ""
    ::= { lcsSetupInterfacesWlan 11 }

-- {ROW} 1.3.6.1.4.1.2356.11.2.23.20.11.1
lcsSetupInterfacesWlanRoamingEntry OBJECT-TYPE
    SYNTAX     LcsSetupInterfacesWlanRoamingEntry
    MAX-ACCESS not-accessible
    STATUS     current
    DESCRIPTION
            ""
    INDEX {
            lcsSetupInterfacesWlanRoamingEntryIfc
          }
    ::= { lcsSetupInterfacesWlanRoamingTable 1 }

LcsSetupInterfacesWlanRoamingEntry ::= SEQUENCE {
            lcsSetupInterfacesWlanRoamingEntryIfc INTEGER,
            lcsSetupInterfacesWlanRoamingEntryBeaconMissThreshold Integer32,
            lcsSetupInterfacesWlanRoamingEntryRoamingThreshold Integer32,
            lcsSetupInterfacesWlanRoamingEntryNoRoamingThreshold Integer32,
            lcsSetupInterfacesWlanRoamingEntryForceRoamingThreshold Integer32,
            lcsSetupInterfacesWlanRoamingEntrySoftRoaming INTEGER,
            lcsSetupInterfacesWlanRoamingEntryConnectThreshold Integer32,
            lcsSetupInterfacesWlanRoamingEntryConnectHoldThreshold Integer32,
            lcsSetupInterfacesWlanRoamingEntryMinConnectSignalLevel Integer32,
            lcsSetupInterfacesWlanRoamingEntryMinConnectHoldSignalLevel Integer32,
            lcsSetupInterfacesWlanRoamingEntryBlockTime Gauge32
    }

-- {COLUMN} 1.3.6.1.4.1.2356.11.2.23.20.11.1.1
lcsSetupInterfacesWlanRoamingEntryIfc OBJECT-TYPE
    SYNTAX     INTEGER {
                  eWlan1 (1),
                  eWlan2 (2)
            }
    MAX-ACCESS read-write
    STATUS     current
    DESCRIPTION
            ""
    ::= { lcsSetupInterfacesWlanRoamingEntry 1 }

-- {COLUMN} 1.3.6.1.4.1.2356.11.2.23.20.11.1.2
lcsSetupInterfacesWlanRoamingEntryBeaconMissThreshold OBJECT-TYPE
    SYNTAX     Integer32 (0..255)
    MAX-ACCESS read-write
    STATUS     current
    DESCRIPTION
            ""
    ::= { lcsSetupInterfacesWlanRoamingEntry 2 }

-- {COLUMN} 1.3.6.1.4.1.2356.11.2.23.20.11.1.3
lcsSetupInterfacesWlanRoamingEntryRoamingThreshold OBJECT-TYPE
    SYNTAX     Integer32 (0..255)
    MAX-ACCESS read-write
    STATUS     current
    DESCRIPTION
            ""
    ::= { lcsSetupInterfacesWlanRoamingEntry 3 }

-- {COLUMN} 1.3.6.1.4.1.2356.11.2.23.20.11.1.4
lcsSetupInterfacesWlanRoamingEntryNoRoamingThreshold OBJECT-TYPE
    SYNTAX     Integer32 (0..255)
    MAX-ACCESS read-write
    STATUS     current
    DESCRIPTION
            ""
    ::= { lcsSetupInterfacesWlanRoamingEntry 4 }

-- {COLUMN} 1.3.6.1.4.1.2356.11.2.23.20.11.1.5
lcsSetupInterfacesWlanRoamingEntryForceRoamingThreshold OBJECT-TYPE
    SYNTAX     Integer32 (0..255)
    MAX-ACCESS read-write
    STATUS     current
    DESCRIPTION
            ""
    ::= { lcsSetupInterfacesWlanRoamingEntry 5 }

-- {COLUMN} 1.3.6.1.4.1.2356.11.2.23.20.11.1.6
lcsSetupInterfacesWlanRoamingEntrySoftRoaming OBJECT-TYPE
    SYNTAX     INTEGER {
                  eNo (0),
                  eYes (1)
            }
    MAX-ACCESS read-write
    STATUS     current
    DESCRIPTION
            ""
    ::= { lcsSetupInterfacesWlanRoamingEntry 6 }

-- {COLUMN} 1.3.6.1.4.1.2356.11.2.23.20.11.1.7
lcsSetupInterfacesWlanRoamingEntryConnectThreshold OBJECT-TYPE
    SYNTAX     Integer32 (0..255)
    MAX-ACCESS read-write
    STATUS     current
    DESCRIPTION
            ""
    ::= { lcsSetupInterfacesWlanRoamingEntry 7 }

-- {COLUMN} 1.3.6.1.4.1.2356.11.2.23.20.11.1.8
lcsSetupInterfacesWlanRoamingEntryConnectHoldThreshold OBJECT-TYPE
    SYNTAX     Integer32 (0..255)
    MAX-ACCESS read-write
    STATUS     current
    DESCRIPTION
            ""
    ::= { lcsSetupInterfacesWlanRoamingEntry 8 }

-- {COLUMN} 1.3.6.1.4.1.2356.11.2.23.20.11.1.9
lcsSetupInterfacesWlanRoamingEntryMinConnectSignalLevel OBJECT-TYPE
    SYNTAX     Integer32 (-128..127)
    MAX-ACCESS read-write
    STATUS     current
    DESCRIPTION
            ""
    ::= { lcsSetupInterfacesWlanRoamingEntry 9 }

-- {COLUMN} 1.3.6.1.4.1.2356.11.2.23.20.11.1.10
lcsSetupInterfacesWlanRoamingEntryMinConnectHoldSignalLevel OBJECT-TYPE
    SYNTAX     Integer32 (-128..127)
    MAX-ACCESS read-write
    STATUS     current
    DESCRIPTION
            ""
    ::= { lcsSetupInterfacesWlanRoamingEntry 10 }

-- {COLUMN} 1.3.6.1.4.1.2356.11.2.23.20.11.1.11
lcsSetupInterfacesWlanRoamingEntryBlockTime OBJECT-TYPE
    SYNTAX     Gauge32
    MAX-ACCESS read-write
    STATUS     current
    DESCRIPTION
            ""
    ::= { lcsSetupInterfacesWlanRoamingEntry 11 }

-- {TABLE} 1.3.6.1.4.1.2356.11.2.23.20.12
lcsSetupInterfacesWlanIntpntPeersTable OBJECT-TYPE
    SYNTAX     SEQUENCE OF LcsSetupInterfacesWlanIntpntPeersEntry
    MAX-ACCESS not-accessible
    STATUS     current
    DESCRIPTION
            ""
    ::= { lcsSetupInterfacesWlan 12 }

-- {ROW} 1.3.6.1.4.1.2356.11.2.23.20.12.1
lcsSetupInterfacesWlanIntpntPeersEntry OBJECT-TYPE
    SYNTAX     LcsSetupInterfacesWlanIntpntPeersEntry
    MAX-ACCESS not-accessible
    STATUS     current
    DESCRIPTION
            ""
    INDEX {
            lcsSetupInterfacesWlanIntpntPeersEntryIfc
          }
    ::= { lcsSetupInterfacesWlanIntpntPeersTable 1 }

LcsSetupInterfacesWlanIntpntPeersEntry ::= SEQUENCE {
            lcsSetupInterfacesWlanIntpntPeersEntryIfc INTEGER,
            lcsSetupInterfacesWlanIntpntPeersEntryRecognizeBy INTEGER,
            lcsSetupInterfacesWlanIntpntPeersEntryMacAddress MacAddress,
            lcsSetupInterfacesWlanIntpntPeersEntryPeerName DisplayString,
            lcsSetupInterfacesWlanIntpntPeersEntryOperating INTEGER,
            lcsSetupInterfacesWlanIntpntPeersEntryTxLimit Integer32,
            lcsSetupInterfacesWlanIntpntPeersEntryRxLimit Integer32,
            lcsSetupInterfacesWlanIntpntPeersEntryKey DisplayString,
            lcsSetupInterfacesWlanIntpntPeersEntryConnectThreshold Integer32,
            lcsSetupInterfacesWlanIntpntPeersEntryConnectHoldThreshold Integer32
    }

-- {COLUMN} 1.3.6.1.4.1.2356.11.2.23.20.12.1.1
lcsSetupInterfacesWlanIntpntPeersEntryIfc OBJECT-TYPE
    SYNTAX     INTEGER {
                  eP2p11 (1),
                  eP2p12 (2),
                  eP2p13 (3),
                  eP2p14 (4),
                  eP2p15 (5),
                  eP2p16 (6),
                  eP2p21 (7),
                  eP2p22 (8),
                  eP2p23 (9),
                  eP2p24 (10),
                  eP2p25 (11),
                  eP2p26 (12),
                  eP2p17 (32),
                  eP2p18 (33),
                  eP2p19 (34),
                  eP2p110 (35),
                  eP2p111 (36),
                  eP2p112 (37),
                  eP2p113 (38),
                  eP2p114 (39),
                  eP2p115 (40),
                  eP2p116 (41),
                  eP2p27 (64),
                  eP2p28 (65),
                  eP2p29 (66),
                  eP2p210 (67),
                  eP2p211 (68),
                  eP2p212 (69),
                  eP2p213 (70),
                  eP2p214 (71),
                  eP2p215 (72),
                  eP2p216 (73)
            }
    MAX-ACCESS read-write
    STATUS     current
    DESCRIPTION
            ""
    ::= { lcsSetupInterfacesWlanIntpntPeersEntry 1 }

-- {COLUMN} 1.3.6.1.4.1.2356.11.2.23.20.12.1.2
lcsSetupInterfacesWlanIntpntPeersEntryRecognizeBy OBJECT-TYPE
    SYNTAX     INTEGER {
                  eMacAddress (0),
                  eName (1)
            }
    MAX-ACCESS read-write
    STATUS     current
    DESCRIPTION
            ""
    ::= { lcsSetupInterfacesWlanIntpntPeersEntry 2 }

-- {COLUMN} 1.3.6.1.4.1.2356.11.2.23.20.12.1.3
lcsSetupInterfacesWlanIntpntPeersEntryMacAddress OBJECT-TYPE
    SYNTAX     MacAddress
    MAX-ACCESS read-write
    STATUS     current
    DESCRIPTION
            ""
    ::= { lcsSetupInterfacesWlanIntpntPeersEntry 3 }

-- {COLUMN} 1.3.6.1.4.1.2356.11.2.23.20.12.1.4
lcsSetupInterfacesWlanIntpntPeersEntryPeerName OBJECT-TYPE
    SYNTAX     DisplayString (SIZE(0..24))
    MAX-ACCESS read-write
    STATUS     current
    DESCRIPTION
            ""
    ::= { lcsSetupInterfacesWlanIntpntPeersEntry 4 }

-- {COLUMN} 1.3.6.1.4.1.2356.11.2.23.20.12.1.5
lcsSetupInterfacesWlanIntpntPeersEntryOperating OBJECT-TYPE
    SYNTAX     INTEGER {
                  eNo (0),
                  eYes (1)
            }
    MAX-ACCESS read-write
    STATUS     current
    DESCRIPTION
            ""
    ::= { lcsSetupInterfacesWlanIntpntPeersEntry 5 }

-- {COLUMN} 1.3.6.1.4.1.2356.11.2.23.20.12.1.6
lcsSetupInterfacesWlanIntpntPeersEntryTxLimit OBJECT-TYPE
    SYNTAX     Integer32 (0..2147483647)
    MAX-ACCESS read-write
    STATUS     current
    DESCRIPTION
            ""
    ::= { lcsSetupInterfacesWlanIntpntPeersEntry 6 }

-- {COLUMN} 1.3.6.1.4.1.2356.11.2.23.20.12.1.7
lcsSetupInterfacesWlanIntpntPeersEntryRxLimit OBJECT-TYPE
    SYNTAX     Integer32 (0..2147483647)
    MAX-ACCESS read-write
    STATUS     current
    DESCRIPTION
            ""
    ::= { lcsSetupInterfacesWlanIntpntPeersEntry 7 }

-- {COLUMN} 1.3.6.1.4.1.2356.11.2.23.20.12.1.8
lcsSetupInterfacesWlanIntpntPeersEntryKey OBJECT-TYPE
    SYNTAX     DisplayString (SIZE(0..63))
    MAX-ACCESS read-write
    STATUS     current
    DESCRIPTION
            "-- empty --"
    ::= { lcsSetupInterfacesWlanIntpntPeersEntry 8 }

-- {COLUMN} 1.3.6.1.4.1.2356.11.2.23.20.12.1.9
lcsSetupInterfacesWlanIntpntPeersEntryConnectThreshold OBJECT-TYPE
    SYNTAX     Integer32 (0..255)
    MAX-ACCESS read-write
    STATUS     current
    DESCRIPTION
            "-- empty --"
    ::= { lcsSetupInterfacesWlanIntpntPeersEntry 9 }

-- {COLUMN} 1.3.6.1.4.1.2356.11.2.23.20.12.1.10
lcsSetupInterfacesWlanIntpntPeersEntryConnectHoldThreshold OBJECT-TYPE
    SYNTAX     Integer32 (0..255)
    MAX-ACCESS read-write
    STATUS     current
    DESCRIPTION
            "-- empty --"
    ::= { lcsSetupInterfacesWlanIntpntPeersEntry 10 }

-- {TABLE} 1.3.6.1.4.1.2356.11.2.23.20.13
lcsSetupInterfacesWlanNetworkAlarmLimitsTable OBJECT-TYPE
    SYNTAX     SEQUENCE OF LcsSetupInterfacesWlanNetworkAlarmLimitsEntry
    MAX-ACCESS not-accessible
    STATUS     current
    DESCRIPTION
            ""
    ::= { lcsSetupInterfacesWlan 13 }

-- {ROW} 1.3.6.1.4.1.2356.11.2.23.20.13.1
lcsSetupInterfacesWlanNetworkAlarmLimitsEntry OBJECT-TYPE
    SYNTAX     LcsSetupInterfacesWlanNetworkAlarmLimitsEntry
    MAX-ACCESS not-accessible
    STATUS     current
    DESCRIPTION
            ""
    INDEX {
            lcsSetupInterfacesWlanNetworkAlarmLimitsEntryIfc
          }
    ::= { lcsSetupInterfacesWlanNetworkAlarmLimitsTable 1 }

LcsSetupInterfacesWlanNetworkAlarmLimitsEntry ::= SEQUENCE {
            lcsSetupInterfacesWlanNetworkAlarmLimitsEntryIfc INTEGER,
            lcsSetupInterfacesWlanNetworkAlarmLimitsEntryPhySignal Integer32,
            lcsSetupInterfacesWlanNetworkAlarmLimitsEntryTotalRetries Integer32,
            lcsSetupInterfacesWlanNetworkAlarmLimitsEntryTxErrors Integer32
    }

-- {COLUMN} 1.3.6.1.4.1.2356.11.2.23.20.13.1.1
lcsSetupInterfacesWlanNetworkAlarmLimitsEntryIfc OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-write
    STATUS     current
    DESCRIPTION
            ""
    ::= { lcsSetupInterfacesWlanNetworkAlarmLimitsEntry 1 }

-- {COLUMN} 1.3.6.1.4.1.2356.11.2.23.20.13.1.2
lcsSetupInterfacesWlanNetworkAlarmLimitsEntryPhySignal OBJECT-TYPE
    SYNTAX     Integer32 (0..65535)
    MAX-ACCESS read-write
    STATUS     current
    DESCRIPTION
            ""
    ::= { lcsSetupInterfacesWlanNetworkAlarmLimitsEntry 2 }

-- {COLUMN} 1.3.6.1.4.1.2356.11.2.23.20.13.1.3
lcsSetupInterfacesWlanNetworkAlarmLimitsEntryTotalRetries OBJECT-TYPE
    SYNTAX     Integer32 (0..65535)
    MAX-ACCESS read-write
    STATUS     current
    DESCRIPTION
            ""
    ::= { lcsSetupInterfacesWlanNetworkAlarmLimitsEntry 3 }

-- {COLUMN} 1.3.6.1.4.1.2356.11.2.23.20.13.1.4
lcsSetupInterfacesWlanNetworkAlarmLimitsEntryTxErrors OBJECT-TYPE
    SYNTAX     Integer32 (0..65535)
    MAX-ACCESS read-write
    STATUS     current
    DESCRIPTION
            ""
    ::= { lcsSetupInterfacesWlanNetworkAlarmLimitsEntry 4 }

-- {TABLE} 1.3.6.1.4.1.2356.11.2.23.20.14
lcsSetupInterfacesWlanInterpointAlarmLimitsTable OBJECT-TYPE
    SYNTAX     SEQUENCE OF LcsSetupInterfacesWlanInterpointAlarmLimitsEntry
    MAX-ACCESS not-accessible
    STATUS     current
    DESCRIPTION
            ""
    ::= { lcsSetupInterfacesWlan 14 }

-- {ROW} 1.3.6.1.4.1.2356.11.2.23.20.14.1
lcsSetupInterfacesWlanInterpointAlarmLimitsEntry OBJECT-TYPE
    SYNTAX     LcsSetupInterfacesWlanInterpointAlarmLimitsEntry
    MAX-ACCESS not-accessible
    STATUS     current
    DESCRIPTION
            ""
    INDEX {
            lcsSetupInterfacesWlanInterpointAlarmLimitsEntryIfc
          }
    ::= { lcsSetupInterfacesWlanInterpointAlarmLimitsTable 1 }

LcsSetupInterfacesWlanInterpointAlarmLimitsEntry ::= SEQUENCE {
            lcsSetupInterfacesWlanInterpointAlarmLimitsEntryIfc INTEGER,
            lcsSetupInterfacesWlanInterpointAlarmLimitsEntryPhySignal Integer32,
            lcsSetupInterfacesWlanInterpointAlarmLimitsEntryTotalRetries Integer32,
            lcsSetupInterfacesWlanInterpointAlarmLimitsEntryTxErrors Integer32
    }

-- {COLUMN} 1.3.6.1.4.1.2356.11.2.23.20.14.1.1
lcsSetupInterfacesWlanInterpointAlarmLimitsEntryIfc OBJECT-TYPE
    SYNTAX     INTEGER {
                  eP2p11 (1),
                  eP2p12 (2),
                  eP2p13 (3),
                  eP2p14 (4),
                  eP2p15 (5),
                  eP2p16 (6),
                  eP2p21 (7),
                  eP2p22 (8),
                  eP2p23 (9),
                  eP2p24 (10),
                  eP2p25 (11),
                  eP2p26 (12),
                  eP2p17 (32),
                  eP2p18 (33),
                  eP2p19 (34),
                  eP2p110 (35),
                  eP2p111 (36),
                  eP2p112 (37),
                  eP2p113 (38),
                  eP2p114 (39),
                  eP2p115 (40),
                  eP2p116 (41),
                  eP2p27 (64),
                  eP2p28 (65),
                  eP2p29 (66),
                  eP2p210 (67),
                  eP2p211 (68),
                  eP2p212 (69),
                  eP2p213 (70),
                  eP2p214 (71),
                  eP2p215 (72),
                  eP2p216 (73)
            }
    MAX-ACCESS read-write
    STATUS     current
    DESCRIPTION
            ""
    ::= { lcsSetupInterfacesWlanInterpointAlarmLimitsEntry 1 }

-- {COLUMN} 1.3.6.1.4.1.2356.11.2.23.20.14.1.2
lcsSetupInterfacesWlanInterpointAlarmLimitsEntryPhySignal OBJECT-TYPE
    SYNTAX     Integer32 (0..65535)
    MAX-ACCESS read-write
    STATUS     current
    DESCRIPTION
            ""
    ::= { lcsSetupInterfacesWlanInterpointAlarmLimitsEntry 2 }

-- {COLUMN} 1.3.6.1.4.1.2356.11.2.23.20.14.1.3
lcsSetupInterfacesWlanInterpointAlarmLimitsEntryTotalRetries OBJECT-TYPE
    SYNTAX     Integer32 (0..65535)
    MAX-ACCESS read-write
    STATUS     current
    DESCRIPTION
            ""
    ::= { lcsSetupInterfacesWlanInterpointAlarmLimitsEntry 3 }

-- {COLUMN} 1.3.6.1.4.1.2356.11.2.23.20.14.1.4
lcsSetupInterfacesWlanInterpointAlarmLimitsEntryTxErrors OBJECT-TYPE
    SYNTAX     Integer32 (0..65535)
    MAX-ACCESS read-write
    STATUS     current
    DESCRIPTION
            ""
    ::= { lcsSetupInterfacesWlanInterpointAlarmLimitsEntry 4 }

-- {TABLE} 1.3.6.1.4.1.2356.11.2.23.20.15
lcsSetupInterfacesWlanProbeSettingsTable OBJECT-TYPE
    SYNTAX     SEQUENCE OF LcsSetupInterfacesWlanProbeSettingsEntry
    MAX-ACCESS not-accessible
    STATUS     current
    DESCRIPTION
            "-- empty --"
    ::= { lcsSetupInterfacesWlan 15 }

-- {ROW} 1.3.6.1.4.1.2356.11.2.23.20.15.1
lcsSetupInterfacesWlanProbeSettingsEntry OBJECT-TYPE
    SYNTAX     LcsSetupInterfacesWlanProbeSettingsEntry
    MAX-ACCESS not-accessible
    STATUS     current
    DESCRIPTION
            ""
    INDEX {
            lcsSetupInterfacesWlanProbeSettingsEntryIfc
          }
    ::= { lcsSetupInterfacesWlanProbeSettingsTable 1 }

LcsSetupInterfacesWlanProbeSettingsEntry ::= SEQUENCE {
            lcsSetupInterfacesWlanProbeSettingsEntryIfc INTEGER,
            lcsSetupInterfacesWlanProbeSettingsEntryRadioBands INTEGER,
            lcsSetupInterfacesWlanProbeSettingsEntrySubbands24ghz INTEGER,
            lcsSetupInterfacesWlanProbeSettingsEntryChannelList24ghz DisplayString,
            lcsSetupInterfacesWlanProbeSettingsEntrySubbands5ghz INTEGER,
            lcsSetupInterfacesWlanProbeSettingsEntryChannelList5ghz DisplayString,
            lcsSetupInterfacesWlanProbeSettingsEntryChannelDwellTime Integer32
    }

-- {COLUMN} 1.3.6.1.4.1.2356.11.2.23.20.15.1.1
lcsSetupInterfacesWlanProbeSettingsEntryIfc OBJECT-TYPE
    SYNTAX     INTEGER {
                  eWlan1 (1),
                  eWlan2 (2)
            }
    MAX-ACCESS read-write
    STATUS     current
    DESCRIPTION
            "-- empty --"
    ::= { lcsSetupInterfacesWlanProbeSettingsEntry 1 }

-- {COLUMN} 1.3.6.1.4.1.2356.11.2.23.20.15.1.2
lcsSetupInterfacesWlanProbeSettingsEntryRadioBands OBJECT-TYPE
    SYNTAX     INTEGER {
                  e24ghz (1),
                  e5ghz (2),
                  e24ghz5ghz (3)
            }
    MAX-ACCESS read-write
    STATUS     current
    DESCRIPTION
            "-- empty --"
    ::= { lcsSetupInterfacesWlanProbeSettingsEntry 2 }

-- {COLUMN} 1.3.6.1.4.1.2356.11.2.23.20.15.1.3
lcsSetupInterfacesWlanProbeSettingsEntrySubbands24ghz OBJECT-TYPE
    SYNTAX     INTEGER {
                  eBand1 (1),
                  eBand2 (2),
                  eBand1Plus2 (3),
                  eBand3 (4),
                  eBand1Plus3 (5),
                  eBand2Plus3 (6),
                  eBand1Plus2Plus3 (7)
            }
    MAX-ACCESS read-write
    STATUS     current
    DESCRIPTION
            "-- empty --"
    ::= { lcsSetupInterfacesWlanProbeSettingsEntry 3 }

-- {COLUMN} 1.3.6.1.4.1.2356.11.2.23.20.15.1.4
lcsSetupInterfacesWlanProbeSettingsEntryChannelList24ghz OBJECT-TYPE
    SYNTAX     DisplayString (SIZE(0..48))
    MAX-ACCESS read-write
    STATUS     current
    DESCRIPTION
            "-- empty --"
    ::= { lcsSetupInterfacesWlanProbeSettingsEntry 4 }

-- {COLUMN} 1.3.6.1.4.1.2356.11.2.23.20.15.1.5
lcsSetupInterfacesWlanProbeSettingsEntrySubbands5ghz OBJECT-TYPE
    SYNTAX     INTEGER {
                  eBand1 (1),
                  eBand2 (2),
                  eBand1Plus2 (3),
                  eBand3 (4),
                  eBand1Plus3 (5),
                  eBand2Plus3 (6),
                  eBand1Plus2Plus3 (7)
            }
    MAX-ACCESS read-write
    STATUS     current
    DESCRIPTION
            "-- empty --"
    ::= { lcsSetupInterfacesWlanProbeSettingsEntry 5 }

-- {COLUMN} 1.3.6.1.4.1.2356.11.2.23.20.15.1.6
lcsSetupInterfacesWlanProbeSettingsEntryChannelList5ghz OBJECT-TYPE
    SYNTAX     DisplayString (SIZE(0..48))
    MAX-ACCESS read-write
    STATUS     current
    DESCRIPTION
            "-- empty --"
    ::= { lcsSetupInterfacesWlanProbeSettingsEntry 6 }

-- {COLUMN} 1.3.6.1.4.1.2356.11.2.23.20.15.1.7
lcsSetupInterfacesWlanProbeSettingsEntryChannelDwellTime OBJECT-TYPE
    SYNTAX     Integer32 (0..2147483647)
    MAX-ACCESS read-write
    STATUS     current
    DESCRIPTION
            "-- empty --"
    ::= { lcsSetupInterfacesWlanProbeSettingsEntry 7 }

-- {TABLE} 1.3.6.1.4.1.2356.11.2.23.20.16
lcsSetupInterfacesWlanIeee80211uTable OBJECT-TYPE
    SYNTAX     SEQUENCE OF LcsSetupInterfacesWlanIeee80211uEntry
    MAX-ACCESS not-accessible
    STATUS     current
    DESCRIPTION
            "-- empty --"
    ::= { lcsSetupInterfacesWlan 16 }

-- {ROW} 1.3.6.1.4.1.2356.11.2.23.20.16.1
lcsSetupInterfacesWlanIeee80211uEntry OBJECT-TYPE
    SYNTAX     LcsSetupInterfacesWlanIeee80211uEntry
    MAX-ACCESS not-accessible
    STATUS     current
    DESCRIPTION
            ""
    INDEX {
            lcsSetupInterfacesWlanIeee80211uEntryIfc
          }
    ::= { lcsSetupInterfacesWlanIeee80211uTable 1 }

LcsSetupInterfacesWlanIeee80211uEntry ::= SEQUENCE {
            lcsSetupInterfacesWlanIeee80211uEntryIfc INTEGER,
            lcsSetupInterfacesWlanIeee80211uEntryOperating INTEGER,
            lcsSetupInterfacesWlanIeee80211uEntryHotspot20 INTEGER,
            lcsSetupInterfacesWlanIeee80211uEntryInternet INTEGER,
            lcsSetupInterfacesWlanIeee80211uEntryNetworkType INTEGER,
            lcsSetupInterfacesWlanIeee80211uEntryAsra INTEGER,
            lcsSetupInterfacesWlanIeee80211uEntryHessid INTEGER,
            lcsSetupInterfacesWlanIeee80211uEntryHessidMac MacAddress,
            lcsSetupInterfacesWlanIeee80211uEntryAnqpProfile DisplayString,
            lcsSetupInterfacesWlanIeee80211uEntryHs20Profile DisplayString
    }

-- {COLUMN} 1.3.6.1.4.1.2356.11.2.23.20.16.1.1
lcsSetupInterfacesWlanIeee80211uEntryIfc OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-write
    STATUS     current
    DESCRIPTION
            "-- empty --"
    ::= { lcsSetupInterfacesWlanIeee80211uEntry 1 }

-- {COLUMN} 1.3.6.1.4.1.2356.11.2.23.20.16.1.2
lcsSetupInterfacesWlanIeee80211uEntryOperating OBJECT-TYPE
    SYNTAX     INTEGER {
                  eNo (0),
                  eYes (1)
            }
    MAX-ACCESS read-write
    STATUS     current
    DESCRIPTION
            "-- empty --"
    ::= { lcsSetupInterfacesWlanIeee80211uEntry 2 }

-- {COLUMN} 1.3.6.1.4.1.2356.11.2.23.20.16.1.3
lcsSetupInterfacesWlanIeee80211uEntryHotspot20 OBJECT-TYPE
    SYNTAX     INTEGER {
                  eNo (0),
                  eYes (1)
            }
    MAX-ACCESS read-write
    STATUS     current
    DESCRIPTION
            "-- empty --"
    ::= { lcsSetupInterfacesWlanIeee80211uEntry 3 }

-- {COLUMN} 1.3.6.1.4.1.2356.11.2.23.20.16.1.4
lcsSetupInterfacesWlanIeee80211uEntryInternet OBJECT-TYPE
    SYNTAX     INTEGER {
                  eNo (0),
                  eYes (1)
            }
    MAX-ACCESS read-write
    STATUS     current
    DESCRIPTION
            "-- empty --"
    ::= { lcsSetupInterfacesWlanIeee80211uEntry 4 }

-- {COLUMN} 1.3.6.1.4.1.2356.11.2.23.20.16.1.5
lcsSetupInterfacesWlanIeee80211uEntryNetworkType OBJECT-TYPE
    SYNTAX     INTEGER {
                  ePrivate (0),
                  ePrivateGuestacc (1),
                  ePublicCharge (2),
                  ePublicFree (3),
                  ePersonalDev (4),
                  eEmergency (5),
                  eExperimental (14),
                  eWildcard (15)
            }
    MAX-ACCESS read-write
    STATUS     current
    DESCRIPTION
            "-- empty --"
    ::= { lcsSetupInterfacesWlanIeee80211uEntry 5 }

-- {COLUMN} 1.3.6.1.4.1.2356.11.2.23.20.16.1.6
lcsSetupInterfacesWlanIeee80211uEntryAsra OBJECT-TYPE
    SYNTAX     INTEGER {
                  eNo (0),
                  eYes (1)
            }
    MAX-ACCESS read-write
    STATUS     current
    DESCRIPTION
            "-- empty --"
    ::= { lcsSetupInterfacesWlanIeee80211uEntry 6 }

-- {COLUMN} 1.3.6.1.4.1.2356.11.2.23.20.16.1.7
lcsSetupInterfacesWlanIeee80211uEntryHessid OBJECT-TYPE
    SYNTAX     INTEGER {
                  eBssid (0),
                  eUser (1),
                  eNone (2)
            }
    MAX-ACCESS read-write
    STATUS     current
    DESCRIPTION
            "-- empty --"
    ::= { lcsSetupInterfacesWlanIeee80211uEntry 7 }

-- {COLUMN} 1.3.6.1.4.1.2356.11.2.23.20.16.1.8
lcsSetupInterfacesWlanIeee80211uEntryHessidMac OBJECT-TYPE
    SYNTAX     MacAddress
    MAX-ACCESS read-write
    STATUS     current
    DESCRIPTION
            "-- empty --"
    ::= { lcsSetupInterfacesWlanIeee80211uEntry 8 }

-- {COLUMN} 1.3.6.1.4.1.2356.11.2.23.20.16.1.10
lcsSetupInterfacesWlanIeee80211uEntryAnqpProfile OBJECT-TYPE
    SYNTAX     DisplayString (SIZE(0..32))
    MAX-ACCESS read-write
    STATUS     current
    DESCRIPTION
            "-- empty --"
    ::= { lcsSetupInterfacesWlanIeee80211uEntry 10 }

-- {COLUMN} 1.3.6.1.4.1.2356.11.2.23.20.16.1.13
lcsSetupInterfacesWlanIeee80211uEntryHs20Profile OBJECT-TYPE
    SYNTAX     DisplayString (SIZE(0..32))
    MAX-ACCESS read-write
    STATUS     current
    DESCRIPTION
            "-- empty --"
    ::= { lcsSetupInterfacesWlanIeee80211uEntry 13 }

-- {TABLE} 1.3.6.1.4.1.2356.11.2.23.20.18
lcsSetupInterfacesWlanRadiusAccountingTable OBJECT-TYPE
    SYNTAX     SEQUENCE OF LcsSetupInterfacesWlanRadiusAccountingEntry
    MAX-ACCESS not-accessible
    STATUS     current
    DESCRIPTION
            "-- empty --"
    ::= { lcsSetupInterfacesWlan 18 }

-- {ROW} 1.3.6.1.4.1.2356.11.2.23.20.18.1
lcsSetupInterfacesWlanRadiusAccountingEntry OBJECT-TYPE
    SYNTAX     LcsSetupInterfacesWlanRadiusAccountingEntry
    MAX-ACCESS not-accessible
    STATUS     current
    DESCRIPTION
            ""
    INDEX {
            lcsSetupInterfacesWlanRadiusAccountingEntryIfc
          }
    ::= { lcsSetupInterfacesWlanRadiusAccountingTable 1 }

LcsSetupInterfacesWlanRadiusAccountingEntry ::= SEQUENCE {
            lcsSetupInterfacesWlanRadiusAccountingEntryIfc INTEGER,
            lcsSetupInterfacesWlanRadiusAccountingEntryServerAddress IpAddress,
            lcsSetupInterfacesWlanRadiusAccountingEntryAuthPort Integer32,
            lcsSetupInterfacesWlanRadiusAccountingEntrySecret DisplayString,
            lcsSetupInterfacesWlanRadiusAccountingEntryLoopbackAddress DisplayString,
            lcsSetupInterfacesWlanRadiusAccountingEntryProtocol INTEGER,
            lcsSetupInterfacesWlanRadiusAccountingEntryBackupServerIpAddress IpAddress,
            lcsSetupInterfacesWlanRadiusAccountingEntryBackupAuthPort Integer32,
            lcsSetupInterfacesWlanRadiusAccountingEntryBackupSecret DisplayString,
            lcsSetupInterfacesWlanRadiusAccountingEntryBackupLoopbackAddress DisplayString,
            lcsSetupInterfacesWlanRadiusAccountingEntryBackupProtocol INTEGER
    }

-- {COLUMN} 1.3.6.1.4.1.2356.11.2.23.20.18.1.1
lcsSetupInterfacesWlanRadiusAccountingEntryIfc OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan22 (32),
                  eWlan23 (33),
                  eWlan24 (34),
                  eWlan25 (35),
                  eWlan26 (36),
                  eWlan27 (37),
                  eWlan28 (38)
            }
    MAX-ACCESS read-write
    STATUS     current
    DESCRIPTION
            "-- empty --"
    ::= { lcsSetupInterfacesWlanRadiusAccountingEntry 1 }

-- {COLUMN} 1.3.6.1.4.1.2356.11.2.23.20.18.1.2
lcsSetupInterfacesWlanRadiusAccountingEntryServerAddress OBJECT-TYPE
    SYNTAX     IpAddress
    MAX-ACCESS read-write
    STATUS     current
    DESCRIPTION
            "-- empty --"
    ::= { lcsSetupInterfacesWlanRadiusAccountingEntry 2 }

-- {COLUMN} 1.3.6.1.4.1.2356.11.2.23.20.18.1.3
lcsSetupInterfacesWlanRadiusAccountingEntryAuthPort OBJECT-TYPE
    SYNTAX     Integer32 (0..65535)
    MAX-ACCESS read-write
    STATUS     current
    DESCRIPTION
            "-- empty --"
    ::= { lcsSetupInterfacesWlanRadiusAccountingEntry 3 }

-- {COLUMN} 1.3.6.1.4.1.2356.11.2.23.20.18.1.4
lcsSetupInterfacesWlanRadiusAccountingEntrySecret OBJECT-TYPE
    SYNTAX     DisplayString (SIZE(0..64))
    MAX-ACCESS read-write
    STATUS     current
    DESCRIPTION
            "-- empty --"
    ::= { lcsSetupInterfacesWlanRadiusAccountingEntry 4 }

-- {COLUMN} 1.3.6.1.4.1.2356.11.2.23.20.18.1.5
lcsSetupInterfacesWlanRadiusAccountingEntryLoopbackAddress OBJECT-TYPE
    SYNTAX     DisplayString (SIZE(0..16))
    MAX-ACCESS read-write
    STATUS     current
    DESCRIPTION
            "-- empty --"
    ::= { lcsSetupInterfacesWlanRadiusAccountingEntry 5 }

-- {COLUMN} 1.3.6.1.4.1.2356.11.2.23.20.18.1.6
lcsSetupInterfacesWlanRadiusAccountingEntryProtocol OBJECT-TYPE
    SYNTAX     INTEGER {
                  eRadius (0),
                  eRadsec (1)
            }
    MAX-ACCESS read-write
    STATUS     current
    DESCRIPTION
            "-- empty --"
    ::= { lcsSetupInterfacesWlanRadiusAccountingEntry 6 }

-- {COLUMN} 1.3.6.1.4.1.2356.11.2.23.20.18.1.7
lcsSetupInterfacesWlanRadiusAccountingEntryBackupServerIpAddress OBJECT-TYPE
    SYNTAX     IpAddress
    MAX-ACCESS read-write
    STATUS     current
    DESCRIPTION
            "-- empty --"
    ::= { lcsSetupInterfacesWlanRadiusAccountingEntry 7 }

-- {COLUMN} 1.3.6.1.4.1.2356.11.2.23.20.18.1.8
lcsSetupInterfacesWlanRadiusAccountingEntryBackupAuthPort OBJECT-TYPE
    SYNTAX     Integer32 (0..65535)
    MAX-ACCESS read-write
    STATUS     current
    DESCRIPTION
            "-- empty --"
    ::= { lcsSetupInterfacesWlanRadiusAccountingEntry 8 }

-- {COLUMN} 1.3.6.1.4.1.2356.11.2.23.20.18.1.9
lcsSetupInterfacesWlanRadiusAccountingEntryBackupSecret OBJECT-TYPE
    SYNTAX     DisplayString (SIZE(0..64))
    MAX-ACCESS read-write
    STATUS     current
    DESCRIPTION
            "-- empty --"
    ::= { lcsSetupInterfacesWlanRadiusAccountingEntry 9 }

-- {COLUMN} 1.3.6.1.4.1.2356.11.2.23.20.18.1.10
lcsSetupInterfacesWlanRadiusAccountingEntryBackupLoopbackAddress OBJECT-TYPE
    SYNTAX     DisplayString (SIZE(0..16))
    MAX-ACCESS read-write
    STATUS     current
    DESCRIPTION
            "-- empty --"
    ::= { lcsSetupInterfacesWlanRadiusAccountingEntry 10 }

-- {COLUMN} 1.3.6.1.4.1.2356.11.2.23.20.18.1.11
lcsSetupInterfacesWlanRadiusAccountingEntryBackupProtocol OBJECT-TYPE
    SYNTAX     INTEGER {
                  eRadius (0),
                  eRadsec (1)
            }
    MAX-ACCESS read-write
    STATUS     current
    DESCRIPTION
            "-- empty --"
    ::= { lcsSetupInterfacesWlanRadiusAccountingEntry 11 }

-- {TABLE} 1.3.6.1.4.1.2356.11.2.23.20.19
lcsSetupInterfacesWlanIntptTrnsmisTable OBJECT-TYPE
    SYNTAX     SEQUENCE OF LcsSetupInterfacesWlanIntptTrnsmisEntry
    MAX-ACCESS not-accessible
    STATUS     current
    DESCRIPTION
            ""
    ::= { lcsSetupInterfacesWlan 19 }

-- {ROW} 1.3.6.1.4.1.2356.11.2.23.20.19.1
lcsSetupInterfacesWlanIntptTrnsmisEntry OBJECT-TYPE
    SYNTAX     LcsSetupInterfacesWlanIntptTrnsmisEntry
    MAX-ACCESS not-accessible
    STATUS     current
    DESCRIPTION
            ""
    INDEX {
            lcsSetupInterfacesWlanIntptTrnsmisEntryIfc
          }
    ::= { lcsSetupInterfacesWlanIntptTrnsmisTable 1 }

LcsSetupInterfacesWlanIntptTrnsmisEntry ::= SEQUENCE {
            lcsSetupInterfacesWlanIntptTrnsmisEntryIfc INTEGER,
            lcsSetupInterfacesWlanIntptTrnsmisEntryPacketSize Integer32,
            lcsSetupInterfacesWlanIntptTrnsmisEntryMinTxRate INTEGER,
            lcsSetupInterfacesWlanIntptTrnsmisEntryRtsThreshold Integer32,
            lcsSetupInterfacesWlanIntptTrnsmisEntry11bPreamble INTEGER,
            lcsSetupInterfacesWlanIntptTrnsmisEntryMaxTxRate INTEGER,
            lcsSetupInterfacesWlanIntptTrnsmisEntryMinFragLen Integer32,
            lcsSetupInterfacesWlanIntptTrnsmisEntrySoftRetries Integer32,
            lcsSetupInterfacesWlanIntptTrnsmisEntryHardRetries Integer32,
            lcsSetupInterfacesWlanIntptTrnsmisEntryShortGuardInterval INTEGER,
            lcsSetupInterfacesWlanIntptTrnsmisEntryMaxSpatialStreams INTEGER,
            lcsSetupInterfacesWlanIntptTrnsmisEntrySendAggregates INTEGER,
            lcsSetupInterfacesWlanIntptTrnsmisEntryMinHtMcs INTEGER,
            lcsSetupInterfacesWlanIntptTrnsmisEntryMaxHtMcs INTEGER,
            lcsSetupInterfacesWlanIntptTrnsmisEntryMinSpatialStreams INTEGER,
            lcsSetupInterfacesWlanIntptTrnsmisEntryEapolRate INTEGER,
            lcsSetupInterfacesWlanIntptTrnsmisEntryMaxAggrPacketCount Integer32,
            lcsSetupInterfacesWlanIntptTrnsmisEntryReceiveAggregates INTEGER,
            lcsSetupInterfacesWlanIntptTrnsmisEntryUseStbc INTEGER,
            lcsSetupInterfacesWlanIntptTrnsmisEntryUseLdpc INTEGER,
            lcsSetupInterfacesWlanIntptTrnsmisEntryQosMapping INTEGER
    }

-- {COLUMN} 1.3.6.1.4.1.2356.11.2.23.20.19.1.1
lcsSetupInterfacesWlanIntptTrnsmisEntryIfc OBJECT-TYPE
    SYNTAX     INTEGER {
                  eP2p11 (1),
                  eP2p12 (2),
                  eP2p13 (3),
                  eP2p14 (4),
                  eP2p15 (5),
                  eP2p16 (6),
                  eP2p21 (7),
                  eP2p22 (8),
                  eP2p23 (9),
                  eP2p24 (10),
                  eP2p25 (11),
                  eP2p26 (12),
                  eP2p17 (32),
                  eP2p18 (33),
                  eP2p19 (34),
                  eP2p110 (35),
                  eP2p111 (36),
                  eP2p112 (37),
                  eP2p113 (38),
                  eP2p114 (39),
                  eP2p115 (40),
                  eP2p116 (41),
                  eP2p27 (64),
                  eP2p28 (65),
                  eP2p29 (66),
                  eP2p210 (67),
                  eP2p211 (68),
                  eP2p212 (69),
                  eP2p213 (70),
                  eP2p214 (71),
                  eP2p215 (72),
                  eP2p216 (73)
            }
    MAX-ACCESS read-write
    STATUS     current
    DESCRIPTION
            "-- empty --"
    ::= { lcsSetupInterfacesWlanIntptTrnsmisEntry 1 }

-- {COLUMN} 1.3.6.1.4.1.2356.11.2.23.20.19.1.2
lcsSetupInterfacesWlanIntptTrnsmisEntryPacketSize OBJECT-TYPE
    SYNTAX     Integer32 (0..65535)
    MAX-ACCESS read-write
    STATUS     current
    DESCRIPTION
            "-- empty --"
    ::= { lcsSetupInterfacesWlanIntptTrnsmisEntry 2 }

-- {COLUMN} 1.3.6.1.4.1.2356.11.2.23.20.19.1.3
lcsSetupInterfacesWlanIntptTrnsmisEntryMinTxRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-write
    STATUS     current
    DESCRIPTION
            "-- empty --"
    ::= { lcsSetupInterfacesWlanIntptTrnsmisEntry 3 }

-- {COLUMN} 1.3.6.1.4.1.2356.11.2.23.20.19.1.6
lcsSetupInterfacesWlanIntptTrnsmisEntryRtsThreshold OBJECT-TYPE
    SYNTAX     Integer32 (0..65535)
    MAX-ACCESS read-write
    STATUS     current
    DESCRIPTION
            "-- empty --"
    ::= { lcsSetupInterfacesWlanIntptTrnsmisEntry 6 }

-- {COLUMN} 1.3.6.1.4.1.2356.11.2.23.20.19.1.7
lcsSetupInterfacesWlanIntptTrnsmisEntry11bPreamble OBJECT-TYPE
    SYNTAX     INTEGER {
                  eAuto (0),
                  eLong (1)
            }
    MAX-ACCESS read-write
    STATUS     current
    DESCRIPTION
            "-- empty --"
    ::= { lcsSetupInterfacesWlanIntptTrnsmisEntry 7 }

-- {COLUMN} 1.3.6.1.4.1.2356.11.2.23.20.19.1.9
lcsSetupInterfacesWlanIntptTrnsmisEntryMaxTxRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-write
    STATUS     current
    DESCRIPTION
            "-- empty --"
    ::= { lcsSetupInterfacesWlanIntptTrnsmisEntry 9 }

-- {COLUMN} 1.3.6.1.4.1.2356.11.2.23.20.19.1.10
lcsSetupInterfacesWlanIntptTrnsmisEntryMinFragLen OBJECT-TYPE
    SYNTAX     Integer32 (0..65535)
    MAX-ACCESS read-write
    STATUS     current
    DESCRIPTION
            "-- empty --"
    ::= { lcsSetupInterfacesWlanIntptTrnsmisEntry 10 }

-- {COLUMN} 1.3.6.1.4.1.2356.11.2.23.20.19.1.11
lcsSetupInterfacesWlanIntptTrnsmisEntrySoftRetries OBJECT-TYPE
    SYNTAX     Integer32 (0..255)
    MAX-ACCESS read-write
    STATUS     current
    DESCRIPTION
            "-- empty --"
    ::= { lcsSetupInterfacesWlanIntptTrnsmisEntry 11 }

-- {COLUMN} 1.3.6.1.4.1.2356.11.2.23.20.19.1.12
lcsSetupInterfacesWlanIntptTrnsmisEntryHardRetries OBJECT-TYPE
    SYNTAX     Integer32 (0..255)
    MAX-ACCESS read-write
    STATUS     current
    DESCRIPTION
            "-- empty --"
    ::= { lcsSetupInterfacesWlanIntptTrnsmisEntry 12 }

-- {COLUMN} 1.3.6.1.4.1.2356.11.2.23.20.19.1.13
lcsSetupInterfacesWlanIntptTrnsmisEntryShortGuardInterval OBJECT-TYPE
    SYNTAX     INTEGER {
                  eAuto (0),
                  eNo (1)
            }
    MAX-ACCESS read-write
    STATUS     current
    DESCRIPTION
            "-- empty --"
    ::= { lcsSetupInterfacesWlanIntptTrnsmisEntry 13 }

-- {COLUMN} 1.3.6.1.4.1.2356.11.2.23.20.19.1.14
lcsSetupInterfacesWlanIntptTrnsmisEntryMaxSpatialStreams OBJECT-TYPE
    SYNTAX     INTEGER {
                  eAuto (0),
                  eOne (1),
                  eTwo (2),
                  eThree (3),
                  eFour (4)
            }
    MAX-ACCESS read-write
    STATUS     current
    DESCRIPTION
            "-- empty --"
    ::= { lcsSetupInterfacesWlanIntptTrnsmisEntry 14 }

-- {COLUMN} 1.3.6.1.4.1.2356.11.2.23.20.19.1.15
lcsSetupInterfacesWlanIntptTrnsmisEntrySendAggregates OBJECT-TYPE
    SYNTAX     INTEGER {
                  eNo (0),
                  eYes (1)
            }
    MAX-ACCESS read-write
    STATUS     current
    DESCRIPTION
            "-- empty --"
    ::= { lcsSetupInterfacesWlanIntptTrnsmisEntry 15 }

-- {COLUMN} 1.3.6.1.4.1.2356.11.2.23.20.19.1.16
lcsSetupInterfacesWlanIntptTrnsmisEntryMinHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-write
    STATUS     current
    DESCRIPTION
            "-- empty --"
    ::= { lcsSetupInterfacesWlanIntptTrnsmisEntry 16 }

-- {COLUMN} 1.3.6.1.4.1.2356.11.2.23.20.19.1.17
lcsSetupInterfacesWlanIntptTrnsmisEntryMaxHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-write
    STATUS     current
    DESCRIPTION
            "-- empty --"
    ::= { lcsSetupInterfacesWlanIntptTrnsmisEntry 17 }

-- {COLUMN} 1.3.6.1.4.1.2356.11.2.23.20.19.1.18
lcsSetupInterfacesWlanIntptTrnsmisEntryMinSpatialStreams OBJECT-TYPE
    SYNTAX     INTEGER {
                  eAuto (0),
                  eOne (1),
                  eTwo (2),
                  eThree (3),
                  eFour (4)
            }
    MAX-ACCESS read-write
    STATUS     current
    DESCRIPTION
            "-- empty --"
    ::= { lcsSetupInterfacesWlanIntptTrnsmisEntry 18 }

-- {COLUMN} 1.3.6.1.4.1.2356.11.2.23.20.19.1.19
lcsSetupInterfacesWlanIntptTrnsmisEntryEapolRate OBJECT-TYPE
    SYNTAX     INTEGER {
                  eLikeData (0),
                  e1M (1),
                  e2M (2),
                  e5M5 (4),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-write
    STATUS     current
    DESCRIPTION
            "-- empty --"
    ::= { lcsSetupInterfacesWlanIntptTrnsmisEntry 19 }

-- {COLUMN} 1.3.6.1.4.1.2356.11.2.23.20.19.1.20
lcsSetupInterfacesWlanIntptTrnsmisEntryMaxAggrPacketCount OBJECT-TYPE
    SYNTAX     Integer32 (0..255)
    MAX-ACCESS read-write
    STATUS     current
    DESCRIPTION
            "-- empty --"
    ::= { lcsSetupInterfacesWlanIntptTrnsmisEntry 20 }

-- {COLUMN} 1.3.6.1.4.1.2356.11.2.23.20.19.1.22
lcsSetupInterfacesWlanIntptTrnsmisEntryReceiveAggregates OBJECT-TYPE
    SYNTAX     INTEGER {
                  eNo (0),
                  eYes (1)
            }
    MAX-ACCESS read-write
    STATUS     current
    DESCRIPTION
            "-- empty --"
    ::= { lcsSetupInterfacesWlanIntptTrnsmisEntry 22 }

-- {COLUMN} 1.3.6.1.4.1.2356.11.2.23.20.19.1.23
lcsSetupInterfacesWlanIntptTrnsmisEntryUseStbc OBJECT-TYPE
    SYNTAX     INTEGER {
                  eNo (0),
                  eYes (1)
            }
    MAX-ACCESS read-write
    STATUS     current
    DESCRIPTION
            "-- empty --"
    ::= { lcsSetupInterfacesWlanIntptTrnsmisEntry 23 }

-- {COLUMN} 1.3.6.1.4.1.2356.11.2.23.20.19.1.24
lcsSetupInterfacesWlanIntptTrnsmisEntryUseLdpc OBJECT-TYPE
    SYNTAX     INTEGER {
                  eNo (0),
                  eYes (1)
            }
    MAX-ACCESS read-write
    STATUS     current
    DESCRIPTION
            "-- empty --"
    ::= { lcsSetupInterfacesWlanIntptTrnsmisEntry 24 }

-- {COLUMN} 1.3.6.1.4.1.2356.11.2.23.20.19.1.27
lcsSetupInterfacesWlanIntptTrnsmisEntryQosMapping OBJECT-TYPE
    SYNTAX     INTEGER {
                  eNo (0),
                  eYes (1)
            }
    MAX-ACCESS read-write
    STATUS     current
    DESCRIPTION
            "-- empty --"
    ::= { lcsSetupInterfacesWlanIntptTrnsmisEntry 27 }

-- {TABLE} 1.3.6.1.4.1.2356.11.2.23.20.20
lcsSetupInterfacesWlanIntptEncTable OBJECT-TYPE
    SYNTAX     SEQUENCE OF LcsSetupInterfacesWlanIntptEncEntry
    MAX-ACCESS not-accessible
    STATUS     current
    DESCRIPTION
            ""
    ::= { lcsSetupInterfacesWlan 20 }

-- {ROW} 1.3.6.1.4.1.2356.11.2.23.20.20.1
lcsSetupInterfacesWlanIntptEncEntry OBJECT-TYPE
    SYNTAX     LcsSetupInterfacesWlanIntptEncEntry
    MAX-ACCESS not-accessible
    STATUS     current
    DESCRIPTION
            ""
    INDEX {
            lcsSetupInterfacesWlanIntptEncEntryIfc
          }
    ::= { lcsSetupInterfacesWlanIntptEncTable 1 }

LcsSetupInterfacesWlanIntptEncEntry ::= SEQUENCE {
            lcsSetupInterfacesWlanIntptEncEntryIfc INTEGER,
            lcsSetupInterfacesWlanIntptEncEntryEncryption INTEGER,
            lcsSetupInterfacesWlanIntptEncEntryDefaultKey Integer32,
            lcsSetupInterfacesWlanIntptEncEntryMethod INTEGER,
            lcsSetupInterfacesWlanIntptEncEntryWpaVersion INTEGER,
            lcsSetupInterfacesWlanIntptEncEntryWpaRekeyingCycle Integer32,
            lcsSetupInterfacesWlanIntptEncEntryWpa1SessionKeytypes INTEGER,
            lcsSetupInterfacesWlanIntptEncEntryWpa2SessionKeytypes INTEGER,
            lcsSetupInterfacesWlanIntptEncEntryProtMgmtFrames INTEGER,
            lcsSetupInterfacesWlanIntptEncEntryPmkCaching INTEGER,
            lcsSetupInterfacesWlanIntptEncEntryWpa2KeyManagement BITS,
            lcsSetupInterfacesWlanIntptEncEntrySaeGroups BITS,
            lcsSetupInterfacesWlanIntptEncEntryWpa23SessionKeytypes BITS
    }

-- {COLUMN} 1.3.6.1.4.1.2356.11.2.23.20.20.1.1
lcsSetupInterfacesWlanIntptEncEntryIfc OBJECT-TYPE
    SYNTAX     INTEGER {
                  eWlan1 (1),
                  eWlan2 (2)
            }
    MAX-ACCESS read-write
    STATUS     current
    DESCRIPTION
            "-- empty --"
    ::= { lcsSetupInterfacesWlanIntptEncEntry 1 }

-- {COLUMN} 1.3.6.1.4.1.2356.11.2.23.20.20.1.2
lcsSetupInterfacesWlanIntptEncEntryEncryption OBJECT-TYPE
    SYNTAX     INTEGER {
                  eNo (0),
                  eYes (2)
            }
    MAX-ACCESS read-write
    STATUS     current
    DESCRIPTION
            "-- empty --"
    ::= { lcsSetupInterfacesWlanIntptEncEntry 2 }

-- {COLUMN} 1.3.6.1.4.1.2356.11.2.23.20.20.1.3
lcsSetupInterfacesWlanIntptEncEntryDefaultKey OBJECT-TYPE
    SYNTAX     Integer32 (0..255)
    MAX-ACCESS read-write
    STATUS     current
    DESCRIPTION
            "-- empty --"
    ::= { lcsSetupInterfacesWlanIntptEncEntry 3 }

-- {COLUMN} 1.3.6.1.4.1.2356.11.2.23.20.20.1.4
lcsSetupInterfacesWlanIntptEncEntryMethod OBJECT-TYPE
    SYNTAX     INTEGER {
                  eWep40Bits (5),
                  eWep104Bits (13),
                  eWep128Bits (16),
                  e80211iWpaPsk (32)
            }
    MAX-ACCESS read-write
    STATUS     current
    DESCRIPTION
            "-- empty --"
    ::= { lcsSetupInterfacesWlanIntptEncEntry 4 }

-- {COLUMN} 1.3.6.1.4.1.2356.11.2.23.20.20.1.9
lcsSetupInterfacesWlanIntptEncEntryWpaVersion OBJECT-TYPE
    SYNTAX     INTEGER {
                  eWpa1 (2),
                  eWpa2 (4),
                  eWpa12 (6),
                  eWpa3 (8),
                  eWpa23 (12),
                  eWpa123 (14)
            }
    MAX-ACCESS read-write
    STATUS     current
    DESCRIPTION
            "-- empty --"
    ::= { lcsSetupInterfacesWlanIntptEncEntry 9 }

-- {COLUMN} 1.3.6.1.4.1.2356.11.2.23.20.20.1.11
lcsSetupInterfacesWlanIntptEncEntryWpaRekeyingCycle OBJECT-TYPE
    SYNTAX     Integer32 (0..2147483647)
    MAX-ACCESS read-write
    STATUS     current
    DESCRIPTION
            "-- empty --"
    ::= { lcsSetupInterfacesWlanIntptEncEntry 11 }

-- {COLUMN} 1.3.6.1.4.1.2356.11.2.23.20.20.1.12
lcsSetupInterfacesWlanIntptEncEntryWpa1SessionKeytypes OBJECT-TYPE
    SYNTAX     INTEGER {
                  eTkip (1),
                  eAes (2),
                  eTkipAes (3)
            }
    MAX-ACCESS read-write
    STATUS     current
    DESCRIPTION
            "-- empty --"
    ::= { lcsSetupInterfacesWlanIntptEncEntry 12 }

-- {COLUMN} 1.3.6.1.4.1.2356.11.2.23.20.20.1.13
lcsSetupInterfacesWlanIntptEncEntryWpa2SessionKeytypes OBJECT-TYPE
    SYNTAX     INTEGER {
                  eTkip (1),
                  eAes (2),
                  eTkipAes (3)
            }
    MAX-ACCESS read-write
    STATUS     current
    DESCRIPTION
            "-- empty --"
    ::= { lcsSetupInterfacesWlanIntptEncEntry 13 }

-- {COLUMN} 1.3.6.1.4.1.2356.11.2.23.20.20.1.14
lcsSetupInterfacesWlanIntptEncEntryProtMgmtFrames OBJECT-TYPE
    SYNTAX     INTEGER {
                  eNo (0),
                  eOptional (1),
                  eMandatory (2)
            }
    MAX-ACCESS read-write
    STATUS     current
    DESCRIPTION
            "-- empty --"
    ::= { lcsSetupInterfacesWlanIntptEncEntry 14 }

-- {COLUMN} 1.3.6.1.4.1.2356.11.2.23.20.20.1.15
lcsSetupInterfacesWlanIntptEncEntryPmkCaching OBJECT-TYPE
    SYNTAX     INTEGER {
                  eNo (0),
                  eYes (1)
            }
    MAX-ACCESS read-write
    STATUS     current
    DESCRIPTION
            "-- empty --"
    ::= { lcsSetupInterfacesWlanIntptEncEntry 15 }

-- {COLUMN} 1.3.6.1.4.1.2356.11.2.23.20.20.1.19
lcsSetupInterfacesWlanIntptEncEntryWpa2KeyManagement OBJECT-TYPE
    SYNTAX     BITS {
                  eSha256 (5),
                  eStandard (7)
            }
    MAX-ACCESS read-write
    STATUS     current
    DESCRIPTION
            "-- empty --"
    ::= { lcsSetupInterfacesWlanIntptEncEntry 19 }

-- {COLUMN} 1.3.6.1.4.1.2356.11.2.23.20.20.1.26
lcsSetupInterfacesWlanIntptEncEntrySaeGroups OBJECT-TYPE
    SYNTAX     BITS {
                  eSecp521r1 (10),
                  eSecp384r1 (11),
                  eSecp256r1 (12)
            }
    MAX-ACCESS read-write
    STATUS     current
    DESCRIPTION
            "-- empty --"
    ::= { lcsSetupInterfacesWlanIntptEncEntry 26 }

-- {COLUMN} 1.3.6.1.4.1.2356.11.2.23.20.20.1.27
lcsSetupInterfacesWlanIntptEncEntryWpa23SessionKeytypes OBJECT-TYPE
    SYNTAX     BITS {
                  eAesGcmp256 (3),
                  eAesGcmp128 (4),
                  eAesCcmp256 (5),
                  eAesCcm (6),
                  eTkip (7)
            }
    MAX-ACCESS read-write
    STATUS     current
    DESCRIPTION
            "-- empty --"
    ::= { lcsSetupInterfacesWlanIntptEncEntry 27 }

-- {TABLE} 1.3.6.1.4.1.2356.11.2.23.20.21
lcsSetupInterfacesWlanCoexistenceSettingsTable OBJECT-TYPE
    SYNTAX     SEQUENCE OF LcsSetupInterfacesWlanCoexistenceSettingsEntry
    MAX-ACCESS not-accessible
    STATUS     current
    DESCRIPTION
            "-- empty --"
    ::= { lcsSetupInterfacesWlan 21 }

-- {ROW} 1.3.6.1.4.1.2356.11.2.23.20.21.1
lcsSetupInterfacesWlanCoexistenceSettingsEntry OBJECT-TYPE
    SYNTAX     LcsSetupInterfacesWlanCoexistenceSettingsEntry
    MAX-ACCESS not-accessible
    STATUS     current
    DESCRIPTION
            ""
    INDEX {
            lcsSetupInterfacesWlanCoexistenceSettingsEntryIfc
          }
    ::= { lcsSetupInterfacesWlanCoexistenceSettingsTable 1 }

LcsSetupInterfacesWlanCoexistenceSettingsEntry ::= SEQUENCE {
            lcsSetupInterfacesWlanCoexistenceSettingsEntryIfc INTEGER,
            lcsSetupInterfacesWlanCoexistenceSettingsEntryCoexistence INTEGER,
            lcsSetupInterfacesWlanCoexistenceSettingsEntryMinIgnorePrio INTEGER
    }

-- {COLUMN} 1.3.6.1.4.1.2356.11.2.23.20.21.1.1
lcsSetupInterfacesWlanCoexistenceSettingsEntryIfc OBJECT-TYPE
    SYNTAX     INTEGER {
                  eWlan1 (1),
                  eWlan2 (2)
            }
    MAX-ACCESS read-write
    STATUS     current
    DESCRIPTION
            "-- empty --"
    ::= { lcsSetupInterfacesWlanCoexistenceSettingsEntry 1 }

-- {COLUMN} 1.3.6.1.4.1.2356.11.2.23.20.21.1.2
lcsSetupInterfacesWlanCoexistenceSettingsEntryCoexistence OBJECT-TYPE
    SYNTAX     INTEGER {
                  eNo (0),
                  eYes (1)
            }
    MAX-ACCESS read-write
    STATUS     current
    DESCRIPTION
            "-- empty --"
    ::= { lcsSetupInterfacesWlanCoexistenceSettingsEntry 2 }

-- {COLUMN} 1.3.6.1.4.1.2356.11.2.23.20.21.1.3
lcsSetupInterfacesWlanCoexistenceSettingsEntryMinIgnorePrio OBJECT-TYPE
    SYNTAX     INTEGER {
                  eNone (0),
                  eBeacon (1),
                  eVoice (2)
            }
    MAX-ACCESS read-write
    STATUS     current
    DESCRIPTION
            "-- empty --"
    ::= { lcsSetupInterfacesWlanCoexistenceSettingsEntry 3 }

-- {TABLE} 1.3.6.1.4.1.2356.11.2.23.20.22
lcsSetupInterfacesWlanInterpointRateSelectionTable OBJECT-TYPE
    SYNTAX     SEQUENCE OF LcsSetupInterfacesWlanInterpointRateSelectionEntry
    MAX-ACCESS not-accessible
    STATUS     current
    DESCRIPTION
            "-- empty --"
    ::= { lcsSetupInterfacesWlan 22 }

-- {ROW} 1.3.6.1.4.1.2356.11.2.23.20.22.1
lcsSetupInterfacesWlanInterpointRateSelectionEntry OBJECT-TYPE
    SYNTAX     LcsSetupInterfacesWlanInterpointRateSelectionEntry
    MAX-ACCESS not-accessible
    STATUS     current
    DESCRIPTION
            ""
    INDEX {
            lcsSetupInterfacesWlanInterpointRateSelectionEntryIfc
          }
    ::= { lcsSetupInterfacesWlanInterpointRateSelectionTable 1 }

LcsSetupInterfacesWlanInterpointRateSelectionEntry ::= SEQUENCE {
            lcsSetupInterfacesWlanInterpointRateSelectionEntry1M INTEGER,
            lcsSetupInterfacesWlanInterpointRateSelectionEntry2M INTEGER,
            lcsSetupInterfacesWlanInterpointRateSelectionEntryIfc INTEGER,
            lcsSetupInterfacesWlanInterpointRateSelectionEntry5M5 INTEGER,
            lcsSetupInterfacesWlanInterpointRateSelectionEntry11M INTEGER,
            lcsSetupInterfacesWlanInterpointRateSelectionEntry6M INTEGER,
            lcsSetupInterfacesWlanInterpointRateSelectionEntry9M INTEGER,
            lcsSetupInterfacesWlanInterpointRateSelectionEntry12M INTEGER,
            lcsSetupInterfacesWlanInterpointRateSelectionEntry18M INTEGER,
            lcsSetupInterfacesWlanInterpointRateSelectionEntry24M INTEGER,
            lcsSetupInterfacesWlanInterpointRateSelectionEntry36M INTEGER,
            lcsSetupInterfacesWlanInterpointRateSelectionEntry48M INTEGER,
            lcsSetupInterfacesWlanInterpointRateSelectionEntry54M INTEGER,
            lcsSetupInterfacesWlanInterpointRateSelectionEntryHT1S6M5 INTEGER,
            lcsSetupInterfacesWlanInterpointRateSelectionEntryHT1S13M INTEGER,
            lcsSetupInterfacesWlanInterpointRateSelectionEntryHT1S19M5 INTEGER,
            lcsSetupInterfacesWlanInterpointRateSelectionEntryHT1S26M INTEGER,
            lcsSetupInterfacesWlanInterpointRateSelectionEntryHT1S39M INTEGER,
            lcsSetupInterfacesWlanInterpointRateSelectionEntryHT1S52M INTEGER,
            lcsSetupInterfacesWlanInterpointRateSelectionEntryHT1S58M5 INTEGER,
            lcsSetupInterfacesWlanInterpointRateSelectionEntryHT1S65M INTEGER,
            lcsSetupInterfacesWlanInterpointRateSelectionEntryHT2S13M INTEGER,
            lcsSetupInterfacesWlanInterpointRateSelectionEntryHT2S26M INTEGER,
            lcsSetupInterfacesWlanInterpointRateSelectionEntryHT2S39M INTEGER,
            lcsSetupInterfacesWlanInterpointRateSelectionEntryHT2S52M INTEGER,
            lcsSetupInterfacesWlanInterpointRateSelectionEntryHT2S78M INTEGER,
            lcsSetupInterfacesWlanInterpointRateSelectionEntryHT2S104M INTEGER,
            lcsSetupInterfacesWlanInterpointRateSelectionEntryHT2S117M INTEGER,
            lcsSetupInterfacesWlanInterpointRateSelectionEntryHT2S130M INTEGER,
            lcsSetupInterfacesWlanInterpointRateSelectionEntryHT3S19M5 INTEGER,
            lcsSetupInterfacesWlanInterpointRateSelectionEntryHT3S39M INTEGER,
            lcsSetupInterfacesWlanInterpointRateSelectionEntryHT3S58M5 INTEGER,
            lcsSetupInterfacesWlanInterpointRateSelectionEntryHT3S78M INTEGER,
            lcsSetupInterfacesWlanInterpointRateSelectionEntryHT3S117M INTEGER,
            lcsSetupInterfacesWlanInterpointRateSelectionEntryHT3S156M INTEGER,
            lcsSetupInterfacesWlanInterpointRateSelectionEntryHT3S175M5 INTEGER,
            lcsSetupInterfacesWlanInterpointRateSelectionEntryHT3S195M INTEGER,
            lcsSetupInterfacesWlanInterpointRateSelectionEntryHT4S26M INTEGER,
            lcsSetupInterfacesWlanInterpointRateSelectionEntryHT4S52M INTEGER,
            lcsSetupInterfacesWlanInterpointRateSelectionEntryHT4S78M INTEGER,
            lcsSetupInterfacesWlanInterpointRateSelectionEntryHT4S104M INTEGER,
            lcsSetupInterfacesWlanInterpointRateSelectionEntryHT4S156M INTEGER,
            lcsSetupInterfacesWlanInterpointRateSelectionEntryHT4S208M INTEGER,
            lcsSetupInterfacesWlanInterpointRateSelectionEntryHT4S234M INTEGER,
            lcsSetupInterfacesWlanInterpointRateSelectionEntryHT4S260M INTEGER,
            lcsSetupInterfacesWlanInterpointRateSelectionEntryVht1MaxTxMcs INTEGER,
            lcsSetupInterfacesWlanInterpointRateSelectionEntryVht1MaxRxMcs INTEGER,
            lcsSetupInterfacesWlanInterpointRateSelectionEntryVht2MaxTxMcs INTEGER,
            lcsSetupInterfacesWlanInterpointRateSelectionEntryVht2MaxRxMcs INTEGER,
            lcsSetupInterfacesWlanInterpointRateSelectionEntryVht3MaxTxMcs INTEGER,
            lcsSetupInterfacesWlanInterpointRateSelectionEntryVht3MaxRxMcs INTEGER,
            lcsSetupInterfacesWlanInterpointRateSelectionEntryVht4MaxTxMcs INTEGER,
            lcsSetupInterfacesWlanInterpointRateSelectionEntryVht4MaxRxMcs INTEGER
    }

-- {COLUMN} 1.3.6.1.4.1.2356.11.2.23.20.22.1.1
lcsSetupInterfacesWlanInterpointRateSelectionEntry1M OBJECT-TYPE
    SYNTAX     INTEGER {
                  eNo (0),
                  eRx (1),
                  eRxTx (3),
                  eRxRequired (5),
                  eRxTxRequired (7)
            }
    MAX-ACCESS read-write
    STATUS     current
    DESCRIPTION
            "1Mbit/s"
    ::= { lcsSetupInterfacesWlanInterpointRateSelectionEntry 1 }

-- {COLUMN} 1.3.6.1.4.1.2356.11.2.23.20.22.1.2
lcsSetupInterfacesWlanInterpointRateSelectionEntry2M OBJECT-TYPE
    SYNTAX     INTEGER {
                  eNo (0),
                  eRx (1),
                  eRxTx (3),
                  eRxRequired (5),
                  eRxTxRequired (7)
            }
    MAX-ACCESS read-write
    STATUS     current
    DESCRIPTION
            "2Mbit/s"
    ::= { lcsSetupInterfacesWlanInterpointRateSelectionEntry 2 }

-- {COLUMN} 1.3.6.1.4.1.2356.11.2.23.20.22.1.3
lcsSetupInterfacesWlanInterpointRateSelectionEntryIfc OBJECT-TYPE
    SYNTAX     INTEGER {
                  eP2p11 (1),
                  eP2p12 (2),
                  eP2p13 (3),
                  eP2p14 (4),
                  eP2p15 (5),
                  eP2p16 (6),
                  eP2p21 (7),
                  eP2p22 (8),
                  eP2p23 (9),
                  eP2p24 (10),
                  eP2p25 (11),
                  eP2p26 (12),
                  eP2p17 (32),
                  eP2p18 (33),
                  eP2p19 (34),
                  eP2p110 (35),
                  eP2p111 (36),
                  eP2p112 (37),
                  eP2p113 (38),
                  eP2p114 (39),
                  eP2p115 (40),
                  eP2p116 (41),
                  eP2p27 (64),
                  eP2p28 (65),
                  eP2p29 (66),
                  eP2p210 (67),
                  eP2p211 (68),
                  eP2p212 (69),
                  eP2p213 (70),
                  eP2p214 (71),
                  eP2p215 (72),
                  eP2p216 (73)
            }
    MAX-ACCESS read-write
    STATUS     current
    DESCRIPTION
            "-- empty --"
    ::= { lcsSetupInterfacesWlanInterpointRateSelectionEntry 3 }

-- {COLUMN} 1.3.6.1.4.1.2356.11.2.23.20.22.1.4
lcsSetupInterfacesWlanInterpointRateSelectionEntry5M5 OBJECT-TYPE
    SYNTAX     INTEGER {
                  eNo (0),
                  eRx (1),
                  eRxTx (3),
                  eRxRequired (5),
                  eRxTxRequired (7)
            }
    MAX-ACCESS read-write
    STATUS     current
    DESCRIPTION
            "5.5Mbit/s"
    ::= { lcsSetupInterfacesWlanInterpointRateSelectionEntry 4 }

-- {COLUMN} 1.3.6.1.4.1.2356.11.2.23.20.22.1.6
lcsSetupInterfacesWlanInterpointRateSelectionEntry11M OBJECT-TYPE
    SYNTAX     INTEGER {
                  eNo (0),
                  eRx (1),
                  eRxTx (3),
                  eRxRequired (5),
                  eRxTxRequired (7)
            }
    MAX-ACCESS read-write
    STATUS     current
    DESCRIPTION
            "11Mbit/s"
    ::= { lcsSetupInterfacesWlanInterpointRateSelectionEntry 6 }

-- {COLUMN} 1.3.6.1.4.1.2356.11.2.23.20.22.1.8
lcsSetupInterfacesWlanInterpointRateSelectionEntry6M OBJECT-TYPE
    SYNTAX     INTEGER {
                  eNo (0),
                  eRx (1),
                  eRxTx (3),
                  eRxRequired (5),
                  eRxTxRequired (7)
            }
    MAX-ACCESS read-write
    STATUS     current
    DESCRIPTION
            "6Mbit/s"
    ::= { lcsSetupInterfacesWlanInterpointRateSelectionEntry 8 }

-- {COLUMN} 1.3.6.1.4.1.2356.11.2.23.20.22.1.9
lcsSetupInterfacesWlanInterpointRateSelectionEntry9M OBJECT-TYPE
    SYNTAX     INTEGER {
                  eNo (0),
                  eRx (1),
                  eRxTx (3),
                  eRxRequired (5),
                  eRxTxRequired (7)
            }
    MAX-ACCESS read-write
    STATUS     current
    DESCRIPTION
            "9Mbit/s"
    ::= { lcsSetupInterfacesWlanInterpointRateSelectionEntry 9 }

-- {COLUMN} 1.3.6.1.4.1.2356.11.2.23.20.22.1.10
lcsSetupInterfacesWlanInterpointRateSelectionEntry12M OBJECT-TYPE
    SYNTAX     INTEGER {
                  eNo (0),
                  eRx (1),
                  eRxTx (3),
                  eRxRequired (5),
                  eRxTxRequired (7)
            }
    MAX-ACCESS read-write
    STATUS     current
    DESCRIPTION
            "12Mbit/s"
    ::= { lcsSetupInterfacesWlanInterpointRateSelectionEntry 10 }

-- {COLUMN} 1.3.6.1.4.1.2356.11.2.23.20.22.1.11
lcsSetupInterfacesWlanInterpointRateSelectionEntry18M OBJECT-TYPE
    SYNTAX     INTEGER {
                  eNo (0),
                  eRx (1),
                  eRxTx (3),
                  eRxRequired (5),
                  eRxTxRequired (7)
            }
    MAX-ACCESS read-write
    STATUS     current
    DESCRIPTION
            "18Mbit/s"
    ::= { lcsSetupInterfacesWlanInterpointRateSelectionEntry 11 }

-- {COLUMN} 1.3.6.1.4.1.2356.11.2.23.20.22.1.12
lcsSetupInterfacesWlanInterpointRateSelectionEntry24M OBJECT-TYPE
    SYNTAX     INTEGER {
                  eNo (0),
                  eRx (1),
                  eRxTx (3),
                  eRxRequired (5),
                  eRxTxRequired (7)
            }
    MAX-ACCESS read-write
    STATUS     current
    DESCRIPTION
            "24Mbit/s"
    ::= { lcsSetupInterfacesWlanInterpointRateSelectionEntry 12 }

-- {COLUMN} 1.3.6.1.4.1.2356.11.2.23.20.22.1.13
lcsSetupInterfacesWlanInterpointRateSelectionEntry36M OBJECT-TYPE
    SYNTAX     INTEGER {
                  eNo (0),
                  eRx (1),
                  eRxTx (3),
                  eRxRequired (5),
                  eRxTxRequired (7)
            }
    MAX-ACCESS read-write
    STATUS     current
    DESCRIPTION
            "36Mbit/s"
    ::= { lcsSetupInterfacesWlanInterpointRateSelectionEntry 13 }

-- {COLUMN} 1.3.6.1.4.1.2356.11.2.23.20.22.1.14
lcsSetupInterfacesWlanInterpointRateSelectionEntry48M OBJECT-TYPE
    SYNTAX     INTEGER {
                  eNo (0),
                  eRx (1),
                  eRxTx (3),
                  eRxRequired (5),
                  eRxTxRequired (7)
            }
    MAX-ACCESS read-write
    STATUS     current
    DESCRIPTION
            "48Mbit/s"
    ::= { lcsSetupInterfacesWlanInterpointRateSelectionEntry 14 }

-- {COLUMN} 1.3.6.1.4.1.2356.11.2.23.20.22.1.15
lcsSetupInterfacesWlanInterpointRateSelectionEntry54M OBJECT-TYPE
    SYNTAX     INTEGER {
                  eNo (0),
                  eRx (1),
                  eRxTx (3),
                  eRxRequired (5),
                  eRxTxRequired (7)
            }
    MAX-ACCESS read-write
    STATUS     current
    DESCRIPTION
            "54Mbit/s"
    ::= { lcsSetupInterfacesWlanInterpointRateSelectionEntry 15 }

-- {COLUMN} 1.3.6.1.4.1.2356.11.2.23.20.22.1.28
lcsSetupInterfacesWlanInterpointRateSelectionEntryHT1S6M5 OBJECT-TYPE
    SYNTAX     INTEGER {
                  eNo (0),
                  eRx (1),
                  eRxTx (3)
            }
    MAX-ACCESS read-write
    STATUS     current
    DESCRIPTION
            "High throughput 1 stream 6.5Mbit/s"
    ::= { lcsSetupInterfacesWlanInterpointRateSelectionEntry 28 }

-- {COLUMN} 1.3.6.1.4.1.2356.11.2.23.20.22.1.29
lcsSetupInterfacesWlanInterpointRateSelectionEntryHT1S13M OBJECT-TYPE
    SYNTAX     INTEGER {
                  eNo (0),
                  eRx (1),
                  eRxTx (3)
            }
    MAX-ACCESS read-write
    STATUS     current
    DESCRIPTION
            "High throughput 1 stream 13Mbit/s"
    ::= { lcsSetupInterfacesWlanInterpointRateSelectionEntry 29 }

-- {COLUMN} 1.3.6.1.4.1.2356.11.2.23.20.22.1.30
lcsSetupInterfacesWlanInterpointRateSelectionEntryHT1S19M5 OBJECT-TYPE
    SYNTAX     INTEGER {
                  eNo (0),
                  eRx (1),
                  eRxTx (3)
            }
    MAX-ACCESS read-write
    STATUS     current
    DESCRIPTION
            "High throughput 1 stream 19.5Mbit/s"
    ::= { lcsSetupInterfacesWlanInterpointRateSelectionEntry 30 }

-- {COLUMN} 1.3.6.1.4.1.2356.11.2.23.20.22.1.31
lcsSetupInterfacesWlanInterpointRateSelectionEntryHT1S26M OBJECT-TYPE
    SYNTAX     INTEGER {
                  eNo (0),
                  eRx (1),
                  eRxTx (3)
            }
    MAX-ACCESS read-write
    STATUS     current
    DESCRIPTION
            "High throughput 1 stream 26Mbit/s"
    ::= { lcsSetupInterfacesWlanInterpointRateSelectionEntry 31 }

-- {COLUMN} 1.3.6.1.4.1.2356.11.2.23.20.22.1.32
lcsSetupInterfacesWlanInterpointRateSelectionEntryHT1S39M OBJECT-TYPE
    SYNTAX     INTEGER {
                  eNo (0),
                  eRx (1),
                  eRxTx (3)
            }
    MAX-ACCESS read-write
    STATUS     current
    DESCRIPTION
            "High throughput 1 stream 39Mbit/s"
    ::= { lcsSetupInterfacesWlanInterpointRateSelectionEntry 32 }

-- {COLUMN} 1.3.6.1.4.1.2356.11.2.23.20.22.1.33
lcsSetupInterfacesWlanInterpointRateSelectionEntryHT1S52M OBJECT-TYPE
    SYNTAX     INTEGER {
                  eNo (0),
                  eRx (1),
                  eRxTx (3)
            }
    MAX-ACCESS read-write
    STATUS     current
    DESCRIPTION
            "High throughput 1 stream 52Mbit/s"
    ::= { lcsSetupInterfacesWlanInterpointRateSelectionEntry 33 }

-- {COLUMN} 1.3.6.1.4.1.2356.11.2.23.20.22.1.34
lcsSetupInterfacesWlanInterpointRateSelectionEntryHT1S58M5 OBJECT-TYPE
    SYNTAX     INTEGER {
                  eNo (0),
                  eRx (1),
                  eRxTx (3)
            }
    MAX-ACCESS read-write
    STATUS     current
    DESCRIPTION
            "High throughput 1 stream 58.5Mbit/s"
    ::= { lcsSetupInterfacesWlanInterpointRateSelectionEntry 34 }

-- {COLUMN} 1.3.6.1.4.1.2356.11.2.23.20.22.1.35
lcsSetupInterfacesWlanInterpointRateSelectionEntryHT1S65M OBJECT-TYPE
    SYNTAX     INTEGER {
                  eNo (0),
                  eRx (1),
                  eRxTx (3)
            }
    MAX-ACCESS read-write
    STATUS     current
    DESCRIPTION
            "High throughput 1 stream 65Mbit/s"
    ::= { lcsSetupInterfacesWlanInterpointRateSelectionEntry 35 }

-- {COLUMN} 1.3.6.1.4.1.2356.11.2.23.20.22.1.36
lcsSetupInterfacesWlanInterpointRateSelectionEntryHT2S13M OBJECT-TYPE
    SYNTAX     INTEGER {
                  eNo (0),
                  eRx (1),
                  eRxTx (3)
            }
    MAX-ACCESS read-write
    STATUS     current
    DESCRIPTION
            "High throughput 2 streams 13Mbit/s"
    ::= { lcsSetupInterfacesWlanInterpointRateSelectionEntry 36 }

-- {COLUMN} 1.3.6.1.4.1.2356.11.2.23.20.22.1.37
lcsSetupInterfacesWlanInterpointRateSelectionEntryHT2S26M OBJECT-TYPE
    SYNTAX     INTEGER {
                  eNo (0),
                  eRx (1),
                  eRxTx (3)
            }
    MAX-ACCESS read-write
    STATUS     current
    DESCRIPTION
            "High throughput 2 streams 26Mbit/s"
    ::= { lcsSetupInterfacesWlanInterpointRateSelectionEntry 37 }

-- {COLUMN} 1.3.6.1.4.1.2356.11.2.23.20.22.1.38
lcsSetupInterfacesWlanInterpointRateSelectionEntryHT2S39M OBJECT-TYPE
    SYNTAX     INTEGER {
                  eNo (0),
                  eRx (1),
                  eRxTx (3)
            }
    MAX-ACCESS read-write
    STATUS     current
    DESCRIPTION
            "High throughput 2 streams 39Mbit/s"
    ::= { lcsSetupInterfacesWlanInterpointRateSelectionEntry 38 }

-- {COLUMN} 1.3.6.1.4.1.2356.11.2.23.20.22.1.39
lcsSetupInterfacesWlanInterpointRateSelectionEntryHT2S52M OBJECT-TYPE
    SYNTAX     INTEGER {
                  eNo (0),
                  eRx (1),
                  eRxTx (3)
            }
    MAX-ACCESS read-write
    STATUS     current
    DESCRIPTION
            "High throughput 2 streams 52Mbit/s"
    ::= { lcsSetupInterfacesWlanInterpointRateSelectionEntry 39 }

-- {COLUMN} 1.3.6.1.4.1.2356.11.2.23.20.22.1.40
lcsSetupInterfacesWlanInterpointRateSelectionEntryHT2S78M OBJECT-TYPE
    SYNTAX     INTEGER {
                  eNo (0),
                  eRx (1),
                  eRxTx (3)
            }
    MAX-ACCESS read-write
    STATUS     current
    DESCRIPTION
            "High throughput 2 streams 78Mbit/s"
    ::= { lcsSetupInterfacesWlanInterpointRateSelectionEntry 40 }

-- {COLUMN} 1.3.6.1.4.1.2356.11.2.23.20.22.1.41
lcsSetupInterfacesWlanInterpointRateSelectionEntryHT2S104M OBJECT-TYPE
    SYNTAX     INTEGER {
                  eNo (0),
                  eRx (1),
                  eRxTx (3)
            }
    MAX-ACCESS read-write
    STATUS     current
    DESCRIPTION
            "High throughput 2 streams 104Mbit/s"
    ::= { lcsSetupInterfacesWlanInterpointRateSelectionEntry 41 }

-- {COLUMN} 1.3.6.1.4.1.2356.11.2.23.20.22.1.42
lcsSetupInterfacesWlanInterpointRateSelectionEntryHT2S117M OBJECT-TYPE
    SYNTAX     INTEGER {
                  eNo (0),
                  eRx (1),
                  eRxTx (3)
            }
    MAX-ACCESS read-write
    STATUS     current
    DESCRIPTION
            "High throughput 2 streams 117Mbit/s"
    ::= { lcsSetupInterfacesWlanInterpointRateSelectionEntry 42 }

-- {COLUMN} 1.3.6.1.4.1.2356.11.2.23.20.22.1.43
lcsSetupInterfacesWlanInterpointRateSelectionEntryHT2S130M OBJECT-TYPE
    SYNTAX     INTEGER {
                  eNo (0),
                  eRx (1),
                  eRxTx (3)
            }
    MAX-ACCESS read-write
    STATUS     current
    DESCRIPTION
            "High throughput 2 streams 130Mbit/s"
    ::= { lcsSetupInterfacesWlanInterpointRateSelectionEntry 43 }

-- {COLUMN} 1.3.6.1.4.1.2356.11.2.23.20.22.1.44
lcsSetupInterfacesWlanInterpointRateSelectionEntryHT3S19M5 OBJECT-TYPE
    SYNTAX     INTEGER {
                  eNo (0),
                  eRx (1),
                  eRxTx (3)
            }
    MAX-ACCESS read-write
    STATUS     current
    DESCRIPTION
            "High throughput 3 streams 19.5Mbit/s"
    ::= { lcsSetupInterfacesWlanInterpointRateSelectionEntry 44 }

-- {COLUMN} 1.3.6.1.4.1.2356.11.2.23.20.22.1.45
lcsSetupInterfacesWlanInterpointRateSelectionEntryHT3S39M OBJECT-TYPE
    SYNTAX     INTEGER {
                  eNo (0),
                  eRx (1),
                  eRxTx (3)
            }
    MAX-ACCESS read-write
    STATUS     current
    DESCRIPTION
            "High throughput 3 streams 39Mbit/s"
    ::= { lcsSetupInterfacesWlanInterpointRateSelectionEntry 45 }

-- {COLUMN} 1.3.6.1.4.1.2356.11.2.23.20.22.1.46
lcsSetupInterfacesWlanInterpointRateSelectionEntryHT3S58M5 OBJECT-TYPE
    SYNTAX     INTEGER {
                  eNo (0),
                  eRx (1),
                  eRxTx (3)
            }
    MAX-ACCESS read-write
    STATUS     current
    DESCRIPTION
            "High throughput 3 streams 58.5Mbit/s"
    ::= { lcsSetupInterfacesWlanInterpointRateSelectionEntry 46 }

-- {COLUMN} 1.3.6.1.4.1.2356.11.2.23.20.22.1.47
lcsSetupInterfacesWlanInterpointRateSelectionEntryHT3S78M OBJECT-TYPE
    SYNTAX     INTEGER {
                  eNo (0),
                  eRx (1),
                  eRxTx (3)
            }
    MAX-ACCESS read-write
    STATUS     current
    DESCRIPTION
            "High throughput 3 streams 78Mbit/s"
    ::= { lcsSetupInterfacesWlanInterpointRateSelectionEntry 47 }

-- {COLUMN} 1.3.6.1.4.1.2356.11.2.23.20.22.1.48
lcsSetupInterfacesWlanInterpointRateSelectionEntryHT3S117M OBJECT-TYPE
    SYNTAX     INTEGER {
                  eNo (0),
                  eRx (1),
                  eRxTx (3)
            }
    MAX-ACCESS read-write
    STATUS     current
    DESCRIPTION
            "High throughput 3 streams 117Mbit/s"
    ::= { lcsSetupInterfacesWlanInterpointRateSelectionEntry 48 }

-- {COLUMN} 1.3.6.1.4.1.2356.11.2.23.20.22.1.49
lcsSetupInterfacesWlanInterpointRateSelectionEntryHT3S156M OBJECT-TYPE
    SYNTAX     INTEGER {
                  eNo (0),
                  eRx (1),
                  eRxTx (3)
            }
    MAX-ACCESS read-write
    STATUS     current
    DESCRIPTION
            "High throughput 3 streams 156Mbit/s"
    ::= { lcsSetupInterfacesWlanInterpointRateSelectionEntry 49 }

-- {COLUMN} 1.3.6.1.4.1.2356.11.2.23.20.22.1.50
lcsSetupInterfacesWlanInterpointRateSelectionEntryHT3S175M5 OBJECT-TYPE
    SYNTAX     INTEGER {
                  eNo (0),
                  eRx (1),
                  eRxTx (3)
            }
    MAX-ACCESS read-write
    STATUS     current
    DESCRIPTION
            "High throughput 3 streams 175.5Mbit/s"
    ::= { lcsSetupInterfacesWlanInterpointRateSelectionEntry 50 }

-- {COLUMN} 1.3.6.1.4.1.2356.11.2.23.20.22.1.51
lcsSetupInterfacesWlanInterpointRateSelectionEntryHT3S195M OBJECT-TYPE
    SYNTAX     INTEGER {
                  eNo (0),
                  eRx (1),
                  eRxTx (3)
            }
    MAX-ACCESS read-write
    STATUS     current
    DESCRIPTION
            "High throughput 3 streams 195Mbit/s"
    ::= { lcsSetupInterfacesWlanInterpointRateSelectionEntry 51 }

-- {COLUMN} 1.3.6.1.4.1.2356.11.2.23.20.22.1.52
lcsSetupInterfacesWlanInterpointRateSelectionEntryHT4S26M OBJECT-TYPE
    SYNTAX     INTEGER {
                  eNo (0),
                  eRx (1),
                  eRxTx (3)
            }
    MAX-ACCESS read-write
    STATUS     current
    DESCRIPTION
            "High throughput 4 streams 26Mbit/s"
    ::= { lcsSetupInterfacesWlanInterpointRateSelectionEntry 52 }

-- {COLUMN} 1.3.6.1.4.1.2356.11.2.23.20.22.1.53
lcsSetupInterfacesWlanInterpointRateSelectionEntryHT4S52M OBJECT-TYPE
    SYNTAX     INTEGER {
                  eNo (0),
                  eRx (1),
                  eRxTx (3)
            }
    MAX-ACCESS read-write
    STATUS     current
    DESCRIPTION
            "High throughput 4 streams 52Mbit/s"
    ::= { lcsSetupInterfacesWlanInterpointRateSelectionEntry 53 }

-- {COLUMN} 1.3.6.1.4.1.2356.11.2.23.20.22.1.54
lcsSetupInterfacesWlanInterpointRateSelectionEntryHT4S78M OBJECT-TYPE
    SYNTAX     INTEGER {
                  eNo (0),
                  eRx (1),
                  eRxTx (3)
            }
    MAX-ACCESS read-write
    STATUS     current
    DESCRIPTION
            "High throughput 4 streams 78Mbit/s"
    ::= { lcsSetupInterfacesWlanInterpointRateSelectionEntry 54 }

-- {COLUMN} 1.3.6.1.4.1.2356.11.2.23.20.22.1.55
lcsSetupInterfacesWlanInterpointRateSelectionEntryHT4S104M OBJECT-TYPE
    SYNTAX     INTEGER {
                  eNo (0),
                  eRx (1),
                  eRxTx (3)
            }
    MAX-ACCESS read-write
    STATUS     current
    DESCRIPTION
            "High throughput 4 streams 104Mbit/s"
    ::= { lcsSetupInterfacesWlanInterpointRateSelectionEntry 55 }

-- {COLUMN} 1.3.6.1.4.1.2356.11.2.23.20.22.1.56
lcsSetupInterfacesWlanInterpointRateSelectionEntryHT4S156M OBJECT-TYPE
    SYNTAX     INTEGER {
                  eNo (0),
                  eRx (1),
                  eRxTx (3)
            }
    MAX-ACCESS read-write
    STATUS     current
    DESCRIPTION
            "High throughput 4 streams 156Mbit/s"
    ::= { lcsSetupInterfacesWlanInterpointRateSelectionEntry 56 }

-- {COLUMN} 1.3.6.1.4.1.2356.11.2.23.20.22.1.57
lcsSetupInterfacesWlanInterpointRateSelectionEntryHT4S208M OBJECT-TYPE
    SYNTAX     INTEGER {
                  eNo (0),
                  eRx (1),
                  eRxTx (3)
            }
    MAX-ACCESS read-write
    STATUS     current
    DESCRIPTION
            "High throughput 4 streams 208Mbit/s"
    ::= { lcsSetupInterfacesWlanInterpointRateSelectionEntry 57 }

-- {COLUMN} 1.3.6.1.4.1.2356.11.2.23.20.22.1.58
lcsSetupInterfacesWlanInterpointRateSelectionEntryHT4S234M OBJECT-TYPE
    SYNTAX     INTEGER {
                  eNo (0),
                  eRx (1),
                  eRxTx (3)
            }
    MAX-ACCESS read-write
    STATUS     current
    DESCRIPTION
            "High throughput 4 streams 234Mbit/s"
    ::= { lcsSetupInterfacesWlanInterpointRateSelectionEntry 58 }

-- {COLUMN} 1.3.6.1.4.1.2356.11.2.23.20.22.1.59
lcsSetupInterfacesWlanInterpointRateSelectionEntryHT4S260M OBJECT-TYPE
    SYNTAX     INTEGER {
                  eNo (0),
                  eRx (1),
                  eRxTx (3)
            }
    MAX-ACCESS read-write
    STATUS     current
    DESCRIPTION
            "High throughput 4 streams 260Mbit/s"
    ::= { lcsSetupInterfacesWlanInterpointRateSelectionEntry 59 }

-- {COLUMN} 1.3.6.1.4.1.2356.11.2.23.20.22.1.105
lcsSetupInterfacesWlanInterpointRateSelectionEntryVht1MaxTxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanInterpointRateSelectionEntry 105 }

-- {COLUMN} 1.3.6.1.4.1.2356.11.2.23.20.22.1.106
lcsSetupInterfacesWlanInterpointRateSelectionEntryVht1MaxRxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanInterpointRateSelectionEntry 106 }

-- {COLUMN} 1.3.6.1.4.1.2356.11.2.23.20.22.1.115
lcsSetupInterfacesWlanInterpointRateSelectionEntryVht2MaxTxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanInterpointRateSelectionEntry 115 }

-- {COLUMN} 1.3.6.1.4.1.2356.11.2.23.20.22.1.116
lcsSetupInterfacesWlanInterpointRateSelectionEntryVht2MaxRxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanInterpointRateSelectionEntry 116 }

-- {COLUMN} 1.3.6.1.4.1.2356.11.2.23.20.22.1.125
lcsSetupInterfacesWlanInterpointRateSelectionEntryVht3MaxTxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanInterpointRateSelectionEntry 125 }

-- {COLUMN} 1.3.6.1.4.1.2356.11.2.23.20.22.1.126
lcsSetupInterfacesWlanInterpointRateSelectionEntryVht3MaxRxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanInterpointRateSelectionEntry 126 }

-- {COLUMN} 1.3.6.1.4.1.2356.11.2.23.20.22.1.135
lcsSetupInterfacesWlanInterpointRateSelectionEntryVht4MaxTxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanInterpointRateSelectionEntry 135 }

-- {COLUMN} 1.3.6.1.4.1.2356.11.2.23.20.22.1.136
lcsSetupInterfacesWlanInterpointRateSelectionEntryVht4MaxRxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanInterpointRateSelectionEntry 136 }

-- {TABLE} 1.3.6.1.4.1.2356.11.2.23.20.23
lcsSetupInterfacesWlanBadAmbDetTable OBJECT-TYPE
    SYNTAX     SEQUENCE OF LcsSetupInterfacesWlanBadAmbDetEntry
    MAX-ACCESS not-accessible
    STATUS     current
    DESCRIPTION
            ""
    ::= { lcsSetupInterfacesWlan 23 }

-- {ROW} 1.3.6.1.4.1.2356.11.2.23.20.23.1
lcsSetupInterfacesWlanBadAmbDetEntry OBJECT-TYPE
    SYNTAX     LcsSetupInterfacesWlanBadAmbDetEntry
    MAX-ACCESS not-accessible
    STATUS     current
    DESCRIPTION
            ""
    INDEX {
            lcsSetupInterfacesWlanBadAmbDetEntryIfc
          }
    ::= { lcsSetupInterfacesWlanBadAmbDetTable 1 }

LcsSetupInterfacesWlanBadAmbDetEntry ::= SEQUENCE {
            lcsSetupInterfacesWlanBadAmbDetEntryIfc INTEGER,
            lcsSetupInterfacesWlanBadAmbDetEntryOperating INTEGER,
            lcsSetupInterfacesWlanBadAmbDetEntryMinClientPhySignal Integer32,
            lcsSetupInterfacesWlanBadAmbDetEntryMinClientTxPackets Integer32,
            lcsSetupInterfacesWlanBadAmbDetEntryTxClientRetryRatioLimit Integer32,
            lcsSetupInterfacesWlanBadAmbDetEntryNoiseLimit Integer32,
            lcsSetupInterfacesWlanBadAmbDetEntryMarkedChannelTimeout Integer32,
            lcsSetupInterfacesWlanBadAmbDetEntryTriggerTimespan Integer32,
            lcsSetupInterfacesWlanBadAmbDetEntryInterferenceLimit Integer32
    }

-- {COLUMN} 1.3.6.1.4.1.2356.11.2.23.20.23.1.1
lcsSetupInterfacesWlanBadAmbDetEntryIfc OBJECT-TYPE
    SYNTAX     INTEGER {
                  eWlan1 (1),
                  eWlan2 (2)
            }
    MAX-ACCESS read-write
    STATUS     current
    DESCRIPTION
            "-- empty --"
    ::= { lcsSetupInterfacesWlanBadAmbDetEntry 1 }

-- {COLUMN} 1.3.6.1.4.1.2356.11.2.23.20.23.1.2
lcsSetupInterfacesWlanBadAmbDetEntryOperating OBJECT-TYPE
    SYNTAX     INTEGER {
                  eNo (0),
                  eYes (1)
            }
    MAX-ACCESS read-write
    STATUS     current
    DESCRIPTION
            "-- empty --"
    ::= { lcsSetupInterfacesWlanBadAmbDetEntry 2 }

-- {COLUMN} 1.3.6.1.4.1.2356.11.2.23.20.23.1.3
lcsSetupInterfacesWlanBadAmbDetEntryMinClientPhySignal OBJECT-TYPE
    SYNTAX     Integer32 (0..255)
    MAX-ACCESS read-write
    STATUS     current
    DESCRIPTION
            "-- empty --"
    ::= { lcsSetupInterfacesWlanBadAmbDetEntry 3 }

-- {COLUMN} 1.3.6.1.4.1.2356.11.2.23.20.23.1.4
lcsSetupInterfacesWlanBadAmbDetEntryMinClientTxPackets OBJECT-TYPE
    SYNTAX     Integer32 (0..65535)
    MAX-ACCESS read-write
    STATUS     current
    DESCRIPTION
            "-- empty --"
    ::= { lcsSetupInterfacesWlanBadAmbDetEntry 4 }

-- {COLUMN} 1.3.6.1.4.1.2356.11.2.23.20.23.1.5
lcsSetupInterfacesWlanBadAmbDetEntryTxClientRetryRatioLimit OBJECT-TYPE
    SYNTAX     Integer32 (0..255)
    MAX-ACCESS read-write
    STATUS     current
    DESCRIPTION
            "-- empty --"
    ::= { lcsSetupInterfacesWlanBadAmbDetEntry 5 }

-- {COLUMN} 1.3.6.1.4.1.2356.11.2.23.20.23.1.6
lcsSetupInterfacesWlanBadAmbDetEntryNoiseLimit OBJECT-TYPE
    SYNTAX     Integer32 (-32768..32767)
    MAX-ACCESS read-write
    STATUS     current
    DESCRIPTION
            "-- empty --"
    ::= { lcsSetupInterfacesWlanBadAmbDetEntry 6 }

-- {COLUMN} 1.3.6.1.4.1.2356.11.2.23.20.23.1.7
lcsSetupInterfacesWlanBadAmbDetEntryMarkedChannelTimeout OBJECT-TYPE
    SYNTAX     Integer32 (0..65535)
    MAX-ACCESS read-write
    STATUS     current
    DESCRIPTION
            "-- empty --"
    ::= { lcsSetupInterfacesWlanBadAmbDetEntry 7 }

-- {COLUMN} 1.3.6.1.4.1.2356.11.2.23.20.23.1.8
lcsSetupInterfacesWlanBadAmbDetEntryTriggerTimespan OBJECT-TYPE
    SYNTAX     Integer32 (0..65535)
    MAX-ACCESS read-write
    STATUS     current
    DESCRIPTION
            "-- empty --"
    ::= { lcsSetupInterfacesWlanBadAmbDetEntry 8 }

-- {COLUMN} 1.3.6.1.4.1.2356.11.2.23.20.23.1.9
lcsSetupInterfacesWlanBadAmbDetEntryInterferenceLimit OBJECT-TYPE
    SYNTAX     Integer32 (0..255)
    MAX-ACCESS read-write
    STATUS     current
    DESCRIPTION
            "-- empty --"
    ::= { lcsSetupInterfacesWlanBadAmbDetEntry 9 }

-- {TABLE} 1.3.6.1.4.1.2356.11.2.23.20.24
lcsSetupInterfacesWlanRedundancySettingsTable OBJECT-TYPE
    SYNTAX     SEQUENCE OF LcsSetupInterfacesWlanRedundancySettingsEntry
    MAX-ACCESS not-accessible
    STATUS     current
    DESCRIPTION
            "-- empty --"
    ::= { lcsSetupInterfacesWlan 24 }

-- {ROW} 1.3.6.1.4.1.2356.11.2.23.20.24.1
lcsSetupInterfacesWlanRedundancySettingsEntry OBJECT-TYPE
    SYNTAX     LcsSetupInterfacesWlanRedundancySettingsEntry
    MAX-ACCESS not-accessible
    STATUS     current
    DESCRIPTION
            ""
    INDEX {
            lcsSetupInterfacesWlanRedundancySettingsEntryIfc
          }
    ::= { lcsSetupInterfacesWlanRedundancySettingsTable 1 }

LcsSetupInterfacesWlanRedundancySettingsEntry ::= SEQUENCE {
            lcsSetupInterfacesWlanRedundancySettingsEntryIfc INTEGER,
            lcsSetupInterfacesWlanRedundancySettingsEntryOtherApsExpected Integer32,
            lcsSetupInterfacesWlanRedundancySettingsEntryBkupTxPwrRed Integer32,
            lcsSetupInterfacesWlanRedundancySettingsEntryBackupEirp Integer32
    }

-- {COLUMN} 1.3.6.1.4.1.2356.11.2.23.20.24.1.1
lcsSetupInterfacesWlanRedundancySettingsEntryIfc OBJECT-TYPE
    SYNTAX     INTEGER {
                  eWlan1 (1),
                  eWlan2 (2)
            }
    MAX-ACCESS read-write
    STATUS     current
    DESCRIPTION
            "-- empty --"
    ::= { lcsSetupInterfacesWlanRedundancySettingsEntry 1 }

-- {COLUMN} 1.3.6.1.4.1.2356.11.2.23.20.24.1.2
lcsSetupInterfacesWlanRedundancySettingsEntryOtherApsExpected OBJECT-TYPE
    SYNTAX     Integer32 (0..65535)
    MAX-ACCESS read-write
    STATUS     current
    DESCRIPTION
            "-- empty --"
    ::= { lcsSetupInterfacesWlanRedundancySettingsEntry 2 }

-- {COLUMN} 1.3.6.1.4.1.2356.11.2.23.20.24.1.3
lcsSetupInterfacesWlanRedundancySettingsEntryBkupTxPwrRed OBJECT-TYPE
    SYNTAX     Integer32 (0..255)
    MAX-ACCESS read-write
    STATUS     current
    DESCRIPTION
            "transmit power reduction in backup case"
    ::= { lcsSetupInterfacesWlanRedundancySettingsEntry 3 }

-- {COLUMN} 1.3.6.1.4.1.2356.11.2.23.20.24.1.4
lcsSetupInterfacesWlanRedundancySettingsEntryBackupEirp OBJECT-TYPE
    SYNTAX     Integer32 (-128..127)
    MAX-ACCESS read-write
    STATUS     current
    DESCRIPTION
            "-- empty --"
    ::= { lcsSetupInterfacesWlanRedundancySettingsEntry 4 }

-- {TABLE} 1.3.6.1.4.1.2356.11.2.23.20.25
lcsSetupInterfacesWlanRateSelectionTable OBJECT-TYPE
    SYNTAX     SEQUENCE OF LcsSetupInterfacesWlanRateSelectionEntry
    MAX-ACCESS not-accessible
    STATUS     current
    DESCRIPTION
            "-- empty --"
    ::= { lcsSetupInterfacesWlan 25 }

-- {ROW} 1.3.6.1.4.1.2356.11.2.23.20.25.1
lcsSetupInterfacesWlanRateSelectionEntry OBJECT-TYPE
    SYNTAX     LcsSetupInterfacesWlanRateSelectionEntry
    MAX-ACCESS not-accessible
    STATUS     current
    DESCRIPTION
            ""
    INDEX {
            lcsSetupInterfacesWlanRateSelectionEntryIfc
          }
    ::= { lcsSetupInterfacesWlanRateSelectionTable 1 }

LcsSetupInterfacesWlanRateSelectionEntry ::= SEQUENCE {
            lcsSetupInterfacesWlanRateSelectionEntry1M INTEGER,
            lcsSetupInterfacesWlanRateSelectionEntry2M INTEGER,
            lcsSetupInterfacesWlanRateSelectionEntryIfc INTEGER,
            lcsSetupInterfacesWlanRateSelectionEntry5M5 INTEGER,
            lcsSetupInterfacesWlanRateSelectionEntry11M INTEGER,
            lcsSetupInterfacesWlanRateSelectionEntry6M INTEGER,
            lcsSetupInterfacesWlanRateSelectionEntry9M INTEGER,
            lcsSetupInterfacesWlanRateSelectionEntry12M INTEGER,
            lcsSetupInterfacesWlanRateSelectionEntry18M INTEGER,
            lcsSetupInterfacesWlanRateSelectionEntry24M INTEGER,
            lcsSetupInterfacesWlanRateSelectionEntry36M INTEGER,
            lcsSetupInterfacesWlanRateSelectionEntry48M INTEGER,
            lcsSetupInterfacesWlanRateSelectionEntry54M INTEGER,
            lcsSetupInterfacesWlanRateSelectionEntryHT1S6M5 INTEGER,
            lcsSetupInterfacesWlanRateSelectionEntryHT1S13M INTEGER,
            lcsSetupInterfacesWlanRateSelectionEntryHT1S19M5 INTEGER,
            lcsSetupInterfacesWlanRateSelectionEntryHT1S26M INTEGER,
            lcsSetupInterfacesWlanRateSelectionEntryHT1S39M INTEGER,
            lcsSetupInterfacesWlanRateSelectionEntryHT1S52M INTEGER,
            lcsSetupInterfacesWlanRateSelectionEntryHT1S58M5 INTEGER,
            lcsSetupInterfacesWlanRateSelectionEntryHT1S65M INTEGER,
            lcsSetupInterfacesWlanRateSelectionEntryHT2S13M INTEGER,
            lcsSetupInterfacesWlanRateSelectionEntryHT2S26M INTEGER,
            lcsSetupInterfacesWlanRateSelectionEntryHT2S39M INTEGER,
            lcsSetupInterfacesWlanRateSelectionEntryHT2S52M INTEGER,
            lcsSetupInterfacesWlanRateSelectionEntryHT2S78M INTEGER,
            lcsSetupInterfacesWlanRateSelectionEntryHT2S104M INTEGER,
            lcsSetupInterfacesWlanRateSelectionEntryHT2S117M INTEGER,
            lcsSetupInterfacesWlanRateSelectionEntryHT2S130M INTEGER,
            lcsSetupInterfacesWlanRateSelectionEntryHT3S19M5 INTEGER,
            lcsSetupInterfacesWlanRateSelectionEntryHT3S39M INTEGER,
            lcsSetupInterfacesWlanRateSelectionEntryHT3S58M5 INTEGER,
            lcsSetupInterfacesWlanRateSelectionEntryHT3S78M INTEGER,
            lcsSetupInterfacesWlanRateSelectionEntryHT3S117M INTEGER,
            lcsSetupInterfacesWlanRateSelectionEntryHT3S156M INTEGER,
            lcsSetupInterfacesWlanRateSelectionEntryHT3S175M5 INTEGER,
            lcsSetupInterfacesWlanRateSelectionEntryHT3S195M INTEGER,
            lcsSetupInterfacesWlanRateSelectionEntryHT4S26M INTEGER,
            lcsSetupInterfacesWlanRateSelectionEntryHT4S52M INTEGER,
            lcsSetupInterfacesWlanRateSelectionEntryHT4S78M INTEGER,
            lcsSetupInterfacesWlanRateSelectionEntryHT4S104M INTEGER,
            lcsSetupInterfacesWlanRateSelectionEntryHT4S156M INTEGER,
            lcsSetupInterfacesWlanRateSelectionEntryHT4S208M INTEGER,
            lcsSetupInterfacesWlanRateSelectionEntryHT4S234M INTEGER,
            lcsSetupInterfacesWlanRateSelectionEntryHT4S260M INTEGER,
            lcsSetupInterfacesWlanRateSelectionEntryVht1MaxTxMcs INTEGER,
            lcsSetupInterfacesWlanRateSelectionEntryVht1MaxRxMcs INTEGER,
            lcsSetupInterfacesWlanRateSelectionEntryVht2MaxTxMcs INTEGER,
            lcsSetupInterfacesWlanRateSelectionEntryVht2MaxRxMcs INTEGER,
            lcsSetupInterfacesWlanRateSelectionEntryVht3MaxTxMcs INTEGER,
            lcsSetupInterfacesWlanRateSelectionEntryVht3MaxRxMcs INTEGER,
            lcsSetupInterfacesWlanRateSelectionEntryVht4MaxTxMcs INTEGER,
            lcsSetupInterfacesWlanRateSelectionEntryVht4MaxRxMcs INTEGER
    }

-- {COLUMN} 1.3.6.1.4.1.2356.11.2.23.20.25.1.1
lcsSetupInterfacesWlanRateSelectionEntry1M OBJECT-TYPE
    SYNTAX     INTEGER {
                  eNo (0),
                  eRx (1),
                  eRxTx (3),
                  eRxRequired (5),
                  eRxTxRequired (7)
            }
    MAX-ACCESS read-write
    STATUS     current
    DESCRIPTION
            "1Mbit/s"
    ::= { lcsSetupInterfacesWlanRateSelectionEntry 1 }

-- {COLUMN} 1.3.6.1.4.1.2356.11.2.23.20.25.1.2
lcsSetupInterfacesWlanRateSelectionEntry2M OBJECT-TYPE
    SYNTAX     INTEGER {
                  eNo (0),
                  eRx (1),
                  eRxTx (3),
                  eRxRequired (5),
                  eRxTxRequired (7)
            }
    MAX-ACCESS read-write
    STATUS     current
    DESCRIPTION
            "2Mbit/s"
    ::= { lcsSetupInterfacesWlanRateSelectionEntry 2 }

-- {COLUMN} 1.3.6.1.4.1.2356.11.2.23.20.25.1.3
lcsSetupInterfacesWlanRateSelectionEntryIfc OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-write
    STATUS     current
    DESCRIPTION
            "-- empty --"
    ::= { lcsSetupInterfacesWlanRateSelectionEntry 3 }

-- {COLUMN} 1.3.6.1.4.1.2356.11.2.23.20.25.1.4
lcsSetupInterfacesWlanRateSelectionEntry5M5 OBJECT-TYPE
    SYNTAX     INTEGER {
                  eNo (0),
                  eRx (1),
                  eRxTx (3),
                  eRxRequired (5),
                  eRxTxRequired (7)
            }
    MAX-ACCESS read-write
    STATUS     current
    DESCRIPTION
            "5.5Mbit/s"
    ::= { lcsSetupInterfacesWlanRateSelectionEntry 4 }

-- {COLUMN} 1.3.6.1.4.1.2356.11.2.23.20.25.1.6
lcsSetupInterfacesWlanRateSelectionEntry11M OBJECT-TYPE
    SYNTAX     INTEGER {
                  eNo (0),
                  eRx (1),
                  eRxTx (3),
                  eRxRequired (5),
                  eRxTxRequired (7)
            }
    MAX-ACCESS read-write
    STATUS     current
    DESCRIPTION
            "11Mbit/s"
    ::= { lcsSetupInterfacesWlanRateSelectionEntry 6 }

-- {COLUMN} 1.3.6.1.4.1.2356.11.2.23.20.25.1.8
lcsSetupInterfacesWlanRateSelectionEntry6M OBJECT-TYPE
    SYNTAX     INTEGER {
                  eNo (0),
                  eRx (1),
                  eRxTx (3),
                  eRxRequired (5),
                  eRxTxRequired (7)
            }
    MAX-ACCESS read-write
    STATUS     current
    DESCRIPTION
            "6Mbit/s"
    ::= { lcsSetupInterfacesWlanRateSelectionEntry 8 }

-- {COLUMN} 1.3.6.1.4.1.2356.11.2.23.20.25.1.9
lcsSetupInterfacesWlanRateSelectionEntry9M OBJECT-TYPE
    SYNTAX     INTEGER {
                  eNo (0),
                  eRx (1),
                  eRxTx (3),
                  eRxRequired (5),
                  eRxTxRequired (7)
            }
    MAX-ACCESS read-write
    STATUS     current
    DESCRIPTION
            "9Mbit/s"
    ::= { lcsSetupInterfacesWlanRateSelectionEntry 9 }

-- {COLUMN} 1.3.6.1.4.1.2356.11.2.23.20.25.1.10
lcsSetupInterfacesWlanRateSelectionEntry12M OBJECT-TYPE
    SYNTAX     INTEGER {
                  eNo (0),
                  eRx (1),
                  eRxTx (3),
                  eRxRequired (5),
                  eRxTxRequired (7)
            }
    MAX-ACCESS read-write
    STATUS     current
    DESCRIPTION
            "12Mbit/s"
    ::= { lcsSetupInterfacesWlanRateSelectionEntry 10 }

-- {COLUMN} 1.3.6.1.4.1.2356.11.2.23.20.25.1.11
lcsSetupInterfacesWlanRateSelectionEntry18M OBJECT-TYPE
    SYNTAX     INTEGER {
                  eNo (0),
                  eRx (1),
                  eRxTx (3),
                  eRxRequired (5),
                  eRxTxRequired (7)
            }
    MAX-ACCESS read-write
    STATUS     current
    DESCRIPTION
            "18Mbit/s"
    ::= { lcsSetupInterfacesWlanRateSelectionEntry 11 }

-- {COLUMN} 1.3.6.1.4.1.2356.11.2.23.20.25.1.12
lcsSetupInterfacesWlanRateSelectionEntry24M OBJECT-TYPE
    SYNTAX     INTEGER {
                  eNo (0),
                  eRx (1),
                  eRxTx (3),
                  eRxRequired (5),
                  eRxTxRequired (7)
            }
    MAX-ACCESS read-write
    STATUS     current
    DESCRIPTION
            "24Mbit/s"
    ::= { lcsSetupInterfacesWlanRateSelectionEntry 12 }

-- {COLUMN} 1.3.6.1.4.1.2356.11.2.23.20.25.1.13
lcsSetupInterfacesWlanRateSelectionEntry36M OBJECT-TYPE
    SYNTAX     INTEGER {
                  eNo (0),
                  eRx (1),
                  eRxTx (3),
                  eRxRequired (5),
                  eRxTxRequired (7)
            }
    MAX-ACCESS read-write
    STATUS     current
    DESCRIPTION
            "36Mbit/s"
    ::= { lcsSetupInterfacesWlanRateSelectionEntry 13 }

-- {COLUMN} 1.3.6.1.4.1.2356.11.2.23.20.25.1.14
lcsSetupInterfacesWlanRateSelectionEntry48M OBJECT-TYPE
    SYNTAX     INTEGER {
                  eNo (0),
                  eRx (1),
                  eRxTx (3),
                  eRxRequired (5),
                  eRxTxRequired (7)
            }
    MAX-ACCESS read-write
    STATUS     current
    DESCRIPTION
            "48Mbit/s"
    ::= { lcsSetupInterfacesWlanRateSelectionEntry 14 }

-- {COLUMN} 1.3.6.1.4.1.2356.11.2.23.20.25.1.15
lcsSetupInterfacesWlanRateSelectionEntry54M OBJECT-TYPE
    SYNTAX     INTEGER {
                  eNo (0),
                  eRx (1),
                  eRxTx (3),
                  eRxRequired (5),
                  eRxTxRequired (7)
            }
    MAX-ACCESS read-write
    STATUS     current
    DESCRIPTION
            "54Mbit/s"
    ::= { lcsSetupInterfacesWlanRateSelectionEntry 15 }

-- {COLUMN} 1.3.6.1.4.1.2356.11.2.23.20.25.1.28
lcsSetupInterfacesWlanRateSelectionEntryHT1S6M5 OBJECT-TYPE
    SYNTAX     INTEGER {
                  eNo (0),
                  eRx (1),
                  eRxTx (3)
            }
    MAX-ACCESS read-write
    STATUS     current
    DESCRIPTION
            "High throughput 1 stream 6.5Mbit/s"
    ::= { lcsSetupInterfacesWlanRateSelectionEntry 28 }

-- {COLUMN} 1.3.6.1.4.1.2356.11.2.23.20.25.1.29
lcsSetupInterfacesWlanRateSelectionEntryHT1S13M OBJECT-TYPE
    SYNTAX     INTEGER {
                  eNo (0),
                  eRx (1),
                  eRxTx (3)
            }
    MAX-ACCESS read-write
    STATUS     current
    DESCRIPTION
            "High throughput 1 stream 13Mbit/s"
    ::= { lcsSetupInterfacesWlanRateSelectionEntry 29 }

-- {COLUMN} 1.3.6.1.4.1.2356.11.2.23.20.25.1.30
lcsSetupInterfacesWlanRateSelectionEntryHT1S19M5 OBJECT-TYPE
    SYNTAX     INTEGER {
                  eNo (0),
                  eRx (1),
                  eRxTx (3)
            }
    MAX-ACCESS read-write
    STATUS     current
    DESCRIPTION
            "High throughput 1 stream 19.5Mbit/s"
    ::= { lcsSetupInterfacesWlanRateSelectionEntry 30 }

-- {COLUMN} 1.3.6.1.4.1.2356.11.2.23.20.25.1.31
lcsSetupInterfacesWlanRateSelectionEntryHT1S26M OBJECT-TYPE
    SYNTAX     INTEGER {
                  eNo (0),
                  eRx (1),
                  eRxTx (3)
            }
    MAX-ACCESS read-write
    STATUS     current
    DESCRIPTION
            "High throughput 1 stream 26Mbit/s"
    ::= { lcsSetupInterfacesWlanRateSelectionEntry 31 }

-- {COLUMN} 1.3.6.1.4.1.2356.11.2.23.20.25.1.32
lcsSetupInterfacesWlanRateSelectionEntryHT1S39M OBJECT-TYPE
    SYNTAX     INTEGER {
                  eNo (0),
                  eRx (1),
                  eRxTx (3)
            }
    MAX-ACCESS read-write
    STATUS     current
    DESCRIPTION
            "High throughput 1 stream 39Mbit/s"
    ::= { lcsSetupInterfacesWlanRateSelectionEntry 32 }

-- {COLUMN} 1.3.6.1.4.1.2356.11.2.23.20.25.1.33
lcsSetupInterfacesWlanRateSelectionEntryHT1S52M OBJECT-TYPE
    SYNTAX     INTEGER {
                  eNo (0),
                  eRx (1),
                  eRxTx (3)
            }
    MAX-ACCESS read-write
    STATUS     current
    DESCRIPTION
            "High throughput 1 stream 52Mbit/s"
    ::= { lcsSetupInterfacesWlanRateSelectionEntry 33 }

-- {COLUMN} 1.3.6.1.4.1.2356.11.2.23.20.25.1.34
lcsSetupInterfacesWlanRateSelectionEntryHT1S58M5 OBJECT-TYPE
    SYNTAX     INTEGER {
                  eNo (0),
                  eRx (1),
                  eRxTx (3)
            }
    MAX-ACCESS read-write
    STATUS     current
    DESCRIPTION
            "High throughput 1 stream 58.5Mbit/s"
    ::= { lcsSetupInterfacesWlanRateSelectionEntry 34 }

-- {COLUMN} 1.3.6.1.4.1.2356.11.2.23.20.25.1.35
lcsSetupInterfacesWlanRateSelectionEntryHT1S65M OBJECT-TYPE
    SYNTAX     INTEGER {
                  eNo (0),
                  eRx (1),
                  eRxTx (3)
            }
    MAX-ACCESS read-write
    STATUS     current
    DESCRIPTION
            "High throughput 1 stream 65Mbit/s"
    ::= { lcsSetupInterfacesWlanRateSelectionEntry 35 }

-- {COLUMN} 1.3.6.1.4.1.2356.11.2.23.20.25.1.36
lcsSetupInterfacesWlanRateSelectionEntryHT2S13M OBJECT-TYPE
    SYNTAX     INTEGER {
                  eNo (0),
                  eRx (1),
                  eRxTx (3)
            }
    MAX-ACCESS read-write
    STATUS     current
    DESCRIPTION
            "High throughput 2 streams 13Mbit/s"
    ::= { lcsSetupInterfacesWlanRateSelectionEntry 36 }

-- {COLUMN} 1.3.6.1.4.1.2356.11.2.23.20.25.1.37
lcsSetupInterfacesWlanRateSelectionEntryHT2S26M OBJECT-TYPE
    SYNTAX     INTEGER {
                  eNo (0),
                  eRx (1),
                  eRxTx (3)
            }
    MAX-ACCESS read-write
    STATUS     current
    DESCRIPTION
            "High throughput 2 streams 26Mbit/s"
    ::= { lcsSetupInterfacesWlanRateSelectionEntry 37 }

-- {COLUMN} 1.3.6.1.4.1.2356.11.2.23.20.25.1.38
lcsSetupInterfacesWlanRateSelectionEntryHT2S39M OBJECT-TYPE
    SYNTAX     INTEGER {
                  eNo (0),
                  eRx (1),
                  eRxTx (3)
            }
    MAX-ACCESS read-write
    STATUS     current
    DESCRIPTION
            "High throughput 2 streams 39Mbit/s"
    ::= { lcsSetupInterfacesWlanRateSelectionEntry 38 }

-- {COLUMN} 1.3.6.1.4.1.2356.11.2.23.20.25.1.39
lcsSetupInterfacesWlanRateSelectionEntryHT2S52M OBJECT-TYPE
    SYNTAX     INTEGER {
                  eNo (0),
                  eRx (1),
                  eRxTx (3)
            }
    MAX-ACCESS read-write
    STATUS     current
    DESCRIPTION
            "High throughput 2 streams 52Mbit/s"
    ::= { lcsSetupInterfacesWlanRateSelectionEntry 39 }

-- {COLUMN} 1.3.6.1.4.1.2356.11.2.23.20.25.1.40
lcsSetupInterfacesWlanRateSelectionEntryHT2S78M OBJECT-TYPE
    SYNTAX     INTEGER {
                  eNo (0),
                  eRx (1),
                  eRxTx (3)
            }
    MAX-ACCESS read-write
    STATUS     current
    DESCRIPTION
            "High throughput 2 streams 78Mbit/s"
    ::= { lcsSetupInterfacesWlanRateSelectionEntry 40 }

-- {COLUMN} 1.3.6.1.4.1.2356.11.2.23.20.25.1.41
lcsSetupInterfacesWlanRateSelectionEntryHT2S104M OBJECT-TYPE
    SYNTAX     INTEGER {
                  eNo (0),
                  eRx (1),
                  eRxTx (3)
            }
    MAX-ACCESS read-write
    STATUS     current
    DESCRIPTION
            "High throughput 2 streams 104Mbit/s"
    ::= { lcsSetupInterfacesWlanRateSelectionEntry 41 }

-- {COLUMN} 1.3.6.1.4.1.2356.11.2.23.20.25.1.42
lcsSetupInterfacesWlanRateSelectionEntryHT2S117M OBJECT-TYPE
    SYNTAX     INTEGER {
                  eNo (0),
                  eRx (1),
                  eRxTx (3)
            }
    MAX-ACCESS read-write
    STATUS     current
    DESCRIPTION
            "High throughput 2 streams 117Mbit/s"
    ::= { lcsSetupInterfacesWlanRateSelectionEntry 42 }

-- {COLUMN} 1.3.6.1.4.1.2356.11.2.23.20.25.1.43
lcsSetupInterfacesWlanRateSelectionEntryHT2S130M OBJECT-TYPE
    SYNTAX     INTEGER {
                  eNo (0),
                  eRx (1),
                  eRxTx (3)
            }
    MAX-ACCESS read-write
    STATUS     current
    DESCRIPTION
            "High throughput 2 streams 130Mbit/s"
    ::= { lcsSetupInterfacesWlanRateSelectionEntry 43 }

-- {COLUMN} 1.3.6.1.4.1.2356.11.2.23.20.25.1.44
lcsSetupInterfacesWlanRateSelectionEntryHT3S19M5 OBJECT-TYPE
    SYNTAX     INTEGER {
                  eNo (0),
                  eRx (1),
                  eRxTx (3)
            }
    MAX-ACCESS read-write
    STATUS     current
    DESCRIPTION
            "High throughput 3 streams 19.5Mbit/s"
    ::= { lcsSetupInterfacesWlanRateSelectionEntry 44 }

-- {COLUMN} 1.3.6.1.4.1.2356.11.2.23.20.25.1.45
lcsSetupInterfacesWlanRateSelectionEntryHT3S39M OBJECT-TYPE
    SYNTAX     INTEGER {
                  eNo (0),
                  eRx (1),
                  eRxTx (3)
            }
    MAX-ACCESS read-write
    STATUS     current
    DESCRIPTION
            "High throughput 3 streams 39Mbit/s"
    ::= { lcsSetupInterfacesWlanRateSelectionEntry 45 }

-- {COLUMN} 1.3.6.1.4.1.2356.11.2.23.20.25.1.46
lcsSetupInterfacesWlanRateSelectionEntryHT3S58M5 OBJECT-TYPE
    SYNTAX     INTEGER {
                  eNo (0),
                  eRx (1),
                  eRxTx (3)
            }
    MAX-ACCESS read-write
    STATUS     current
    DESCRIPTION
            "High throughput 3 streams 58.5Mbit/s"
    ::= { lcsSetupInterfacesWlanRateSelectionEntry 46 }

-- {COLUMN} 1.3.6.1.4.1.2356.11.2.23.20.25.1.47
lcsSetupInterfacesWlanRateSelectionEntryHT3S78M OBJECT-TYPE
    SYNTAX     INTEGER {
                  eNo (0),
                  eRx (1),
                  eRxTx (3)
            }
    MAX-ACCESS read-write
    STATUS     current
    DESCRIPTION
            "High throughput 3 streams 78Mbit/s"
    ::= { lcsSetupInterfacesWlanRateSelectionEntry 47 }

-- {COLUMN} 1.3.6.1.4.1.2356.11.2.23.20.25.1.48
lcsSetupInterfacesWlanRateSelectionEntryHT3S117M OBJECT-TYPE
    SYNTAX     INTEGER {
                  eNo (0),
                  eRx (1),
                  eRxTx (3)
            }
    MAX-ACCESS read-write
    STATUS     current
    DESCRIPTION
            "High throughput 3 streams 117Mbit/s"
    ::= { lcsSetupInterfacesWlanRateSelectionEntry 48 }

-- {COLUMN} 1.3.6.1.4.1.2356.11.2.23.20.25.1.49
lcsSetupInterfacesWlanRateSelectionEntryHT3S156M OBJECT-TYPE
    SYNTAX     INTEGER {
                  eNo (0),
                  eRx (1),
                  eRxTx (3)
            }
    MAX-ACCESS read-write
    STATUS     current
    DESCRIPTION
            "High throughput 3 streams 156Mbit/s"
    ::= { lcsSetupInterfacesWlanRateSelectionEntry 49 }

-- {COLUMN} 1.3.6.1.4.1.2356.11.2.23.20.25.1.50
lcsSetupInterfacesWlanRateSelectionEntryHT3S175M5 OBJECT-TYPE
    SYNTAX     INTEGER {
                  eNo (0),
                  eRx (1),
                  eRxTx (3)
            }
    MAX-ACCESS read-write
    STATUS     current
    DESCRIPTION
            "High throughput 3 streams 175.5Mbit/s"
    ::= { lcsSetupInterfacesWlanRateSelectionEntry 50 }

-- {COLUMN} 1.3.6.1.4.1.2356.11.2.23.20.25.1.51
lcsSetupInterfacesWlanRateSelectionEntryHT3S195M OBJECT-TYPE
    SYNTAX     INTEGER {
                  eNo (0),
                  eRx (1),
                  eRxTx (3)
            }
    MAX-ACCESS read-write
    STATUS     current
    DESCRIPTION
            "High throughput 3 streams 195Mbit/s"
    ::= { lcsSetupInterfacesWlanRateSelectionEntry 51 }

-- {COLUMN} 1.3.6.1.4.1.2356.11.2.23.20.25.1.52
lcsSetupInterfacesWlanRateSelectionEntryHT4S26M OBJECT-TYPE
    SYNTAX     INTEGER {
                  eNo (0),
                  eRx (1),
                  eRxTx (3)
            }
    MAX-ACCESS read-write
    STATUS     current
    DESCRIPTION
            "High throughput 4 streams 26Mbit/s"
    ::= { lcsSetupInterfacesWlanRateSelectionEntry 52 }

-- {COLUMN} 1.3.6.1.4.1.2356.11.2.23.20.25.1.53
lcsSetupInterfacesWlanRateSelectionEntryHT4S52M OBJECT-TYPE
    SYNTAX     INTEGER {
                  eNo (0),
                  eRx (1),
                  eRxTx (3)
            }
    MAX-ACCESS read-write
    STATUS     current
    DESCRIPTION
            "High throughput 4 streams 52Mbit/s"
    ::= { lcsSetupInterfacesWlanRateSelectionEntry 53 }

-- {COLUMN} 1.3.6.1.4.1.2356.11.2.23.20.25.1.54
lcsSetupInterfacesWlanRateSelectionEntryHT4S78M OBJECT-TYPE
    SYNTAX     INTEGER {
                  eNo (0),
                  eRx (1),
                  eRxTx (3)
            }
    MAX-ACCESS read-write
    STATUS     current
    DESCRIPTION
            "High throughput 4 streams 78Mbit/s"
    ::= { lcsSetupInterfacesWlanRateSelectionEntry 54 }

-- {COLUMN} 1.3.6.1.4.1.2356.11.2.23.20.25.1.55
lcsSetupInterfacesWlanRateSelectionEntryHT4S104M OBJECT-TYPE
    SYNTAX     INTEGER {
                  eNo (0),
                  eRx (1),
                  eRxTx (3)
            }
    MAX-ACCESS read-write
    STATUS     current
    DESCRIPTION
            "High throughput 4 streams 104Mbit/s"
    ::= { lcsSetupInterfacesWlanRateSelectionEntry 55 }

-- {COLUMN} 1.3.6.1.4.1.2356.11.2.23.20.25.1.56
lcsSetupInterfacesWlanRateSelectionEntryHT4S156M OBJECT-TYPE
    SYNTAX     INTEGER {
                  eNo (0),
                  eRx (1),
                  eRxTx (3)
            }
    MAX-ACCESS read-write
    STATUS     current
    DESCRIPTION
            "High throughput 4 streams 156Mbit/s"
    ::= { lcsSetupInterfacesWlanRateSelectionEntry 56 }

-- {COLUMN} 1.3.6.1.4.1.2356.11.2.23.20.25.1.57
lcsSetupInterfacesWlanRateSelectionEntryHT4S208M OBJECT-TYPE
    SYNTAX     INTEGER {
                  eNo (0),
                  eRx (1),
                  eRxTx (3)
            }
    MAX-ACCESS read-write
    STATUS     current
    DESCRIPTION
            "High throughput 4 streams 208Mbit/s"
    ::= { lcsSetupInterfacesWlanRateSelectionEntry 57 }

-- {COLUMN} 1.3.6.1.4.1.2356.11.2.23.20.25.1.58
lcsSetupInterfacesWlanRateSelectionEntryHT4S234M OBJECT-TYPE
    SYNTAX     INTEGER {
                  eNo (0),
                  eRx (1),
                  eRxTx (3)
            }
    MAX-ACCESS read-write
    STATUS     current
    DESCRIPTION
            "High throughput 4 streams 234Mbit/s"
    ::= { lcsSetupInterfacesWlanRateSelectionEntry 58 }

-- {COLUMN} 1.3.6.1.4.1.2356.11.2.23.20.25.1.59
lcsSetupInterfacesWlanRateSelectionEntryHT4S260M OBJECT-TYPE
    SYNTAX     INTEGER {
                  eNo (0),
                  eRx (1),
                  eRxTx (3)
            }
    MAX-ACCESS read-write
    STATUS     current
    DESCRIPTION
            "High throughput 4 streams 260Mbit/s"
    ::= { lcsSetupInterfacesWlanRateSelectionEntry 59 }

-- {COLUMN} 1.3.6.1.4.1.2356.11.2.23.20.25.1.105
lcsSetupInterfacesWlanRateSelectionEntryVht1MaxTxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanRateSelectionEntry 105 }

-- {COLUMN} 1.3.6.1.4.1.2356.11.2.23.20.25.1.106
lcsSetupInterfacesWlanRateSelectionEntryVht1MaxRxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanRateSelectionEntry 106 }

-- {COLUMN} 1.3.6.1.4.1.2356.11.2.23.20.25.1.115
lcsSetupInterfacesWlanRateSelectionEntryVht2MaxTxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanRateSelectionEntry 115 }

-- {COLUMN} 1.3.6.1.4.1.2356.11.2.23.20.25.1.116
lcsSetupInterfacesWlanRateSelectionEntryVht2MaxRxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanRateSelectionEntry 116 }

-- {COLUMN} 1.3.6.1.4.1.2356.11.2.23.20.25.1.125
lcsSetupInterfacesWlanRateSelectionEntryVht3MaxTxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanRateSelectionEntry 125 }

-- {COLUMN} 1.3.6.1.4.1.2356.11.2.23.20.25.1.126
lcsSetupInterfacesWlanRateSelectionEntryVht3MaxRxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanRateSelectionEntry 126 }

-- {COLUMN} 1.3.6.1.4.1.2356.11.2.23.20.25.1.135
lcsSetupInterfacesWlanRateSelectionEntryVht4MaxTxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanRateSelectionEntry 135 }

-- {COLUMN} 1.3.6.1.4.1.2356.11.2.23.20.25.1.136
lcsSetupInterfacesWlanRateSelectionEntryVht4MaxRxMcs OBJECT-TYPE
    SYNTAX     INTEGER {
                  eMcs7 (0),
                  eMcs8 (1),
                  eMcs9 (2),
                  eNone (3)
            }
    MAX-ACCESS read-write
    STATUS     current
    DESCRIPTION
            "-- empty --"
    ::= { lcsSetupInterfacesWlanRateSelectionEntry 136 }

-- {TABLE} 1.3.6.1.4.1.2356.11.2.23.20.26
lcsSetupInterfacesWlanBlinkModeTable OBJECT-TYPE
    SYNTAX     SEQUENCE OF LcsSetupInterfacesWlanBlinkModeEntry
    MAX-ACCESS not-accessible
    STATUS     current
    DESCRIPTION
            "-- empty --"
    ::= { lcsSetupInterfacesWlan 26 }

-- {ROW} 1.3.6.1.4.1.2356.11.2.23.20.26.1
lcsSetupInterfacesWlanBlinkModeEntry OBJECT-TYPE
    SYNTAX     LcsSetupInterfacesWlanBlinkModeEntry
    MAX-ACCESS not-accessible
    STATUS     current
    DESCRIPTION
            ""
    INDEX {
            lcsSetupInterfacesWlanBlinkModeEntryIfc
          }
    ::= { lcsSetupInterfacesWlanBlinkModeTable 1 }

LcsSetupInterfacesWlanBlinkModeEntry ::= SEQUENCE {
            lcsSetupInterfacesWlanBlinkModeEntryIfc INTEGER,
            lcsSetupInterfacesWlanBlinkModeEntryOperating INTEGER,
            lcsSetupInterfacesWlanBlinkModeEntryNetwork INTEGER
    }

-- {COLUMN} 1.3.6.1.4.1.2356.11.2.23.20.26.1.1
lcsSetupInterfacesWlanBlinkModeEntryIfc OBJECT-TYPE
    SYNTAX     INTEGER {
                  eWlan1 (1),
                  eWlan2 (2)
            }
    MAX-ACCESS read-write
    STATUS     current
    DESCRIPTION
            "-- empty --"
    ::= { lcsSetupInterfacesWlanBlinkModeEntry 1 }

-- {COLUMN} 1.3.6.1.4.1.2356.11.2.23.20.26.1.2
lcsSetupInterfacesWlanBlinkModeEntryOperating OBJECT-TYPE
    SYNTAX     INTEGER {
                  eYes (0),
                  eNo (1)
            }
    MAX-ACCESS read-write
    STATUS     current
    DESCRIPTION
            "-- empty --"
    ::= { lcsSetupInterfacesWlanBlinkModeEntry 2 }

-- {COLUMN} 1.3.6.1.4.1.2356.11.2.23.20.26.1.3
lcsSetupInterfacesWlanBlinkModeEntryNetwork OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan19 (23),
                  eWlan110 (24),
                  eWlan111 (25),
                  eWlan112 (26),
                  eWlan113 (27),
                  eWlan114 (28),
                  eWlan115 (29),
                  eWlan116 (30),
                  eWlan22 (32),
                  eWlan23 (33),
                  eWlan24 (34),
                  eWlan25 (35),
                  eWlan26 (36),
                  eWlan27 (37),
                  eWlan28 (38),
                  eWlan29 (39),
                  eWlan210 (40),
                  eWlan211 (41),
                  eWlan212 (42),
                  eWlan213 (43),
                  eWlan214 (44),
                  eWlan215 (45),
                  eWlan216 (46)
            }
    MAX-ACCESS read-write
    STATUS     current
    DESCRIPTION
            "-- empty --"
    ::= { lcsSetupInterfacesWlanBlinkModeEntry 3 }

-- {TABLE} 1.3.6.1.4.1.2356.11.2.23.20.27
lcsSetupInterfacesWlanEnvironmentScanTable OBJECT-TYPE
    SYNTAX     SEQUENCE OF LcsSetupInterfacesWlanEnvironmentScanEntry
    MAX-ACCESS not-accessible
    STATUS     current
    DESCRIPTION
            "-- empty --"
    ::= { lcsSetupInterfacesWlan 27 }

-- {ROW} 1.3.6.1.4.1.2356.11.2.23.20.27.1
lcsSetupInterfacesWlanEnvironmentScanEntry OBJECT-TYPE
    SYNTAX     LcsSetupInterfacesWlanEnvironmentScanEntry
    MAX-ACCESS not-accessible
    STATUS     current
    DESCRIPTION
            ""
    INDEX {
            lcsSetupInterfacesWlanEnvironmentScanEntryIfc
          }
    ::= { lcsSetupInterfacesWlanEnvironmentScanTable 1 }

LcsSetupInterfacesWlanEnvironmentScanEntry ::= SEQUENCE {
            lcsSetupInterfacesWlanEnvironmentScanEntryIfc INTEGER,
            lcsSetupInterfacesWlanEnvironmentScanEntryOperating INTEGER,
            lcsSetupInterfacesWlanEnvironmentScanEntryHours DisplayString,
            lcsSetupInterfacesWlanEnvironmentScanEntryMinutes DisplayString,
            lcsSetupInterfacesWlanEnvironmentScanEntryRadioBands INTEGER,
            lcsSetupInterfacesWlanEnvironmentScanEntrySubbands5ghz INTEGER,
            lcsSetupInterfacesWlanEnvironmentScanEntryChannelList24ghz DisplayString,
            lcsSetupInterfacesWlanEnvironmentScanEntryChannelList5ghz DisplayString
    }

-- {COLUMN} 1.3.6.1.4.1.2356.11.2.23.20.27.1.1
lcsSetupInterfacesWlanEnvironmentScanEntryIfc OBJECT-TYPE
    SYNTAX     INTEGER {
                  eWlan1 (1),
                  eWlan2 (2)
            }
    MAX-ACCESS read-write
    STATUS     current
    DESCRIPTION
            "-- empty --"
    ::= { lcsSetupInterfacesWlanEnvironmentScanEntry 1 }

-- {COLUMN} 1.3.6.1.4.1.2356.11.2.23.20.27.1.2
lcsSetupInterfacesWlanEnvironmentScanEntryOperating OBJECT-TYPE
    SYNTAX     INTEGER {
                  eNo (0),
                  eYes (1)
            }
    MAX-ACCESS read-write
    STATUS     current
    DESCRIPTION
            "-- empty --"
    ::= { lcsSetupInterfacesWlanEnvironmentScanEntry 2 }

-- {COLUMN} 1.3.6.1.4.1.2356.11.2.23.20.27.1.6
lcsSetupInterfacesWlanEnvironmentScanEntryHours OBJECT-TYPE
    SYNTAX     DisplayString (SIZE(0..20))
    MAX-ACCESS read-write
    STATUS     current
    DESCRIPTION
            "-- empty --"
    ::= { lcsSetupInterfacesWlanEnvironmentScanEntry 6 }

-- {COLUMN} 1.3.6.1.4.1.2356.11.2.23.20.27.1.7
lcsSetupInterfacesWlanEnvironmentScanEntryMinutes OBJECT-TYPE
    SYNTAX     DisplayString (SIZE(0..20))
    MAX-ACCESS read-write
    STATUS     current
    DESCRIPTION
            "-- empty --"
    ::= { lcsSetupInterfacesWlanEnvironmentScanEntry 7 }

-- {COLUMN} 1.3.6.1.4.1.2356.11.2.23.20.27.1.8
lcsSetupInterfacesWlanEnvironmentScanEntryRadioBands OBJECT-TYPE
    SYNTAX     INTEGER {
                  e24ghz (1),
                  e5ghz (2),
                  e24ghz5ghz (3)
            }
    MAX-ACCESS read-write
    STATUS     current
    DESCRIPTION
            "-- empty --"
    ::= { lcsSetupInterfacesWlanEnvironmentScanEntry 8 }

-- {COLUMN} 1.3.6.1.4.1.2356.11.2.23.20.27.1.9
lcsSetupInterfacesWlanEnvironmentScanEntrySubbands5ghz OBJECT-TYPE
    SYNTAX     INTEGER {
                  eBand1 (1),
                  eBand2 (2),
                  eBand1Plus2 (3),
                  eBand3 (4),
                  eBand1Plus3 (5),
                  eBand2Plus3 (6),
                  eBand1Plus2Plus3 (7)
            }
    MAX-ACCESS read-write
    STATUS     current
    DESCRIPTION
            "-- empty --"
    ::= { lcsSetupInterfacesWlanEnvironmentScanEntry 9 }

-- {COLUMN} 1.3.6.1.4.1.2356.11.2.23.20.27.1.10
lcsSetupInterfacesWlanEnvironmentScanEntryChannelList24ghz OBJECT-TYPE
    SYNTAX     DisplayString (SIZE(0..48))
    MAX-ACCESS read-write
    STATUS     current
    DESCRIPTION
            "-- empty --"
    ::= { lcsSetupInterfacesWlanEnvironmentScanEntry 10 }

-- {COLUMN} 1.3.6.1.4.1.2356.11.2.23.20.27.1.11
lcsSetupInterfacesWlanEnvironmentScanEntryChannelList5ghz OBJECT-TYPE
    SYNTAX     DisplayString (SIZE(0..48))
    MAX-ACCESS read-write
    STATUS     current
    DESCRIPTION
            "-- empty --"
    ::= { lcsSetupInterfacesWlanEnvironmentScanEntry 11 }

-- {TABLE} 1.3.6.1.4.1.2356.11.2.23.21
lcsSetupInterfacesLanInterfacesTable OBJECT-TYPE
    SYNTAX     SEQUENCE OF LcsSetupInterfacesLanInterfacesEntry
    MAX-ACCESS not-accessible
    STATUS     current
    DESCRIPTION
            ""
    ::= { lcsSetupInterfaces 21 }

-- {ROW} 1.3.6.1.4.1.2356.11.2.23.21.1
lcsSetupInterfacesLanInterfacesEntry OBJECT-TYPE
    SYNTAX     LcsSetupInterfacesLanInterfacesEntry
    MAX-ACCESS not-accessible
    STATUS     current
    DESCRIPTION
            ""
    INDEX {
            lcsSetupInterfacesLanInterfacesEntryIfc
          }
    ::= { lcsSetupInterfacesLanInterfacesTable 1 }

LcsSetupInterfacesLanInterfacesEntry ::= SEQUENCE {
            lcsSetupInterfacesLanInterfacesEntryIfc INTEGER,
            lcsSetupInterfacesLanInterfacesEntryConnector INTEGER,
            lcsSetupInterfacesLanInterfacesEntryMdiMode INTEGER,
            lcsSetupInterfacesLanInterfacesEntryClockRole INTEGER,
            lcsSetupInterfacesLanInterfacesEntryMtu Integer32,
            lcsSetupInterfacesLanInterfacesEntryOperating INTEGER,
            lcsSetupInterfacesLanInterfacesEntryTxLimit Integer32,
            lcsSetupInterfacesLanInterfacesEntryRxLimit Integer32,
            lcsSetupInterfacesLanInterfacesEntryPowerSaving INTEGER,
            lcsSetupInterfacesLanInterfacesEntryFlowControl INTEGER
    }

-- {COLUMN} 1.3.6.1.4.1.2356.11.2.23.21.1.1
lcsSetupInterfacesLanInterfacesEntryIfc OBJECT-TYPE
    SYNTAX     INTEGER {
                  eLan1 (1),
                  eLan2 (2),
                  eLan3 (3),
                  eLan4 (4),
                  eLan5 (5),
                  eLan6 (6)
            }
    MAX-ACCESS read-only
    STATUS     current
    DESCRIPTION
            ""
    ::= { lcsSetupInterfacesLanInterfacesEntry 1 }

-- {COLUMN} 1.3.6.1.4.1.2356.11.2.23.21.1.2
lcsSetupInterfacesLanInterfacesEntryConnector OBJECT-TYPE
    SYNTAX     INTEGER {
                  eAuto (0),
                  e10bT (1),
                  eFd10bTx (2),
                  e100bTx (3),
                  eFd100bTx (4),
                  eAuto10 (5),
                  eFd1000bTx (6),
                  eAuto100 (7),
                  ePowerDown (255)
            }
    MAX-ACCESS read-write
    STATUS     current
    DESCRIPTION
            ""
    ::= { lcsSetupInterfacesLanInterfacesEntry 2 }

-- {COLUMN} 1.3.6.1.4.1.2356.11.2.23.21.1.3
lcsSetupInterfacesLanInterfacesEntryMdiMode OBJECT-TYPE
    SYNTAX     INTEGER {
                  eAuto (0),
                  eMdi (1),
                  eMdix (2)
            }
    MAX-ACCESS read-write
    STATUS     current
    DESCRIPTION
            ""
    ::= { lcsSetupInterfacesLanInterfacesEntry 3 }

-- {COLUMN} 1.3.6.1.4.1.2356.11.2.23.21.1.5
lcsSetupInterfacesLanInterfacesEntryClockRole OBJECT-TYPE
    SYNTAX     INTEGER {
                  eSlavePreferred (0),
                  eMaster (1),
                  eSlave (2),
                  eMasterPreferred (4)
            }
    MAX-ACCESS read-write
    STATUS     current
    DESCRIPTION
            ""
    ::= { lcsSetupInterfacesLanInterfacesEntry 5 }

-- {COLUMN} 1.3.6.1.4.1.2356.11.2.23.21.1.6
lcsSetupInterfacesLanInterfacesEntryMtu OBJECT-TYPE
    SYNTAX     Integer32 (0..2147483647)
    MAX-ACCESS read-write
    STATUS     current
    DESCRIPTION
            ""
    ::= { lcsSetupInterfacesLanInterfacesEntry 6 }

-- {COLUMN} 1.3.6.1.4.1.2356.11.2.23.21.1.7
lcsSetupInterfacesLanInterfacesEntryOperating OBJECT-TYPE
    SYNTAX     INTEGER {
                  eYes (0),
                  eNo (1)
            }
    MAX-ACCESS read-write
    STATUS     current
    DESCRIPTION
            ""
    ::= { lcsSetupInterfacesLanInterfacesEntry 7 }

-- {COLUMN} 1.3.6.1.4.1.2356.11.2.23.21.1.8
lcsSetupInterfacesLanInterfacesEntryTxLimit OBJECT-TYPE
    SYNTAX     Integer32 (0..2147483647)
    MAX-ACCESS read-write
    STATUS     current
    DESCRIPTION
            ""
    ::= { lcsSetupInterfacesLanInterfacesEntry 8 }

-- {COLUMN} 1.3.6.1.4.1.2356.11.2.23.21.1.9
lcsSetupInterfacesLanInterfacesEntryRxLimit OBJECT-TYPE
    SYNTAX     Integer32 (0..2147483647)
    MAX-ACCESS read-write
    STATUS     current
    DESCRIPTION
            ""
    ::= { lcsSetupInterfacesLanInterfacesEntry 9 }

-- {COLUMN} 1.3.6.1.4.1.2356.11.2.23.21.1.10
lcsSetupInterfacesLanInterfacesEntryPowerSaving OBJECT-TYPE
    SYNTAX     INTEGER {
                  eNo (0),
                  eYes (1)
            }
    MAX-ACCESS read-write
    STATUS     current
    DESCRIPTION
            "-- empty --"
    ::= { lcsSetupInterfacesLanInterfacesEntry 10 }

-- {COLUMN} 1.3.6.1.4.1.2356.11.2.23.21.1.11
lcsSetupInterfacesLanInterfacesEntryFlowControl OBJECT-TYPE
    SYNTAX     INTEGER {
                  eAuto (0),
                  eOn (1),
                  eOff (2)
            }
    MAX-ACCESS read-write
    STATUS     current
    DESCRIPTION
            "-- empty --"
    ::= { lcsSetupInterfacesLanInterfacesEntry 11 }

-- {TABLE} 1.3.6.1.4.1.2356.11.2.23.30
lcsSetupInterfacesEthernetPortsTable OBJECT-TYPE
    SYNTAX     SEQUENCE OF LcsSetupInterfacesEthernetPortsEntry
    MAX-ACCESS not-accessible
    STATUS     current
    DESCRIPTION
            ""
    ::= { lcsSetupInterfaces 30 }

-- {ROW} 1.3.6.1.4.1.2356.11.2.23.30.1
lcsSetupInterfacesEthernetPortsEntry OBJECT-TYPE
    SYNTAX     LcsSetupInterfacesEthernetPortsEntry
    MAX-ACCESS not-accessible
    STATUS     current
    DESCRIPTION
            ""
    INDEX {
            lcsSetupInterfacesEthernetPortsEntryPort
          }
    ::= { lcsSetupInterfacesEthernetPortsTable 1 }

LcsSetupInterfacesEthernetPortsEntry ::= SEQUENCE {
            lcsSetupInterfacesEthernetPortsEntryPort INTEGER,
            lcsSetupInterfacesEthernetPortsEntryConnector INTEGER,
            lcsSetupInterfacesEthernetPortsEntryPrivateMode INTEGER,
            lcsSetupInterfacesEthernetPortsEntryAssignment INTEGER,
            lcsSetupInterfacesEthernetPortsEntryMdiMode INTEGER,
            lcsSetupInterfacesEthernetPortsEntryClockRole INTEGER,
            lcsSetupInterfacesEthernetPortsEntryDownshift INTEGER,
            lcsSetupInterfacesEthernetPortsEntryPowerSaving INTEGER,
            lcsSetupInterfacesEthernetPortsEntryFlowControl INTEGER
    }

-- {COLUMN} 1.3.6.1.4.1.2356.11.2.23.30.1.1
lcsSetupInterfacesEthernetPortsEntryPort OBJECT-TYPE
    SYNTAX     INTEGER {
                  eUnknown (0),
                  eUplink (1),
                  eEth1 (2),
                  eEth2 (3),
                  eEth3 (4),
                  eEth4 (5),
                  eWan (16),
                  eWan1 (17),
                  eWan2 (18),
                  eSfp1 (32)
            }
    MAX-ACCESS read-only
    STATUS     current
    DESCRIPTION
            ""
    ::= { lcsSetupInterfacesEthernetPortsEntry 1 }

-- {COLUMN} 1.3.6.1.4.1.2356.11.2.23.30.1.2
lcsSetupInterfacesEthernetPortsEntryConnector OBJECT-TYPE
    SYNTAX     INTEGER {
                  eAuto (0),
                  e10bT (1),
                  eFd10bTx (2),
                  e100bTx (3),
                  eFd100bTx (4),
                  eAuto10 (5),
                  eFd1000bTx (6),
                  eAuto100 (7)
            }
    MAX-ACCESS read-write
    STATUS     current
    DESCRIPTION
            ""
    ::= { lcsSetupInterfacesEthernetPortsEntry 2 }

-- {COLUMN} 1.3.6.1.4.1.2356.11.2.23.30.1.3
lcsSetupInterfacesEthernetPortsEntryPrivateMode OBJECT-TYPE
    SYNTAX     INTEGER {
                  eNo (0),
                  eYes (1)
            }
    MAX-ACCESS read-write
    STATUS     current
    DESCRIPTION
            ""
    ::= { lcsSetupInterfacesEthernetPortsEntry 3 }

-- {COLUMN} 1.3.6.1.4.1.2356.11.2.23.30.1.4
lcsSetupInterfacesEthernetPortsEntryAssignment OBJECT-TYPE
    SYNTAX     INTEGER {
                  eLan1 (0),
                  eLan2 (1),
                  eLan3 (2),
                  eLan4 (3),
                  eLan5 (4),
                  eLan6 (5),
                  eDsl1 (512),
                  eDsl2 (513),
                  eDsl3 (514),
                  eDsl4 (515),
                  eDsl5 (516),
                  eIdle (65533),
                  eMonitor (65534),
                  ePowerDown (65535)
            }
    MAX-ACCESS read-write
    STATUS     current
    DESCRIPTION
            ""
    ::= { lcsSetupInterfacesEthernetPortsEntry 4 }

-- {COLUMN} 1.3.6.1.4.1.2356.11.2.23.30.1.5
lcsSetupInterfacesEthernetPortsEntryMdiMode OBJECT-TYPE
    SYNTAX     INTEGER {
                  eAuto (0),
                  eMdi (1),
                  eMdix (2)
            }
    MAX-ACCESS read-write
    STATUS     current
    DESCRIPTION
            ""
    ::= { lcsSetupInterfacesEthernetPortsEntry 5 }

-- {COLUMN} 1.3.6.1.4.1.2356.11.2.23.30.1.6
lcsSetupInterfacesEthernetPortsEntryClockRole OBJECT-TYPE
    SYNTAX     INTEGER {
                  eSlavePreferred (0),
                  eMaster (1),
                  eSlave (2),
                  eMasterPreferred (4)
            }
    MAX-ACCESS read-write
    STATUS     current
    DESCRIPTION
            ""
    ::= { lcsSetupInterfacesEthernetPortsEntry 6 }

-- {COLUMN} 1.3.6.1.4.1.2356.11.2.23.30.1.7
lcsSetupInterfacesEthernetPortsEntryDownshift OBJECT-TYPE
    SYNTAX     INTEGER {
                  eNo (0),
                  eYes (1)
            }
    MAX-ACCESS read-write
    STATUS     current
    DESCRIPTION
            "-- empty --"
    ::= { lcsSetupInterfacesEthernetPortsEntry 7 }

-- {COLUMN} 1.3.6.1.4.1.2356.11.2.23.30.1.8
lcsSetupInterfacesEthernetPortsEntryPowerSaving OBJECT-TYPE
    SYNTAX     INTEGER {
                  eNo (0),
                  eYes (1)
            }
    MAX-ACCESS read-write
    STATUS     current
    DESCRIPTION
            "-- empty --"
    ::= { lcsSetupInterfacesEthernetPortsEntry 8 }

-- {COLUMN} 1.3.6.1.4.1.2356.11.2.23.30.1.9
lcsSetupInterfacesEthernetPortsEntryFlowControl OBJECT-TYPE
    SYNTAX     INTEGER {
                  eAuto (0),
                  eOn (1),
                  eOff (2)
            }
    MAX-ACCESS read-write
    STATUS     current
    DESCRIPTION
            "-- empty --"
    ::= { lcsSetupInterfacesEthernetPortsEntry 9 }

-- {NODE} 1.3.6.1.4.1.2356.11.2.23.40
lcsSetupInterfacesModem OBJECT IDENTIFIER ::= { lcsSetupInterfaces 40 }

-- {SCALAR} 1.3.6.1.4.1.2356.11.2.23.40.1
lcsSetupInterfacesModemRingCount OBJECT-TYPE
    SYNTAX     Integer32 (0..255)
    MAX-ACCESS read-write
    STATUS     current
    DESCRIPTION
            ""
    ::= { lcsSetupInterfacesModem 1 }

-- {SCALAR} 1.3.6.1.4.1.2356.11.2.23.40.2
lcsSetupInterfacesModemEchoOffCommand OBJECT-TYPE
    SYNTAX     DisplayString (SIZE(0..9))
    MAX-ACCESS read-write
    STATUS     current
    DESCRIPTION
            ""
    ::= { lcsSetupInterfacesModem 2 }

-- {SCALAR} 1.3.6.1.4.1.2356.11.2.23.40.3
lcsSetupInterfacesModemResetCommand OBJECT-TYPE
    SYNTAX     DisplayString (SIZE(0..9))
    MAX-ACCESS read-write
    STATUS     current
    DESCRIPTION
            ""
    ::= { lcsSetupInterfacesModem 3 }

-- {SCALAR} 1.3.6.1.4.1.2356.11.2.23.40.4
lcsSetupInterfacesModemInitCommand OBJECT-TYPE
    SYNTAX     DisplayString (SIZE(0..63))
    MAX-ACCESS read-write
    STATUS     current
    DESCRIPTION
            ""
    ::= { lcsSetupInterfacesModem 4 }

-- {SCALAR} 1.3.6.1.4.1.2356.11.2.23.40.5
lcsSetupInterfacesModemDialCommand OBJECT-TYPE
    SYNTAX     DisplayString (SIZE(0..31))
    MAX-ACCESS read-write
    STATUS     current
    DESCRIPTION
            ""
    ::= { lcsSetupInterfacesModem 5 }

-- {SCALAR} 1.3.6.1.4.1.2356.11.2.23.40.6
lcsSetupInterfacesModemRequestId OBJECT-TYPE
    SYNTAX     DisplayString (SIZE(0..9))
    MAX-ACCESS read-write
    STATUS     current
    DESCRIPTION
            ""
    ::= { lcsSetupInterfacesModem 6 }

-- {SCALAR} 1.3.6.1.4.1.2356.11.2.23.40.7
lcsSetupInterfacesModemAnswerCommand OBJECT-TYPE
    SYNTAX     DisplayString (SIZE(0..9))
    MAX-ACCESS read-write
    STATUS     current
    DESCRIPTION
            ""
    ::= { lcsSetupInterfacesModem 7 }

-- {SCALAR} 1.3.6.1.4.1.2356.11.2.23.40.8
lcsSetupInterfacesModemDisconnectCommand OBJECT-TYPE
    SYNTAX     DisplayString (SIZE(0..9))
    MAX-ACCESS read-write
    STATUS     current
    DESCRIPTION
            ""
    ::= { lcsSetupInterfacesModem 8 }

-- {SCALAR} 1.3.6.1.4.1.2356.11.2.23.40.9
lcsSetupInterfacesModemEscapeSequence OBJECT-TYPE
    SYNTAX     DisplayString (SIZE(0..9))
    MAX-ACCESS read-write
    STATUS     current
    DESCRIPTION
            ""
    ::= { lcsSetupInterfacesModem 9 }

-- {SCALAR} 1.3.6.1.4.1.2356.11.2.23.40.10
lcsSetupInterfacesModemEscapePromtDelayMs OBJECT-TYPE
    SYNTAX     Integer32 (0..65535)
    MAX-ACCESS read-write
    STATUS     current
    DESCRIPTION
            ""
    ::= { lcsSetupInterfacesModem 10 }

-- {SCALAR} 1.3.6.1.4.1.2356.11.2.23.40.11
lcsSetupInterfacesModemInitDial OBJECT-TYPE
    SYNTAX     DisplayString (SIZE(0..63))
    MAX-ACCESS read-write
    STATUS     current
    DESCRIPTION
            ""
    ::= { lcsSetupInterfacesModem 11 }

-- {SCALAR} 1.3.6.1.4.1.2356.11.2.23.40.12
lcsSetupInterfacesModemInitAnswer OBJECT-TYPE
    SYNTAX     DisplayString (SIZE(0..63))
    MAX-ACCESS read-write
    STATUS     current
    DESCRIPTION
            ""
    ::= { lcsSetupInterfacesModem 12 }

-- {SCALAR} 1.3.6.1.4.1.2356.11.2.23.40.13
lcsSetupInterfacesModemCycletimeAtPollS OBJECT-TYPE
    SYNTAX     Integer32 (0..255)
    MAX-ACCESS read-write
    STATUS     current
    DESCRIPTION
            ""
    ::= { lcsSetupInterfacesModem 13 }

-- {SCALAR} 1.3.6.1.4.1.2356.11.2.23.40.14
lcsSetupInterfacesModemAtPollCount OBJECT-TYPE
    SYNTAX     Integer32 (0..255)
    MAX-ACCESS read-write
    STATUS     current
    DESCRIPTION
            ""
    ::= { lcsSetupInterfacesModem 14 }

-- {NODE} 1.3.6.1.4.1.2356.11.2.23.41
lcsSetupInterfacesMobile OBJECT IDENTIFIER ::= { lcsSetupInterfaces 41 }

-- {TABLE} 1.3.6.1.4.1.2356.11.2.23.41.1
lcsSetupInterfacesMobileProfilesTable OBJECT-TYPE
    SYNTAX     SEQUENCE OF LcsSetupInterfacesMobileProfilesEntry
    MAX-ACCESS not-accessible
    STATUS     current
    DESCRIPTION
            ""
    ::= { lcsSetupInterfacesMobile 1 }

-- {ROW} 1.3.6.1.4.1.2356.11.2.23.41.1.1
lcsSetupInterfacesMobileProfilesEntry OBJECT-TYPE
    SYNTAX     LcsSetupInterfacesMobileProfilesEntry
    MAX-ACCESS not-accessible
    STATUS     current
    DESCRIPTION
            ""
    INDEX {
            lcsSetupInterfacesMobileProfilesEntryProfile
          }
    ::= { lcsSetupInterfacesMobileProfilesTable 1 }

LcsSetupInterfacesMobileProfilesEntry ::= SEQUENCE {
            lcsSetupInterfacesMobileProfilesEntryProfile DisplayString,
            lcsSetupInterfacesMobileProfilesEntryPin DisplayString,
            lcsSetupInterfacesMobileProfilesEntryApn DisplayString,
            lcsSetupInterfacesMobileProfilesEntryNetwork DisplayString,
            lcsSetupInterfacesMobileProfilesEntrySelect INTEGER,
            lcsSetupInterfacesMobileProfilesEntryMode INTEGER,
            lcsSetupInterfacesMobileProfilesEntryQosDownstreamDataRate Integer32,
            lcsSetupInterfacesMobileProfilesEntryQosUpstreamDataRate Integer32,
            lcsSetupInterfacesMobileProfilesEntryPdpType INTEGER,
            lcsSetupInterfacesMobileProfilesEntryLteBands BITS,
            lcsSetupInterfacesMobileProfilesEntryLteAttach INTEGER,
            lcsSetupInterfacesMobileProfilesEntrySimSlot INTEGER
    }

-- {COLUMN} 1.3.6.1.4.1.2356.11.2.23.41.1.1.1
lcsSetupInterfacesMobileProfilesEntryProfile OBJECT-TYPE
    SYNTAX     DisplayString (SIZE(0..15))
    MAX-ACCESS read-write
    STATUS     current
    DESCRIPTION
            ""
    ::= { lcsSetupInterfacesMobileProfilesEntry 1 }

-- {COLUMN} 1.3.6.1.4.1.2356.11.2.23.41.1.1.2
lcsSetupInterfacesMobileProfilesEntryPin OBJECT-TYPE
    SYNTAX     DisplayString (SIZE(0..8))
    MAX-ACCESS read-write
    STATUS     current
    DESCRIPTION
            ""
    ::= { lcsSetupInterfacesMobileProfilesEntry 2 }

-- {COLUMN} 1.3.6.1.4.1.2356.11.2.23.41.1.1.3
lcsSetupInterfacesMobileProfilesEntryApn OBJECT-TYPE
    SYNTAX     DisplayString (SIZE(0..47))
    MAX-ACCESS read-write
    STATUS     current
    DESCRIPTION
            ""
    ::= { lcsSetupInterfacesMobileProfilesEntry 3 }

-- {COLUMN} 1.3.6.1.4.1.2356.11.2.23.41.1.1.4
lcsSetupInterfacesMobileProfilesEntryNetwork OBJECT-TYPE
    SYNTAX     DisplayString (SIZE(0..16))
    MAX-ACCESS read-write
    STATUS     current
    DESCRIPTION
            ""
    ::= { lcsSetupInterfacesMobileProfilesEntry 4 }

-- {COLUMN} 1.3.6.1.4.1.2356.11.2.23.41.1.1.5
lcsSetupInterfacesMobileProfilesEntrySelect OBJECT-TYPE
    SYNTAX     INTEGER {
                  eAuto (0),
                  eManual (1),
                  eSAuto (2),
                  eQuality (4)
            }
    MAX-ACCESS read-write
    STATUS     current
    DESCRIPTION
            ""
    ::= { lcsSetupInterfacesMobileProfilesEntry 5 }

-- {COLUMN} 1.3.6.1.4.1.2356.11.2.23.41.1.1.6
lcsSetupInterfacesMobileProfilesEntryMode OBJECT-TYPE
    SYNTAX     INTEGER {
                  eAuto (0),
                  e3g (1),
                  e2g (2),
                  e4g (8),
                  e3g2g (11),
                  e4g3g (12),
                  e4g2g (13)
            }
    MAX-ACCESS read-write
    STATUS     current
    DESCRIPTION
            ""
    ::= { lcsSetupInterfacesMobileProfilesEntry 6 }

-- {COLUMN} 1.3.6.1.4.1.2356.11.2.23.41.1.1.7
lcsSetupInterfacesMobileProfilesEntryQosDownstreamDataRate OBJECT-TYPE
    SYNTAX     Integer32 (0..2147483647)
    MAX-ACCESS read-write
    STATUS     current
    DESCRIPTION
            ""
    ::= { lcsSetupInterfacesMobileProfilesEntry 7 }

-- {COLUMN} 1.3.6.1.4.1.2356.11.2.23.41.1.1.8
lcsSetupInterfacesMobileProfilesEntryQosUpstreamDataRate OBJECT-TYPE
    SYNTAX     Integer32 (0..2147483647)
    MAX-ACCESS read-write
    STATUS     current
    DESCRIPTION
            ""
    ::= { lcsSetupInterfacesMobileProfilesEntry 8 }

-- {COLUMN} 1.3.6.1.4.1.2356.11.2.23.41.1.1.9
lcsSetupInterfacesMobileProfilesEntryPdpType OBJECT-TYPE
    SYNTAX     INTEGER {
                  eIpv4 (0),
                  eIpv6 (2),
                  eIpv4v6 (3)
            }
    MAX-ACCESS read-write
    STATUS     current
    DESCRIPTION
            "-- empty --"
    ::= { lcsSetupInterfacesMobileProfilesEntry 9 }

-- {COLUMN} 1.3.6.1.4.1.2356.11.2.23.41.1.1.10
lcsSetupInterfacesMobileProfilesEntryLteBands OBJECT-TYPE
    SYNTAX     BITS {
                  eB412600 (16),
                  eB302300 (17),
                  eB29700 (18),
                  eB26800 (19),
                  eB251900 (20),
                  eB13700 (21),
                  eB12700 (22),
                  eB5850 (23),
                  eB42100 (24),
                  eB21900 (25),
                  eB20800 (26),
                  eB8900 (27),
                  eB72600 (28),
                  eB31800 (29),
                  eB12100 (30),
                  eAll (31)
            }
    MAX-ACCESS read-write
    STATUS     current
    DESCRIPTION
            "-- empty --"
    ::= { lcsSetupInterfacesMobileProfilesEntry 10 }

-- {COLUMN} 1.3.6.1.4.1.2356.11.2.23.41.1.1.11
lcsSetupInterfacesMobileProfilesEntryLteAttach OBJECT-TYPE
    SYNTAX     INTEGER {
                  eImmediate (0),
                  eDelayed (1)
            }
    MAX-ACCESS read-write
    STATUS     current
    DESCRIPTION
            "-- empty --"
    ::= { lcsSetupInterfacesMobileProfilesEntry 11 }

-- {COLUMN} 1.3.6.1.4.1.2356.11.2.23.41.1.1.12
lcsSetupInterfacesMobileProfilesEntrySimSlot OBJECT-TYPE
    SYNTAX     INTEGER {
                  eDisabled (0),
                  eSlot1 (1),
                  eSlot2 (2)
            }
    MAX-ACCESS read-write
    STATUS     current
    DESCRIPTION
            "-- empty --"
    ::= { lcsSetupInterfacesMobileProfilesEntry 12 }

-- {SCALAR} 1.3.6.1.4.1.2356.11.2.23.41.2
lcsSetupInterfacesMobileScanNetworks OBJECT-TYPE
    SYNTAX     DisplayString
    MAX-ACCESS read-write
    STATUS     current
    DESCRIPTION
            ""
    ::= { lcsSetupInterfacesMobile 2 }

-- {SCALAR} 1.3.6.1.4.1.2356.11.2.23.41.3
lcsSetupInterfacesMobileInputPuk OBJECT-TYPE
    SYNTAX     DisplayString
    MAX-ACCESS read-write
    STATUS     current
    DESCRIPTION
            ""
    ::= { lcsSetupInterfacesMobile 3 }

-- {SCALAR} 1.3.6.1.4.1.2356.11.2.23.41.4
lcsSetupInterfacesMobileConnectMonitoring OBJECT-TYPE
    SYNTAX     INTEGER {
                  eNone (0),
                  ePpp (1),
                  ePppIp (3)
            }
    MAX-ACCESS read-only
    STATUS     current
    DESCRIPTION
            ""
    ::= { lcsSetupInterfacesMobile 4 }

-- {SCALAR} 1.3.6.1.4.1.2356.11.2.23.41.5
lcsSetupInterfacesMobileTries OBJECT-TYPE
    SYNTAX     Integer32 (0..255)
    MAX-ACCESS read-only
    STATUS     current
    DESCRIPTION
            ""
    ::= { lcsSetupInterfacesMobile 5 }

-- {SCALAR} 1.3.6.1.4.1.2356.11.2.23.41.6
lcsSetupInterfacesMobileHistoryIntervalSec OBJECT-TYPE
    SYNTAX     Integer32 (0..2147483647)
    MAX-ACCESS read-write
    STATUS     current
    DESCRIPTION
            ""
    ::= { lcsSetupInterfacesMobile 6 }

-- {SCALAR} 1.3.6.1.4.1.2356.11.2.23.41.7
lcsSetupInterfacesMobileSyslogEnabled OBJECT-TYPE
    SYNTAX     INTEGER {
                  eNo (0),
                  eYes (1)
            }
    MAX-ACCESS read-write
    STATUS     current
    DESCRIPTION
            ""
    ::= { lcsSetupInterfacesMobile 7 }

-- {SCALAR} 1.3.6.1.4.1.2356.11.2.23.41.8
lcsSetupInterfacesMobileEnableHsupa OBJECT-TYPE
    SYNTAX     INTEGER {
                  eNo (0),
                  eYes (1)
            }
    MAX-ACCESS read-write
    STATUS     current
    DESCRIPTION
            ""
    ::= { lcsSetupInterfacesMobile 8 }

-- {SCALAR} 1.3.6.1.4.1.2356.11.2.23.41.9
lcsSetupInterfacesMobileSignalCheckIntervallMin OBJECT-TYPE
    SYNTAX     Integer32 (0..2147483647)
    MAX-ACCESS read-write
    STATUS     current
    DESCRIPTION
            ""
    ::= { lcsSetupInterfacesMobile 9 }

-- {SCALAR} 1.3.6.1.4.1.2356.11.2.23.41.10
lcsSetupInterfacesMobileTreshold3gTo2gDb OBJECT-TYPE
    SYNTAX     Integer32 (-2147483648..2147483647)
    MAX-ACCESS read-write
    STATUS     current
    DESCRIPTION
            ""
    ::= { lcsSetupInterfacesMobile 10 }

-- {SCALAR} 1.3.6.1.4.1.2356.11.2.23.41.11
lcsSetupInterfacesMobileCheckWhileConnected OBJECT-TYPE
    SYNTAX     INTEGER {
                  eNo (0),
                  eYes (1)
            }
    MAX-ACCESS read-write
    STATUS     current
    DESCRIPTION
            ""
    ::= { lcsSetupInterfacesMobile 11 }

-- {SCALAR} 1.3.6.1.4.1.2356.11.2.23.41.12
lcsSetupInterfacesMobilePinChange OBJECT-TYPE
    SYNTAX     DisplayString
    MAX-ACCESS read-write
    STATUS     current
    DESCRIPTION
            "-- empty --"
    ::= { lcsSetupInterfacesMobile 12 }

-- {TABLE} 1.3.6.1.4.1.2356.11.2.23.41.13
lcsSetupInterfacesMobileSignalThresholdsTable OBJECT-TYPE
    SYNTAX     SEQUENCE OF LcsSetupInterfacesMobileSignalThresholdsEntry
    MAX-ACCESS not-accessible
    STATUS     current
    DESCRIPTION
            "-- empty --"
    ::= { lcsSetupInterfacesMobile 13 }

-- {ROW} 1.3.6.1.4.1.2356.11.2.23.41.13.1
lcsSetupInterfacesMobileSignalThresholdsEntry OBJECT-TYPE
    SYNTAX     LcsSetupInterfacesMobileSignalThresholdsEntry
    MAX-ACCESS not-accessible
    STATUS     current
    DESCRIPTION
            ""
    INDEX {
            lcsSetupInterfacesMobileSignalThresholdsEntryIndex
          }
    ::= { lcsSetupInterfacesMobileSignalThresholdsTable 1 }

LcsSetupInterfacesMobileSignalThresholdsEntry ::= SEQUENCE {
            lcsSetupInterfacesMobileSignalThresholdsEntryIndex Integer32,
            lcsSetupInterfacesMobileSignalThresholdsEntryStatus INTEGER,
            lcsSetupInterfacesMobileSignalThresholdsEntryRsrp Integer32,
            lcsSetupInterfacesMobileSignalThresholdsEntryRscp Integer32,
            lcsSetupInterfacesMobileSignalThresholdsEntryRssi Integer32,
            lcsSetupInterfacesMobileSignalThresholdsEntryMcc DisplayString,
            lcsSetupInterfacesMobileSignalThresholdsEntryMnc DisplayString
    }

-- {COLUMN} 1.3.6.1.4.1.2356.11.2.23.41.13.1.1
lcsSetupInterfacesMobileSignalThresholdsEntryIndex OBJECT-TYPE
    SYNTAX     Integer32 (0..2147483647)
    MAX-ACCESS read-only
    STATUS     current
    DESCRIPTION
            "-- empty --"
    ::= { lcsSetupInterfacesMobileSignalThresholdsEntry 1 }

-- {COLUMN} 1.3.6.1.4.1.2356.11.2.23.41.13.1.2
lcsSetupInterfacesMobileSignalThresholdsEntryStatus OBJECT-TYPE
    SYNTAX     INTEGER {
                  eActive (1),
                  eNotinservice (2),
                  eDestroy (6)
            }
    MAX-ACCESS read-write
    STATUS     current
    DESCRIPTION
            "-- empty --"
    ::= { lcsSetupInterfacesMobileSignalThresholdsEntry 2 }

-- {COLUMN} 1.3.6.1.4.1.2356.11.2.23.41.13.1.3
lcsSetupInterfacesMobileSignalThresholdsEntryRsrp OBJECT-TYPE
    SYNTAX     Integer32 (-2147483648..2147483647)
    MAX-ACCESS read-write
    STATUS     current
    DESCRIPTION
            "-- empty --"
    ::= { lcsSetupInterfacesMobileSignalThresholdsEntry 3 }

-- {COLUMN} 1.3.6.1.4.1.2356.11.2.23.41.13.1.4
lcsSetupInterfacesMobileSignalThresholdsEntryRscp OBJECT-TYPE
    SYNTAX     Integer32 (-2147483648..2147483647)
    MAX-ACCESS read-write
    STATUS     current
    DESCRIPTION
            "-- empty --"
    ::= { lcsSetupInterfacesMobileSignalThresholdsEntry 4 }

-- {COLUMN} 1.3.6.1.4.1.2356.11.2.23.41.13.1.5
lcsSetupInterfacesMobileSignalThresholdsEntryRssi OBJECT-TYPE
    SYNTAX     Integer32 (-2147483648..2147483647)
    MAX-ACCESS read-write
    STATUS     current
    DESCRIPTION
            "-- empty --"
    ::= { lcsSetupInterfacesMobileSignalThresholdsEntry 5 }

-- {COLUMN} 1.3.6.1.4.1.2356.11.2.23.41.13.1.6
lcsSetupInterfacesMobileSignalThresholdsEntryMcc OBJECT-TYPE
    SYNTAX     DisplayString (SIZE(0..3))
    MAX-ACCESS read-write
    STATUS     current
    DESCRIPTION
            "-- empty --"
    ::= { lcsSetupInterfacesMobileSignalThresholdsEntry 6 }

-- {COLUMN} 1.3.6.1.4.1.2356.11.2.23.41.13.1.7
lcsSetupInterfacesMobileSignalThresholdsEntryMnc OBJECT-TYPE
    SYNTAX     DisplayString (SIZE(0..3))
    MAX-ACCESS read-write
    STATUS     current
    DESCRIPTION
            "-- empty --"
    ::= { lcsSetupInterfacesMobileSignalThresholdsEntry 7 }

-- {TABLE} 1.3.6.1.4.1.2356.11.2.23.51
lcsSetupInterfacesAnalogTable OBJECT-TYPE
    SYNTAX     SEQUENCE OF LcsSetupInterfacesAnalogEntry
    MAX-ACCESS not-accessible
    STATUS     current
    DESCRIPTION
            "-- empty --"
    ::= { lcsSetupInterfaces 51 }

-- {ROW} 1.3.6.1.4.1.2356.11.2.23.51.1
lcsSetupInterfacesAnalogEntry OBJECT-TYPE
    SYNTAX     LcsSetupInterfacesAnalogEntry
    MAX-ACCESS not-accessible
    STATUS     current
    DESCRIPTION
            ""
    INDEX {
            lcsSetupInterfacesAnalogEntryIfc
          }
    ::= { lcsSetupInterfacesAnalogTable 1 }

LcsSetupInterfacesAnalogEntry ::= SEQUENCE {
            lcsSetupInterfacesAnalogEntryIfc INTEGER,
            lcsSetupInterfacesAnalogEntryOperating INTEGER,
            lcsSetupInterfacesAnalogEntryMicrophoneGain Integer32,
            lcsSetupInterfacesAnalogEntrySpeakerGain Integer32,
            lcsSetupInterfacesAnalogEntryLineDisruption Integer32
    }

-- {COLUMN} 1.3.6.1.4.1.2356.11.2.23.51.1.1
lcsSetupInterfacesAnalogEntryIfc OBJECT-TYPE
    SYNTAX     INTEGER {
                  eAnalog1 (16),
                  eAnalog2 (17),
                  eAnalog3 (18),
                  eAnalog4 (19)
            }
    MAX-ACCESS read-write
    STATUS     current
    DESCRIPTION
            "-- empty --"
    ::= { lcsSetupInterfacesAnalogEntry 1 }

-- {COLUMN} 1.3.6.1.4.1.2356.11.2.23.51.1.2
lcsSetupInterfacesAnalogEntryOperating OBJECT-TYPE
    SYNTAX     INTEGER {
                  eYes (0),
                  eNo (1)
            }
    MAX-ACCESS read-write
    STATUS     current
    DESCRIPTION
            "-- empty --"
    ::= { lcsSetupInterfacesAnalogEntry 2 }

-- {COLUMN} 1.3.6.1.4.1.2356.11.2.23.51.1.3
lcsSetupInterfacesAnalogEntryMicrophoneGain OBJECT-TYPE
    SYNTAX     Integer32 (-32768..32767)
    MAX-ACCESS read-write
    STATUS     current
    DESCRIPTION
            "-- empty --"
    ::= { lcsSetupInterfacesAnalogEntry 3 }

-- {COLUMN} 1.3.6.1.4.1.2356.11.2.23.51.1.4
lcsSetupInterfacesAnalogEntrySpeakerGain OBJECT-TYPE
    SYNTAX     Integer32 (-32768..32767)
    MAX-ACCESS read-write
    STATUS     current
    DESCRIPTION
            "-- empty --"
    ::= { lcsSetupInterfacesAnalogEntry 4 }

-- {COLUMN} 1.3.6.1.4.1.2356.11.2.23.51.1.5
lcsSetupInterfacesAnalogEntryLineDisruption OBJECT-TYPE
    SYNTAX     Integer32 (0..255)
    MAX-ACCESS read-write
    STATUS     current
    DESCRIPTION
            "-- empty --"
    ::= { lcsSetupInterfacesAnalogEntry 5 }

-- {NODE} 1.3.6.1.4.1.2356.11.2.23.52
lcsSetupInterfacesMonitorCapacity OBJECT IDENTIFIER ::= { lcsSetupInterfaces 52 }

-- {SCALAR} 1.3.6.1.4.1.2356.11.2.23.52.1
lcsSetupInterfacesMonitorCapacityWarning OBJECT-TYPE
    SYNTAX     INTEGER {
                  eNo (0),
                  eYes (1)
            }
    MAX-ACCESS read-write
    STATUS     current
    DESCRIPTION
            "-- empty --"
    ::= { lcsSetupInterfacesMonitorCapacity 1 }

-- {SCALAR} 1.3.6.1.4.1.2356.11.2.23.52.2
lcsSetupInterfacesMonitorCapacityEMail OBJECT-TYPE
    SYNTAX     DisplayString (SIZE(0..150))
    MAX-ACCESS read-write
    STATUS     current
    DESCRIPTION
            "-- empty --"
    ::= { lcsSetupInterfacesMonitorCapacity 2 }

-- {NODE} 1.3.6.1.4.1.2356.11.2.23.90
lcsSetupInterfacesBluetooth OBJECT IDENTIFIER ::= { lcsSetupInterfaces 90 }

-- {NODE} 1.3.6.1.4.1.2356.11.2.23.90.1
lcsSetupInterfacesBluetoothIbeacon OBJECT IDENTIFIER ::= { lcsSetupInterfacesBluetooth 1 }

-- {SCALAR} 1.3.6.1.4.1.2356.11.2.23.90.1.1
lcsSetupInterfacesBluetoothIbeaconOperating OBJECT-TYPE
    SYNTAX     INTEGER {
                  eOff (0),
                  eManual (1),
                  eManaged (2)
            }
    MAX-ACCESS read-write
    STATUS     current
    DESCRIPTION
            "-- empty --"
    ::= { lcsSetupInterfacesBluetoothIbeacon 1 }

-- {SCALAR} 1.3.6.1.4.1.2356.11.2.23.90.1.2
lcsSetupInterfacesBluetoothIbeaconUuid OBJECT-TYPE
    SYNTAX     DisplayString (SIZE(0..36))
    MAX-ACCESS read-write
    STATUS     current
    DESCRIPTION
            "-- empty --"
    ::= { lcsSetupInterfacesBluetoothIbeacon 2 }

-- {SCALAR} 1.3.6.1.4.1.2356.11.2.23.90.1.3
lcsSetupInterfacesBluetoothIbeaconMajor OBJECT-TYPE
    SYNTAX     Integer32 (0..65535)
    MAX-ACCESS read-write
    STATUS     current
    DESCRIPTION
            "-- empty --"
    ::= { lcsSetupInterfacesBluetoothIbeacon 3 }

-- {SCALAR} 1.3.6.1.4.1.2356.11.2.23.90.1.4
lcsSetupInterfacesBluetoothIbeaconMinor OBJECT-TYPE
    SYNTAX     Integer32 (0..65535)
    MAX-ACCESS read-write
    STATUS     current
    DESCRIPTION
            "-- empty --"
    ::= { lcsSetupInterfacesBluetoothIbeacon 4 }

-- {SCALAR} 1.3.6.1.4.1.2356.11.2.23.90.1.5
lcsSetupInterfacesBluetoothIbeaconMeasuredPowerOffset OBJECT-TYPE
    SYNTAX     Integer32 (-128..127)
    MAX-ACCESS read-write
    STATUS     current
    DESCRIPTION
            "-- empty --"
    ::= { lcsSetupInterfacesBluetoothIbeacon 5 }

-- {SCALAR} 1.3.6.1.4.1.2356.11.2.23.90.1.6
lcsSetupInterfacesBluetoothIbeaconTransmitPower OBJECT-TYPE
    SYNTAX     INTEGER {
                  eLow (0),
                  eMedium (1),
                  eHigh (2)
            }
    MAX-ACCESS read-write
    STATUS     current
    DESCRIPTION
            "-- empty --"
    ::= { lcsSetupInterfacesBluetoothIbeacon 6 }

-- {SCALAR} 1.3.6.1.4.1.2356.11.2.23.90.1.7
lcsSetupInterfacesBluetoothIbeaconChannelS OBJECT-TYPE
    SYNTAX     BITS {
                  e2480mhz (5),
                  e2426mhz (6),
                  e2402mhz (7)
            }
    MAX-ACCESS read-write
    STATUS     current
    DESCRIPTION
            "-- empty --"
    ::= { lcsSetupInterfacesBluetoothIbeacon 7 }

-- {SCALAR} 1.3.6.1.4.1.2356.11.2.23.90.1.8
lcsSetupInterfacesBluetoothIbeaconCoexistence OBJECT-TYPE
    SYNTAX     INTEGER {
                  eNo (0),
                  eYes (1)
            }
    MAX-ACCESS read-write
    STATUS     current
    DESCRIPTION
            "-- empty --"
    ::= { lcsSetupInterfacesBluetoothIbeacon 8 }

-- {NODE} 1.3.6.1.4.1.2356.11.2.24
lcsSetupPublicSpotModule OBJECT IDENTIFIER ::= { lcsSetup 24 }

-- {SCALAR} 1.3.6.1.4.1.2356.11.2.24.1
lcsSetupPublicSpotModuleAuthenticationMode OBJECT-TYPE
    SYNTAX     INTEGER {
                  eNone (0),
                  eUserPlusPassword (1),
                  eMacPlusUserPlusPassword (2),
                  eEMail (3),
                  eEMail2sms (4),
                  eLoginViaAgreement (5)
            }
    MAX-ACCESS read-write
    STATUS     current
    DESCRIPTION
            ""
    ::= { lcsSetupPublicSpotModule 1 }

-- {TABLE} 1.3.6.1.4.1.2356.11.2.24.2
lcsSetupPublicSpotModuleUserTableTable OBJECT-TYPE
    SYNTAX     SEQUENCE OF LcsSetupPublicSpotModuleUserTableEntry
    MAX-ACCESS not-accessible
    STATUS     current
    DESCRIPTION
            ""
    ::= { lcsSetupPublicSpotModule 2 }

-- {ROW} 1.3.6.1.4.1.2356.11.2.24.2.1
lcsSetupPublicSpotModuleUserTableEntry OBJECT-TYPE
    SYNTAX     LcsSetupPublicSpotModuleUserTableEntry
    MAX-ACCESS not-accessible
    STATUS     current
    DESCRIPTION
            ""
    INDEX {
            lcsSetupPublicSpotModuleUserTableEntryName
          }
    ::= { lcsSetupPublicSpotModuleUserTableTable 1 }

LcsSetupPublicSpotModuleUserTableEntry ::= SEQUENCE {
            lcsSetupPublicSpotModuleUserTableEntryName DisplayString,
            lcsSetupPublicSpotModuleUserTableEntryPassword DisplayString,
            lcsSetupPublicSpotModuleUserTableEntryMacAddress MacAddress,
            lcsSetupPublicSpotModuleUserTableEntryComment DisplayString,
            lcsSetupPublicSpotModuleUserTableEntryProvider DisplayString,
            lcsSetupPublicSpotModuleUserTableEntryExpiry DisplayString
    }

-- {COLUMN} 1.3.6.1.4.1.2356.11.2.24.2.1.1
lcsSetupPublicSpotModuleUserTableEntryName OBJECT-TYPE
    SYNTAX     DisplayString (SIZE(0..64))
    MAX-ACCESS read-write
    STATUS     current
    DESCRIPTION
            ""
    ::= { lcsSetupPublicSpotModuleUserTableEntry 1 }

-- {COLUMN} 1.3.6.1.4.1.2356.11.2.24.2.1.2
lcsSetupPublicSpotModuleUserTableEntryPassword OBJECT-TYPE
    SYNTAX     DisplayString (SIZE(0..16))
    MAX-ACCESS read-write
    STATUS     current
    DESCRIPTION
            ""
    ::= { lcsSetupPublicSpotModuleUserTableEntry 2 }

-- {COLUMN} 1.3.6.1.4.1.2356.11.2.24.2.1.3
lcsSetupPublicSpotModuleUserTableEntryMacAddress OBJECT-TYPE
    SYNTAX     MacAddress
    MAX-ACCESS read-write
    STATUS     current
    DESCRIPTION
            ""
    ::= { lcsSetupPublicSpotModuleUserTableEntry 3 }

-- {COLUMN} 1.3.6.1.4.1.2356.11.2.24.2.1.4
lcsSetupPublicSpotModuleUserTableEntryComment OBJECT-TYPE
    SYNTAX     DisplayString (SIZE(0..80))
    MAX-ACCESS read-write
    STATUS     current
    DESCRIPTION
            ""
    ::= { lcsSetupPublicSpotModuleUserTableEntry 4 }

-- {COLUMN} 1.3.6.1.4.1.2356.11.2.24.2.1.5
lcsSetupPublicSpotModuleUserTableEntryProvider OBJECT-TYPE
    SYNTAX     DisplayString (SIZE(0..16))
    MAX-ACCESS read-write
    STATUS     current
    DESCRIPTION
            ""
    ::= { lcsSetupPublicSpotModuleUserTableEntry 5 }

-- {COLUMN} 1.3.6.1.4.1.2356.11.2.24.2.1.6
lcsSetupPublicSpotModuleUserTableEntryExpiry OBJECT-TYPE
    SYNTAX     DisplayString (SIZE(0..21))
    MAX-ACCESS read-write
    STATUS     current
    DESCRIPTION
            ""
    ::= { lcsSetupPublicSpotModuleUserTableEntry 6 }

-- {TABLE} 1.3.6.1.4.1.2356.11.2.24.3
lcsSetupPublicSpotModuleProviderTableTable OBJECT-TYPE
    SYNTAX     SEQUENCE OF LcsSetupPublicSpotModuleProviderTableEntry
    MAX-ACCESS not-accessible
    STATUS     current
    DESCRIPTION
            ""
    ::= { lcsSetupPublicSpotModule 3 }

-- {ROW} 1.3.6.1.4.1.2356.11.2.24.3.1
lcsSetupPublicSpotModuleProviderTableEntry OBJECT-TYPE
    SYNTAX     LcsSetupPublicSpotModuleProviderTableEntry
    MAX-ACCESS not-accessible
    STATUS     current
    DESCRIPTION
            ""
    INDEX {
            lcsSetupPublicSpotModuleProviderTableEntryProvider
          }
    ::= { lcsSetupPublicSpotModuleProviderTableTable 1 }

LcsSetupPublicSpotModuleProviderTableEntry ::= SEQUENCE {
            lcsSetupPublicSpotModuleProviderTableEntryProvider DisplayString,
            lcsSetupPublicSpotModuleProviderTableEntryAuthServerAddress IpAddress,
            lcsSetupPublicSpotModuleProviderTableEntryAuthServerPort Integer32,
            lcsSetupPublicSpotModuleProviderTableEntryAuthServerSecret DisplayString,
            lcsSetupPublicSpotModuleProviderTableEntryAccServerAddress IpAddress,
            lcsSetupPublicSpotModuleProviderTableEntryAccServerPort Integer32,
            lcsSetupPublicSpotModuleProviderTableEntryAccServerSecret DisplayString,
            lcsSetupPublicSpotModuleProviderTableEntryBackup DisplayString,
            lcsSetupPublicSpotModuleProviderTableEntryAuthServerLoopbackAddr DisplayString,
            lcsSetupPublicSpotModuleProviderTableEntryAccServerLoopbackAddr DisplayString,
            lcsSetupPublicSpotModuleProviderTableEntryAuthServerProtocol INTEGER,
            lcsSetupPublicSpotModuleProviderTableEntryAccServerProtocol INTEGER,
            lcsSetupPublicSpotModuleProviderTableEntryAuthServerHostname DisplayString,
            lcsSetupPublicSpotModuleProviderTableEntryAccServerHostname DisplayString,
            lcsSetupPublicSpotModuleProviderTableEntryAuthAttributeValues DisplayString,
            lcsSetupPublicSpotModuleProviderTableEntryAccAttributeValues DisplayString
    }

-- {COLUMN} 1.3.6.1.4.1.2356.11.2.24.3.1.1
lcsSetupPublicSpotModuleProviderTableEntryProvider OBJECT-TYPE
    SYNTAX     DisplayString (SIZE(0..16))
    MAX-ACCESS read-write
    STATUS     current
    DESCRIPTION
            ""
    ::= { lcsSetupPublicSpotModuleProviderTableEntry 1 }

-- {COLUMN} 1.3.6.1.4.1.2356.11.2.24.3.1.2
lcsSetupPublicSpotModuleProviderTableEntryAuthServerAddress OBJECT-TYPE
    SYNTAX     IpAddress
    MAX-ACCESS read-write
    STATUS     current
    DESCRIPTION
            ""
    ::= { lcsSetupPublicSpotModuleProviderTableEntry 2 }

-- {COLUMN} 1.3.6.1.4.1.2356.11.2.24.3.1.3
lcsSetupPublicSpotModuleProviderTableEntryAuthServerPort OBJECT-TYPE
    SYNTAX     Integer32 (0..65535)
    MAX-ACCESS read-write
    STATUS     current
    DESCRIPTION
            ""
    ::= { lcsSetupPublicSpotModuleProviderTableEntry 3 }

-- {COLUMN} 1.3.6.1.4.1.2356.11.2.24.3.1.4
lcsSetupPublicSpotModuleProviderTableEntryAuthServerSecret OBJECT-TYPE
    SYNTAX     DisplayString (SIZE(0..64))
    MAX-ACCESS read-write
    STATUS     current
    DESCRIPTION
            ""
    ::= { lcsSetupPublicSpotModuleProviderTableEntry 4 }

-- {COLUMN} 1.3.6.1.4.1.2356.11.2.24.3.1.5
lcsSetupPublicSpotModuleProviderTableEntryAccServerAddress OBJECT-TYPE
    SYNTAX     IpAddress
    MAX-ACCESS read-write
    STATUS     current
    DESCRIPTION
            ""
    ::= { lcsSetupPublicSpotModuleProviderTableEntry 5 }

-- {COLUMN} 1.3.6.1.4.1.2356.11.2.24.3.1.6
lcsSetupPublicSpotModuleProviderTableEntryAccServerPort OBJECT-TYPE
    SYNTAX     Integer32 (0..65535)
    MAX-ACCESS read-write
    STATUS     current
    DESCRIPTION
            ""
    ::= { lcsSetupPublicSpotModuleProviderTableEntry 6 }

-- {COLUMN} 1.3.6.1.4.1.2356.11.2.24.3.1.7
lcsSetupPublicSpotModuleProviderTableEntryAccServerSecret OBJECT-TYPE
    SYNTAX     DisplayString (SIZE(0..64))
    MAX-ACCESS read-write
    STATUS     current
    DESCRIPTION
            ""
    ::= { lcsSetupPublicSpotModuleProviderTableEntry 7 }

-- {COLUMN} 1.3.6.1.4.1.2356.11.2.24.3.1.8
lcsSetupPublicSpotModuleProviderTableEntryBackup OBJECT-TYPE
    SYNTAX     DisplayString (SIZE(0..16))
    MAX-ACCESS read-write
    STATUS     current
    DESCRIPTION
            ""
    ::= { lcsSetupPublicSpotModuleProviderTableEntry 8 }

-- {COLUMN} 1.3.6.1.4.1.2356.11.2.24.3.1.9
lcsSetupPublicSpotModuleProviderTableEntryAuthServerLoopbackAddr OBJECT-TYPE
    SYNTAX     DisplayString (SIZE(0..16))
    MAX-ACCESS read-write
    STATUS     current
    DESCRIPTION
            ""
    ::= { lcsSetupPublicSpotModuleProviderTableEntry 9 }

-- {COLUMN} 1.3.6.1.4.1.2356.11.2.24.3.1.10
lcsSetupPublicSpotModuleProviderTableEntryAccServerLoopbackAddr OBJECT-TYPE
    SYNTAX     DisplayString (SIZE(0..16))
    MAX-ACCESS read-write
    STATUS     current
    DESCRIPTION
            ""
    ::= { lcsSetupPublicSpotModuleProviderTableEntry 10 }

-- {COLUMN} 1.3.6.1.4.1.2356.11.2.24.3.1.11
lcsSetupPublicSpotModuleProviderTableEntryAuthServerProtocol OBJECT-TYPE
    SYNTAX     INTEGER {
                  eRadius (0),
                  eRadsec (1)
            }
    MAX-ACCESS read-write
    STATUS     current
    DESCRIPTION
            ""
    ::= { lcsSetupPublicSpotModuleProviderTableEntry 11 }

-- {COLUMN} 1.3.6.1.4.1.2356.11.2.24.3.1.12
lcsSetupPublicSpotModuleProviderTableEntryAccServerProtocol OBJECT-TYPE
    SYNTAX     INTEGER {
                  eRadius (0),
                  eRadsec (1)
            }
    MAX-ACCESS read-write
    STATUS     current
    DESCRIPTION
            ""
    ::= { lcsSetupPublicSpotModuleProviderTableEntry 12 }

-- {COLUMN} 1.3.6.1.4.1.2356.11.2.24.3.1.13
lcsSetupPublicSpotModuleProviderTableEntryAuthServerHostname OBJECT-TYPE
    SYNTAX     DisplayString (SIZE(0..64))
    MAX-ACCESS read-write
    STATUS     current
    DESCRIPTION
            "-- empty --"
    ::= { lcsSetupPublicSpotModuleProviderTableEntry 13 }

-- {COLUMN} 1.3.6.1.4.1.2356.11.2.24.3.1.14
lcsSetupPublicSpotModuleProviderTableEntryAccServerHostname OBJECT-TYPE
    SYNTAX     DisplayString (SIZE(0..64))
    MAX-ACCESS read-write
    STATUS     current
    DESCRIPTION
            "-- empty --"
    ::= { lcsSetupPublicSpotModuleProviderTableEntry 14 }

-- {COLUMN} 1.3.6.1.4.1.2356.11.2.24.3.1.15
lcsSetupPublicSpotModuleProviderTableEntryAuthAttributeValues OBJECT-TYPE
    SYNTAX     DisplayString (SIZE(0..251))
    MAX-ACCESS read-write
    STATUS     current
    DESCRIPTION
            "-- empty --"
    ::= { lcsSetupPublicSpotModuleProviderTableEntry 15 }

-- {COLUMN} 1.3.6.1.4.1.2356.11.2.24.3.1.16
lcsSetupPublicSpotModuleProviderTableEntryAccAttributeValues OBJECT-TYPE
    SYNTAX     DisplayString (SIZE(0..251))
    MAX-ACCESS read-write
    STATUS     current
    DESCRIPTION
            "-- empty --"
    ::= { lcsSetupPublicSpotModuleProviderTableEntry 16 }

-- {SCALAR} 1.3.6.1.4.1.2356.11.2.24.5
lcsSetupPublicSpotModuleTrafficLimitBytes OBJECT-TYPE
    SYNTAX     Integer32 (0..2147483647)
    MAX-ACCESS read-write
    STATUS     current
    DESCRIPTION
            ""
    ::= { lcsSetupPublicSpotModule 5 }

-- {SCALAR} 1.3.6.1.4.1.2356.11.2.24.6
lcsSetupPublicSpotModuleServerSubdir OBJECT-TYPE
    SYNTAX     DisplayString (SIZE(0..127))
    MAX-ACCESS read-write
    STATUS     current
    DESCRIPTION
            ""
    ::= { lcsSetupPublicSpotModule 6 }

-- {SCALAR} 1.3.6.1.4.1.2356.11.2.24.7
lcsSetupPublicSpotModuleAccountingCycle OBJECT-TYPE
    SYNTAX     Integer32 (0..2147483647)
    MAX-ACCESS read-write
    STATUS     current
    DESCRIPTION
            ""
    ::= { lcsSetupPublicSpotModule 7 }

-- {TABLE} 1.3.6.1.4.1.2356.11.2.24.8
lcsSetupPublicSpotModulePageTableTable OBJECT-TYPE
    SYNTAX     SEQUENCE OF LcsSetupPublicSpotModulePageTableEntry
    MAX-ACCESS not-accessible
    STATUS     current
    DESCRIPTION
            ""
    ::= { lcsSetupPublicSpotModule 8 }

-- {ROW} 1.3.6.1.4.1.2356.11.2.24.8.1
lcsSetupPublicSpotModulePageTableEntry OBJECT-TYPE
    SYNTAX     LcsSetupPublicSpotModulePageTableEntry
    MAX-ACCESS not-accessible
    STATUS     current
    DESCRIPTION
            ""
    INDEX {
            lcsSetupPublicSpotModulePageTableEntryPage
          }
    ::= { lcsSetupPublicSpotModulePageTableTable 1 }

LcsSetupPublicSpotModulePageTableEntry ::= SEQUENCE {
            lcsSetupPublicSpotModulePageTableEntryPage INTEGER,
            lcsSetupPublicSpotModulePageTableEntryUrl DisplayString,
            lcsSetupPublicSpotModulePageTableEntryFallback INTEGER,
            lcsSetupPublicSpotModulePageTableEntryType INTEGER,
            lcsSetupPublicSpotModulePageTableEntryLoopbackAddr DisplayString,
            lcsSetupPublicSpotModulePageTableEntryTemplateCache INTEGER
    }

-- {COLUMN} 1.3.6.1.4.1.2356.11.2.24.8.1.1
lcsSetupPublicSpotModulePageTableEntryPage OBJECT-TYPE
    SYNTAX     INTEGER {
                  eWelcome (1),
                  eLogin (2),
                  eError (3),
                  eStart (4),
                  eStatus (5),
                  eLogoff (6),
                  eHelp (7),
                  eNoProxy (8),
                  eVoucher (9),
                  eGtc (10),
                  eFallbackError (11),
                  eRegistrationEMail (12),
                  eSignEMail (13),
                  eRegistrationEMailToSms (14),
                  eSignEMailToSms (15)
            }
    MAX-ACCESS read-only
    STATUS     current
    DESCRIPTION
            ""
    ::= { lcsSetupPublicSpotModulePageTableEntry 1 }

-- {COLUMN} 1.3.6.1.4.1.2356.11.2.24.8.1.2
lcsSetupPublicSpotModulePageTableEntryUrl OBJECT-TYPE
    SYNTAX     DisplayString (SIZE(0..251))
    MAX-ACCESS read-write
    STATUS     current
    DESCRIPTION
            ""
    ::= { lcsSetupPublicSpotModulePageTableEntry 2 }

-- {COLUMN} 1.3.6.1.4.1.2356.11.2.24.8.1.3
lcsSetupPublicSpotModulePageTableEntryFallback OBJECT-TYPE
    SYNTAX     INTEGER {
                  eNo (0),
                  eYes (1)
            }
    MAX-ACCESS read-write
    STATUS     current
    DESCRIPTION
            ""
    ::= { lcsSetupPublicSpotModulePageTableEntry 3 }

-- {COLUMN} 1.3.6.1.4.1.2356.11.2.24.8.1.4
lcsSetupPublicSpotModulePageTableEntryType OBJECT-TYPE
    SYNTAX     INTEGER {
                  eTemplate (0),
                  eRedirect (1)
            }
    MAX-ACCESS read-write
    STATUS     current
    DESCRIPTION
            ""
    ::= { lcsSetupPublicSpotModulePageTableEntry 4 }

-- {COLUMN} 1.3.6.1.4.1.2356.11.2.24.8.1.5
lcsSetupPublicSpotModulePageTableEntryLoopbackAddr OBJECT-TYPE
    SYNTAX     DisplayString (SIZE(0..16))
    MAX-ACCESS read-write
    STATUS     current
    DESCRIPTION
            ""
    ::= { lcsSetupPublicSpotModulePageTableEntry 5 }

-- {COLUMN} 1.3.6.1.4.1.2356.11.2.24.8.1.6
lcsSetupPublicSpotModulePageTableEntryTemplateCache OBJECT-TYPE
    SYNTAX     INTEGER {
                  eNo (0),
                  eYes (1)
            }
    MAX-ACCESS read-write
    STATUS     current
    DESCRIPTION
            "-- empty --"
    ::= { lcsSetupPublicSpotModulePageTableEntry 6 }

-- {SCALAR} 1.3.6.1.4.1.2356.11.2.24.9
lcsSetupPublicSpotModuleRoamingSecret OBJECT-TYPE
    SYNTAX     DisplayString (SIZE(0..32))
    MAX-ACCESS read-write
    STATUS     current
    DESCRIPTION
            ""
    ::= { lcsSetupPublicSpotModule 9 }

-- {SCALAR} 1.3.6.1.4.1.2356.11.2.24.12
lcsSetupPublicSpotModuleCommunicationPort OBJECT-TYPE
    SYNTAX     Integer32 (0..65535)
    MAX-ACCESS read-write
    STATUS     current
    DESCRIPTION
            ""
    ::= { lcsSetupPublicSpotModule 12 }

-- {SCALAR} 1.3.6.1.4.1.2356.11.2.24.14
lcsSetupPublicSpotModuleIdleTimeout OBJECT-TYPE
    SYNTAX     Integer32 (0..2147483647)
    MAX-ACCESS read-write
    STATUS     current
    DESCRIPTION
            ""
    ::= { lcsSetupPublicSpotModule 14 }

-- {TABLE} 1.3.6.1.4.1.2356.11.2.24.15
lcsSetupPublicSpotModulePortTableTable OBJECT-TYPE
    SYNTAX     SEQUENCE OF LcsSetupPublicSpotModulePortTableEntry
    MAX-ACCESS not-accessible
    STATUS     current
    DESCRIPTION
            ""
    ::= { lcsSetupPublicSpotModule 15 }

-- {ROW} 1.3.6.1.4.1.2356.11.2.24.15.1
lcsSetupPublicSpotModulePortTableEntry OBJECT-TYPE
    SYNTAX     LcsSetupPublicSpotModulePortTableEntry
    MAX-ACCESS not-accessible
    STATUS     current
    DESCRIPTION
            ""
    INDEX {
            lcsSetupPublicSpotModulePortTableEntryPort
          }
    ::= { lcsSetupPublicSpotModulePortTableTable 1 }

LcsSetupPublicSpotModulePortTableEntry ::= SEQUENCE {
            lcsSetupPublicSpotModulePortTableEntryPort DisplayString,
            lcsSetupPublicSpotModulePortTableEntryAuthenticationNecessary INTEGER
    }

-- {COLUMN} 1.3.6.1.4.1.2356.11.2.24.15.1.2
lcsSetupPublicSpotModulePortTableEntryPort OBJECT-TYPE
    SYNTAX     DisplayString (SIZE(0..18))
    MAX-ACCESS read-only
    STATUS     current
    DESCRIPTION
            ""
    ::= { lcsSetupPublicSpotModulePortTableEntry 2 }

-- {COLUMN} 1.3.6.1.4.1.2356.11.2.24.15.1.3
lcsSetupPublicSpotModulePortTableEntryAuthenticationNecessary OBJECT-TYPE
    SYNTAX     INTEGER {
                  eNo (0),
                  eYes (1)
            }
    MAX-ACCESS read-write
    STATUS     current
    DESCRIPTION
            ""
    ::= { lcsSetupPublicSpotModulePortTableEntry 3 }

-- {SCALAR} 1.3.6.1.4.1.2356.11.2.24.16
lcsSetupPublicSpotModuleAutoCleanupUserTable OBJECT-TYPE
    SYNTAX     INTEGER {
                  eNo (0),
                  eYes (1)
            }
    MAX-ACCESS read-write
    STATUS     current
    DESCRIPTION
            ""
    ::= { lcsSetupPublicSpotModule 16 }

-- {SCALAR} 1.3.6.1.4.1.2356.11.2.24.17
lcsSetupPublicSpotModuleProvideServerDatabase OBJECT-TYPE
    SYNTAX     INTEGER {
                  eNo (0),
                  eYes (1)
            }
    MAX-ACCESS read-write
    STATUS     current
    DESCRIPTION
            ""
    ::= { lcsSetupPublicSpotModule 17 }

-- {SCALAR} 1.3.6.1.4.1.2356.11.2.24.18
lcsSetupPublicSpotModuleDisallowMultipleLogin OBJECT-TYPE
    SYNTAX     INTEGER {
                  eNo (0),
                  eYes (1)
            }
    MAX-ACCESS read-write
    STATUS     current
    DESCRIPTION
            ""
    ::= { lcsSetupPublicSpotModule 18 }

-- {NODE} 1.3.6.1.4.1.2356.11.2.24.19
lcsSetupPublicSpotModuleAddUserWizard OBJECT IDENTIFIER ::= { lcsSetupPublicSpotModule 19 }

-- {SCALAR} 1.3.6.1.4.1.2356.11.2.24.19.2
lcsSetupPublicSpotModuleAddUserWizardUsernamePattern OBJECT-TYPE
    SYNTAX     DisplayString (SIZE(0..19))
    MAX-ACCESS read-write
    STATUS     current
    DESCRIPTION
            ""
    ::= { lcsSetupPublicSpotModuleAddUserWizard 2 }

-- {SCALAR} 1.3.6.1.4.1.2356.11.2.24.19.3
lcsSetupPublicSpotModuleAddUserWizardPasswordLength OBJECT-TYPE
    SYNTAX     Integer32 (0..255)
    MAX-ACCESS read-write
    STATUS     current
    DESCRIPTION
            ""
    ::= { lcsSetupPublicSpotModuleAddUserWizard 3 }

-- {SCALAR} 1.3.6.1.4.1.2356.11.2.24.19.4
lcsSetupPublicSpotModuleAddUserWizardSsid OBJECT-TYPE
    SYNTAX     DisplayString (SIZE(0..32))
    MAX-ACCESS read-write
    STATUS     current
    DESCRIPTION
            ""
    ::= { lcsSetupPublicSpotModuleAddUserWizard 4 }

-- {TABLE} 1.3.6.1.4.1.2356.11.2.24.19.5
lcsSetupPublicSpotModuleAddUserWizardDefaultRuntimeTable OBJECT-TYPE
    SYNTAX     SEQUENCE OF LcsSetupPublicSpotModuleAddUserWizardDefaultRuntimeEntry
    MAX-ACCESS not-accessible
    STATUS     current
    DESCRIPTION
            ""
    ::= { lcsSetupPublicSpotModuleAddUserWizard 5 }

-- {ROW} 1.3.6.1.4.1.2356.11.2.24.19.5.1
lcsSetupPublicSpotModuleAddUserWizardDefaultRuntimeEntry OBJECT-TYPE
    SYNTAX     LcsSetupPublicSpotModuleAddUserWizardDefaultRuntimeEntry
    MAX-ACCESS not-accessible
    STATUS     current
    DESCRIPTION
            ""
    INDEX {
            lcsSetupPublicSpotModuleAddUserWizardDefaultRuntimeEntryRuntime,
            lcsSetupPublicSpotModuleAddUserWizardDefaultRuntimeEntryUnit
          }
    ::= { lcsSetupPublicSpotModuleAddUserWizardDefaultRuntimeTable 1 }

LcsSetupPublicSpotModuleAddUserWizardDefaultRuntimeEntry ::= SEQUENCE {
            lcsSetupPublicSpotModuleAddUserWizardDefaultRuntimeEntryRuntime Integer32,
            lcsSetupPublicSpotModuleAddUserWizardDefaultRuntimeEntryUnit INTEGER
    }

-- {COLUMN} 1.3.6.1.4.1.2356.11.2.24.19.5.1.1
lcsSetupPublicSpotModuleAddUserWizardDefaultRuntimeEntryRuntime OBJECT-TYPE
    SYNTAX     Integer32 (0..65535)
    MAX-ACCESS read-write
    STATUS     current
    DESCRIPTION
            ""
    ::= { lcsSetupPublicSpotModuleAddUserWizardDefaultRuntimeEntry 1 }

-- {COLUMN} 1.3.6.1.4.1.2356.11.2.24.19.5.1.2
lcsSetupPublicSpotModuleAddUserWizardDefaultRuntimeEntryUnit OBJECT-TYPE
    SYNTAX     INTEGER {
                  eHourS (0),
                  eDayS (1),
                  eMinuteS (2)
            }
    MAX-ACCESS read-write
    STATUS     current
    DESCRIPTION
            ""
    ::= { lcsSetupPublicSpotModuleAddUserWizardDefaultRuntimeEntry 2 }

-- {TABLE} 1.3.6.1.4.1.2356.11.2.24.19.6
lcsSetupPublicSpotModuleAddUserWizardCommentFieldsTable OBJECT-TYPE
    SYNTAX     SEQUENCE OF LcsSetupPublicSpotModuleAddUserWizardCommentFieldsEntry
    MAX-ACCESS not-accessible
    STATUS     current
    DESCRIPTION
            ""
    ::= { lcsSetupPublicSpotModuleAddUserWizard 6 }

-- {ROW} 1.3.6.1.4.1.2356.11.2.24.19.6.1
lcsSetupPublicSpotModuleAddUserWizardCommentFieldsEntry OBJECT-TYPE
    SYNTAX     LcsSetupPublicSpotModuleAddUserWizardCommentFieldsEntry
    MAX-ACCESS not-accessible
    STATUS     current
    DESCRIPTION
            ""
    INDEX {
            lcsSetupPublicSpotModuleAddUserWizardCommentFieldsEntryFieldName
          }
    ::= { lcsSetupPublicSpotModuleAddUserWizardCommentFieldsTable 1 }

LcsSetupPublicSpotModuleAddUserWizardCommentFieldsEntry ::= SEQUENCE {
            lcsSetupPublicSpotModuleAddUserWizardCommentFieldsEntryFieldName DisplayString
    }

-- {COLUMN} 1.3.6.1.4.1.2356.11.2.24.19.6.1.1
lcsSetupPublicSpotModuleAddUserWizardCommentFieldsEntryFieldName OBJECT-TYPE
    SYNTAX     DisplayString (SIZE(0..31))
    MAX-ACCESS read-write
    STATUS     current
    DESCRIPTION
            ""
    ::= { lcsSetupPublicSpotModuleAddUserWizardCommentFieldsEntry 1 }

-- {SCALAR} 1.3.6.1.4.1.2356.11.2.24.19.7
lcsSetupPublicSpotModuleAddUserWizardDefaultStartingTime OBJECT-TYPE
    SYNTAX     INTEGER {
                  eImmediately (1),
                  eFirstLogin (3)
            }
    MAX-ACCESS read-write
    STATUS     current
    DESCRIPTION
            ""
    ::= { lcsSetupPublicSpotModuleAddUserWizard 7 }

-- {SCALAR} 1.3.6.1.4.1.2356.11.2.24.19.8
lcsSetupPublicSpotModuleAddUserWizardPrintCommentsOnVoucher OBJECT-TYPE
    SYNTAX     INTEGER {
                  eNo (0),
                  eYes (1)
            }
    MAX-ACCESS read-write
    STATUS     current
    DESCRIPTION
            ""
    ::= { lcsSetupPublicSpotModuleAddUserWizard 8 }

-- {SCALAR} 1.3.6.1.4.1.2356.11.2.24.19.9
lcsSetupPublicSpotModuleAddUserWizardMaxVoucherValPeriod OBJECT-TYPE
    SYNTAX     Integer32 (0..2147483647)
    MAX-ACCESS read-write
    STATUS     current
    DESCRIPTION
            "Maximal voucher validate period"
    ::= { lcsSetupPublicSpotModuleAddUserWizard 9 }

-- {SCALAR} 1.3.6.1.4.1.2356.11.2.24.19.10
lcsSetupPublicSpotModuleAddUserWizardAvailableExpiryMethods OBJECT-TYPE
    SYNTAX     INTEGER {
                  eAllMethods (0),
                  eCurrentTimeMethod (1),
                  eLoginTimeMethod (2)
            }
    MAX-ACCESS read-write
    STATUS     current
    DESCRIPTION
            ""
    ::= { lcsSetupPublicSpotModuleAddUserWizard 10 }

-- {TABLE} 1.3.6.1.4.1.2356.11.2.24.19.11
lcsSetupPublicSpotModuleAddUserWizardSsidTableTable OBJECT-TYPE
    SYNTAX     SEQUENCE OF LcsSetupPublicSpotModuleAddUserWizardSsidTableEntry
    MAX-ACCESS not-accessible
    STATUS     current
    DESCRIPTION
            "-- empty --"
    ::= { lcsSetupPublicSpotModuleAddUserWizard 11 }

-- {ROW} 1.3.6.1.4.1.2356.11.2.24.19.11.1
lcsSetupPublicSpotModuleAddUserWizardSsidTableEntry OBJECT-TYPE
    SYNTAX     LcsSetupPublicSpotModuleAddUserWizardSsidTableEntry
    MAX-ACCESS not-accessible
    STATUS     current
    DESCRIPTION
            ""
    INDEX {
            lcsSetupPublicSpotModuleAddUserWizardSsidTableEntryNetworkName
          }
    ::= { lcsSetupPublicSpotModuleAddUserWizardSsidTableTable 1 }

LcsSetupPublicSpotModuleAddUserWizardSsidTableEntry ::= SEQUENCE {
            lcsSetupPublicSpotModuleAddUserWizardSsidTableEntryNetworkName DisplayString,
            lcsSetupPublicSpotModuleAddUserWizardSsidTableEntryDefault INTEGER
    }

-- {COLUMN} 1.3.6.1.4.1.2356.11.2.24.19.11.1.1
lcsSetupPublicSpotModuleAddUserWizardSsidTableEntryNetworkName OBJECT-TYPE
    SYNTAX     DisplayString (SIZE(0..32))
    MAX-ACCESS read-write
    STATUS     current
    DESCRIPTION
            "-- empty --"
    ::= { lcsSetupPublicSpotModuleAddUserWizardSsidTableEntry 1 }

-- {COLUMN} 1.3.6.1.4.1.2356.11.2.24.19.11.1.2
lcsSetupPublicSpotModuleAddUserWizardSsidTableEntryDefault OBJECT-TYPE
    SYNTAX     INTEGER {
                  eNo (0),
                  eYes (1)
            }
    MAX-ACCESS read-write
    STATUS     current
    DESCRIPTION
            "-- empty --"
    ::= { lcsSetupPublicSpotModuleAddUserWizardSsidTableEntry 2 }

-- {SCALAR} 1.3.6.1.4.1.2356.11.2.24.19.12
lcsSetupPublicSpotModuleAddUserWizardUserNameCaseSensitive OBJECT-TYPE
    SYNTAX     INTEGER {
                  eNo (0),
                  eYes (1)
            }
    MAX-ACCESS read-write
    STATUS     current
    DESCRIPTION
            "-- empty --"
    ::= { lcsSetupPublicSpotModuleAddUserWizard 12 }

-- {SCALAR} 1.3.6.1.4.1.2356.11.2.24.19.13
lcsSetupPublicSpotModuleAddUserWizardHideCaseSensitiveCheckbox OBJECT-TYPE
    SYNTAX     INTEGER {
                  eNo (0),
                  eYes (1)
            }
    MAX-ACCESS read-write
    STATUS     current
    DESCRIPTION
            "-- empty --"
    ::= { lcsSetupPublicSpotModuleAddUserWizard 13 }

-- {TABLE} 1.3.6.1.4.1.2356.11.2.24.19.14
lcsSetupPublicSpotModuleAddUserWizardMaxConcLoginsTable OBJECT-TYPE
    SYNTAX     SEQUENCE OF LcsSetupPublicSpotModuleAddUserWizardMaxConcLoginsEntry
    MAX-ACCESS not-accessible
    STATUS     current
    DESCRIPTION
            ""
    ::= { lcsSetupPublicSpotModuleAddUserWizard 14 }

-- {ROW} 1.3.6.1.4.1.2356.11.2.24.19.14.1
lcsSetupPublicSpotModuleAddUserWizardMaxConcLoginsEntry OBJECT-TYPE
    SYNTAX     LcsSetupPublicSpotModuleAddUserWizardMaxConcLoginsEntry
    MAX-ACCESS not-accessible
    STATUS     current
    DESCRIPTION
            ""
    INDEX {
            lcsSetupPublicSpotModuleAddUserWizardMaxConcLoginsEntryValue
          }
    ::= { lcsSetupPublicSpotModuleAddUserWizardMaxConcLoginsTable 1 }

LcsSetupPublicSpotModuleAddUserWizardMaxConcLoginsEntry ::= SEQUENCE {
            lcsSetupPublicSpotModuleAddUserWizardMaxConcLoginsEntryValue DisplayString
    }

-- {COLUMN} 1.3.6.1.4.1.2356.11.2.24.19.14.1.1
lcsSetupPublicSpotModuleAddUserWizardMaxConcLoginsEntryValue OBJECT-TYPE
    SYNTAX     DisplayString (SIZE(0..5))
    MAX-ACCESS read-write
    STATUS     current
    DESCRIPTION
            "-- empty --"
    ::= { lcsSetupPublicSpotModuleAddUserWizardMaxConcLoginsEntry 1 }

-- {SCALAR} 1.3.6.1.4.1.2356.11.2.24.19.15
lcsSetupPublicSpotModuleAddUserWizardMultiLogin OBJECT-TYPE
    SYNTAX     INTEGER {
                  eNo (0),
                  eYes (1)
            }
    MAX-ACCESS read-write
    STATUS     current
    DESCRIPTION
            "-- empty --"
    ::= { lcsSetupPublicSpotModuleAddUserWizard 15 }

-- {SCALAR} 1.3.6.1.4.1.2356.11.2.24.19.16
lcsSetupPublicSpotModuleAddUserWizardHideMultiLoginCheckbox OBJECT-TYPE
    SYNTAX     INTEGER {
                  eNo (0),
                  eYes (1)
            }
    MAX-ACCESS read-write
    STATUS     current
    DESCRIPTION
            "-- empty --"
    ::= { lcsSetupPublicSpotModuleAddUserWizard 16 }

-- {TABLE} 1.3.6.1.4.1.2356.11.2.24.19.17
lcsSetupPublicSpotModuleAddUserWizardBWidthProTable OBJECT-TYPE
    SYNTAX     SEQUENCE OF LcsSetupPublicSpotModuleAddUserWizardBWidthProEntry
    MAX-ACCESS not-accessible
    STATUS     current
    DESCRIPTION
            ""
    ::= { lcsSetupPublicSpotModuleAddUserWizard 17 }

-- {ROW} 1.3.6.1.4.1.2356.11.2.24.19.17.1
lcsSetupPublicSpotModuleAddUserWizardBWidthProEntry OBJECT-TYPE
    SYNTAX     LcsSetupPublicSpotModuleAddUserWizardBWidthProEntry
    MAX-ACCESS not-accessible
    STATUS     current
    DESCRIPTION
            ""
    INDEX {
            lcsSetupPublicSpotModuleAddUserWizardBWidthProEntryProfileName
          }
    ::= { lcsSetupPublicSpotModuleAddUserWizardBWidthProTable 1 }

LcsSetupPublicSpotModuleAddUserWizardBWidthProEntry ::= SEQUENCE {
            lcsSetupPublicSpotModuleAddUserWizardBWidthProEntryProfileName DisplayString,
            lcsSetupPublicSpotModuleAddUserWizardBWidthProEntryTxBandwidth Integer32,
            lcsSetupPublicSpotModuleAddUserWizardBWidthProEntryRxBandwidth Integer32
    }

-- {COLUMN} 1.3.6.1.4.1.2356.11.2.24.19.17.1.1
lcsSetupPublicSpotModuleAddUserWizardBWidthProEntryProfileName OBJECT-TYPE
    SYNTAX     DisplayString (SIZE(0..255))
    MAX-ACCESS read-write
    STATUS     current
    DESCRIPTION
            "-- empty --"
    ::= { lcsSetupPublicSpotModuleAddUserWizardBWidthProEntry 1 }

-- {COLUMN} 1.3.6.1.4.1.2356.11.2.24.19.17.1.2
lcsSetupPublicSpotModuleAddUserWizardBWidthProEntryTxBandwidth OBJECT-TYPE
    SYNTAX     Integer32 (0..2147483647)
    MAX-ACCESS read-write
    STATUS     current
    DESCRIPTION
            "-- empty --"
    ::= { lcsSetupPublicSpotModuleAddUserWizardBWidthProEntry 2 }

-- {COLUMN} 1.3.6.1.4.1.2356.11.2.24.19.17.1.3
lcsSetupPublicSpotModuleAddUserWizardBWidthProEntryRxBandwidth OBJECT-TYPE
    SYNTAX     Integer32 (0..2147483647)
    MAX-ACCESS read-write
    STATUS     current
    DESCRIPTION
            "-- empty --"
    ::= { lcsSetupPublicSpotModuleAddUserWizardBWidthProEntry 3 }

-- {SCALAR} 1.3.6.1.4.1.2356.11.2.24.19.18
lcsSetupPublicSpotModuleAddUserWizardPasswordCharacterSet OBJECT-TYPE
    SYNTAX     INTEGER {
                  eCharactersPlusDigits (0),
                  eCharacters (1),
                  eDigits (2)
            }
    MAX-ACCESS read-write
    STATUS     current
    DESCRIPTION
            "-- empty --"
    ::= { lcsSetupPublicSpotModuleAddUserWizard 18 }

-- {SCALAR} 1.3.6.1.4.1.2356.11.2.24.19.19
lcsSetupPublicSpotModuleAddUserWizardHideCsvExport OBJECT-TYPE
    SYNTAX     INTEGER {
                  eNo (0),
                  eYes (1)
            }
    MAX-ACCESS read-write
    STATUS     current
    DESCRIPTION
            "-- empty --"
    ::= { lcsSetupPublicSpotModuleAddUserWizard 19 }

-- {SCALAR} 1.3.6.1.4.1.2356.11.2.24.19.20
lcsSetupPublicSpotModuleAddUserWizardHideUserManagementButton OBJECT-TYPE
    SYNTAX     INTEGER {
                  eNo (0),
                  eYes (1)
            }
    MAX-ACCESS read-write
    STATUS     current
    DESCRIPTION
            "-- empty --"
    ::= { lcsSetupPublicSpotModuleAddUserWizard 20 }

-- {SCALAR} 1.3.6.1.4.1.2356.11.2.24.19.21
lcsSetupPublicSpotModuleAddUserWizardMaxVoucherValPerUnit OBJECT-TYPE
    SYNTAX     INTEGER {
                  eMinuteS (1),
                  eHourS (2),
                  eDayS (3)
            }
    MAX-ACCESS read-write
    STATUS     current
    DESCRIPTION
            ""
    ::= { lcsSetupPublicSpotModuleAddUserWizard 21 }

-- {TABLE} 1.3.6.1.4.1.2356.11.2.24.20
lcsSetupPublicSpotModuleVlanTableTable OBJECT-TYPE
    SYNTAX     SEQUENCE OF LcsSetupPublicSpotModuleVlanTableEntry
    MAX-ACCESS not-accessible
    STATUS     current
    DESCRIPTION
            ""
    ::= { lcsSetupPublicSpotModule 20 }

-- {ROW} 1.3.6.1.4.1.2356.11.2.24.20.1
lcsSetupPublicSpotModuleVlanTableEntry OBJECT-TYPE
    SYNTAX     LcsSetupPublicSpotModuleVlanTableEntry
    MAX-ACCESS not-accessible
    STATUS     current
    DESCRIPTION
            ""
    INDEX {
            lcsSetupPublicSpotModuleVlanTableEntryVlanId
          }
    ::= { lcsSetupPublicSpotModuleVlanTableTable 1 }

LcsSetupPublicSpotModuleVlanTableEntry ::= SEQUENCE {
            lcsSetupPublicSpotModuleVlanTableEntryVlanId Integer32
    }

-- {COLUMN} 1.3.6.1.4.1.2356.11.2.24.20.1.1
lcsSetupPublicSpotModuleVlanTableEntryVlanId OBJECT-TYPE
    SYNTAX     Integer32 (0..65535)
    MAX-ACCESS read-write
    STATUS     current
    DESCRIPTION
            ""
    ::= { lcsSetupPublicSpotModuleVlanTableEntry 1 }

-- {SCALAR} 1.3.6.1.4.1.2356.11.2.24.21
lcsSetupPublicSpotModuleLoginPageType OBJECT-TYPE
    SYNTAX     INTEGER {
                  eHttps (0),
                  eHttp (1)
            }
    MAX-ACCESS read-write
    STATUS     current
    DESCRIPTION
            ""
    ::= { lcsSetupPublicSpotModule 21 }

-- {SCALAR} 1.3.6.1.4.1.2356.11.2.24.22
lcsSetupPublicSpotModuleDeviceHostname OBJECT-TYPE
    SYNTAX     DisplayString (SIZE(0..31))
    MAX-ACCESS read-write
    STATUS     current
    DESCRIPTION
            ""
    ::= { lcsSetupPublicSpotModule 22 }

-- {TABLE} 1.3.6.1.4.1.2356.11.2.24.23
lcsSetupPublicSpotModuleMacAddressTableTable OBJECT-TYPE
    SYNTAX     SEQUENCE OF LcsSetupPublicSpotModuleMacAddressTableEntry
    MAX-ACCESS not-accessible
    STATUS     current
    DESCRIPTION
            ""
    ::= { lcsSetupPublicSpotModule 23 }

-- {ROW} 1.3.6.1.4.1.2356.11.2.24.23.1
lcsSetupPublicSpotModuleMacAddressTableEntry OBJECT-TYPE
    SYNTAX     LcsSetupPublicSpotModuleMacAddressTableEntry
    MAX-ACCESS not-accessible
    STATUS     current
    DESCRIPTION
            ""
    INDEX {
            lcsSetupPublicSpotModuleMacAddressTableEntryMacAddress
          }
    ::= { lcsSetupPublicSpotModuleMacAddressTableTable 1 }

LcsSetupPublicSpotModuleMacAddressTableEntry ::= SEQUENCE {
            lcsSetupPublicSpotModuleMacAddressTableEntryMacAddress MacAddress,
            lcsSetupPublicSpotModuleMacAddressTableEntryUserName DisplayString,
            lcsSetupPublicSpotModuleMacAddressTableEntryProvider DisplayString
    }

-- {COLUMN} 1.3.6.1.4.1.2356.11.2.24.23.1.1
lcsSetupPublicSpotModuleMacAddressTableEntryMacAddress OBJECT-TYPE
    SYNTAX     MacAddress
    MAX-ACCESS read-write
    STATUS     current
    DESCRIPTION
            ""
    ::= { lcsSetupPublicSpotModuleMacAddressTableEntry 1 }

-- {COLUMN} 1.3.6.1.4.1.2356.11.2.24.23.1.2
lcsSetupPublicSpotModuleMacAddressTableEntryUserName OBJECT-TYPE
    SYNTAX     DisplayString (SIZE(0..64))
    MAX-ACCESS read-write
    STATUS     current
    DESCRIPTION
            ""
    ::= { lcsSetupPublicSpotModuleMacAddressTableEntry 2 }

-- {COLUMN} 1.3.6.1.4.1.2356.11.2.24.23.1.3
lcsSetupPublicSpotModuleMacAddressTableEntryProvider OBJECT-TYPE
    SYNTAX     DisplayString (SIZE(0..16))
    MAX-ACCESS read-write
    STATUS     current
    DESCRIPTION
            ""
    ::= { lcsSetupPublicSpotModuleMacAddressTableEntry 3 }

-- {SCALAR} 1.3.6.1.4.1.2356.11.2.24.24
lcsSetupPublicSpotModuleMacAddressCheckProvider OBJECT-TYPE
    SYNTAX     DisplayString (SIZE(0..16))
    MAX-ACCESS read-write
    STATUS     current
    DESCRIPTION
            ""
    ::= { lcsSetupPublicSpotModule 24 }

-- {SCALAR} 1.3.6.1.4.1.2356.11.2.24.25
lcsSetupPublicSpotModuleMacAddressCheckCacheTime OBJECT-TYPE
    SYNTAX     Integer32 (0..2147483647)
    MAX-ACCESS read-write
    STATUS     current
    DESCRIPTION
            ""
    ::= { lcsSetupPublicSpotModule 25 }

-- {SCALAR} 1.3.6.1.4.1.2356.11.2.24.26
lcsSetupPublicSpotModuleStationTableLimit OBJECT-TYPE
    SYNTAX     Integer32 (0..2147483647)
    MAX-ACCESS read-write
    STATUS     current
    DESCRIPTION
            "-- empty --"
    ::= { lcsSetupPublicSpotModule 26 }

-- {SCALAR} 1.3.6.1.4.1.2356.11.2.24.30
lcsSetupPublicSpotModuleFreeServer OBJECT-TYPE
    SYNTAX     DisplayString (SIZE(0..64))
    MAX-ACCESS read-write
    STATUS     current
    DESCRIPTION
            ""
    ::= { lcsSetupPublicSpotModule 30 }

-- {TABLE} 1.3.6.1.4.1.2356.11.2.24.31
lcsSetupPublicSpotModuleFreeNetworksTable OBJECT-TYPE
    SYNTAX     SEQUENCE OF LcsSetupPublicSpotModuleFreeNetworksEntry
    MAX-ACCESS not-accessible
    STATUS     current
    DESCRIPTION
            ""
    ::= { lcsSetupPublicSpotModule 31 }

-- {ROW} 1.3.6.1.4.1.2356.11.2.24.31.1
lcsSetupPublicSpotModuleFreeNetworksEntry OBJECT-TYPE
    SYNTAX     LcsSetupPublicSpotModuleFreeNetworksEntry
    MAX-ACCESS not-accessible
    STATUS     current
    DESCRIPTION
            ""
    INDEX {
            lcsSetupPublicSpotModuleFreeNetworksEntryHostName
          }
    ::= { lcsSetupPublicSpotModuleFreeNetworksTable 1 }

LcsSetupPublicSpotModuleFreeNetworksEntry ::= SEQUENCE {
            lcsSetupPublicSpotModuleFreeNetworksEntryHostName DisplayString,
            lcsSetupPublicSpotModuleFreeNetworksEntryMask IpAddress,
            lcsSetupPublicSpotModuleFreeNetworksEntryVlans DisplayString
    }

-- {COLUMN} 1.3.6.1.4.1.2356.11.2.24.31.1.1
lcsSetupPublicSpotModuleFreeNetworksEntryHostName OBJECT-TYPE
    SYNTAX     DisplayString (SIZE(0..64))
    MAX-ACCESS read-write
    STATUS     current
    DESCRIPTION
            ""
    ::= { lcsSetupPublicSpotModuleFreeNetworksEntry 1 }

-- {COLUMN} 1.3.6.1.4.1.2356.11.2.24.31.1.2
lcsSetupPublicSpotModuleFreeNetworksEntryMask OBJECT-TYPE
    SYNTAX     IpAddress
    MAX-ACCESS read-write
    STATUS     current
    DESCRIPTION
            ""
    ::= { lcsSetupPublicSpotModuleFreeNetworksEntry 2 }

-- {COLUMN} 1.3.6.1.4.1.2356.11.2.24.31.1.3
lcsSetupPublicSpotModuleFreeNetworksEntryVlans OBJECT-TYPE
    SYNTAX     DisplayString (SIZE(0..254))
    MAX-ACCESS read-write
    STATUS     current
    DESCRIPTION
            "-- empty --"
    ::= { lcsSetupPublicSpotModuleFreeNetworksEntry 3 }

-- {SCALAR} 1.3.6.1.4.1.2356.11.2.24.32
lcsSetupPublicSpotModuleFreeHostsMinimumTtl OBJECT-TYPE
    SYNTAX     Integer32 (0..2147483647)
    MAX-ACCESS read-write
    STATUS     current
    DESCRIPTION
            "-- empty --"
    ::= { lcsSetupPublicSpotModule 32 }

-- {SCALAR} 1.3.6.1.4.1.2356.11.2.24.33
lcsSetupPublicSpotModuleLoginText OBJECT-TYPE
    SYNTAX     DisplayString (SIZE(0..254))
    MAX-ACCESS read-write
    STATUS     current
    DESCRIPTION
            "-- empty --"
    ::= { lcsSetupPublicSpotModule 33 }

-- {SCALAR} 1.3.6.1.4.1.2356.11.2.24.34
lcsSetupPublicSpotModuleWanConnection OBJECT-TYPE
    SYNTAX     DisplayString (SIZE(0..16))
    MAX-ACCESS read-write
    STATUS     current
    DESCRIPTION
            "-- empty --"
    ::= { lcsSetupPublicSpotModule 34 }

-- {SCALAR} 1.3.6.1.4.1.2356.11.2.24.35
lcsSetupPublicSpotModulePrintLogoAndHeaderboard OBJECT-TYPE
    SYNTAX     INTEGER {
                  eNo (0),
                  eYes (1)
            }
    MAX-ACCESS read-write
    STATUS     current
    DESCRIPTION
            "-- empty --"
    ::= { lcsSetupPublicSpotModule 35 }

-- {SCALAR} 1.3.6.1.4.1.2356.11.2.24.36
lcsSetupPublicSpotModuleUserMustAcceptGtc OBJECT-TYPE
    SYNTAX     INTEGER {
                  eNo (0),
                  eYes (1)
            }
    MAX-ACCESS read-write
    STATUS     current
    DESCRIPTION
            "-- empty --"
    ::= { lcsSetupPublicSpotModule 36 }

-- {SCALAR} 1.3.6.1.4.1.2356.11.2.24.37
lcsSetupPublicSpotModulePrintLogoutLink OBJECT-TYPE
    SYNTAX     INTEGER {
                  eNo (0),
                  eYes (1)
            }
    MAX-ACCESS read-write
    STATUS     current
    DESCRIPTION
            "-- empty --"
    ::= { lcsSetupPublicSpotModule 37 }

-- {SCALAR} 1.3.6.1.4.1.2356.11.2.24.38
lcsSetupPublicSpotModuleLbsTracking OBJECT-TYPE
    SYNTAX     INTEGER {
                  eNo (0),
                  eYes (1)
            }
    MAX-ACCESS read-write
    STATUS     current
    DESCRIPTION
            "-- empty --"
    ::= { lcsSetupPublicSpotModule 38 }

-- {SCALAR} 1.3.6.1.4.1.2356.11.2.24.39
lcsSetupPublicSpotModuleLbsTrackingList OBJECT-TYPE
    SYNTAX     DisplayString (SIZE(0..32))
    MAX-ACCESS read-write
    STATUS     current
    DESCRIPTION
            "-- empty --"
    ::= { lcsSetupPublicSpotModule 39 }

-- {NODE} 1.3.6.1.4.1.2356.11.2.24.40
lcsSetupPublicSpotModuleXmlInterface OBJECT IDENTIFIER ::= { lcsSetupPublicSpotModule 40 }

-- {SCALAR} 1.3.6.1.4.1.2356.11.2.24.40.1
lcsSetupPublicSpotModuleXmlInterfaceOperating OBJECT-TYPE
    SYNTAX     INTEGER {
                  eNo (0),
                  eYes (1)
            }
    MAX-ACCESS read-write
    STATUS     current
    DESCRIPTION
            "-- empty --"
    ::= { lcsSetupPublicSpotModuleXmlInterface 1 }

-- {SCALAR} 1.3.6.1.4.1.2356.11.2.24.40.2
lcsSetupPublicSpotModuleXmlInterfaceRadiusAuthentication OBJECT-TYPE
    SYNTAX     INTEGER {
                  eNo (0),
                  eYes (1)
            }
    MAX-ACCESS read-write
    STATUS     current
    DESCRIPTION
            "-- empty --"
    ::= { lcsSetupPublicSpotModuleXmlInterface 2 }

-- {NODE} 1.3.6.1.4.1.2356.11.2.24.41
lcsSetupPublicSpotModuleAuthMod OBJECT IDENTIFIER ::= { lcsSetupPublicSpotModule 41 }

-- {NODE} 1.3.6.1.4.1.2356.11.2.24.41.1
lcsSetupPublicSpotModuleAuthModEmlAuth OBJECT IDENTIFIER ::= { lcsSetupPublicSpotModuleAuthMod 1 }

-- {SCALAR} 1.3.6.1.4.1.2356.11.2.24.41.1.1
lcsSetupPublicSpotModuleAuthModEmlAuthLimitEMailsPerHour OBJECT-TYPE
    SYNTAX     Integer32 (0..65535)
    MAX-ACCESS read-write
    STATUS     current
    DESCRIPTION
            "-- empty --"
    ::= { lcsSetupPublicSpotModuleAuthModEmlAuth 1 }

-- {SCALAR} 1.3.6.1.4.1.2356.11.2.24.41.1.2
lcsSetupPublicSpotModuleAuthModEmlAuthUserMustAcceptGtc OBJECT-TYPE
    SYNTAX     INTEGER {
                  eNo (0),
                  eYes (1)
            }
    MAX-ACCESS read-only
    STATUS     current
    DESCRIPTION
            "-- empty --"
    ::= { lcsSetupPublicSpotModuleAuthModEmlAuth 2 }

-- {SCALAR} 1.3.6.1.4.1.2356.11.2.24.41.1.3
lcsSetupPublicSpotModuleAuthModEmlAuthSubject OBJECT-TYPE
    SYNTAX     DisplayString (SIZE(0..256))
    MAX-ACCESS read-write
    STATUS     current
    DESCRIPTION
            "-- empty --"
    ::= { lcsSetupPublicSpotModuleAuthModEmlAuth 3 }

-- {SCALAR} 1.3.6.1.4.1.2356.11.2.24.41.1.4
lcsSetupPublicSpotModuleAuthModEmlAuthBody OBJECT-TYPE
    SYNTAX     DisplayString (SIZE(0..256))
    MAX-ACCESS read-write
    STATUS     current
    DESCRIPTION
            "-- empty --"
    ::= { lcsSetupPublicSpotModuleAuthModEmlAuth 4 }

-- {SCALAR} 1.3.6.1.4.1.2356.11.2.24.41.1.5
lcsSetupPublicSpotModuleAuthModEmlAuthMaxRequestAttempts OBJECT-TYPE
    SYNTAX     Integer32 (0..65535)
    MAX-ACCESS read-write
    STATUS     current
    DESCRIPTION
            "-- empty --"
    ::= { lcsSetupPublicSpotModuleAuthModEmlAuth 5 }

-- {SCALAR} 1.3.6.1.4.1.2356.11.2.24.41.1.6
lcsSetupPublicSpotModuleAuthModEmlAuthLocalEMailAddress OBJECT-TYPE
    SYNTAX     DisplayString (SIZE(0..150))
    MAX-ACCESS read-write
    STATUS     current
    DESCRIPTION
            "-- empty --"
    ::= { lcsSetupPublicSpotModuleAuthModEmlAuth 6 }

-- {SCALAR} 1.3.6.1.4.1.2356.11.2.24.41.1.7
lcsSetupPublicSpotModuleAuthModEmlAuthRealName OBJECT-TYPE
    SYNTAX     DisplayString (SIZE(0..150))
    MAX-ACCESS read-write
    STATUS     current
    DESCRIPTION
            "-- empty --"
    ::= { lcsSetupPublicSpotModuleAuthModEmlAuth 7 }

-- {SCALAR} 1.3.6.1.4.1.2356.11.2.24.41.1.8
lcsSetupPublicSpotModuleAuthModEmlAuthBlackWhiteDomainList OBJECT-TYPE
    SYNTAX     INTEGER {
                  eBlacklist (0),
                  eWhitelist (1)
            }
    MAX-ACCESS read-write
    STATUS     current
    DESCRIPTION
            "-- empty --"
    ::= { lcsSetupPublicSpotModuleAuthModEmlAuth 8 }

-- {TABLE} 1.3.6.1.4.1.2356.11.2.24.41.1.9
lcsSetupPublicSpotModuleAuthModEmlAuthDomainListTable OBJECT-TYPE
    SYNTAX     SEQUENCE OF LcsSetupPublicSpotModuleAuthModEmlAuthDomainListEntry
    MAX-ACCESS not-accessible
    STATUS     current
    DESCRIPTION
            "-- empty --"
    ::= { lcsSetupPublicSpotModuleAuthModEmlAuth 9 }

-- {ROW} 1.3.6.1.4.1.2356.11.2.24.41.1.9.1
lcsSetupPublicSpotModuleAuthModEmlAuthDomainListEntry OBJECT-TYPE
    SYNTAX     LcsSetupPublicSpotModuleAuthModEmlAuthDomainListEntry
    MAX-ACCESS not-accessible
    STATUS     current
    DESCRIPTION
            ""
    INDEX {
            lcsSetupPublicSpotModuleAuthModEmlAuthDomainListEntryDomain
          }
    ::= { lcsSetupPublicSpotModuleAuthModEmlAuthDomainListTable 1 }

LcsSetupPublicSpotModuleAuthModEmlAuthDomainListEntry ::= SEQUENCE {
            lcsSetupPublicSpotModuleAuthModEmlAuthDomainListEntryDomain DisplayString
    }

-- {COLUMN} 1.3.6.1.4.1.2356.11.2.24.41.1.9.1.1
lcsSetupPublicSpotModuleAuthModEmlAuthDomainListEntryDomain OBJECT-TYPE
    SYNTAX     DisplayString (SIZE(0..150))
    MAX-ACCESS read-write
    STATUS     current
    DESCRIPTION
            "-- empty --"
    ::= { lcsSetupPublicSpotModuleAuthModEmlAuthDomainListEntry 1 }

-- {TABLE} 1.3.6.1.4.1.2356.11.2.24.41.1.20
lcsSetupPublicSpotModuleAuthModEmlAuthRealNameTable OBJECT-TYPE
    SYNTAX     SEQUENCE OF LcsSetupPublicSpotModuleAuthModEmlAuthRealNameEntry
    MAX-ACCESS not-accessible
    STATUS     current
    DESCRIPTION
            "-- empty --"
    ::= { lcsSetupPublicSpotModuleAuthModEmlAuth 20 }

-- {ROW} 1.3.6.1.4.1.2356.11.2.24.41.1.20.1
lcsSetupPublicSpotModuleAuthModEmlAuthRealNameEntry OBJECT-TYPE
    SYNTAX     LcsSetupPublicSpotModuleAuthModEmlAuthRealNameEntry
    MAX-ACCESS not-accessible
    STATUS     current
    DESCRIPTION
            ""
    INDEX {
            lcsSetupPublicSpotModuleAuthModEmlAuthRealNameEntryLanguage
          }
    ::= { lcsSetupPublicSpotModuleAuthModEmlAuthRealNameTable 1 }

LcsSetupPublicSpotModuleAuthModEmlAuthRealNameEntry ::= SEQUENCE {
            lcsSetupPublicSpotModuleAuthModEmlAuthRealNameEntryLanguage INTEGER,
            lcsSetupPublicSpotModuleAuthModEmlAuthRealNameEntryContent DisplayString
    }

-- {COLUMN} 1.3.6.1.4.1.2356.11.2.24.41.1.20.1.1
lcsSetupPublicSpotModuleAuthModEmlAuthRealNameEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { lcsSetupPublicSpotModuleAuthModEmlAuthRealNameEntry 1 }

-- {COLUMN} 1.3.6.1.4.1.2356.11.2.24.41.1.20.1.2
lcsSetupPublicSpotModuleAuthModEmlAuthRealNameEntryContent OBJECT-TYPE
    SYNTAX     DisplayString (SIZE(0..251))
    MAX-ACCESS read-write
    STATUS     current
    DESCRIPTION
            "-- empty --"
    ::= { lcsSetupPublicSpotModuleAuthModEmlAuthRealNameEntry 2 }

-- {TABLE} 1.3.6.1.4.1.2356.11.2.24.41.1.21
lcsSetupPublicSpotModuleAuthModEmlAuthBodyTable OBJECT-TYPE
    SYNTAX     SEQUENCE OF LcsSetupPublicSpotModuleAuthModEmlAuthBodyEntry
    MAX-ACCESS not-accessible
    STATUS     current
    DESCRIPTION
            "-- empty --"
    ::= { lcsSetupPublicSpotModuleAuthModEmlAuth 21 }

-- {ROW} 1.3.6.1.4.1.2356.11.2.24.41.1.21.1
lcsSetupPublicSpotModuleAuthModEmlAuthBodyEntry OBJECT-TYPE
    SYNTAX     LcsSetupPublicSpotModuleAuthModEmlAuthBodyEntry
    MAX-ACCESS not-accessible
    STATUS     current
    DESCRIPTION
            ""
    INDEX {
            lcsSetupPublicSpotModuleAuthModEmlAuthBodyEntryLanguage
          }
    ::= { lcsSetupPublicSpotModuleAuthModEmlAuthBodyTable 1 }

LcsSetupPublicSpotModuleAuthModEmlAuthBodyEntry ::= SEQUENCE {
            lcsSetupPublicSpotModuleAuthModEmlAuthBodyEntryLanguage INTEGER,
            lcsSetupPublicSpotModuleAuthModEmlAuthBodyEntryContent DisplayString
    }

-- {COLUMN} 1.3.6.1.4.1.2356.11.2.24.41.1.21.1.1
lcsSetupPublicSpotModuleAuthModEmlAuthBodyEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { lcsSetupPublicSpotModuleAuthModEmlAuthBodyEntry 1 }

-- {COLUMN} 1.3.6.1.4.1.2356.11.2.24.41.1.21.1.2
lcsSetupPublicSpotModuleAuthModEmlAuthBodyEntryContent OBJECT-TYPE
    SYNTAX     DisplayString (SIZE(0..251))
    MAX-ACCESS read-write
    STATUS     current
    DESCRIPTION
            "-- empty --"
    ::= { lcsSetupPublicSpotModuleAuthModEmlAuthBodyEntry 2 }

-- {TABLE} 1.3.6.1.4.1.2356.11.2.24.41.1.22
lcsSetupPublicSpotModuleAuthModEmlAuthSubjectTable OBJECT-TYPE
    SYNTAX     SEQUENCE OF LcsSetupPublicSpotModuleAuthModEmlAuthSubjectEntry
    MAX-ACCESS not-accessible
    STATUS     current
    DESCRIPTION
            "-- empty --"
    ::= { lcsSetupPublicSpotModuleAuthModEmlAuth 22 }

-- {ROW} 1.3.6.1.4.1.2356.11.2.24.41.1.22.1
lcsSetupPublicSpotModuleAuthModEmlAuthSubjectEntry OBJECT-TYPE
    SYNTAX     LcsSetupPublicSpotModuleAuthModEmlAuthSubjectEntry
    MAX-ACCESS not-accessible
    STATUS     current
    DESCRIPTION
            ""
    INDEX {
            lcsSetupPublicSpotModuleAuthModEmlAuthSubjectEntryLanguage
          }
    ::= { lcsSetupPublicSpotModuleAuthModEmlAuthSubjectTable 1 }

LcsSetupPublicSpotModuleAuthModEmlAuthSubjectEntry ::= SEQUENCE {
            lcsSetupPublicSpotModuleAuthModEmlAuthSubjectEntryLanguage INTEGER,
            lcsSetupPublicSpotModuleAuthModEmlAuthSubjectEntryContent DisplayString
    }

-- {COLUMN} 1.3.6.1.4.1.2356.11.2.24.41.1.22.1.1
lcsSetupPublicSpotModuleAuthModEmlAuthSubjectEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { lcsSetupPublicSpotModuleAuthModEmlAuthSubjectEntry 1 }

-- {COLUMN} 1.3.6.1.4.1.2356.11.2.24.41.1.22.1.2
lcsSetupPublicSpotModuleAuthModEmlAuthSubjectEntryContent OBJECT-TYPE
    SYNTAX     DisplayString (SIZE(0..251))
    MAX-ACCESS read-write
    STATUS     current
    DESCRIPTION
            "-- empty --"
    ::= { lcsSetupPublicSpotModuleAuthModEmlAuthSubjectEntry 2 }

-- {NODE} 1.3.6.1.4.1.2356.11.2.24.41.2
lcsSetupPublicSpotModuleAuthModEmlSmsAuth OBJECT IDENTIFIER ::= { lcsSetupPublicSpotModuleAuthMod 2 }

-- {SCALAR} 1.3.6.1.4.1.2356.11.2.24.41.2.1
lcsSetupPublicSpotModuleAuthModEmlSmsAuthLimitEMailsPerHour OBJECT-TYPE
    SYNTAX     Integer32 (0..65535)
    MAX-ACCESS read-write
    STATUS     current
    DESCRIPTION
            "-- empty --"
    ::= { lcsSetupPublicSpotModuleAuthModEmlSmsAuth 1 }

-- {SCALAR} 1.3.6.1.4.1.2356.11.2.24.41.2.2
lcsSetupPublicSpotModuleAuthModEmlSmsAuthUserMustAcceptGtc OBJECT-TYPE
    SYNTAX     INTEGER {
                  eNo (0),
                  eYes (1)
            }
    MAX-ACCESS read-only
    STATUS     current
    DESCRIPTION
            "-- empty --"
    ::= { lcsSetupPublicSpotModuleAuthModEmlSmsAuth 2 }

-- {SCALAR} 1.3.6.1.4.1.2356.11.2.24.41.2.3
lcsSetupPublicSpotModuleAuthModEmlSmsAuthSubject OBJECT-TYPE
    SYNTAX     DisplayString (SIZE(0..256))
    MAX-ACCESS read-write
    STATUS     current
    DESCRIPTION
            "-- empty --"
    ::= { lcsSetupPublicSpotModuleAuthModEmlSmsAuth 3 }

-- {SCALAR} 1.3.6.1.4.1.2356.11.2.24.41.2.4
lcsSetupPublicSpotModuleAuthModEmlSmsAuthMaxRequestAttempts OBJECT-TYPE
    SYNTAX     Integer32 (0..65535)
    MAX-ACCESS read-write
    STATUS     current
    DESCRIPTION
            "-- empty --"
    ::= { lcsSetupPublicSpotModuleAuthModEmlSmsAuth 4 }

-- {SCALAR} 1.3.6.1.4.1.2356.11.2.24.41.2.5
lcsSetupPublicSpotModuleAuthModEmlSmsAuthLocalEMailAddress OBJECT-TYPE
    SYNTAX     DisplayString (SIZE(0..150))
    MAX-ACCESS read-write
    STATUS     current
    DESCRIPTION
            "-- empty --"
    ::= { lcsSetupPublicSpotModuleAuthModEmlSmsAuth 5 }

-- {SCALAR} 1.3.6.1.4.1.2356.11.2.24.41.2.6
lcsSetupPublicSpotModuleAuthModEmlSmsAuthRealName OBJECT-TYPE
    SYNTAX     DisplayString (SIZE(0..150))
    MAX-ACCESS read-write
    STATUS     current
    DESCRIPTION
            "-- empty --"
    ::= { lcsSetupPublicSpotModuleAuthModEmlSmsAuth 6 }

-- {SCALAR} 1.3.6.1.4.1.2356.11.2.24.41.2.12
lcsSetupPublicSpotModuleAuthModEmlSmsAuthBody OBJECT-TYPE
    SYNTAX     DisplayString (SIZE(0..256))
    MAX-ACCESS read-write
    STATUS     current
    DESCRIPTION
            "-- empty --"
    ::= { lcsSetupPublicSpotModuleAuthModEmlSmsAuth 12 }

-- {SCALAR} 1.3.6.1.4.1.2356.11.2.24.41.2.13
lcsSetupPublicSpotModuleAuthModEmlSmsAuthGatewayEMailAddress OBJECT-TYPE
    SYNTAX     DisplayString (SIZE(0..150))
    MAX-ACCESS read-write
    STATUS     current
    DESCRIPTION
            "-- empty --"
    ::= { lcsSetupPublicSpotModuleAuthModEmlSmsAuth 13 }

-- {TABLE} 1.3.6.1.4.1.2356.11.2.24.41.2.14
lcsSetupPublicSpotModuleAuthModEmlSmsAuthAlldCtryCodsTable OBJECT-TYPE
    SYNTAX     SEQUENCE OF LcsSetupPublicSpotModuleAuthModEmlSmsAuthAlldCtryCodsEntry
    MAX-ACCESS not-accessible
    STATUS     current
    DESCRIPTION
            ""
    ::= { lcsSetupPublicSpotModuleAuthModEmlSmsAuth 14 }

-- {ROW} 1.3.6.1.4.1.2356.11.2.24.41.2.14.1
lcsSetupPublicSpotModuleAuthModEmlSmsAuthAlldCtryCodsEntry OBJECT-TYPE
    SYNTAX     LcsSetupPublicSpotModuleAuthModEmlSmsAuthAlldCtryCodsEntry
    MAX-ACCESS not-accessible
    STATUS     current
    DESCRIPTION
            ""
    INDEX {
            lcsSetupPublicSpotModuleAuthModEmlSmsAuthAlldCtryCodsEntryName
          }
    ::= { lcsSetupPublicSpotModuleAuthModEmlSmsAuthAlldCtryCodsTable 1 }

LcsSetupPublicSpotModuleAuthModEmlSmsAuthAlldCtryCodsEntry ::= SEQUENCE {
            lcsSetupPublicSpotModuleAuthModEmlSmsAuthAlldCtryCodsEntryName DisplayString,
            lcsSetupPublicSpotModuleAuthModEmlSmsAuthAlldCtryCodsEntryCode Integer32
    }

-- {COLUMN} 1.3.6.1.4.1.2356.11.2.24.41.2.14.1.1
lcsSetupPublicSpotModuleAuthModEmlSmsAuthAlldCtryCodsEntryName OBJECT-TYPE
    SYNTAX     DisplayString (SIZE(0..100))
    MAX-ACCESS read-write
    STATUS     current
    DESCRIPTION
            "-- empty --"
    ::= { lcsSetupPublicSpotModuleAuthModEmlSmsAuthAlldCtryCodsEntry 1 }

-- {COLUMN} 1.3.6.1.4.1.2356.11.2.24.41.2.14.1.2
lcsSetupPublicSpotModuleAuthModEmlSmsAuthAlldCtryCodsEntryCode OBJECT-TYPE
    SYNTAX     Integer32 (0..65535)
    MAX-ACCESS read-write
    STATUS     current
    DESCRIPTION
            "-- empty --"
    ::= { lcsSetupPublicSpotModuleAuthModEmlSmsAuthAlldCtryCodsEntry 2 }

-- {SCALAR} 1.3.6.1.4.1.2356.11.2.24.41.2.15
lcsSetupPublicSpotModuleAuthModEmlSmsAuthSendSms OBJECT-TYPE
    SYNTAX     INTEGER {
                  eSmsGateway (0),
                  eHttp2sms (1),
                  eSendDirect (2)
            }
    MAX-ACCESS read-write
    STATUS     current
    DESCRIPTION
            "-- empty --"
    ::= { lcsSetupPublicSpotModuleAuthModEmlSmsAuth 15 }

-- {SCALAR} 1.3.6.1.4.1.2356.11.2.24.41.2.16
lcsSetupPublicSpotModuleAuthModEmlSmsAuthHttpUserName OBJECT-TYPE
    SYNTAX     DisplayString (SIZE(0..16))
    MAX-ACCESS read-write
    STATUS     current
    DESCRIPTION
            "-- empty --"
    ::= { lcsSetupPublicSpotModuleAuthModEmlSmsAuth 16 }

-- {SCALAR} 1.3.6.1.4.1.2356.11.2.24.41.2.17
lcsSetupPublicSpotModuleAuthModEmlSmsAuthHttpPassword OBJECT-TYPE
    SYNTAX     DisplayString (SIZE(0..16))
    MAX-ACCESS read-write
    STATUS     current
    DESCRIPTION
            "-- empty --"
    ::= { lcsSetupPublicSpotModuleAuthModEmlSmsAuth 17 }

-- {SCALAR} 1.3.6.1.4.1.2356.11.2.24.41.2.18
lcsSetupPublicSpotModuleAuthModEmlSmsAuthHttpGatewayAddress OBJECT-TYPE
    SYNTAX     DisplayString (SIZE(0..63))
    MAX-ACCESS read-write
    STATUS     current
    DESCRIPTION
            "-- empty --"
    ::= { lcsSetupPublicSpotModuleAuthModEmlSmsAuth 18 }

-- {NODE} 1.3.6.1.4.1.2356.11.2.24.41.2.19
lcsSetupPublicSpotModuleAuthModEmlSmsAuthSslNew OBJECT IDENTIFIER ::= { lcsSetupPublicSpotModuleAuthModEmlSmsAuth 19 }

-- {SCALAR} 1.3.6.1.4.1.2356.11.2.24.41.2.19.1
lcsSetupPublicSpotModuleAuthModEmlSmsAuthSslNewVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupPublicSpotModuleAuthModEmlSmsAuthSslNew 1 }

-- {SCALAR} 1.3.6.1.4.1.2356.11.2.24.41.2.19.2
lcsSetupPublicSpotModuleAuthModEmlSmsAuthSslNewKeyexAlgorithms OBJECT-TYPE
    SYNTAX     BITS {
                  eEcdhe (27),
                  eDhe (29),
                  eRsa (31)
            }
    MAX-ACCESS read-write
    STATUS     current
    DESCRIPTION
            "-- empty --"
    ::= { lcsSetupPublicSpotModuleAuthModEmlSmsAuthSslNew 2 }

-- {SCALAR} 1.3.6.1.4.1.2356.11.2.24.41.2.19.3
lcsSetupPublicSpotModuleAuthModEmlSmsAuthSslNewCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupPublicSpotModuleAuthModEmlSmsAuthSslNew 3 }

-- {SCALAR} 1.3.6.1.4.1.2356.11.2.24.41.2.19.4
lcsSetupPublicSpotModuleAuthModEmlSmsAuthSslNewHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupPublicSpotModuleAuthModEmlSmsAuthSslNew 4 }

-- {SCALAR} 1.3.6.1.4.1.2356.11.2.24.41.2.19.5
lcsSetupPublicSpotModuleAuthModEmlSmsAuthSslNewPreferPfs OBJECT-TYPE
    SYNTAX     BITS {
                  eNo (0),
                  eYes (7)
            }
    MAX-ACCESS read-write
    STATUS     current
    DESCRIPTION
            "-- empty --"
    ::= { lcsSetupPublicSpotModuleAuthModEmlSmsAuthSslNew 5 }

-- {SCALAR} 1.3.6.1.4.1.2356.11.2.24.41.2.19.6
lcsSetupPublicSpotModuleAuthModEmlSmsAuthSslNewRenegotiations OBJECT-TYPE
    SYNTAX     INTEGER {
                  eForbidden (0),
                  eAllowed (1),
                  eIgnored (2)
            }
    MAX-ACCESS read-write
    STATUS     current
    DESCRIPTION
            "-- empty --"
    ::= { lcsSetupPublicSpotModuleAuthModEmlSmsAuthSslNew 6 }

-- {SCALAR} 1.3.6.1.4.1.2356.11.2.24.41.2.19.7
lcsSetupPublicSpotModuleAuthModEmlSmsAuthSslNewEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupPublicSpotModuleAuthModEmlSmsAuthSslNew 7 }

-- {SCALAR} 1.3.6.1.4.1.2356.11.2.24.41.2.19.21
lcsSetupPublicSpotModuleAuthModEmlSmsAuthSslNewSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupPublicSpotModuleAuthModEmlSmsAuthSslNew 21 }

-- {TABLE} 1.3.6.1.4.1.2356.11.2.24.41.2.23
lcsSetupPublicSpotModuleAuthModEmlSmsAuthRealNameTable OBJECT-TYPE
    SYNTAX     SEQUENCE OF LcsSetupPublicSpotModuleAuthModEmlSmsAuthRealNameEntry
    MAX-ACCESS not-accessible
    STATUS     current
    DESCRIPTION
            "-- empty --"
    ::= { lcsSetupPublicSpotModuleAuthModEmlSmsAuth 23 }

-- {ROW} 1.3.6.1.4.1.2356.11.2.24.41.2.23.1
lcsSetupPublicSpotModuleAuthModEmlSmsAuthRealNameEntry OBJECT-TYPE
    SYNTAX     LcsSetupPublicSpotModuleAuthModEmlSmsAuthRealNameEntry
    MAX-ACCESS not-accessible
    STATUS     current
    DESCRIPTION
            ""
    INDEX {
            lcsSetupPublicSpotModuleAuthModEmlSmsAuthRealNameEntryLanguage
          }
    ::= { lcsSetupPublicSpotModuleAuthModEmlSmsAuthRealNameTable 1 }

LcsSetupPublicSpotModuleAuthModEmlSmsAuthRealNameEntry ::= SEQUENCE {
            lcsSetupPublicSpotModuleAuthModEmlSmsAuthRealNameEntryLanguage INTEGER,
            lcsSetupPublicSpotModuleAuthModEmlSmsAuthRealNameEntryContent DisplayString
    }

-- {COLUMN} 1.3.6.1.4.1.2356.11.2.24.41.2.23.1.1
lcsSetupPublicSpotModuleAuthModEmlSmsAuthRealNameEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { lcsSetupPublicSpotModuleAuthModEmlSmsAuthRealNameEntry 1 }

-- {COLUMN} 1.3.6.1.4.1.2356.11.2.24.41.2.23.1.2
lcsSetupPublicSpotModuleAuthModEmlSmsAuthRealNameEntryContent OBJECT-TYPE
    SYNTAX     DisplayString (SIZE(0..251))
    MAX-ACCESS read-write
    STATUS     current
    DESCRIPTION
            "-- empty --"
    ::= { lcsSetupPublicSpotModuleAuthModEmlSmsAuthRealNameEntry 2 }

-- {TABLE} 1.3.6.1.4.1.2356.11.2.24.41.2.24
lcsSetupPublicSpotModuleAuthModEmlSmsAuthBodyTable OBJECT-TYPE
    SYNTAX     SEQUENCE OF LcsSetupPublicSpotModuleAuthModEmlSmsAuthBodyEntry
    MAX-ACCESS not-accessible
    STATUS     current
    DESCRIPTION
            "-- empty --"
    ::= { lcsSetupPublicSpotModuleAuthModEmlSmsAuth 24 }

-- {ROW} 1.3.6.1.4.1.2356.11.2.24.41.2.24.1
lcsSetupPublicSpotModuleAuthModEmlSmsAuthBodyEntry OBJECT-TYPE
    SYNTAX     LcsSetupPublicSpotModuleAuthModEmlSmsAuthBodyEntry
    MAX-ACCESS not-accessible
    STATUS     current
    DESCRIPTION
            ""
    INDEX {
            lcsSetupPublicSpotModuleAuthModEmlSmsAuthBodyEntryLanguage
          }
    ::= { lcsSetupPublicSpotModuleAuthModEmlSmsAuthBodyTable 1 }

LcsSetupPublicSpotModuleAuthModEmlSmsAuthBodyEntry ::= SEQUENCE {
            lcsSetupPublicSpotModuleAuthModEmlSmsAuthBodyEntryLanguage INTEGER,
            lcsSetupPublicSpotModuleAuthModEmlSmsAuthBodyEntryContent DisplayString
    }

-- {COLUMN} 1.3.6.1.4.1.2356.11.2.24.41.2.24.1.1
lcsSetupPublicSpotModuleAuthModEmlSmsAuthBodyEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { lcsSetupPublicSpotModuleAuthModEmlSmsAuthBodyEntry 1 }

-- {COLUMN} 1.3.6.1.4.1.2356.11.2.24.41.2.24.1.2
lcsSetupPublicSpotModuleAuthModEmlSmsAuthBodyEntryContent OBJECT-TYPE
    SYNTAX     DisplayString (SIZE(0..251))
    MAX-ACCESS read-write
    STATUS     current
    DESCRIPTION
            "-- empty --"
    ::= { lcsSetupPublicSpotModuleAuthModEmlSmsAuthBodyEntry 2 }

-- {TABLE} 1.3.6.1.4.1.2356.11.2.24.41.2.25
lcsSetupPublicSpotModuleAuthModEmlSmsAuthSubjectTable OBJECT-TYPE
    SYNTAX     SEQUENCE OF LcsSetupPublicSpotModuleAuthModEmlSmsAuthSubjectEntry
    MAX-ACCESS not-accessible
    STATUS     current
    DESCRIPTION
            "-- empty --"
    ::= { lcsSetupPublicSpotModuleAuthModEmlSmsAuth 25 }

-- {ROW} 1.3.6.1.4.1.2356.11.2.24.41.2.25.1
lcsSetupPublicSpotModuleAuthModEmlSmsAuthSubjectEntry OBJECT-TYPE
    SYNTAX     LcsSetupPublicSpotModuleAuthModEmlSmsAuthSubjectEntry
    MAX-ACCESS not-accessible
    STATUS     current
    DESCRIPTION
            ""
    INDEX {
            lcsSetupPublicSpotModuleAuthModEmlSmsAuthSubjectEntryLanguage
          }
    ::= { lcsSetupPublicSpotModuleAuthModEmlSmsAuthSubjectTable 1 }

LcsSetupPublicSpotModuleAuthModEmlSmsAuthSubjectEntry ::= SEQUENCE {
            lcsSetupPublicSpotModuleAuthModEmlSmsAuthSubjectEntryLanguage INTEGER,
            lcsSetupPublicSpotModuleAuthModEmlSmsAuthSubjectEntryContent DisplayString
    }

-- {COLUMN} 1.3.6.1.4.1.2356.11.2.24.41.2.25.1.1
lcsSetupPublicSpotModuleAuthModEmlSmsAuthSubjectEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { lcsSetupPublicSpotModuleAuthModEmlSmsAuthSubjectEntry 1 }

-- {COLUMN} 1.3.6.1.4.1.2356.11.2.24.41.2.25.1.2
lcsSetupPublicSpotModuleAuthModEmlSmsAuthSubjectEntryContent OBJECT-TYPE
    SYNTAX     DisplayString (SIZE(0..251))
    MAX-ACCESS read-write
    STATUS     current
    DESCRIPTION
            "-- empty --"
    ::= { lcsSetupPublicSpotModuleAuthModEmlSmsAuthSubjectEntry 2 }

-- {TABLE} 1.3.6.1.4.1.2356.11.2.24.41.2.26
lcsSetupPublicSpotModuleAuthModEmlSmsAuthAlwPrefTable OBJECT-TYPE
    SYNTAX     SEQUENCE OF LcsSetupPublicSpotModuleAuthModEmlSmsAuthAlwPrefEntry
    MAX-ACCESS not-accessible
    STATUS     current
    DESCRIPTION
            ""
    ::= { lcsSetupPublicSpotModuleAuthModEmlSmsAuth 26 }

-- {ROW} 1.3.6.1.4.1.2356.11.2.24.41.2.26.1
lcsSetupPublicSpotModuleAuthModEmlSmsAuthAlwPrefEntry OBJECT-TYPE
    SYNTAX     LcsSetupPublicSpotModuleAuthModEmlSmsAuthAlwPrefEntry
    MAX-ACCESS not-accessible
    STATUS     current
    DESCRIPTION
            ""
    INDEX {
            lcsSetupPublicSpotModuleAuthModEmlSmsAuthAlwPrefEntryCName
          }
    ::= { lcsSetupPublicSpotModuleAuthModEmlSmsAuthAlwPrefTable 1 }

LcsSetupPublicSpotModuleAuthModEmlSmsAuthAlwPrefEntry ::= SEQUENCE {
            lcsSetupPublicSpotModuleAuthModEmlSmsAuthAlwPrefEntryCName DisplayString,
            lcsSetupPublicSpotModuleAuthModEmlSmsAuthAlwPrefEntryAlwPref DisplayString
    }

-- {COLUMN} 1.3.6.1.4.1.2356.11.2.24.41.2.26.1.1
lcsSetupPublicSpotModuleAuthModEmlSmsAuthAlwPrefEntryCName OBJECT-TYPE
    SYNTAX     DisplayString (SIZE(0..100))
    MAX-ACCESS read-write
    STATUS     current
    DESCRIPTION
            ""
    ::= { lcsSetupPublicSpotModuleAuthModEmlSmsAuthAlwPrefEntry 1 }

-- {COLUMN} 1.3.6.1.4.1.2356.11.2.24.41.2.26.1.2
lcsSetupPublicSpotModuleAuthModEmlSmsAuthAlwPrefEntryAlwPref OBJECT-TYPE
    SYNTAX     DisplayString (SIZE(0..254))
    MAX-ACCESS read-write
    STATUS     current
    DESCRIPTION
            ""
    ::= { lcsSetupPublicSpotModuleAuthModEmlSmsAuthAlwPrefEntry 2 }

-- {NODE} 1.3.6.1.4.1.2356.11.2.24.41.3
lcsSetupPublicSpotModuleAuthModUserTemplate OBJECT IDENTIFIER ::= { lcsSetupPublicSpotModuleAuthMod 3 }

-- {SCALAR} 1.3.6.1.4.1.2356.11.2.24.41.3.2
lcsSetupPublicSpotModuleAuthModUserTemplateComment OBJECT-TYPE
    SYNTAX     DisplayString (SIZE(0..251))
    MAX-ACCESS read-write
    STATUS     current
    DESCRIPTION
            "-- empty --"
    ::= { lcsSetupPublicSpotModuleAuthModUserTemplate 2 }

-- {SCALAR} 1.3.6.1.4.1.2356.11.2.24.41.3.3
lcsSetupPublicSpotModuleAuthModUserTemplateVolumeBudget OBJECT-TYPE
    SYNTAX     Integer32 (0..2147483647)
    MAX-ACCESS read-write
    STATUS     current
    DESCRIPTION
            "-- empty --"
    ::= { lcsSetupPublicSpotModuleAuthModUserTemplate 3 }

-- {SCALAR} 1.3.6.1.4.1.2356.11.2.24.41.3.4
lcsSetupPublicSpotModuleAuthModUserTemplateTimeBudget OBJECT-TYPE
    SYNTAX     Integer32 (0..2147483647)
    MAX-ACCESS read-write
    STATUS     current
    DESCRIPTION
            "-- empty --"
    ::= { lcsSetupPublicSpotModuleAuthModUserTemplate 4 }

-- {SCALAR} 1.3.6.1.4.1.2356.11.2.24.41.3.5
lcsSetupPublicSpotModuleAuthModUserTemplateRelExpiry OBJECT-TYPE
    SYNTAX     Integer32 (0..2147483647)
    MAX-ACCESS read-write
    STATUS     current
    DESCRIPTION
            "-- empty --"
    ::= { lcsSetupPublicSpotModuleAuthModUserTemplate 5 }

-- {SCALAR} 1.3.6.1.4.1.2356.11.2.24.41.3.6
lcsSetupPublicSpotModuleAuthModUserTemplateAbsExpiry OBJECT-TYPE
    SYNTAX     Integer32 (0..2147483647)
    MAX-ACCESS read-write
    STATUS     current
    DESCRIPTION
            "-- empty --"
    ::= { lcsSetupPublicSpotModuleAuthModUserTemplate 6 }

-- {SCALAR} 1.3.6.1.4.1.2356.11.2.24.41.3.7
lcsSetupPublicSpotModuleAuthModUserTemplateExpiryType OBJECT-TYPE
    SYNTAX     BITS {
                  eNone (0),
                  eRelative (6),
                  eAbsolute (7)
            }
    MAX-ACCESS read-write
    STATUS     current
    DESCRIPTION
            "-- empty --"
    ::= { lcsSetupPublicSpotModuleAuthModUserTemplate 7 }

-- {SCALAR} 1.3.6.1.4.1.2356.11.2.24.41.3.8
lcsSetupPublicSpotModuleAuthModUserTemplateMaxConcurrentLogins OBJECT-TYPE
    SYNTAX     Integer32 (0..2147483647)
    MAX-ACCESS read-write
    STATUS     current
    DESCRIPTION
            "-- empty --"
    ::= { lcsSetupPublicSpotModuleAuthModUserTemplate 8 }

-- {SCALAR} 1.3.6.1.4.1.2356.11.2.24.41.3.9
lcsSetupPublicSpotModuleAuthModUserTemplateMultipleLogin OBJECT-TYPE
    SYNTAX     INTEGER {
                  eYes (0),
                  eNo (1)
            }
    MAX-ACCESS read-write
    STATUS     current
    DESCRIPTION
            "-- empty --"
    ::= { lcsSetupPublicSpotModuleAuthModUserTemplate 9 }

-- {SCALAR} 1.3.6.1.4.1.2356.11.2.24.41.3.10
lcsSetupPublicSpotModuleAuthModUserTemplateTxLimit OBJECT-TYPE
    SYNTAX     Integer32 (0..2147483647)
    MAX-ACCESS read-write
    STATUS     current
    DESCRIPTION
            "-- empty --"
    ::= { lcsSetupPublicSpotModuleAuthModUserTemplate 10 }

-- {SCALAR} 1.3.6.1.4.1.2356.11.2.24.41.3.11
lcsSetupPublicSpotModuleAuthModUserTemplateRxLimit OBJECT-TYPE
    SYNTAX     Integer32 (0..2147483647)
    MAX-ACCESS read-write
    STATUS     current
    DESCRIPTION
            "-- empty --"
    ::= { lcsSetupPublicSpotModuleAuthModUserTemplate 11 }

-- {SCALAR} 1.3.6.1.4.1.2356.11.2.24.41.3.12
lcsSetupPublicSpotModuleAuthModUserTemplateAbsExpiryUnit OBJECT-TYPE
    SYNTAX     INTEGER {
                  eMinuteS (1),
                  eHourS (2),
                  eDayS (3)
            }
    MAX-ACCESS read-write
    STATUS     current
    DESCRIPTION
            "-- empty --"
    ::= { lcsSetupPublicSpotModuleAuthModUserTemplate 12 }

-- {NODE} 1.3.6.1.4.1.2356.11.2.24.41.4
lcsSetupPublicSpotModuleAuthModNoAuth OBJECT IDENTIFIER ::= { lcsSetupPublicSpotModuleAuthMod 4 }

-- {SCALAR} 1.3.6.1.4.1.2356.11.2.24.41.4.1
lcsSetupPublicSpotModuleAuthModNoAuthMaxRequestPerHour OBJECT-TYPE
    SYNTAX     Integer32 (0..65535)
    MAX-ACCESS read-write
    STATUS     current
    DESCRIPTION
            "-- empty --"
    ::= { lcsSetupPublicSpotModuleAuthModNoAuth 1 }

-- {SCALAR} 1.3.6.1.4.1.2356.11.2.24.41.4.2
lcsSetupPublicSpotModuleAuthModNoAuthUserAccountsPerDay OBJECT-TYPE
    SYNTAX     Integer32 (0..65535)
    MAX-ACCESS read-write
    STATUS     current
    DESCRIPTION
            "-- empty --"
    ::= { lcsSetupPublicSpotModuleAuthModNoAuth 2 }

-- {SCALAR} 1.3.6.1.4.1.2356.11.2.24.41.4.3
lcsSetupPublicSpotModuleAuthModNoAuthUsernamePrefix OBJECT-TYPE
    SYNTAX     DisplayString (SIZE(0..10))
    MAX-ACCESS read-write
    STATUS     current
    DESCRIPTION
            "-- empty --"
    ::= { lcsSetupPublicSpotModuleAuthModNoAuth 3 }

-- {SCALAR} 1.3.6.1.4.1.2356.11.2.24.41.4.4
lcsSetupPublicSpotModuleAuthModNoAuthRequireEMail OBJECT-TYPE
    SYNTAX     INTEGER {
                  eNo (0),
                  eYes (1)
            }
    MAX-ACCESS read-write
    STATUS     current
    DESCRIPTION
            "-- empty --"
    ::= { lcsSetupPublicSpotModuleAuthModNoAuth 4 }

-- {SCALAR} 1.3.6.1.4.1.2356.11.2.24.41.4.5
lcsSetupPublicSpotModuleAuthModNoAuthSaveInMin OBJECT-TYPE
    SYNTAX     Integer32 (0..65535)
    MAX-ACCESS read-write
    STATUS     current
    DESCRIPTION
            "-- empty --"
    ::= { lcsSetupPublicSpotModuleAuthModNoAuth 5 }

-- {SCALAR} 1.3.6.1.4.1.2356.11.2.24.41.4.6
lcsSetupPublicSpotModuleAuthModNoAuthMailInMin OBJECT-TYPE
    SYNTAX     Integer32 (0..65535)
    MAX-ACCESS read-write
    STATUS     current
    DESCRIPTION
            "-- empty --"
    ::= { lcsSetupPublicSpotModuleAuthModNoAuth 6 }

-- {SCALAR} 1.3.6.1.4.1.2356.11.2.24.41.4.7
lcsSetupPublicSpotModuleAuthModNoAuthEMailListRecipient OBJECT-TYPE
    SYNTAX     DisplayString (SIZE(0..150))
    MAX-ACCESS read-write
    STATUS     current
    DESCRIPTION
            "-- empty --"
    ::= { lcsSetupPublicSpotModuleAuthModNoAuth 7 }

-- {SCALAR} 1.3.6.1.4.1.2356.11.2.24.41.4.8
lcsSetupPublicSpotModuleAuthModNoAuthUnlockAccountCreation OBJECT-TYPE
    SYNTAX     INTEGER {
                  eNo (0),
                  eYes (1)
            }
    MAX-ACCESS read-write
    STATUS     current
    DESCRIPTION
            "-- empty --"
    ::= { lcsSetupPublicSpotModuleAuthModNoAuth 8 }

-- {SCALAR} 1.3.6.1.4.1.2356.11.2.24.41.4.9
lcsSetupPublicSpotModuleAuthModNoAuthUnlockDailyOnHr OBJECT-TYPE
    SYNTAX     Integer32 (0..255)
    MAX-ACCESS read-write
    STATUS     current
    DESCRIPTION
            "-- empty --"
    ::= { lcsSetupPublicSpotModuleAuthModNoAuth 9 }

-- {NODE} 1.3.6.1.4.1.2356.11.2.24.41.5
lcsSetupPublicSpotModuleAuthModRadiusServer OBJECT IDENTIFIER ::= { lcsSetupPublicSpotModuleAuthMod 5 }

-- {SCALAR} 1.3.6.1.4.1.2356.11.2.24.41.5.1
lcsSetupPublicSpotModuleAuthModRadiusServerProvider OBJECT-TYPE
    SYNTAX     DisplayString (SIZE(0..16))
    MAX-ACCESS read-write
    STATUS     current
    DESCRIPTION
            "-- empty --"
    ::= { lcsSetupPublicSpotModuleAuthModRadiusServer 1 }

-- {SCALAR} 1.3.6.1.4.1.2356.11.2.24.41.5.2
lcsSetupPublicSpotModuleAuthModRadiusServerName OBJECT-TYPE
    SYNTAX     DisplayString (SIZE(0..64))
    MAX-ACCESS read-write
    STATUS     current
    DESCRIPTION
            "-- empty --"
    ::= { lcsSetupPublicSpotModuleAuthModRadiusServer 2 }

-- {SCALAR} 1.3.6.1.4.1.2356.11.2.24.41.5.3
lcsSetupPublicSpotModuleAuthModRadiusServerPassword OBJECT-TYPE
    SYNTAX     DisplayString (SIZE(0..16))
    MAX-ACCESS read-write
    STATUS     current
    DESCRIPTION
            "-- empty --"
    ::= { lcsSetupPublicSpotModuleAuthModRadiusServer 3 }

-- {NODE} 1.3.6.1.4.1.2356.11.2.24.41.5.4
lcsSetupPublicSpotModuleAuthModRadiusServerSslNew OBJECT IDENTIFIER ::= { lcsSetupPublicSpotModuleAuthModRadiusServer 4 }

-- {SCALAR} 1.3.6.1.4.1.2356.11.2.24.41.5.4.1
lcsSetupPublicSpotModuleAuthModRadiusServerSslNewVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupPublicSpotModuleAuthModRadiusServerSslNew 1 }

-- {SCALAR} 1.3.6.1.4.1.2356.11.2.24.41.5.4.2
lcsSetupPublicSpotModuleAuthModRadiusServerSslNewKeyexAlgorithms OBJECT-TYPE
    SYNTAX     BITS {
                  eEcdhe (27),
                  eDhe (29),
                  eRsa (31)
            }
    MAX-ACCESS read-write
    STATUS     current
    DESCRIPTION
            "-- empty --"
    ::= { lcsSetupPublicSpotModuleAuthModRadiusServerSslNew 2 }

-- {SCALAR} 1.3.6.1.4.1.2356.11.2.24.41.5.4.3
lcsSetupPublicSpotModuleAuthModRadiusServerSslNewCryptoAlgo OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupPublicSpotModuleAuthModRadiusServerSslNew 3 }

-- {SCALAR} 1.3.6.1.4.1.2356.11.2.24.41.5.4.4
lcsSetupPublicSpotModuleAuthModRadiusServerSslNewHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupPublicSpotModuleAuthModRadiusServerSslNew 4 }

-- {SCALAR} 1.3.6.1.4.1.2356.11.2.24.41.5.4.5
lcsSetupPublicSpotModuleAuthModRadiusServerSslNewPreferPfs OBJECT-TYPE
    SYNTAX     BITS {
                  eNo (0),
                  eYes (7)
            }
    MAX-ACCESS read-write
    STATUS     current
    DESCRIPTION
            "-- empty --"
    ::= { lcsSetupPublicSpotModuleAuthModRadiusServerSslNew 5 }

-- {SCALAR} 1.3.6.1.4.1.2356.11.2.24.41.5.4.6
lcsSetupPublicSpotModuleAuthModRadiusServerSslNewRenegotiations OBJECT-TYPE
    SYNTAX     INTEGER {
                  eForbidden (0),
                  eAllowed (1),
                  eIgnored (2)
            }
    MAX-ACCESS read-write
    STATUS     current
    DESCRIPTION
            "-- empty --"
    ::= { lcsSetupPublicSpotModuleAuthModRadiusServerSslNew 6 }

-- {SCALAR} 1.3.6.1.4.1.2356.11.2.24.41.5.4.7
lcsSetupPublicSpotModuleAuthModRadiusServerSslNewEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupPublicSpotModuleAuthModRadiusServerSslNew 7 }

-- {SCALAR} 1.3.6.1.4.1.2356.11.2.24.41.5.4.21
lcsSetupPublicSpotModuleAuthModRadiusServerSslNewSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupPublicSpotModuleAuthModRadiusServerSslNew 21 }

-- {NODE} 1.3.6.1.4.1.2356.11.2.24.42
lcsSetupPublicSpotModuleWispr OBJECT IDENTIFIER ::= { lcsSetupPublicSpotModule 42 }

-- {SCALAR} 1.3.6.1.4.1.2356.11.2.24.42.1
lcsSetupPublicSpotModuleWisprOperating OBJECT-TYPE
    SYNTAX     INTEGER {
                  eNo (0),
                  eYes (1)
            }
    MAX-ACCESS read-write
    STATUS     current
    DESCRIPTION
            "-- empty --"
    ::= { lcsSetupPublicSpotModuleWispr 1 }

-- {SCALAR} 1.3.6.1.4.1.2356.11.2.24.42.2
lcsSetupPublicSpotModuleWisprLocationId OBJECT-TYPE
    SYNTAX     DisplayString (SIZE(0..255))
    MAX-ACCESS read-write
    STATUS     current
    DESCRIPTION
            "-- empty --"
    ::= { lcsSetupPublicSpotModuleWispr 2 }

-- {SCALAR} 1.3.6.1.4.1.2356.11.2.24.42.3
lcsSetupPublicSpotModuleWisprOperatorName OBJECT-TYPE
    SYNTAX     DisplayString (SIZE(0..255))
    MAX-ACCESS read-write
    STATUS     current
    DESCRIPTION
            "-- empty --"
    ::= { lcsSetupPublicSpotModuleWispr 3 }

-- {SCALAR} 1.3.6.1.4.1.2356.11.2.24.42.4
lcsSetupPublicSpotModuleWisprLocationName OBJECT-TYPE
    SYNTAX     DisplayString (SIZE(0..255))
    MAX-ACCESS read-write
    STATUS     current
    DESCRIPTION
            "-- empty --"
    ::= { lcsSetupPublicSpotModuleWispr 4 }

-- {SCALAR} 1.3.6.1.4.1.2356.11.2.24.42.5
lcsSetupPublicSpotModuleWisprLoginUrl OBJECT-TYPE
    SYNTAX     DisplayString (SIZE(0..255))
    MAX-ACCESS read-write
    STATUS     current
    DESCRIPTION
            "-- empty --"
    ::= { lcsSetupPublicSpotModuleWispr 5 }

-- {SCALAR} 1.3.6.1.4.1.2356.11.2.24.42.6
lcsSetupPublicSpotModuleWisprLogoffUrl OBJECT-TYPE
    SYNTAX     DisplayString (SIZE(0..255))
    MAX-ACCESS read-write
    STATUS     current
    DESCRIPTION
            "-- empty --"
    ::= { lcsSetupPublicSpotModuleWispr 6 }

-- {SCALAR} 1.3.6.1.4.1.2356.11.2.24.42.7
lcsSetupPublicSpotModuleWisprAbortLoginUrl OBJECT-TYPE
    SYNTAX     DisplayString (SIZE(0..255))
    MAX-ACCESS read-write
    STATUS     current
    DESCRIPTION
            "-- empty --"
    ::= { lcsSetupPublicSpotModuleWispr 7 }

-- {SCALAR} 1.3.6.1.4.1.2356.11.2.24.42.8
lcsSetupPublicSpotModuleWisprMaxAuthenFailure OBJECT-TYPE
    SYNTAX     Integer32 (0..65535)
    MAX-ACCESS read-write
    STATUS     current
    DESCRIPTION
            "-- empty --"
    ::= { lcsSetupPublicSpotModuleWispr 8 }

-- {NODE} 1.3.6.1.4.1.2356.11.2.24.43
lcsSetupPublicSpotModuleAdvertisement OBJECT IDENTIFIER ::= { lcsSetupPublicSpotModule 43 }

-- {SCALAR} 1.3.6.1.4.1.2356.11.2.24.43.1
lcsSetupPublicSpotModuleAdvertisementOperating OBJECT-TYPE
    SYNTAX     INTEGER {
                  eNo (0),
                  eYes (1)
            }
    MAX-ACCESS read-write
    STATUS     current
    DESCRIPTION
            "-- empty --"
    ::= { lcsSetupPublicSpotModuleAdvertisement 1 }

-- {SCALAR} 1.3.6.1.4.1.2356.11.2.24.43.2
lcsSetupPublicSpotModuleAdvertisementInterval OBJECT-TYPE
    SYNTAX     Integer32 (0..65535)
    MAX-ACCESS read-write
    STATUS     current
    DESCRIPTION
            "-- empty --"
    ::= { lcsSetupPublicSpotModuleAdvertisement 2 }

-- {TABLE} 1.3.6.1.4.1.2356.11.2.24.43.3
lcsSetupPublicSpotModuleAdvertisementUrlTable OBJECT-TYPE
    SYNTAX     SEQUENCE OF LcsSetupPublicSpotModuleAdvertisementUrlEntry
    MAX-ACCESS not-accessible
    STATUS     current
    DESCRIPTION
            "-- empty --"
    ::= { lcsSetupPublicSpotModuleAdvertisement 3 }

-- {ROW} 1.3.6.1.4.1.2356.11.2.24.43.3.1
lcsSetupPublicSpotModuleAdvertisementUrlEntry OBJECT-TYPE
    SYNTAX     LcsSetupPublicSpotModuleAdvertisementUrlEntry
    MAX-ACCESS not-accessible
    STATUS     current
    DESCRIPTION
            ""
    INDEX {
            lcsSetupPublicSpotModuleAdvertisementUrlEntryContent
          }
    ::= { lcsSetupPublicSpotModuleAdvertisementUrlTable 1 }

LcsSetupPublicSpotModuleAdvertisementUrlEntry ::= SEQUENCE {
            lcsSetupPublicSpotModuleAdvertisementUrlEntryContent DisplayString
    }

-- {COLUMN} 1.3.6.1.4.1.2356.11.2.24.43.3.1.1
lcsSetupPublicSpotModuleAdvertisementUrlEntryContent OBJECT-TYPE
    SYNTAX     DisplayString (SIZE(0..150))
    MAX-ACCESS read-write
    STATUS     current
    DESCRIPTION
            "-- empty --"
    ::= { lcsSetupPublicSpotModuleAdvertisementUrlEntry 1 }

-- {TABLE} 1.3.6.1.4.1.2356.11.2.24.43.4
lcsSetupPublicSpotModuleAdvertisementUsrAgtWhtLstTable OBJECT-TYPE
    SYNTAX     SEQUENCE OF LcsSetupPublicSpotModuleAdvertisementUsrAgtWhtLstEntry
    MAX-ACCESS not-accessible
    STATUS     current
    DESCRIPTION
            ""
    ::= { lcsSetupPublicSpotModuleAdvertisement 4 }

-- {ROW} 1.3.6.1.4.1.2356.11.2.24.43.4.1
lcsSetupPublicSpotModuleAdvertisementUsrAgtWhtLstEntry OBJECT-TYPE
    SYNTAX     LcsSetupPublicSpotModuleAdvertisementUsrAgtWhtLstEntry
    MAX-ACCESS not-accessible
    STATUS     current
    DESCRIPTION
            ""
    INDEX {
            lcsSetupPublicSpotModuleAdvertisementUsrAgtWhtLstEntryUserAgent
          }
    ::= { lcsSetupPublicSpotModuleAdvertisementUsrAgtWhtLstTable 1 }

LcsSetupPublicSpotModuleAdvertisementUsrAgtWhtLstEntry ::= SEQUENCE {
            lcsSetupPublicSpotModuleAdvertisementUsrAgtWhtLstEntryUserAgent DisplayString
    }

-- {COLUMN} 1.3.6.1.4.1.2356.11.2.24.43.4.1.1
lcsSetupPublicSpotModuleAdvertisementUsrAgtWhtLstEntryUserAgent OBJECT-TYPE
    SYNTAX     DisplayString (SIZE(0..150))
    MAX-ACCESS read-write
    STATUS     current
    DESCRIPTION
            "-- empty --"
    ::= { lcsSetupPublicSpotModuleAdvertisementUsrAgtWhtLstEntry 1 }

-- {SCALAR} 1.3.6.1.4.1.2356.11.2.24.43.5
lcsSetupPublicSpotModuleAdvertisementProcessWisprRedirectUrl OBJECT-TYPE
    SYNTAX     INTEGER {
                  eNo (0),
                  eYes (1)
            }
    MAX-ACCESS read-write
    STATUS     current
    DESCRIPTION
            "-- empty --"
    ::= { lcsSetupPublicSpotModuleAdvertisement 5 }

-- {TABLE} 1.3.6.1.4.1.2356.11.2.24.43.6
lcsSetupPublicSpotModuleAdvertisementFreeNetworksTable OBJECT-TYPE
    SYNTAX     SEQUENCE OF LcsSetupPublicSpotModuleAdvertisementFreeNetworksEntry
    MAX-ACCESS not-accessible
    STATUS     current
    DESCRIPTION
            "-- empty --"
    ::= { lcsSetupPublicSpotModuleAdvertisement 6 }

-- {ROW} 1.3.6.1.4.1.2356.11.2.24.43.6.1
lcsSetupPublicSpotModuleAdvertisementFreeNetworksEntry OBJECT-TYPE
    SYNTAX     LcsSetupPublicSpotModuleAdvertisementFreeNetworksEntry
    MAX-ACCESS not-accessible
    STATUS     current
    DESCRIPTION
            ""
    INDEX {
            lcsSetupPublicSpotModuleAdvertisementFreeNetworksEntryHostName
          }
    ::= { lcsSetupPublicSpotModuleAdvertisementFreeNetworksTable 1 }

LcsSetupPublicSpotModuleAdvertisementFreeNetworksEntry ::= SEQUENCE {
            lcsSetupPublicSpotModuleAdvertisementFreeNetworksEntryHostName DisplayString,
            lcsSetupPublicSpotModuleAdvertisementFreeNetworksEntryMask IpAddress
    }

-- {COLUMN} 1.3.6.1.4.1.2356.11.2.24.43.6.1.1
lcsSetupPublicSpotModuleAdvertisementFreeNetworksEntryHostName OBJECT-TYPE
    SYNTAX     DisplayString (SIZE(0..64))
    MAX-ACCESS read-write
    STATUS     current
    DESCRIPTION
            "-- empty --"
    ::= { lcsSetupPublicSpotModuleAdvertisementFreeNetworksEntry 1 }

-- {COLUMN} 1.3.6.1.4.1.2356.11.2.24.43.6.1.2
lcsSetupPublicSpotModuleAdvertisementFreeNetworksEntryMask OBJECT-TYPE
    SYNTAX     IpAddress
    MAX-ACCESS read-write
    STATUS     current
    DESCRIPTION
            "-- empty --"
    ::= { lcsSetupPublicSpotModuleAdvertisementFreeNetworksEntry 2 }

-- {NODE} 1.3.6.1.4.1.2356.11.2.24.44
lcsSetupPublicSpotModuleManageUserWizard OBJECT IDENTIFIER ::= { lcsSetupPublicSpotModule 44 }

-- {SCALAR} 1.3.6.1.4.1.2356.11.2.24.44.10
lcsSetupPublicSpotModuleManageUserWizardShowStatusInformation OBJECT-TYPE
    SYNTAX     INTEGER {
                  eNo (0),
                  eYes (1)
            }
    MAX-ACCESS read-write
    STATUS     current
    DESCRIPTION
            "-- empty --"
    ::= { lcsSetupPublicSpotModuleManageUserWizard 10 }

-- {SCALAR} 1.3.6.1.4.1.2356.11.2.24.44.11
lcsSetupPublicSpotModuleManageUserWizardShowAllUserAdmIndep OBJECT-TYPE
    SYNTAX     INTEGER {
                  eNo (0),
                  eYes (1)
            }
    MAX-ACCESS read-write
    STATUS     current
    DESCRIPTION
            ""
    ::= { lcsSetupPublicSpotModuleManageUserWizard 11 }

-- {SCALAR} 1.3.6.1.4.1.2356.11.2.24.44.12
lcsSetupPublicSpotModuleManageUserWizardShowExpiryTyp OBJECT-TYPE
    SYNTAX     INTEGER {
                  eNo (0),
                  eYes (1)
            }
    MAX-ACCESS read-write
    STATUS     current
    DESCRIPTION
            "-- empty --"
    ::= { lcsSetupPublicSpotModuleManageUserWizard 12 }

-- {SCALAR} 1.3.6.1.4.1.2356.11.2.24.44.13
lcsSetupPublicSpotModuleManageUserWizardShowAbsExpiry OBJECT-TYPE
    SYNTAX     INTEGER {
                  eNo (0),
                  eYes (1)
            }
    MAX-ACCESS read-write
    STATUS     current
    DESCRIPTION
            "-- empty --"
    ::= { lcsSetupPublicSpotModuleManageUserWizard 13 }

-- {SCALAR} 1.3.6.1.4.1.2356.11.2.24.44.14
lcsSetupPublicSpotModuleManageUserWizardShowRelExpiry OBJECT-TYPE
    SYNTAX     INTEGER {
                  eNo (0),
                  eYes (1)
            }
    MAX-ACCESS read-write
    STATUS     current
    DESCRIPTION
            "-- empty --"
    ::= { lcsSetupPublicSpotModuleManageUserWizard 14 }

-- {SCALAR} 1.3.6.1.4.1.2356.11.2.24.44.15
lcsSetupPublicSpotModuleManageUserWizardShowTimeBudget OBJECT-TYPE
    SYNTAX     INTEGER {
                  eNo (0),
                  eYes (1)
            }
    MAX-ACCESS read-write
    STATUS     current
    DESCRIPTION
            "-- empty --"
    ::= { lcsSetupPublicSpotModuleManageUserWizard 15 }

-- {SCALAR} 1.3.6.1.4.1.2356.11.2.24.44.16
lcsSetupPublicSpotModuleManageUserWizardShowVolumeBudget OBJECT-TYPE
    SYNTAX     INTEGER {
                  eNo (0),
                  eYes (1)
            }
    MAX-ACCESS read-write
    STATUS     current
    DESCRIPTION
            "-- empty --"
    ::= { lcsSetupPublicSpotModuleManageUserWizard 16 }

-- {SCALAR} 1.3.6.1.4.1.2356.11.2.24.44.17
lcsSetupPublicSpotModuleManageUserWizardShowCaseSensitive OBJECT-TYPE
    SYNTAX     INTEGER {
                  eNo (0),
                  eYes (1)
            }
    MAX-ACCESS read-write
    STATUS     current
    DESCRIPTION
            "-- empty --"
    ::= { lcsSetupPublicSpotModuleManageUserWizard 17 }

-- {SCALAR} 1.3.6.1.4.1.2356.11.2.24.44.18
lcsSetupPublicSpotModuleManageUserWizardShowActive OBJECT-TYPE
    SYNTAX     INTEGER {
                  eNo (0),
                  eYes (1)
            }
    MAX-ACCESS read-write
    STATUS     current
    DESCRIPTION
            "-- empty --"
    ::= { lcsSetupPublicSpotModuleManageUserWizard 18 }

-- {SCALAR} 1.3.6.1.4.1.2356.11.2.24.44.19
lcsSetupPublicSpotModuleManageUserWizardShowTxLimit OBJECT-TYPE
    SYNTAX     INTEGER {
                  eNo (0),
                  eYes (1)
            }
    MAX-ACCESS read-write
    STATUS     current
    DESCRIPTION
            "-- empty --"
    ::= { lcsSetupPublicSpotModuleManageUserWizard 19 }

-- {SCALAR} 1.3.6.1.4.1.2356.11.2.24.44.20
lcsSetupPublicSpotModuleManageUserWizardShowRxLimit OBJECT-TYPE
    SYNTAX     INTEGER {
                  eNo (0),
                  eYes (1)
            }
    MAX-ACCESS read-write
    STATUS     current
    DESCRIPTION
            "-- empty --"
    ::= { lcsSetupPublicSpotModuleManageUserWizard 20 }

-- {SCALAR} 1.3.6.1.4.1.2356.11.2.24.44.21
lcsSetupPublicSpotModuleManageUserWizardShowCallingStation OBJECT-TYPE
    SYNTAX     INTEGER {
                  eNo (0),
                  eYes (1)
            }
    MAX-ACCESS read-write
    STATUS     current
    DESCRIPTION
            "-- empty --"
    ::= { lcsSetupPublicSpotModuleManageUserWizard 21 }

-- {SCALAR} 1.3.6.1.4.1.2356.11.2.24.44.22
lcsSetupPublicSpotModuleManageUserWizardShowCalledStation OBJECT-TYPE
    SYNTAX     INTEGER {
                  eNo (0),
                  eYes (1)
            }
    MAX-ACCESS read-write
    STATUS     current
    DESCRIPTION
            "-- empty --"
    ::= { lcsSetupPublicSpotModuleManageUserWizard 22 }

-- {SCALAR} 1.3.6.1.4.1.2356.11.2.24.44.23
lcsSetupPublicSpotModuleManageUserWizardShowOnlineTime OBJECT-TYPE
    SYNTAX     INTEGER {
                  eNo (0),
                  eYes (1)
            }
    MAX-ACCESS read-write
    STATUS     current
    DESCRIPTION
            "-- empty --"
    ::= { lcsSetupPublicSpotModuleManageUserWizard 23 }

-- {SCALAR} 1.3.6.1.4.1.2356.11.2.24.44.24
lcsSetupPublicSpotModuleManageUserWizardShowTraffic OBJECT-TYPE
    SYNTAX     INTEGER {
                  eNo (0),
                  eYes (1)
            }
    MAX-ACCESS read-write
    STATUS     current
    DESCRIPTION
            "-- empty --"
    ::= { lcsSetupPublicSpotModuleManageUserWizard 24 }

-- {SCALAR} 1.3.6.1.4.1.2356.11.2.24.44.25
lcsSetupPublicSpotModuleManageUserWizardShowStatusColumn OBJECT-TYPE
    SYNTAX     INTEGER {
                  eNo (0),
                  eYes (1)
            }
    MAX-ACCESS read-write
    STATUS     current
    DESCRIPTION
            "-- empty --"
    ::= { lcsSetupPublicSpotModuleManageUserWizard 25 }

-- {SCALAR} 1.3.6.1.4.1.2356.11.2.24.44.26
lcsSetupPublicSpotModuleManageUserWizardShowMacAddress OBJECT-TYPE
    SYNTAX     INTEGER {
                  eNo (0),
                  eYes (1)
            }
    MAX-ACCESS read-write
    STATUS     current
    DESCRIPTION
            "-- empty --"
    ::= { lcsSetupPublicSpotModuleManageUserWizard 26 }

-- {SCALAR} 1.3.6.1.4.1.2356.11.2.24.44.27
lcsSetupPublicSpotModuleManageUserWizardShowIpAddress OBJECT-TYPE
    SYNTAX     INTEGER {
                  eNo (0),
                  eYes (1)
            }
    MAX-ACCESS read-write
    STATUS     current
    DESCRIPTION
            "-- empty --"
    ::= { lcsSetupPublicSpotModuleManageUserWizard 27 }

-- {SCALAR} 1.3.6.1.4.1.2356.11.2.24.47
lcsSetupPublicSpotModuleCheckOriginVlan OBJECT-TYPE
    SYNTAX     INTEGER {
                  eNo (0),
                  eYes (1)
            }
    MAX-ACCESS read-write
    STATUS     current
    DESCRIPTION
            "-- empty --"
    ::= { lcsSetupPublicSpotModule 47 }

-- {TABLE} 1.3.6.1.4.1.2356.11.2.24.48
lcsSetupPublicSpotModuleCircuitIdsTable OBJECT-TYPE
    SYNTAX     SEQUENCE OF LcsSetupPublicSpotModuleCircuitIdsEntry
    MAX-ACCESS not-accessible
    STATUS     current
    DESCRIPTION
            "-- empty --"
    ::= { lcsSetupPublicSpotModule 48 }

-- {ROW} 1.3.6.1.4.1.2356.11.2.24.48.1
lcsSetupPublicSpotModuleCircuitIdsEntry OBJECT-TYPE
    SYNTAX     LcsSetupPublicSpotModuleCircuitIdsEntry
    MAX-ACCESS not-accessible
    STATUS     current
    DESCRIPTION
            ""
    INDEX {
            lcsSetupPublicSpotModuleCircuitIdsEntryAdministrator
          }
    ::= { lcsSetupPublicSpotModuleCircuitIdsTable 1 }

LcsSetupPublicSpotModuleCircuitIdsEntry ::= SEQUENCE {
            lcsSetupPublicSpotModuleCircuitIdsEntryAdministrator DisplayString,
            lcsSetupPublicSpotModuleCircuitIdsEntryCircuitId DisplayString
    }

-- {COLUMN} 1.3.6.1.4.1.2356.11.2.24.48.1.1
lcsSetupPublicSpotModuleCircuitIdsEntryAdministrator OBJECT-TYPE
    SYNTAX     DisplayString (SIZE(0..16))
    MAX-ACCESS read-write
    STATUS     current
    DESCRIPTION
            "-- empty --"
    ::= { lcsSetupPublicSpotModuleCircuitIdsEntry 1 }

-- {COLUMN} 1.3.6.1.4.1.2356.11.2.24.48.1.2
lcsSetupPublicSpotModuleCircuitIdsEntryCircuitId OBJECT-TYPE
    SYNTAX     DisplayString (SIZE(0..64))
    MAX-ACCESS read-write
    STATUS     current
    DESCRIPTION
            "-- empty --"
    ::= { lcsSetupPublicSpotModuleCircuitIdsEntry 2 }

-- {NODE} 1.3.6.1.4.1.2356.11.2.24.49
lcsSetupPublicSpotModuleBruteForce OBJECT IDENTIFIER ::= { lcsSetupPublicSpotModule 49 }

-- {SCALAR} 1.3.6.1.4.1.2356.11.2.24.49.1
lcsSetupPublicSpotModuleBruteForceMaxLoginTries OBJECT-TYPE
    SYNTAX     Integer32 (0..255)
    MAX-ACCESS read-write
    STATUS     current
    DESCRIPTION
            "-- empty --"
    ::= { lcsSetupPublicSpotModuleBruteForce 1 }

-- {SCALAR} 1.3.6.1.4.1.2356.11.2.24.49.2
lcsSetupPublicSpotModuleBruteForceBlockingTimeInMinute OBJECT-TYPE
    SYNTAX     Integer32 (0..65535)
    MAX-ACCESS read-write
    STATUS     current
    DESCRIPTION
            "-- empty --"
    ::= { lcsSetupPublicSpotModuleBruteForce 2 }

-- {SCALAR} 1.3.6.1.4.1.2356.11.2.24.49.3
lcsSetupPublicSpotModuleBruteForceUnblockCheck OBJECT-TYPE
    SYNTAX     Integer32 (0..65535)
    MAX-ACCESS read-write
    STATUS     current
    DESCRIPTION
            ""
    ::= { lcsSetupPublicSpotModuleBruteForce 3 }

-- {SCALAR} 1.3.6.1.4.1.2356.11.2.24.49.4
lcsSetupPublicSpotModuleBruteForceUnblock OBJECT-TYPE
    SYNTAX     DisplayString
    MAX-ACCESS read-write
    STATUS     current
    DESCRIPTION
            "-- empty --"
    ::= { lcsSetupPublicSpotModuleBruteForce 4 }

-- {NODE} 1.3.6.1.4.1.2356.11.2.24.50
lcsSetupPublicSpotModuleAutoReLogin OBJECT IDENTIFIER ::= { lcsSetupPublicSpotModule 50 }

-- {SCALAR} 1.3.6.1.4.1.2356.11.2.24.50.1
lcsSetupPublicSpotModuleAutoReLoginOperating OBJECT-TYPE
    SYNTAX     INTEGER {
                  eNo (0),
                  eYes (1)
            }
    MAX-ACCESS read-write
    STATUS     current
    DESCRIPTION
            "-- empty --"
    ::= { lcsSetupPublicSpotModuleAutoReLogin 1 }

-- {SCALAR} 1.3.6.1.4.1.2356.11.2.24.50.2
lcsSetupPublicSpotModuleAutoReLoginStationTableLimit OBJECT-TYPE
    SYNTAX     Integer32 (0..2147483647)
    MAX-ACCESS read-write
    STATUS     current
    DESCRIPTION
            "-- empty --"
    ::= { lcsSetupPublicSpotModuleAutoReLogin 2 }

-- {SCALAR} 1.3.6.1.4.1.2356.11.2.24.50.3
lcsSetupPublicSpotModuleAutoReLoginExistTimeout OBJECT-TYPE
    SYNTAX     Integer32 (0..2147483647)
    MAX-ACCESS read-write
    STATUS     current
    DESCRIPTION
            "-- empty --"
    ::= { lcsSetupPublicSpotModuleAutoReLogin 3 }

-- {SCALAR} 1.3.6.1.4.1.2356.11.2.24.51
lcsSetupPublicSpotModuleRedirectTlsConnections OBJECT-TYPE
    SYNTAX     INTEGER {
                  eNo (0),
                  eYes (1)
            }
    MAX-ACCESS read-write
    STATUS     current
    DESCRIPTION
            "-- empty --"
    ::= { lcsSetupPublicSpotModule 51 }

-- {NODE} 1.3.6.1.4.1.2356.11.2.24.52
lcsSetupPublicSpotModuleMonitorCapacity OBJECT IDENTIFIER ::= { lcsSetupPublicSpotModule 52 }

-- {SCALAR} 1.3.6.1.4.1.2356.11.2.24.52.1
lcsSetupPublicSpotModuleMonitorCapacityWarning OBJECT-TYPE
    SYNTAX     INTEGER {
                  eNo (0),
                  eYes (1)
            }
    MAX-ACCESS read-write
    STATUS     current
    DESCRIPTION
            "-- empty --"
    ::= { lcsSetupPublicSpotModuleMonitorCapacity 1 }

-- {SCALAR} 1.3.6.1.4.1.2356.11.2.24.52.2
lcsSetupPublicSpotModuleMonitorCapacityEMail OBJECT-TYPE
    SYNTAX     DisplayString (SIZE(0..150))
    MAX-ACCESS read-write
    STATUS     current
    DESCRIPTION
            "-- empty --"
    ::= { lcsSetupPublicSpotModuleMonitorCapacity 2 }

-- {NODE} 1.3.6.1.4.1.2356.11.2.24.53
lcsSetupPublicSpotModuleSslForPageTable OBJECT IDENTIFIER ::= { lcsSetupPublicSpotModule 53 }

-- {SCALAR} 1.3.6.1.4.1.2356.11.2.24.53.1
lcsSetupPublicSpotModuleSslForPageTableVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupPublicSpotModuleSslForPageTable 1 }

-- {SCALAR} 1.3.6.1.4.1.2356.11.2.24.53.2
lcsSetupPublicSpotModuleSslForPageTableKeyexAlgorithms OBJECT-TYPE
    SYNTAX     BITS {
                  eEcdhe (27),
                  eDhe (29),
                  eRsa (31)
            }
    MAX-ACCESS read-write
    STATUS     current
    DESCRIPTION
            "-- empty --"
    ::= { lcsSetupPublicSpotModuleSslForPageTable 2 }

-- {SCALAR} 1.3.6.1.4.1.2356.11.2.24.53.3
lcsSetupPublicSpotModuleSslForPageTableCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupPublicSpotModuleSslForPageTable 3 }

-- {SCALAR} 1.3.6.1.4.1.2356.11.2.24.53.4
lcsSetupPublicSpotModuleSslForPageTableHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupPublicSpotModuleSslForPageTable 4 }

-- {SCALAR} 1.3.6.1.4.1.2356.11.2.24.53.5
lcsSetupPublicSpotModuleSslForPageTablePreferPfs OBJECT-TYPE
    SYNTAX     BITS {
                  eNo (0),
                  eYes (7)
            }
    MAX-ACCESS read-write
    STATUS     current
    DESCRIPTION
            "-- empty --"
    ::= { lcsSetupPublicSpotModuleSslForPageTable 5 }

-- {SCALAR} 1.3.6.1.4.1.2356.11.2.24.53.6
lcsSetupPublicSpotModuleSslForPageTableRenegotiations OBJECT-TYPE
    SYNTAX     INTEGER {
                  eForbidden (0),
                  eAllowed (1),
                  eIgnored (2)
            }
    MAX-ACCESS read-write
    STATUS     current
    DESCRIPTION
            "-- empty --"
    ::= { lcsSetupPublicSpotModuleSslForPageTable 6 }

-- {SCALAR} 1.3.6.1.4.1.2356.11.2.24.53.7
lcsSetupPublicSpotModuleSslForPageTableEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupPublicSpotModuleSslForPageTable 7 }

-- {SCALAR} 1.3.6.1.4.1.2356.11.2.24.53.21
lcsSetupPublicSpotModuleSslForPageTableSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupPublicSpotModuleSslForPageTable 21 }

-- {SCALAR} 1.3.6.1.4.1.2356.11.2.24.55
lcsSetupPublicSpotModuleAcceptCoa OBJECT-TYPE
    SYNTAX     INTEGER {
                  eNo (0),
                  eYes (1)
            }
    MAX-ACCESS read-write
    STATUS     current
    DESCRIPTION
            "-- empty --"
    ::= { lcsSetupPublicSpotModule 55 }

-- {TABLE} 1.3.6.1.4.1.2356.11.2.24.60
lcsSetupPublicSpotModuleLoginTextTable OBJECT-TYPE
    SYNTAX     SEQUENCE OF LcsSetupPublicSpotModuleLoginTextEntry
    MAX-ACCESS not-accessible
    STATUS     current
    DESCRIPTION
            "-- empty --"
    ::= { lcsSetupPublicSpotModule 60 }

-- {ROW} 1.3.6.1.4.1.2356.11.2.24.60.1
lcsSetupPublicSpotModuleLoginTextEntry OBJECT-TYPE
    SYNTAX     LcsSetupPublicSpotModuleLoginTextEntry
    MAX-ACCESS not-accessible
    STATUS     current
    DESCRIPTION
            ""
    INDEX {
            lcsSetupPublicSpotModuleLoginTextEntryLanguage
          }
    ::= { lcsSetupPublicSpotModuleLoginTextTable 1 }

LcsSetupPublicSpotModuleLoginTextEntry ::= SEQUENCE {
            lcsSetupPublicSpotModuleLoginTextEntryLanguage INTEGER,
            lcsSetupPublicSpotModuleLoginTextEntryContent DisplayString
    }

-- {COLUMN} 1.3.6.1.4.1.2356.11.2.24.60.1.1
lcsSetupPublicSpotModuleLoginTextEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { lcsSetupPublicSpotModuleLoginTextEntry 1 }

-- {COLUMN} 1.3.6.1.4.1.2356.11.2.24.60.1.2
lcsSetupPublicSpotModuleLoginTextEntryContent OBJECT-TYPE
    SYNTAX     DisplayString (SIZE(0..251))
    MAX-ACCESS read-write
    STATUS     current
    DESCRIPTION
            "-- empty --"
    ::= { lcsSetupPublicSpotModuleLoginTextEntry 2 }

-- {TABLE} 1.3.6.1.4.1.2356.11.2.24.61
lcsSetupPublicSpotModuleLoginInstructionsTable OBJECT-TYPE
    SYNTAX     SEQUENCE OF LcsSetupPublicSpotModuleLoginInstructionsEntry
    MAX-ACCESS not-accessible
    STATUS     current
    DESCRIPTION
            "-- empty --"
    ::= { lcsSetupPublicSpotModule 61 }

-- {ROW} 1.3.6.1.4.1.2356.11.2.24.61.1
lcsSetupPublicSpotModuleLoginInstructionsEntry OBJECT-TYPE
    SYNTAX     LcsSetupPublicSpotModuleLoginInstructionsEntry
    MAX-ACCESS not-accessible
    STATUS     current
    DESCRIPTION
            ""
    INDEX {
            lcsSetupPublicSpotModuleLoginInstructionsEntryLanguage
          }
    ::= { lcsSetupPublicSpotModuleLoginInstructionsTable 1 }

LcsSetupPublicSpotModuleLoginInstructionsEntry ::= SEQUENCE {
            lcsSetupPublicSpotModuleLoginInstructionsEntryLanguage INTEGER,
            lcsSetupPublicSpotModuleLoginInstructionsEntryContent DisplayString
    }

-- {COLUMN} 1.3.6.1.4.1.2356.11.2.24.61.1.1
lcsSetupPublicSpotModuleLoginInstructionsEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { lcsSetupPublicSpotModuleLoginInstructionsEntry 1 }

-- {COLUMN} 1.3.6.1.4.1.2356.11.2.24.61.1.2
lcsSetupPublicSpotModuleLoginInstructionsEntryContent OBJECT-TYPE
    SYNTAX     DisplayString (SIZE(0..251))
    MAX-ACCESS read-write
    STATUS     current
    DESCRIPTION
            "-- empty --"
    ::= { lcsSetupPublicSpotModuleLoginInstructionsEntry 2 }

-- {NODE} 1.3.6.1.4.1.2356.11.2.25
lcsSetupRadius OBJECT IDENTIFIER ::= { lcsSetup 25 }

-- {SCALAR} 1.3.6.1.4.1.2356.11.2.25.4
lcsSetupRadiusAuthTimeout OBJECT-TYPE
    SYNTAX     Integer32 (0..65535)
    MAX-ACCESS read-write
    STATUS     current
    DESCRIPTION
            ""
    ::= { lcsSetupRadius 4 }

-- {SCALAR} 1.3.6.1.4.1.2356.11.2.25.5
lcsSetupRadiusAuthRetry OBJECT-TYPE
    SYNTAX     Integer32 (0..255)
    MAX-ACCESS read-write
    STATUS     current
    DESCRIPTION
            ""
    ::= { lcsSetupRadius 5 }

-- {SCALAR} 1.3.6.1.4.1.2356.11.2.25.9
lcsSetupRadiusBackupQueryStrategy OBJECT-TYPE
    SYNTAX     INTEGER {
                  eBlock (0),
                  eCyclic (1)
            }
    MAX-ACCESS read-write
    STATUS     current
    DESCRIPTION
            ""
    ::= { lcsSetupRadius 9 }

-- {NODE} 1.3.6.1.4.1.2356.11.2.25.10
lcsSetupRadiusServer OBJECT IDENTIFIER ::= { lcsSetupRadius 10 }

-- {SCALAR} 1.3.6.1.4.1.2356.11.2.25.10.1
lcsSetupRadiusServerAuthentificationPort OBJECT-TYPE
    SYNTAX     Integer32 (0..65535)
    MAX-ACCESS read-write
    STATUS     current
    DESCRIPTION
            ""
    ::= { lcsSetupRadiusServer 1 }

-- {TABLE} 1.3.6.1.4.1.2356.11.2.25.10.2
lcsSetupRadiusServerClientsTable OBJECT-TYPE
    SYNTAX     SEQUENCE OF LcsSetupRadiusServerClientsEntry
    MAX-ACCESS not-accessible
    STATUS     current
    DESCRIPTION
            ""
    ::= { lcsSetupRadiusServer 2 }

-- {ROW} 1.3.6.1.4.1.2356.11.2.25.10.2.1
lcsSetupRadiusServerClientsEntry OBJECT-TYPE
    SYNTAX     LcsSetupRadiusServerClientsEntry
    MAX-ACCESS not-accessible
    STATUS     current
    DESCRIPTION
            ""
    INDEX {
            lcsSetupRadiusServerClientsEntryIpNetwork,
            lcsSetupRadiusServerClientsEntryIpNetmask
          }
    ::= { lcsSetupRadiusServerClientsTable 1 }

LcsSetupRadiusServerClientsEntry ::= SEQUENCE {
            lcsSetupRadiusServerClientsEntryIpNetwork IpAddress,
            lcsSetupRadiusServerClientsEntrySecret DisplayString,
            lcsSetupRadiusServerClientsEntryIpNetmask IpAddress,
            lcsSetupRadiusServerClientsEntryProtocols INTEGER,
            lcsSetupRadiusServerClientsEntryComment DisplayString
    }

-- {COLUMN} 1.3.6.1.4.1.2356.11.2.25.10.2.1.1
lcsSetupRadiusServerClientsEntryIpNetwork OBJECT-TYPE
    SYNTAX     IpAddress
    MAX-ACCESS read-write
    STATUS     current
    DESCRIPTION
            ""
    ::= { lcsSetupRadiusServerClientsEntry 1 }

-- {COLUMN} 1.3.6.1.4.1.2356.11.2.25.10.2.1.2
lcsSetupRadiusServerClientsEntrySecret OBJECT-TYPE
    SYNTAX     DisplayString (SIZE(0..64))
    MAX-ACCESS read-write
    STATUS     current
    DESCRIPTION
            ""
    ::= { lcsSetupRadiusServerClientsEntry 2 }

-- {COLUMN} 1.3.6.1.4.1.2356.11.2.25.10.2.1.3
lcsSetupRadiusServerClientsEntryIpNetmask OBJECT-TYPE
    SYNTAX     IpAddress
    MAX-ACCESS read-write
    STATUS     current
    DESCRIPTION
            ""
    ::= { lcsSetupRadiusServerClientsEntry 3 }

-- {COLUMN} 1.3.6.1.4.1.2356.11.2.25.10.2.1.4
lcsSetupRadiusServerClientsEntryProtocols OBJECT-TYPE
    SYNTAX     INTEGER {
                  eRadius (0),
                  eRadsec (1),
                  eAll (255)
            }
    MAX-ACCESS read-write
    STATUS     current
    DESCRIPTION
            ""
    ::= { lcsSetupRadiusServerClientsEntry 4 }

-- {COLUMN} 1.3.6.1.4.1.2356.11.2.25.10.2.1.5
lcsSetupRadiusServerClientsEntryComment OBJECT-TYPE
    SYNTAX     DisplayString (SIZE(0..251))
    MAX-ACCESS read-write
    STATUS     current
    DESCRIPTION
            "-- empty --"
    ::= { lcsSetupRadiusServerClientsEntry 5 }

-- {TABLE} 1.3.6.1.4.1.2356.11.2.25.10.3
lcsSetupRadiusServerForwardServersTable OBJECT-TYPE
    SYNTAX     SEQUENCE OF LcsSetupRadiusServerForwardServersEntry
    MAX-ACCESS not-accessible
    STATUS     current
    DESCRIPTION
            ""
    ::= { lcsSetupRadiusServer 3 }

-- {ROW} 1.3.6.1.4.1.2356.11.2.25.10.3.1
lcsSetupRadiusServerForwardServersEntry OBJECT-TYPE
    SYNTAX     LcsSetupRadiusServerForwardServersEntry
    MAX-ACCESS not-accessible
    STATUS     current
    DESCRIPTION
            ""
    INDEX {
            lcsSetupRadiusServerForwardServersEntryRealm
          }
    ::= { lcsSetupRadiusServerForwardServersTable 1 }

LcsSetupRadiusServerForwardServersEntry ::= SEQUENCE {
            lcsSetupRadiusServerForwardServersEntryRealm DisplayString,
            lcsSetupRadiusServerForwardServersEntryIpAddress IpAddress,
            lcsSetupRadiusServerForwardServersEntryPort Integer32,
            lcsSetupRadiusServerForwardServersEntrySecret DisplayString,
            lcsSetupRadiusServerForwardServersEntryBackup DisplayString,
            lcsSetupRadiusServerForwardServersEntryLoopbackAddr DisplayString,
            lcsSetupRadiusServerForwardServersEntryProtocol INTEGER,
            lcsSetupRadiusServerForwardServersEntryAccntIpAddress IpAddress,
            lcsSetupRadiusServerForwardServersEntryAccntPort Integer32,
            lcsSetupRadiusServerForwardServersEntryAccntSecret DisplayString,
            lcsSetupRadiusServerForwardServersEntryAccntLoopbackAddr DisplayString,
            lcsSetupRadiusServerForwardServersEntryAccntProtocol INTEGER,
            lcsSetupRadiusServerForwardServersEntryHostname DisplayString,
            lcsSetupRadiusServerForwardServersEntryAccntHostname DisplayString,
            lcsSetupRadiusServerForwardServersEntryAttributeValues DisplayString,
            lcsSetupRadiusServerForwardServersEntryAccntAttributeValues DisplayString
    }

-- {COLUMN} 1.3.6.1.4.1.2356.11.2.25.10.3.1.1
lcsSetupRadiusServerForwardServersEntryRealm OBJECT-TYPE
    SYNTAX     DisplayString (SIZE(0..64))
    MAX-ACCESS read-write
    STATUS     current
    DESCRIPTION
            ""
    ::= { lcsSetupRadiusServerForwardServersEntry 1 }

-- {COLUMN} 1.3.6.1.4.1.2356.11.2.25.10.3.1.2
lcsSetupRadiusServerForwardServersEntryIpAddress OBJECT-TYPE
    SYNTAX     IpAddress
    MAX-ACCESS read-write
    STATUS     current
    DESCRIPTION
            ""
    ::= { lcsSetupRadiusServerForwardServersEntry 2 }

-- {COLUMN} 1.3.6.1.4.1.2356.11.2.25.10.3.1.3
lcsSetupRadiusServerForwardServersEntryPort OBJECT-TYPE
    SYNTAX     Integer32 (0..65535)
    MAX-ACCESS read-write
    STATUS     current
    DESCRIPTION
            ""
    ::= { lcsSetupRadiusServerForwardServersEntry 3 }

-- {COLUMN} 1.3.6.1.4.1.2356.11.2.25.10.3.1.4
lcsSetupRadiusServerForwardServersEntrySecret OBJECT-TYPE
    SYNTAX     DisplayString (SIZE(0..64))
    MAX-ACCESS read-write
    STATUS     current
    DESCRIPTION
            ""
    ::= { lcsSetupRadiusServerForwardServersEntry 4 }

-- {COLUMN} 1.3.6.1.4.1.2356.11.2.25.10.3.1.5
lcsSetupRadiusServerForwardServersEntryBackup OBJECT-TYPE
    SYNTAX     DisplayString (SIZE(0..64))
    MAX-ACCESS read-write
    STATUS     current
    DESCRIPTION
            ""
    ::= { lcsSetupRadiusServerForwardServersEntry 5 }

-- {COLUMN} 1.3.6.1.4.1.2356.11.2.25.10.3.1.6
lcsSetupRadiusServerForwardServersEntryLoopbackAddr OBJECT-TYPE
    SYNTAX     DisplayString (SIZE(0..16))
    MAX-ACCESS read-write
    STATUS     current
    DESCRIPTION
            ""
    ::= { lcsSetupRadiusServerForwardServersEntry 6 }

-- {COLUMN} 1.3.6.1.4.1.2356.11.2.25.10.3.1.7
lcsSetupRadiusServerForwardServersEntryProtocol OBJECT-TYPE
    SYNTAX     INTEGER {
                  eRadius (0),
                  eRadsec (1)
            }
    MAX-ACCESS read-write
    STATUS     current
    DESCRIPTION
            ""
    ::= { lcsSetupRadiusServerForwardServersEntry 7 }

-- {COLUMN} 1.3.6.1.4.1.2356.11.2.25.10.3.1.8
lcsSetupRadiusServerForwardServersEntryAccntIpAddress OBJECT-TYPE
    SYNTAX     IpAddress
    MAX-ACCESS read-write
    STATUS     current
    DESCRIPTION
            ""
    ::= { lcsSetupRadiusServerForwardServersEntry 8 }

-- {COLUMN} 1.3.6.1.4.1.2356.11.2.25.10.3.1.9
lcsSetupRadiusServerForwardServersEntryAccntPort OBJECT-TYPE
    SYNTAX     Integer32 (0..65535)
    MAX-ACCESS read-write
    STATUS     current
    DESCRIPTION
            ""
    ::= { lcsSetupRadiusServerForwardServersEntry 9 }

-- {COLUMN} 1.3.6.1.4.1.2356.11.2.25.10.3.1.10
lcsSetupRadiusServerForwardServersEntryAccntSecret OBJECT-TYPE
    SYNTAX     DisplayString (SIZE(0..64))
    MAX-ACCESS read-write
    STATUS     current
    DESCRIPTION
            ""
    ::= { lcsSetupRadiusServerForwardServersEntry 10 }

-- {COLUMN} 1.3.6.1.4.1.2356.11.2.25.10.3.1.11
lcsSetupRadiusServerForwardServersEntryAccntLoopbackAddr OBJECT-TYPE
    SYNTAX     DisplayString (SIZE(0..16))
    MAX-ACCESS read-write
    STATUS     current
    DESCRIPTION
            ""
    ::= { lcsSetupRadiusServerForwardServersEntry 11 }

-- {COLUMN} 1.3.6.1.4.1.2356.11.2.25.10.3.1.12
lcsSetupRadiusServerForwardServersEntryAccntProtocol OBJECT-TYPE
    SYNTAX     INTEGER {
                  eRadius (0),
                  eRadsec (1)
            }
    MAX-ACCESS read-write
    STATUS     current
    DESCRIPTION
            ""
    ::= { lcsSetupRadiusServerForwardServersEntry 12 }

-- {COLUMN} 1.3.6.1.4.1.2356.11.2.25.10.3.1.13
lcsSetupRadiusServerForwardServersEntryHostname OBJECT-TYPE
    SYNTAX     DisplayString (SIZE(0..64))
    MAX-ACCESS read-write
    STATUS     current
    DESCRIPTION
            "-- empty --"
    ::= { lcsSetupRadiusServerForwardServersEntry 13 }

-- {COLUMN} 1.3.6.1.4.1.2356.11.2.25.10.3.1.14
lcsSetupRadiusServerForwardServersEntryAccntHostname OBJECT-TYPE
    SYNTAX     DisplayString (SIZE(0..64))
    MAX-ACCESS read-write
    STATUS     current
    DESCRIPTION
            "-- empty --"
    ::= { lcsSetupRadiusServerForwardServersEntry 14 }

-- {COLUMN} 1.3.6.1.4.1.2356.11.2.25.10.3.1.15
lcsSetupRadiusServerForwardServersEntryAttributeValues OBJECT-TYPE
    SYNTAX     DisplayString (SIZE(0..251))
    MAX-ACCESS read-write
    STATUS     current
    DESCRIPTION
            "-- empty --"
    ::= { lcsSetupRadiusServerForwardServersEntry 15 }

-- {COLUMN} 1.3.6.1.4.1.2356.11.2.25.10.3.1.16
lcsSetupRadiusServerForwardServersEntryAccntAttributeValues OBJECT-TYPE
    SYNTAX     DisplayString (SIZE(0..251))
    MAX-ACCESS read-write
    STATUS     current
    DESCRIPTION
            "-- empty --"
    ::= { lcsSetupRadiusServerForwardServersEntry 16 }

-- {SCALAR} 1.3.6.1.4.1.2356.11.2.25.10.5
lcsSetupRadiusServerDefaultRealm OBJECT-TYPE
    SYNTAX     DisplayString (SIZE(0..64))
    MAX-ACCESS read-write
    STATUS     current
    DESCRIPTION
            ""
    ::= { lcsSetupRadiusServer 5 }

-- {SCALAR} 1.3.6.1.4.1.2356.11.2.25.10.6
lcsSetupRadiusServerEmptyRealm OBJECT-TYPE
    SYNTAX     DisplayString (SIZE(0..64))
    MAX-ACCESS read-write
    STATUS     current
    DESCRIPTION
            ""
    ::= { lcsSetupRadiusServer 6 }

-- {TABLE} 1.3.6.1.4.1.2356.11.2.25.10.7
lcsSetupRadiusServerUsersTable OBJECT-TYPE
    SYNTAX     SEQUENCE OF LcsSetupRadiusServerUsersEntry
    MAX-ACCESS not-accessible
    STATUS     current
    DESCRIPTION
            ""
    ::= { lcsSetupRadiusServer 7 }

-- {ROW} 1.3.6.1.4.1.2356.11.2.25.10.7.1
lcsSetupRadiusServerUsersEntry OBJECT-TYPE
    SYNTAX     LcsSetupRadiusServerUsersEntry
    MAX-ACCESS not-accessible
    STATUS     current
    DESCRIPTION
            ""
    INDEX {
            lcsSetupRadiusServerUsersEntryUserName,
            lcsSetupRadiusServerUsersEntryCallingStationIdMask,
            lcsSetupRadiusServerUsersEntryCalledStationIdMask
          }
    ::= { lcsSetupRadiusServerUsersTable 1 }

LcsSetupRadiusServerUsersEntry ::= SEQUENCE {
            lcsSetupRadiusServerUsersEntryUserName DisplayString,
            lcsSetupRadiusServerUsersEntryPassword DisplayString,
            lcsSetupRadiusServerUsersEntryLimitAuthMethods BITS,
            lcsSetupRadiusServerUsersEntryVlanId Integer32,
            lcsSetupRadiusServerUsersEntryCallingStationIdMask DisplayString,
            lcsSetupRadiusServerUsersEntryCalledStationIdMask DisplayString,
            lcsSetupRadiusServerUsersEntryTxLimit Integer32,
            lcsSetupRadiusServerUsersEntryRxLimit Integer32,
            lcsSetupRadiusServerUsersEntryMultipleLogin INTEGER,
            lcsSetupRadiusServerUsersEntryAbsExpiry DisplayString,
            lcsSetupRadiusServerUsersEntryTimeBudget Integer32,
            lcsSetupRadiusServerUsersEntryVolumeBudget Integer32,
            lcsSetupRadiusServerUsersEntryExpiryType BITS,
            lcsSetupRadiusServerUsersEntryRelExpiry Integer32,
            lcsSetupRadiusServerUsersEntryComment DisplayString,
            lcsSetupRadiusServerUsersEntryServiceType INTEGER,
            lcsSetupRadiusServerUsersEntryCaseSensitive INTEGER,
            lcsSetupRadiusServerUsersEntryWpaPassphrase DisplayString,
            lcsSetupRadiusServerUsersEntryMaxConcurrentLogins Integer32,
            lcsSetupRadiusServerUsersEntryActive INTEGER,
            lcsSetupRadiusServerUsersEntryShellPrivLevel Integer32,
            lcsSetupRadiusServerUsersEntryVolumeBudgetMbytes Integer32,
            lcsSetupRadiusServerUsersEntryTunnelPassword DisplayString,
            lcsSetupRadiusServerUsersEntryLcsRoutingTag Integer32,
            lcsSetupRadiusServerUsersEntryAttributeValues DisplayString
    }

-- {COLUMN} 1.3.6.1.4.1.2356.11.2.25.10.7.1.1
lcsSetupRadiusServerUsersEntryUserName OBJECT-TYPE
    SYNTAX     DisplayString (SIZE(0..48))
    MAX-ACCESS read-write
    STATUS     current
    DESCRIPTION
            ""
    ::= { lcsSetupRadiusServerUsersEntry 1 }

-- {COLUMN} 1.3.6.1.4.1.2356.11.2.25.10.7.1.2
lcsSetupRadiusServerUsersEntryPassword OBJECT-TYPE
    SYNTAX     DisplayString (SIZE(0..32))
    MAX-ACCESS read-write
    STATUS     current
    DESCRIPTION
            ""
    ::= { lcsSetupRadiusServerUsersEntry 2 }

-- {COLUMN} 1.3.6.1.4.1.2356.11.2.25.10.7.1.3
lcsSetupRadiusServerUsersEntryLimitAuthMethods OBJECT-TYPE
    SYNTAX     BITS {
                  eAll (0),
                  eEap (11),
                  eMschapv2 (12),
                  eMschap (13),
                  eChap (14),
                  ePap (15)
            }
    MAX-ACCESS read-write
    STATUS     current
    DESCRIPTION
            ""
    ::= { lcsSetupRadiusServerUsersEntry 3 }

-- {COLUMN} 1.3.6.1.4.1.2356.11.2.25.10.7.1.4
lcsSetupRadiusServerUsersEntryVlanId OBJECT-TYPE
    SYNTAX     Integer32 (0..65535)
    MAX-ACCESS read-write
    STATUS     current
    DESCRIPTION
            ""
    ::= { lcsSetupRadiusServerUsersEntry 4 }

-- {COLUMN} 1.3.6.1.4.1.2356.11.2.25.10.7.1.5
lcsSetupRadiusServerUsersEntryCallingStationIdMask OBJECT-TYPE
    SYNTAX     DisplayString (SIZE(0..64))
    MAX-ACCESS read-write
    STATUS     current
    DESCRIPTION
            ""
    ::= { lcsSetupRadiusServerUsersEntry 5 }

-- {COLUMN} 1.3.6.1.4.1.2356.11.2.25.10.7.1.6
lcsSetupRadiusServerUsersEntryCalledStationIdMask OBJECT-TYPE
    SYNTAX     DisplayString (SIZE(0..64))
    MAX-ACCESS read-write
    STATUS     current
    DESCRIPTION
            ""
    ::= { lcsSetupRadiusServerUsersEntry 6 }

-- {COLUMN} 1.3.6.1.4.1.2356.11.2.25.10.7.1.7
lcsSetupRadiusServerUsersEntryTxLimit OBJECT-TYPE
    SYNTAX     Integer32 (0..2147483647)
    MAX-ACCESS read-write
    STATUS     current
    DESCRIPTION
            ""
    ::= { lcsSetupRadiusServerUsersEntry 7 }

-- {COLUMN} 1.3.6.1.4.1.2356.11.2.25.10.7.1.8
lcsSetupRadiusServerUsersEntryRxLimit OBJECT-TYPE
    SYNTAX     Integer32 (0..2147483647)
    MAX-ACCESS read-write
    STATUS     current
    DESCRIPTION
            ""
    ::= { lcsSetupRadiusServerUsersEntry 8 }

-- {COLUMN} 1.3.6.1.4.1.2356.11.2.25.10.7.1.9
lcsSetupRadiusServerUsersEntryMultipleLogin OBJECT-TYPE
    SYNTAX     INTEGER {
                  eYes (0),
                  eNo (1)
            }
    MAX-ACCESS read-write
    STATUS     current
    DESCRIPTION
            ""
    ::= { lcsSetupRadiusServerUsersEntry 9 }

-- {COLUMN} 1.3.6.1.4.1.2356.11.2.25.10.7.1.10
lcsSetupRadiusServerUsersEntryAbsExpiry OBJECT-TYPE
    SYNTAX     DisplayString (SIZE(0..21))
    MAX-ACCESS read-write
    STATUS     current
    DESCRIPTION
            ""
    ::= { lcsSetupRadiusServerUsersEntry 10 }

-- {COLUMN} 1.3.6.1.4.1.2356.11.2.25.10.7.1.11
lcsSetupRadiusServerUsersEntryTimeBudget OBJECT-TYPE
    SYNTAX     Integer32 (0..2147483647)
    MAX-ACCESS read-write
    STATUS     current
    DESCRIPTION
            ""
    ::= { lcsSetupRadiusServerUsersEntry 11 }

-- {COLUMN} 1.3.6.1.4.1.2356.11.2.25.10.7.1.12
lcsSetupRadiusServerUsersEntryVolumeBudget OBJECT-TYPE
    SYNTAX     Integer32 (0..2147483647)
    MAX-ACCESS read-write
    STATUS     current
    DESCRIPTION
            ""
    ::= { lcsSetupRadiusServerUsersEntry 12 }

-- {COLUMN} 1.3.6.1.4.1.2356.11.2.25.10.7.1.13
lcsSetupRadiusServerUsersEntryExpiryType OBJECT-TYPE
    SYNTAX     BITS {
                  eNone (0),
                  eRelative (6),
                  eAbsolute (7)
            }
    MAX-ACCESS read-write
    STATUS     current
    DESCRIPTION
            ""
    ::= { lcsSetupRadiusServerUsersEntry 13 }

-- {COLUMN} 1.3.6.1.4.1.2356.11.2.25.10.7.1.14
lcsSetupRadiusServerUsersEntryRelExpiry OBJECT-TYPE
    SYNTAX     Integer32 (0..2147483647)
    MAX-ACCESS read-write
    STATUS     current
    DESCRIPTION
            ""
    ::= { lcsSetupRadiusServerUsersEntry 14 }

-- {COLUMN} 1.3.6.1.4.1.2356.11.2.25.10.7.1.15
lcsSetupRadiusServerUsersEntryComment OBJECT-TYPE
    SYNTAX     DisplayString (SIZE(0..251))
    MAX-ACCESS read-write
    STATUS     current
    DESCRIPTION
            ""
    ::= { lcsSetupRadiusServerUsersEntry 15 }

-- {COLUMN} 1.3.6.1.4.1.2356.11.2.25.10.7.1.16
lcsSetupRadiusServerUsersEntryServiceType OBJECT-TYPE
    SYNTAX     INTEGER {
                  eAny (0),
                  eLogin (1),
                  eFramed (2),
                  eCallbackLogin (3),
                  eCallbackFramed (4),
                  eOutbound (5),
                  eAdministrative (6),
                  eNasPrompt (7),
                  eAuthOnly (8),
                  eCallbackNasPrompt (9),
                  eCallCheck (10),
                  eCallbackAdministrative (11),
                  eVoice (12),
                  eFax (13),
                  eModemRelay (14),
                  eAuthorizeOnly (17),
                  eFramedManagement (18)
            }
    MAX-ACCESS read-write
    STATUS     current
    DESCRIPTION
            ""
    ::= { lcsSetupRadiusServerUsersEntry 16 }

-- {COLUMN} 1.3.6.1.4.1.2356.11.2.25.10.7.1.17
lcsSetupRadiusServerUsersEntryCaseSensitive OBJECT-TYPE
    SYNTAX     INTEGER {
                  eYes (0),
                  eNo (1)
            }
    MAX-ACCESS read-write
    STATUS     current
    DESCRIPTION
            "-- empty --"
    ::= { lcsSetupRadiusServerUsersEntry 17 }

-- {COLUMN} 1.3.6.1.4.1.2356.11.2.25.10.7.1.18
lcsSetupRadiusServerUsersEntryWpaPassphrase OBJECT-TYPE
    SYNTAX     DisplayString (SIZE(0..63))
    MAX-ACCESS read-write
    STATUS     current
    DESCRIPTION
            "-- empty --"
    ::= { lcsSetupRadiusServerUsersEntry 18 }

-- {COLUMN} 1.3.6.1.4.1.2356.11.2.25.10.7.1.19
lcsSetupRadiusServerUsersEntryMaxConcurrentLogins OBJECT-TYPE
    SYNTAX     Integer32 (0..2147483647)
    MAX-ACCESS read-write
    STATUS     current
    DESCRIPTION
            "-- empty --"
    ::= { lcsSetupRadiusServerUsersEntry 19 }

-- {COLUMN} 1.3.6.1.4.1.2356.11.2.25.10.7.1.20
lcsSetupRadiusServerUsersEntryActive OBJECT-TYPE
    SYNTAX     INTEGER {
                  eNo (0),
                  eYes (1)
            }
    MAX-ACCESS read-write
    STATUS     current
    DESCRIPTION
            "-- empty --"
    ::= { lcsSetupRadiusServerUsersEntry 20 }

-- {COLUMN} 1.3.6.1.4.1.2356.11.2.25.10.7.1.21
lcsSetupRadiusServerUsersEntryShellPrivLevel OBJECT-TYPE
    SYNTAX     Integer32 (0..2147483647)
    MAX-ACCESS read-write
    STATUS     current
    DESCRIPTION
            "-- empty --"
    ::= { lcsSetupRadiusServerUsersEntry 21 }

-- {COLUMN} 1.3.6.1.4.1.2356.11.2.25.10.7.1.22
lcsSetupRadiusServerUsersEntryVolumeBudgetMbytes OBJECT-TYPE
    SYNTAX     Integer32 (0..2147483647)
    MAX-ACCESS read-write
    STATUS     current
    DESCRIPTION
            "-- empty --"
    ::= { lcsSetupRadiusServerUsersEntry 22 }

-- {COLUMN} 1.3.6.1.4.1.2356.11.2.25.10.7.1.23
lcsSetupRadiusServerUsersEntryTunnelPassword OBJECT-TYPE
    SYNTAX     DisplayString (SIZE(0..32))
    MAX-ACCESS read-write
    STATUS     current
    DESCRIPTION
            "-- empty --"
    ::= { lcsSetupRadiusServerUsersEntry 23 }

-- {COLUMN} 1.3.6.1.4.1.2356.11.2.25.10.7.1.24
lcsSetupRadiusServerUsersEntryLcsRoutingTag OBJECT-TYPE
    SYNTAX     Integer32 (0..65535)
    MAX-ACCESS read-write
    STATUS     current
    DESCRIPTION
            "-- empty --"
    ::= { lcsSetupRadiusServerUsersEntry 24 }

-- {COLUMN} 1.3.6.1.4.1.2356.11.2.25.10.7.1.25
lcsSetupRadiusServerUsersEntryAttributeValues OBJECT-TYPE
    SYNTAX     DisplayString (SIZE(0..251))
    MAX-ACCESS read-write
    STATUS     current
    DESCRIPTION
            "-- empty --"
    ::= { lcsSetupRadiusServerUsersEntry 25 }

-- {NODE} 1.3.6.1.4.1.2356.11.2.25.10.10
lcsSetupRadiusServerEap OBJECT IDENTIFIER ::= { lcsSetupRadiusServer 10 }

-- {SCALAR} 1.3.6.1.4.1.2356.11.2.25.10.10.1
lcsSetupRadiusServerEapTunnelServer OBJECT-TYPE
    SYNTAX     DisplayString (SIZE(0..64))
    MAX-ACCESS read-write
    STATUS     current
    DESCRIPTION
            ""
    ::= { lcsSetupRadiusServerEap 1 }

-- {SCALAR} 1.3.6.1.4.1.2356.11.2.25.10.10.2
lcsSetupRadiusServerEapTlsCheckUsername OBJECT-TYPE
    SYNTAX     INTEGER {
                  eNo (0),
                  eYes (1)
            }
    MAX-ACCESS read-write
    STATUS     current
    DESCRIPTION
            ""
    ::= { lcsSetupRadiusServerEap 2 }

-- {SCALAR} 1.3.6.1.4.1.2356.11.2.25.10.10.3
lcsSetupRadiusServerEapReauthPeriod OBJECT-TYPE
    SYNTAX     Integer32 (0..2147483647)
    MAX-ACCESS read-write
    STATUS     current
    DESCRIPTION
            ""
    ::= { lcsSetupRadiusServerEap 3 }

-- {SCALAR} 1.3.6.1.4.1.2356.11.2.25.10.10.4
lcsSetupRadiusServerEapRetransmitTimeout OBJECT-TYPE
    SYNTAX     Integer32 (0..2147483647)
    MAX-ACCESS read-write
    STATUS     current
    DESCRIPTION
            ""
    ::= { lcsSetupRadiusServerEap 4 }

-- {SCALAR} 1.3.6.1.4.1.2356.11.2.25.10.10.5
lcsSetupRadiusServerEapTtlsDefaultTunnelMethod OBJECT-TYPE
    SYNTAX     INTEGER {
                  eNone (0),
                  eMd5 (4),
                  eGtc (6),
                  eMschapv2 (26)
            }
    MAX-ACCESS read-write
    STATUS     current
    DESCRIPTION
            ""
    ::= { lcsSetupRadiusServerEap 5 }

-- {SCALAR} 1.3.6.1.4.1.2356.11.2.25.10.10.6
lcsSetupRadiusServerEapPeapDefaultTunnelMethod OBJECT-TYPE
    SYNTAX     INTEGER {
                  eNone (0),
                  eMd5 (4),
                  eGtc (6),
                  eMschapv2 (26)
            }
    MAX-ACCESS read-write
    STATUS     current
    DESCRIPTION
            ""
    ::= { lcsSetupRadiusServerEap 6 }

-- {SCALAR} 1.3.6.1.4.1.2356.11.2.25.10.10.7
lcsSetupRadiusServerEapDefaultMethod OBJECT-TYPE
    SYNTAX     INTEGER {
                  eMd5 (4),
                  eGtc (6),
                  eTls (13),
                  eSim (18),
                  eTtls (21),
                  ePeap (25),
                  eMschapv2 (26),
                  eWfaUnauth (141)
            }
    MAX-ACCESS read-write
    STATUS     current
    DESCRIPTION
            ""
    ::= { lcsSetupRadiusServerEap 7 }

-- {SCALAR} 1.3.6.1.4.1.2356.11.2.25.10.10.8
lcsSetupRadiusServerEapDefaultMtu OBJECT-TYPE
    SYNTAX     Integer32 (0..65535)
    MAX-ACCESS read-write
    STATUS     current
    DESCRIPTION
            ""
    ::= { lcsSetupRadiusServerEap 8 }

-- {TABLE} 1.3.6.1.4.1.2356.11.2.25.10.10.9
lcsSetupRadiusServerEapAllowMethodsTable OBJECT-TYPE
    SYNTAX     SEQUENCE OF LcsSetupRadiusServerEapAllowMethodsEntry
    MAX-ACCESS not-accessible
    STATUS     current
    DESCRIPTION
            "-- empty --"
    ::= { lcsSetupRadiusServerEap 9 }

-- {ROW} 1.3.6.1.4.1.2356.11.2.25.10.10.9.1
lcsSetupRadiusServerEapAllowMethodsEntry OBJECT-TYPE
    SYNTAX     LcsSetupRadiusServerEapAllowMethodsEntry
    MAX-ACCESS not-accessible
    STATUS     current
    DESCRIPTION
            ""
    INDEX {
            lcsSetupRadiusServerEapAllowMethodsEntryMethod
          }
    ::= { lcsSetupRadiusServerEapAllowMethodsTable 1 }

LcsSetupRadiusServerEapAllowMethodsEntry ::= SEQUENCE {
            lcsSetupRadiusServerEapAllowMethodsEntryMethod INTEGER,
            lcsSetupRadiusServerEapAllowMethodsEntryAllow INTEGER
    }

-- {COLUMN} 1.3.6.1.4.1.2356.11.2.25.10.10.9.1.1
lcsSetupRadiusServerEapAllowMethodsEntryMethod OBJECT-TYPE
    SYNTAX     INTEGER {
                  eMd5 (4),
                  eGtc (6),
                  eTls (13),
                  eSim (18),
                  eTtls (21),
                  ePeap (25),
                  eMschapv2 (26),
                  eWfaUnauth (141)
            }
    MAX-ACCESS read-write
    STATUS     current
    DESCRIPTION
            "-- empty --"
    ::= { lcsSetupRadiusServerEapAllowMethodsEntry 1 }

-- {COLUMN} 1.3.6.1.4.1.2356.11.2.25.10.10.9.1.2
lcsSetupRadiusServerEapAllowMethodsEntryAllow OBJECT-TYPE
    SYNTAX     INTEGER {
                  eOff (0),
                  eOn (1),
                  eInternalOnly (2)
            }
    MAX-ACCESS read-write
    STATUS     current
    DESCRIPTION
            "-- empty --"
    ::= { lcsSetupRadiusServerEapAllowMethodsEntry 2 }

-- {SCALAR} 1.3.6.1.4.1.2356.11.2.25.10.10.10
lcsSetupRadiusServerEapMschapv2BackendServer OBJECT-TYPE
    SYNTAX     DisplayString (SIZE(0..64))
    MAX-ACCESS read-write
    STATUS     current
    DESCRIPTION
            "-- empty --"
    ::= { lcsSetupRadiusServerEap 10 }

-- {NODE} 1.3.6.1.4.1.2356.11.2.25.10.10.18
lcsSetupRadiusServerEapEapSim OBJECT IDENTIFIER ::= { lcsSetupRadiusServerEap 18 }

-- {TABLE} 1.3.6.1.4.1.2356.11.2.25.10.10.18.1
lcsSetupRadiusServerEapEapSimCardKeysTable OBJECT-TYPE
    SYNTAX     SEQUENCE OF LcsSetupRadiusServerEapEapSimCardKeysEntry
    MAX-ACCESS not-accessible
    STATUS     current
    DESCRIPTION
            "-- empty --"
    ::= { lcsSetupRadiusServerEapEapSim 1 }

-- {ROW} 1.3.6.1.4.1.2356.11.2.25.10.10.18.1.1
lcsSetupRadiusServerEapEapSimCardKeysEntry OBJECT-TYPE
    SYNTAX     LcsSetupRadiusServerEapEapSimCardKeysEntry
    MAX-ACCESS not-accessible
    STATUS     current
    DESCRIPTION
            ""
    INDEX {
            lcsSetupRadiusServerEapEapSimCardKeysEntryUserName,
            lcsSetupRadiusServerEapEapSimCardKeysEntryCallingStationIdMask,
            lcsSetupRadiusServerEapEapSimCardKeysEntryCalledStationIdMask
          }
    ::= { lcsSetupRadiusServerEapEapSimCardKeysTable 1 }

LcsSetupRadiusServerEapEapSimCardKeysEntry ::= SEQUENCE {
            lcsSetupRadiusServerEapEapSimCardKeysEntryUserName DisplayString,
            lcsSetupRadiusServerEapEapSimCardKeysEntryCallingStationIdMask DisplayString,
            lcsSetupRadiusServerEapEapSimCardKeysEntryCalledStationIdMask DisplayString,
            lcsSetupRadiusServerEapEapSimCardKeysEntryRand1 OCTET STRING,
            lcsSetupRadiusServerEapEapSimCardKeysEntrySres1 OCTET STRING,
            lcsSetupRadiusServerEapEapSimCardKeysEntryKc1 OCTET STRING,
            lcsSetupRadiusServerEapEapSimCardKeysEntryRand2 OCTET STRING,
            lcsSetupRadiusServerEapEapSimCardKeysEntrySres2 OCTET STRING,
            lcsSetupRadiusServerEapEapSimCardKeysEntryKc2 OCTET STRING,
            lcsSetupRadiusServerEapEapSimCardKeysEntryRand3 OCTET STRING,
            lcsSetupRadiusServerEapEapSimCardKeysEntrySres3 OCTET STRING,
            lcsSetupRadiusServerEapEapSimCardKeysEntryKc3 OCTET STRING
    }

-- {COLUMN} 1.3.6.1.4.1.2356.11.2.25.10.10.18.1.1.1
lcsSetupRadiusServerEapEapSimCardKeysEntryUserName OBJECT-TYPE
    SYNTAX     DisplayString (SIZE(0..48))
    MAX-ACCESS read-write
    STATUS     current
    DESCRIPTION
            "-- empty --"
    ::= { lcsSetupRadiusServerEapEapSimCardKeysEntry 1 }

-- {COLUMN} 1.3.6.1.4.1.2356.11.2.25.10.10.18.1.1.5
lcsSetupRadiusServerEapEapSimCardKeysEntryCallingStationIdMask OBJECT-TYPE
    SYNTAX     DisplayString (SIZE(0..64))
    MAX-ACCESS read-write
    STATUS     current
    DESCRIPTION
            "-- empty --"
    ::= { lcsSetupRadiusServerEapEapSimCardKeysEntry 5 }

-- {COLUMN} 1.3.6.1.4.1.2356.11.2.25.10.10.18.1.1.6
lcsSetupRadiusServerEapEapSimCardKeysEntryCalledStationIdMask OBJECT-TYPE
    SYNTAX     DisplayString (SIZE(0..64))
    MAX-ACCESS read-write
    STATUS     current
    DESCRIPTION
            "-- empty --"
    ::= { lcsSetupRadiusServerEapEapSimCardKeysEntry 6 }

-- {COLUMN} 1.3.6.1.4.1.2356.11.2.25.10.10.18.1.1.7
lcsSetupRadiusServerEapEapSimCardKeysEntryRand1 OBJECT-TYPE
    SYNTAX     OCTET STRING
    MAX-ACCESS read-write
    STATUS     current
    DESCRIPTION
            "-- empty --"
    ::= { lcsSetupRadiusServerEapEapSimCardKeysEntry 7 }

-- {COLUMN} 1.3.6.1.4.1.2356.11.2.25.10.10.18.1.1.8
lcsSetupRadiusServerEapEapSimCardKeysEntrySres1 OBJECT-TYPE
    SYNTAX     OCTET STRING
    MAX-ACCESS read-write
    STATUS     current
    DESCRIPTION
            "-- empty --"
    ::= { lcsSetupRadiusServerEapEapSimCardKeysEntry 8 }

-- {COLUMN} 1.3.6.1.4.1.2356.11.2.25.10.10.18.1.1.9
lcsSetupRadiusServerEapEapSimCardKeysEntryKc1 OBJECT-TYPE
    SYNTAX     OCTET STRING
    MAX-ACCESS read-write
    STATUS     current
    DESCRIPTION
            "-- empty --"
    ::= { lcsSetupRadiusServerEapEapSimCardKeysEntry 9 }

-- {COLUMN} 1.3.6.1.4.1.2356.11.2.25.10.10.18.1.1.10
lcsSetupRadiusServerEapEapSimCardKeysEntryRand2 OBJECT-TYPE
    SYNTAX     OCTET STRING
    MAX-ACCESS read-write
    STATUS     current
    DESCRIPTION
            "-- empty --"
    ::= { lcsSetupRadiusServerEapEapSimCardKeysEntry 10 }

-- {COLUMN} 1.3.6.1.4.1.2356.11.2.25.10.10.18.1.1.11
lcsSetupRadiusServerEapEapSimCardKeysEntrySres2 OBJECT-TYPE
    SYNTAX     OCTET STRING
    MAX-ACCESS read-write
    STATUS     current
    DESCRIPTION
            "-- empty --"
    ::= { lcsSetupRadiusServerEapEapSimCardKeysEntry 11 }

-- {COLUMN} 1.3.6.1.4.1.2356.11.2.25.10.10.18.1.1.12
lcsSetupRadiusServerEapEapSimCardKeysEntryKc2 OBJECT-TYPE
    SYNTAX     OCTET STRING
    MAX-ACCESS read-write
    STATUS     current
    DESCRIPTION
            "-- empty --"
    ::= { lcsSetupRadiusServerEapEapSimCardKeysEntry 12 }

-- {COLUMN} 1.3.6.1.4.1.2356.11.2.25.10.10.18.1.1.13
lcsSetupRadiusServerEapEapSimCardKeysEntryRand3 OBJECT-TYPE
    SYNTAX     OCTET STRING
    MAX-ACCESS read-write
    STATUS     current
    DESCRIPTION
            "-- empty --"
    ::= { lcsSetupRadiusServerEapEapSimCardKeysEntry 13 }

-- {COLUMN} 1.3.6.1.4.1.2356.11.2.25.10.10.18.1.1.14
lcsSetupRadiusServerEapEapSimCardKeysEntrySres3 OBJECT-TYPE
    SYNTAX     OCTET STRING
    MAX-ACCESS read-write
    STATUS     current
    DESCRIPTION
            "-- empty --"
    ::= { lcsSetupRadiusServerEapEapSimCardKeysEntry 14 }

-- {COLUMN} 1.3.6.1.4.1.2356.11.2.25.10.10.18.1.1.15
lcsSetupRadiusServerEapEapSimCardKeysEntryKc3 OBJECT-TYPE
    SYNTAX     OCTET STRING
    MAX-ACCESS read-write
    STATUS     current
    DESCRIPTION
            "-- empty --"
    ::= { lcsSetupRadiusServerEapEapSimCardKeysEntry 15 }

-- {NODE} 1.3.6.1.4.1.2356.11.2.25.10.10.19
lcsSetupRadiusServerEapEapTls OBJECT IDENTIFIER ::= { lcsSetupRadiusServerEap 19 }

-- {SCALAR} 1.3.6.1.4.1.2356.11.2.25.10.10.19.2
lcsSetupRadiusServerEapEapTlsVersions OBJECT-TYPE
    SYNTAX     BITS {
                  eTlsv12 (28),
                  eTlsv11 (29),
                  eTlsv1 (30)
            }
    MAX-ACCESS read-write
    STATUS     current
    DESCRIPTION
            "-- empty --"
    ::= { lcsSetupRadiusServerEapEapTls 2 }

-- {SCALAR} 1.3.6.1.4.1.2356.11.2.25.10.10.19.3
lcsSetupRadiusServerEapEapTlsKeyexAlgorithms OBJECT-TYPE
    SYNTAX     BITS {
                  eEcdhe (27),
                  eDhe (29),
                  eRsa (31)
            }
    MAX-ACCESS read-write
    STATUS     current
    DESCRIPTION
            "-- empty --"
    ::= { lcsSetupRadiusServerEapEapTls 3 }

-- {SCALAR} 1.3.6.1.4.1.2356.11.2.25.10.10.19.4
lcsSetupRadiusServerEapEapTlsCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupRadiusServerEapEapTls 4 }

-- {SCALAR} 1.3.6.1.4.1.2356.11.2.25.10.10.19.5
lcsSetupRadiusServerEapEapTlsHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupRadiusServerEapEapTls 5 }

-- {SCALAR} 1.3.6.1.4.1.2356.11.2.25.10.10.19.6
lcsSetupRadiusServerEapEapTlsPreferPfs OBJECT-TYPE
    SYNTAX     BITS {
                  eNo (0),
                  eYes (7)
            }
    MAX-ACCESS read-write
    STATUS     current
    DESCRIPTION
            "-- empty --"
    ::= { lcsSetupRadiusServerEapEapTls 6 }

-- {SCALAR} 1.3.6.1.4.1.2356.11.2.25.10.10.19.8
lcsSetupRadiusServerEapEapTlsEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupRadiusServerEapEapTls 8 }

-- {SCALAR} 1.3.6.1.4.1.2356.11.2.25.10.10.19.10
lcsSetupRadiusServerEapEapTlsCheckUsername OBJECT-TYPE
    SYNTAX     INTEGER {
                  eNo (0),
                  eYes (1)
            }
    MAX-ACCESS read-write
    STATUS     current
    DESCRIPTION
            "-- empty --"
    ::= { lcsSetupRadiusServerEapEapTls 10 }

-- {SCALAR} 1.3.6.1.4.1.2356.11.2.25.10.10.19.11
lcsSetupRadiusServerEapEapTlsUseOcsp OBJECT-TYPE
    SYNTAX     INTEGER {
                  eNo (0),
                  eYes (1)
            }
    MAX-ACCESS read-write
    STATUS     current
    DESCRIPTION
            "-- empty --"
    ::= { lcsSetupRadiusServerEapEapTls 11 }

-- {SCALAR} 1.3.6.1.4.1.2356.11.2.25.10.10.19.12
lcsSetupRadiusServerEapEapTlsOcspUnreachableBehaviour OBJECT-TYPE
    SYNTAX     INTEGER {
                  eReject (0),
                  eAccept (1)
            }
    MAX-ACCESS read-write
    STATUS     current
    DESCRIPTION
            "-- empty --"
    ::= { lcsSetupRadiusServerEapEapTls 12 }

-- {SCALAR} 1.3.6.1.4.1.2356.11.2.25.10.10.19.22
lcsSetupRadiusServerEapEapTlsSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupRadiusServerEapEapTls 22 }

-- {SCALAR} 1.3.6.1.4.1.2356.11.2.25.10.11
lcsSetupRadiusServerAccountingPort OBJECT-TYPE
    SYNTAX     Integer32 (0..65535)
    MAX-ACCESS read-write
    STATUS     current
    DESCRIPTION
            ""
    ::= { lcsSetupRadiusServer 11 }

-- {SCALAR} 1.3.6.1.4.1.2356.11.2.25.10.12
lcsSetupRadiusServerAccountingInterimInterval OBJECT-TYPE
    SYNTAX     Integer32 (0..2147483647)
    MAX-ACCESS read-write
    STATUS     current
    DESCRIPTION
            ""
    ::= { lcsSetupRadiusServer 12 }

-- {SCALAR} 1.3.6.1.4.1.2356.11.2.25.10.13
lcsSetupRadiusServerRadsecPort OBJECT-TYPE
    SYNTAX     Integer32 (0..65535)
    MAX-ACCESS read-write
    STATUS     current
    DESCRIPTION
            ""
    ::= { lcsSetupRadiusServer 13 }

-- {SCALAR} 1.3.6.1.4.1.2356.11.2.25.10.14
lcsSetupRadiusServerAutoCleanupUserTable OBJECT-TYPE
    SYNTAX     INTEGER {
                  eNo (0),
                  eYes (1)
            }
    MAX-ACCESS read-write
    STATUS     current
    DESCRIPTION
            ""
    ::= { lcsSetupRadiusServer 14 }

-- {SCALAR} 1.3.6.1.4.1.2356.11.2.25.10.15
lcsSetupRadiusServerAllowStatusRequests OBJECT-TYPE
    SYNTAX     INTEGER {
                  eNo (0),
                  eYes (1)
            }
    MAX-ACCESS read-write
    STATUS     current
    DESCRIPTION
            ""
    ::= { lcsSetupRadiusServer 15 }

-- {TABLE} 1.3.6.1.4.1.2356.11.2.25.10.16
lcsSetupRadiusServerIpv6ClientsTable OBJECT-TYPE
    SYNTAX     SEQUENCE OF LcsSetupRadiusServerIpv6ClientsEntry
    MAX-ACCESS not-accessible
    STATUS     current
    DESCRIPTION
            "-- empty --"
    ::= { lcsSetupRadiusServer 16 }

-- {ROW} 1.3.6.1.4.1.2356.11.2.25.10.16.1
lcsSetupRadiusServerIpv6ClientsEntry OBJECT-TYPE
    SYNTAX     LcsSetupRadiusServerIpv6ClientsEntry
    MAX-ACCESS not-accessible
    STATUS     current
    DESCRIPTION
            ""
    INDEX {
            lcsSetupRadiusServerIpv6ClientsEntryAddressPrefixlength
          }
    ::= { lcsSetupRadiusServerIpv6ClientsTable 1 }

LcsSetupRadiusServerIpv6ClientsEntry ::= SEQUENCE {
            lcsSetupRadiusServerIpv6ClientsEntryAddressPrefixlength DisplayString,
            lcsSetupRadiusServerIpv6ClientsEntrySecret DisplayString,
            lcsSetupRadiusServerIpv6ClientsEntryProtocols INTEGER,
            lcsSetupRadiusServerIpv6ClientsEntryComment DisplayString
    }

-- {COLUMN} 1.3.6.1.4.1.2356.11.2.25.10.16.1.1
lcsSetupRadiusServerIpv6ClientsEntryAddressPrefixlength OBJECT-TYPE
    SYNTAX     DisplayString (SIZE(0..43))
    MAX-ACCESS read-write
    STATUS     current
    DESCRIPTION
            "-- empty --"
    ::= { lcsSetupRadiusServerIpv6ClientsEntry 1 }

-- {COLUMN} 1.3.6.1.4.1.2356.11.2.25.10.16.1.2
lcsSetupRadiusServerIpv6ClientsEntrySecret OBJECT-TYPE
    SYNTAX     DisplayString (SIZE(0..64))
    MAX-ACCESS read-write
    STATUS     current
    DESCRIPTION
            "-- empty --"
    ::= { lcsSetupRadiusServerIpv6ClientsEntry 2 }

-- {COLUMN} 1.3.6.1.4.1.2356.11.2.25.10.16.1.4
lcsSetupRadiusServerIpv6ClientsEntryProtocols OBJECT-TYPE
    SYNTAX     INTEGER {
                  eRadius (0),
                  eRadsec (1),
                  eAll (255)
            }
    MAX-ACCESS read-write
    STATUS     current
    DESCRIPTION
            "-- empty --"
    ::= { lcsSetupRadiusServerIpv6ClientsEntry 4 }

-- {COLUMN} 1.3.6.1.4.1.2356.11.2.25.10.16.1.5
lcsSetupRadiusServerIpv6ClientsEntryComment OBJECT-TYPE
    SYNTAX     DisplayString (SIZE(0..251))
    MAX-ACCESS read-write
    STATUS     current
    DESCRIPTION
            "-- empty --"
    ::= { lcsSetupRadiusServerIpv6ClientsEntry 5 }

-- {SCALAR} 1.3.6.1.4.1.2356.11.2.25.10.17
lcsSetupRadiusServerRealmTypes OBJECT-TYPE
    SYNTAX     BITS {
                  eMsCompauth (29),
                  eMsDomain (30),
                  eMailDomain (31)
            }
    MAX-ACCESS read-write
    STATUS     current
    DESCRIPTION
            "-- empty --"
    ::= { lcsSetupRadiusServer 17 }

-- {SCALAR} 1.3.6.1.4.1.2356.11.2.25.10.18
lcsSetupRadiusServerAutoCleanupAccountingTotals OBJECT-TYPE
    SYNTAX     INTEGER {
                  eNo (0),
                  eYes (1)
            }
    MAX-ACCESS read-write
    STATUS     current
    DESCRIPTION
            "-- empty --"
    ::= { lcsSetupRadiusServer 18 }

-- {SCALAR} 1.3.6.1.4.1.2356.11.2.25.10.19
lcsSetupRadiusServerAllowMultilogin OBJECT-TYPE
    SYNTAX     INTEGER {
                  eNone (0),
                  eSameCallingStationId (1)
            }
    MAX-ACCESS read-write
    STATUS     current
    DESCRIPTION
            "-- empty --"
    ::= { lcsSetupRadiusServer 19 }

-- {SCALAR} 1.3.6.1.4.1.2356.11.2.25.10.21
lcsSetupRadiusServerAuthenticationOperating OBJECT-TYPE
    SYNTAX     INTEGER {
                  eNo (0),
                  eYes (1)
            }
    MAX-ACCESS read-write
    STATUS     current
    DESCRIPTION
            "-- empty --"
    ::= { lcsSetupRadiusServer 21 }

-- {SCALAR} 1.3.6.1.4.1.2356.11.2.25.10.22
lcsSetupRadiusServerIpv4WanAccess OBJECT-TYPE
    SYNTAX     INTEGER {
                  eNo (0),
                  eYes (1),
                  eVpn (2)
            }
    MAX-ACCESS read-write
    STATUS     current
    DESCRIPTION
            "-- empty --"
    ::= { lcsSetupRadiusServer 22 }

-- {SCALAR} 1.3.6.1.4.1.2356.11.2.25.10.31
lcsSetupRadiusServerAccountingOperating OBJECT-TYPE
    SYNTAX     INTEGER {
                  eNo (0),
                  eYes (1)
            }
    MAX-ACCESS read-write
    STATUS     current
    DESCRIPTION
            "-- empty --"
    ::= { lcsSetupRadiusServer 31 }

-- {SCALAR} 1.3.6.1.4.1.2356.11.2.25.10.33
lcsSetupRadiusServerRadsecOperating OBJECT-TYPE
    SYNTAX     INTEGER {
                  eNo (0),
                  eYes (1)
            }
    MAX-ACCESS read-write
    STATUS     current
    DESCRIPTION
            "-- empty --"
    ::= { lcsSetupRadiusServer 33 }

-- {NODE} 1.3.6.1.4.1.2356.11.2.25.19
lcsSetupRadiusDynAuth OBJECT IDENTIFIER ::= { lcsSetupRadius 19 }

-- {SCALAR} 1.3.6.1.4.1.2356.11.2.25.19.1
lcsSetupRadiusDynAuthOperating OBJECT-TYPE
    SYNTAX     INTEGER {
                  eNo (0),
                  eYes (1)
            }
    MAX-ACCESS read-write
    STATUS     current
    DESCRIPTION
            "-- empty --"
    ::= { lcsSetupRadiusDynAuth 1 }

-- {SCALAR} 1.3.6.1.4.1.2356.11.2.25.19.2
lcsSetupRadiusDynAuthPort OBJECT-TYPE
    SYNTAX     Integer32 (0..65535)
    MAX-ACCESS read-write
    STATUS     current
    DESCRIPTION
            "-- empty --"
    ::= { lcsSetupRadiusDynAuth 2 }

-- {SCALAR} 1.3.6.1.4.1.2356.11.2.25.19.3
lcsSetupRadiusDynAuthWanAccess OBJECT-TYPE
    SYNTAX     INTEGER {
                  eNo (0),
                  eYes (1),
                  eOverVpn (2)
            }
    MAX-ACCESS read-write
    STATUS     current
    DESCRIPTION
            "-- empty --"
    ::= { lcsSetupRadiusDynAuth 3 }

-- {TABLE} 1.3.6.1.4.1.2356.11.2.25.19.4
lcsSetupRadiusDynAuthClientsTable OBJECT-TYPE
    SYNTAX     SEQUENCE OF LcsSetupRadiusDynAuthClientsEntry
    MAX-ACCESS not-accessible
    STATUS     current
    DESCRIPTION
            "-- empty --"
    ::= { lcsSetupRadiusDynAuth 4 }

-- {ROW} 1.3.6.1.4.1.2356.11.2.25.19.4.1
lcsSetupRadiusDynAuthClientsEntry OBJECT-TYPE
    SYNTAX     LcsSetupRadiusDynAuthClientsEntry
    MAX-ACCESS not-accessible
    STATUS     current
    DESCRIPTION
            ""
    INDEX {
            lcsSetupRadiusDynAuthClientsEntryHostname
          }
    ::= { lcsSetupRadiusDynAuthClientsTable 1 }

LcsSetupRadiusDynAuthClientsEntry ::= SEQUENCE {
            lcsSetupRadiusDynAuthClientsEntryHostname DisplayString,
            lcsSetupRadiusDynAuthClientsEntrySecret DisplayString
    }

-- {COLUMN} 1.3.6.1.4.1.2356.11.2.25.19.4.1.1
lcsSetupRadiusDynAuthClientsEntryHostname OBJECT-TYPE
    SYNTAX     DisplayString (SIZE(0..64))
    MAX-ACCESS read-write
    STATUS     current
    DESCRIPTION
            "-- empty --"
    ::= { lcsSetupRadiusDynAuthClientsEntry 1 }

-- {COLUMN} 1.3.6.1.4.1.2356.11.2.25.19.4.1.2
lcsSetupRadiusDynAuthClientsEntrySecret OBJECT-TYPE
    SYNTAX     DisplayString (SIZE(0..64))
    MAX-ACCESS read-write
    STATUS     current
    DESCRIPTION
            "-- empty --"
    ::= { lcsSetupRadiusDynAuthClientsEntry 2 }

-- {TABLE} 1.3.6.1.4.1.2356.11.2.25.19.5
lcsSetupRadiusDynAuthForwardServersTable OBJECT-TYPE
    SYNTAX     SEQUENCE OF LcsSetupRadiusDynAuthForwardServersEntry
    MAX-ACCESS not-accessible
    STATUS     current
    DESCRIPTION
            "-- empty --"
    ::= { lcsSetupRadiusDynAuth 5 }

-- {ROW} 1.3.6.1.4.1.2356.11.2.25.19.5.1
lcsSetupRadiusDynAuthForwardServersEntry OBJECT-TYPE
    SYNTAX     LcsSetupRadiusDynAuthForwardServersEntry
    MAX-ACCESS not-accessible
    STATUS     current
    DESCRIPTION
            ""
    INDEX {
            lcsSetupRadiusDynAuthForwardServersEntryRealm
          }
    ::= { lcsSetupRadiusDynAuthForwardServersTable 1 }

LcsSetupRadiusDynAuthForwardServersEntry ::= SEQUENCE {
            lcsSetupRadiusDynAuthForwardServersEntryRealm DisplayString,
            lcsSetupRadiusDynAuthForwardServersEntryHostname DisplayString,
            lcsSetupRadiusDynAuthForwardServersEntryPort Integer32,
            lcsSetupRadiusDynAuthForwardServersEntrySecret DisplayString,
            lcsSetupRadiusDynAuthForwardServersEntryLoopback DisplayString
    }

-- {COLUMN} 1.3.6.1.4.1.2356.11.2.25.19.5.1.1
lcsSetupRadiusDynAuthForwardServersEntryRealm OBJECT-TYPE
    SYNTAX     DisplayString (SIZE(0..64))
    MAX-ACCESS read-write
    STATUS     current
    DESCRIPTION
            "-- empty --"
    ::= { lcsSetupRadiusDynAuthForwardServersEntry 1 }

-- {COLUMN} 1.3.6.1.4.1.2356.11.2.25.19.5.1.2
lcsSetupRadiusDynAuthForwardServersEntryHostname OBJECT-TYPE
    SYNTAX     DisplayString (SIZE(0..64))
    MAX-ACCESS read-write
    STATUS     current
    DESCRIPTION
            "-- empty --"
    ::= { lcsSetupRadiusDynAuthForwardServersEntry 2 }

-- {COLUMN} 1.3.6.1.4.1.2356.11.2.25.19.5.1.3
lcsSetupRadiusDynAuthForwardServersEntryPort OBJECT-TYPE
    SYNTAX     Integer32 (0..65535)
    MAX-ACCESS read-write
    STATUS     current
    DESCRIPTION
            "-- empty --"
    ::= { lcsSetupRadiusDynAuthForwardServersEntry 3 }

-- {COLUMN} 1.3.6.1.4.1.2356.11.2.25.19.5.1.4
lcsSetupRadiusDynAuthForwardServersEntrySecret OBJECT-TYPE
    SYNTAX     DisplayString (SIZE(0..64))
    MAX-ACCESS read-write
    STATUS     current
    DESCRIPTION
            "-- empty --"
    ::= { lcsSetupRadiusDynAuthForwardServersEntry 4 }

-- {COLUMN} 1.3.6.1.4.1.2356.11.2.25.19.5.1.5
lcsSetupRadiusDynAuthForwardServersEntryLoopback OBJECT-TYPE
    SYNTAX     DisplayString (SIZE(0..64))
    MAX-ACCESS read-write
    STATUS     current
    DESCRIPTION
            "-- empty --"
    ::= { lcsSetupRadiusDynAuthForwardServersEntry 5 }

-- {SCALAR} 1.3.6.1.4.1.2356.11.2.25.19.6
lcsSetupRadiusDynAuthDefaultRealm OBJECT-TYPE
    SYNTAX     DisplayString (SIZE(0..65))
    MAX-ACCESS read-write
    STATUS     current
    DESCRIPTION
            "-- empty --"
    ::= { lcsSetupRadiusDynAuth 6 }

-- {SCALAR} 1.3.6.1.4.1.2356.11.2.25.19.7
lcsSetupRadiusDynAuthEmptyRealm OBJECT-TYPE
    SYNTAX     DisplayString (SIZE(0..65))
    MAX-ACCESS read-write
    STATUS     current
    DESCRIPTION
            "-- empty --"
    ::= { lcsSetupRadiusDynAuth 7 }

-- {SCALAR} 1.3.6.1.4.1.2356.11.2.25.19.8
lcsSetupRadiusDynAuthRadclient OBJECT-TYPE
    SYNTAX     DisplayString
    MAX-ACCESS read-write
    STATUS     current
    DESCRIPTION
            "-- empty --"
    ::= { lcsSetupRadiusDynAuth 8 }

-- {NODE} 1.3.6.1.4.1.2356.11.2.25.20
lcsSetupRadiusRadsec OBJECT IDENTIFIER ::= { lcsSetupRadius 20 }

-- {SCALAR} 1.3.6.1.4.1.2356.11.2.25.20.1
lcsSetupRadiusRadsecVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupRadiusRadsec 1 }

-- {SCALAR} 1.3.6.1.4.1.2356.11.2.25.20.2
lcsSetupRadiusRadsecKeyexAlgorithms OBJECT-TYPE
    SYNTAX     BITS {
                  eEcdhe (27),
                  eDhe (29),
                  eRsa (31)
            }
    MAX-ACCESS read-write
    STATUS     current
    DESCRIPTION
            "-- empty --"
    ::= { lcsSetupRadiusRadsec 2 }

-- {SCALAR} 1.3.6.1.4.1.2356.11.2.25.20.3
lcsSetupRadiusRadsecCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupRadiusRadsec 3 }

-- {SCALAR} 1.3.6.1.4.1.2356.11.2.25.20.4
lcsSetupRadiusRadsecHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupRadiusRadsec 4 }

-- {SCALAR} 1.3.6.1.4.1.2356.11.2.25.20.5
lcsSetupRadiusRadsecPreferPfs OBJECT-TYPE
    SYNTAX     BITS {
                  eNo (0),
                  eYes (7)
            }
    MAX-ACCESS read-write
    STATUS     current
    DESCRIPTION
            "-- empty --"
    ::= { lcsSetupRadiusRadsec 5 }

-- {SCALAR} 1.3.6.1.4.1.2356.11.2.25.20.6
lcsSetupRadiusRadsecRenegotiations OBJECT-TYPE
    SYNTAX     INTEGER {
                  eForbidden (0),
                  eAllowed (1),
                  eIgnored (2)
            }
    MAX-ACCESS read-write
    STATUS     current
    DESCRIPTION
            "-- empty --"
    ::= { lcsSetupRadiusRadsec 6 }

-- {SCALAR} 1.3.6.1.4.1.2356.11.2.25.20.7
lcsSetupRadiusRadsecEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupRadiusRadsec 7 }

-- {SCALAR} 1.3.6.1.4.1.2356.11.2.25.20.21
lcsSetupRadiusRadsecSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupRadiusRadsec 21 }

-- {NODE} 1.3.6.1.4.1.2356.11.2.25.21
lcsSetupRadiusSuperSrv OBJECT IDENTIFIER ::= { lcsSetupRadius 21 }

-- {TABLE} 1.3.6.1.4.1.2356.11.2.25.21.1
lcsSetupRadiusSuperSrvProfilesTable OBJECT-TYPE
    SYNTAX     SEQUENCE OF LcsSetupRadiusSuperSrvProfilesEntry
    MAX-ACCESS not-accessible
    STATUS     current
    DESCRIPTION
            "-- empty --"
    ::= { lcsSetupRadiusSuperSrv 1 }

-- {ROW} 1.3.6.1.4.1.2356.11.2.25.21.1.1
lcsSetupRadiusSuperSrvProfilesEntry OBJECT-TYPE
    SYNTAX     LcsSetupRadiusSuperSrvProfilesEntry
    MAX-ACCESS not-accessible
    STATUS     current
    DESCRIPTION
            ""
    INDEX {
            lcsSetupRadiusSuperSrvProfilesEntryName
          }
    ::= { lcsSetupRadiusSuperSrvProfilesTable 1 }

LcsSetupRadiusSuperSrvProfilesEntry ::= SEQUENCE {
            lcsSetupRadiusSuperSrvProfilesEntryName DisplayString,
            lcsSetupRadiusSuperSrvProfilesEntryType INTEGER,
            lcsSetupRadiusSuperSrvProfilesEntryAttributes DisplayString,
            lcsSetupRadiusSuperSrvProfilesEntryRequestInterval Integer32
    }

-- {COLUMN} 1.3.6.1.4.1.2356.11.2.25.21.1.1.1
lcsSetupRadiusSuperSrvProfilesEntryName OBJECT-TYPE
    SYNTAX     DisplayString (SIZE(0..8))
    MAX-ACCESS read-write
    STATUS     current
    DESCRIPTION
            "-- empty --"
    ::= { lcsSetupRadiusSuperSrvProfilesEntry 1 }

-- {COLUMN} 1.3.6.1.4.1.2356.11.2.25.21.1.1.2
lcsSetupRadiusSuperSrvProfilesEntryType OBJECT-TYPE
    SYNTAX     INTEGER {
                  eStatusServer (0),
                  eDummyRequest (1)
            }
    MAX-ACCESS read-write
    STATUS     current
    DESCRIPTION
            "-- empty --"
    ::= { lcsSetupRadiusSuperSrvProfilesEntry 2 }

-- {COLUMN} 1.3.6.1.4.1.2356.11.2.25.21.1.1.3
lcsSetupRadiusSuperSrvProfilesEntryAttributes OBJECT-TYPE
    SYNTAX     DisplayString (SIZE(0..48))
    MAX-ACCESS read-write
    STATUS     current
    DESCRIPTION
            "-- empty --"
    ::= { lcsSetupRadiusSuperSrvProfilesEntry 3 }

-- {COLUMN} 1.3.6.1.4.1.2356.11.2.25.21.1.1.4
lcsSetupRadiusSuperSrvProfilesEntryRequestInterval OBJECT-TYPE
    SYNTAX     Integer32 (0..2147483647)
    MAX-ACCESS read-write
    STATUS     current
    DESCRIPTION
            "-- empty --"
    ::= { lcsSetupRadiusSuperSrvProfilesEntry 4 }

-- {NODE} 1.3.6.1.4.1.2356.11.2.25.22
lcsSetupRadiusUserDefinedAttributes OBJECT IDENTIFIER ::= { lcsSetupRadius 22 }

-- {TABLE} 1.3.6.1.4.1.2356.11.2.25.22.1
lcsSetupRadiusUserDefinedAttributesAttributesTable OBJECT-TYPE
    SYNTAX     SEQUENCE OF LcsSetupRadiusUserDefinedAttributesAttributesEntry
    MAX-ACCESS not-accessible
    STATUS     current
    DESCRIPTION
            "-- empty --"
    ::= { lcsSetupRadiusUserDefinedAttributes 1 }

-- {ROW} 1.3.6.1.4.1.2356.11.2.25.22.1.1
lcsSetupRadiusUserDefinedAttributesAttributesEntry OBJECT-TYPE
    SYNTAX     LcsSetupRadiusUserDefinedAttributesAttributesEntry
    MAX-ACCESS not-accessible
    STATUS     current
    DESCRIPTION
            ""
    INDEX {
            lcsSetupRadiusUserDefinedAttributesAttributesEntryName
          }
    ::= { lcsSetupRadiusUserDefinedAttributesAttributesTable 1 }

LcsSetupRadiusUserDefinedAttributesAttributesEntry ::= SEQUENCE {
            lcsSetupRadiusUserDefinedAttributesAttributesEntryName DisplayString,
            lcsSetupRadiusUserDefinedAttributesAttributesEntryVendorId Integer32,
            lcsSetupRadiusUserDefinedAttributesAttributesEntryVendorType Integer32,
            lcsSetupRadiusUserDefinedAttributesAttributesEntryDataType INTEGER
    }

-- {COLUMN} 1.3.6.1.4.1.2356.11.2.25.22.1.1.1
lcsSetupRadiusUserDefinedAttributesAttributesEntryName OBJECT-TYPE
    SYNTAX     DisplayString (SIZE(0..64))
    MAX-ACCESS read-write
    STATUS     current
    DESCRIPTION
            "-- empty --"
    ::= { lcsSetupRadiusUserDefinedAttributesAttributesEntry 1 }

-- {COLUMN} 1.3.6.1.4.1.2356.11.2.25.22.1.1.2
lcsSetupRadiusUserDefinedAttributesAttributesEntryVendorId OBJECT-TYPE
    SYNTAX     Integer32 (0..2147483647)
    MAX-ACCESS read-write
    STATUS     current
    DESCRIPTION
            "-- empty --"
    ::= { lcsSetupRadiusUserDefinedAttributesAttributesEntry 2 }

-- {COLUMN} 1.3.6.1.4.1.2356.11.2.25.22.1.1.3
lcsSetupRadiusUserDefinedAttributesAttributesEntryVendorType OBJECT-TYPE
    SYNTAX     Integer32 (0..255)
    MAX-ACCESS read-write
    STATUS     current
    DESCRIPTION
            "-- empty --"
    ::= { lcsSetupRadiusUserDefinedAttributesAttributesEntry 3 }

-- {COLUMN} 1.3.6.1.4.1.2356.11.2.25.22.1.1.4
lcsSetupRadiusUserDefinedAttributesAttributesEntryDataType OBJECT-TYPE
    SYNTAX     INTEGER {
                  eInteger (1),
                  eDate (3),
                  eText (4),
                  eIpv4Address (8),
                  eIpv6Address (9)
            }
    MAX-ACCESS read-write
    STATUS     current
    DESCRIPTION
            "-- empty --"
    ::= { lcsSetupRadiusUserDefinedAttributesAttributesEntry 4 }

-- {NODE} 1.3.6.1.4.1.2356.11.2.26
lcsSetupNtp OBJECT IDENTIFIER ::= { lcsSetup 26 }

-- {SCALAR} 1.3.6.1.4.1.2356.11.2.26.2
lcsSetupNtpServerOperating OBJECT-TYPE
    SYNTAX     INTEGER {
                  eNo (0),
                  eYes (1)
            }
    MAX-ACCESS read-write
    STATUS     current
    DESCRIPTION
            ""
    ::= { lcsSetupNtp 2 }

-- {SCALAR} 1.3.6.1.4.1.2356.11.2.26.3
lcsSetupNtpBcMode OBJECT-TYPE
    SYNTAX     INTEGER {
                  eNo (0),
                  eYes (1)
            }
    MAX-ACCESS read-write
    STATUS     current
    DESCRIPTION
            ""
    ::= { lcsSetupNtp 3 }

-- {SCALAR} 1.3.6.1.4.1.2356.11.2.26.4
lcsSetupNtpBcInterval OBJECT-TYPE
    SYNTAX     Integer32 (0..65535)
    MAX-ACCESS read-write
    STATUS     current
    DESCRIPTION
            ""
    ::= { lcsSetupNtp 4 }

-- {SCALAR} 1.3.6.1.4.1.2356.11.2.26.7
lcsSetupNtpRqInterval OBJECT-TYPE
    SYNTAX     Integer32 (0..2147483647)
    MAX-ACCESS read-write
    STATUS     current
    DESCRIPTION
            ""
    ::= { lcsSetupNtp 7 }

-- {TABLE} 1.3.6.1.4.1.2356.11.2.26.11
lcsSetupNtpRqAddressTable OBJECT-TYPE
    SYNTAX     SEQUENCE OF LcsSetupNtpRqAddressEntry
    MAX-ACCESS not-accessible
    STATUS     current
    DESCRIPTION
            ""
    ::= { lcsSetupNtp 11 }

-- {ROW} 1.3.6.1.4.1.2356.11.2.26.11.1
lcsSetupNtpRqAddressEntry OBJECT-TYPE
    SYNTAX     LcsSetupNtpRqAddressEntry
    MAX-ACCESS not-accessible
    STATUS     current
    DESCRIPTION
            ""
    INDEX {
            lcsSetupNtpRqAddressEntryRqAddress
          }
    ::= { lcsSetupNtpRqAddressTable 1 }

LcsSetupNtpRqAddressEntry ::= SEQUENCE {
            lcsSetupNtpRqAddressEntryRqAddress DisplayString,
            lcsSetupNtpRqAddressEntryLoopbackAddr DisplayString,
            lcsSetupNtpRqAddressEntryAuthenticationEnabled INTEGER,
            lcsSetupNtpRqAddressEntryKeyId Integer32
    }

-- {COLUMN} 1.3.6.1.4.1.2356.11.2.26.11.1.1
lcsSetupNtpRqAddressEntryRqAddress OBJECT-TYPE
    SYNTAX     DisplayString (SIZE(0..64))
    MAX-ACCESS read-write
    STATUS     current
    DESCRIPTION
            ""
    ::= { lcsSetupNtpRqAddressEntry 1 }

-- {COLUMN} 1.3.6.1.4.1.2356.11.2.26.11.1.2
lcsSetupNtpRqAddressEntryLoopbackAddr OBJECT-TYPE
    SYNTAX     DisplayString (SIZE(0..39))
    MAX-ACCESS read-write
    STATUS     current
    DESCRIPTION
            ""
    ::= { lcsSetupNtpRqAddressEntry 2 }

-- {COLUMN} 1.3.6.1.4.1.2356.11.2.26.11.1.3
lcsSetupNtpRqAddressEntryAuthenticationEnabled OBJECT-TYPE
    SYNTAX     INTEGER {
                  eNo (0),
                  eYes (1)
            }
    MAX-ACCESS read-write
    STATUS     current
    DESCRIPTION
            "-- empty --"
    ::= { lcsSetupNtpRqAddressEntry 3 }

-- {COLUMN} 1.3.6.1.4.1.2356.11.2.26.11.1.4
lcsSetupNtpRqAddressEntryKeyId OBJECT-TYPE
    SYNTAX     Integer32 (0..2147483647)
    MAX-ACCESS read-write
    STATUS     current
    DESCRIPTION
            "-- empty --"
    ::= { lcsSetupNtpRqAddressEntry 4 }

-- {SCALAR} 1.3.6.1.4.1.2356.11.2.26.12
lcsSetupNtpRqTries OBJECT-TYPE
    SYNTAX     Integer32 (0..2147483647)
    MAX-ACCESS read-write
    STATUS     current
    DESCRIPTION
            ""
    ::= { lcsSetupNtp 12 }

-- {SCALAR} 1.3.6.1.4.1.2356.11.2.26.13
lcsSetupNtpServerAuthentication OBJECT-TYPE
    SYNTAX     INTEGER {
                  eNo (0),
                  eYes (1)
            }
    MAX-ACCESS read-write
    STATUS     current
    DESCRIPTION
            "-- empty --"
    ::= { lcsSetupNtp 13 }

-- {TABLE} 1.3.6.1.4.1.2356.11.2.26.14
lcsSetupNtpAuthenticationKeysTable OBJECT-TYPE
    SYNTAX     SEQUENCE OF LcsSetupNtpAuthenticationKeysEntry
    MAX-ACCESS not-accessible
    STATUS     current
    DESCRIPTION
            "-- empty --"
    ::= { lcsSetupNtp 14 }

-- {ROW} 1.3.6.1.4.1.2356.11.2.26.14.1
lcsSetupNtpAuthenticationKeysEntry OBJECT-TYPE
    SYNTAX     LcsSetupNtpAuthenticationKeysEntry
    MAX-ACCESS not-accessible
    STATUS     current
    DESCRIPTION
            ""
    INDEX {
            lcsSetupNtpAuthenticationKeysEntryKeyId
          }
    ::= { lcsSetupNtpAuthenticationKeysTable 1 }

LcsSetupNtpAuthenticationKeysEntry ::= SEQUENCE {
            lcsSetupNtpAuthenticationKeysEntryKeyId Integer32,
            lcsSetupNtpAuthenticationKeysEntryKey DisplayString
    }

-- {COLUMN} 1.3.6.1.4.1.2356.11.2.26.14.1.1
lcsSetupNtpAuthenticationKeysEntryKeyId OBJECT-TYPE
    SYNTAX     Integer32 (0..2147483647)
    MAX-ACCESS read-write
    STATUS     current
    DESCRIPTION
            "-- empty --"
    ::= { lcsSetupNtpAuthenticationKeysEntry 1 }

-- {COLUMN} 1.3.6.1.4.1.2356.11.2.26.14.1.2
lcsSetupNtpAuthenticationKeysEntryKey OBJECT-TYPE
    SYNTAX     DisplayString (SIZE(0..64))
    MAX-ACCESS read-write
    STATUS     current
    DESCRIPTION
            "-- empty --"
    ::= { lcsSetupNtpAuthenticationKeysEntry 2 }

-- {SCALAR} 1.3.6.1.4.1.2356.11.2.26.15
lcsSetupNtpServerTrustedKeys OBJECT-TYPE
    SYNTAX     DisplayString (SIZE(0..63))
    MAX-ACCESS read-write
    STATUS     current
    DESCRIPTION
            "-- empty --"
    ::= { lcsSetupNtp 15 }

-- {TABLE} 1.3.6.1.4.1.2356.11.2.26.16
lcsSetupNtpNetworklistTable OBJECT-TYPE
    SYNTAX     SEQUENCE OF LcsSetupNtpNetworklistEntry
    MAX-ACCESS not-accessible
    STATUS     current
    DESCRIPTION
            "-- empty --"
    ::= { lcsSetupNtp 16 }

-- {ROW} 1.3.6.1.4.1.2356.11.2.26.16.1
lcsSetupNtpNetworklistEntry OBJECT-TYPE
    SYNTAX     LcsSetupNtpNetworklistEntry
    MAX-ACCESS not-accessible
    STATUS     current
    DESCRIPTION
            ""
    INDEX {
            lcsSetupNtpNetworklistEntryNetworkName
          }
    ::= { lcsSetupNtpNetworklistTable 1 }

LcsSetupNtpNetworklistEntry ::= SEQUENCE {
            lcsSetupNtpNetworklistEntryNetworkName DisplayString,
            lcsSetupNtpNetworklistEntryServerOperating INTEGER
    }

-- {COLUMN} 1.3.6.1.4.1.2356.11.2.26.16.1.1
lcsSetupNtpNetworklistEntryNetworkName OBJECT-TYPE
    SYNTAX     DisplayString (SIZE(0..16))
    MAX-ACCESS read-write
    STATUS     current
    DESCRIPTION
            "-- empty --"
    ::= { lcsSetupNtpNetworklistEntry 1 }

-- {COLUMN} 1.3.6.1.4.1.2356.11.2.26.16.1.2
lcsSetupNtpNetworklistEntryServerOperating OBJECT-TYPE
    SYNTAX     INTEGER {
                  eNo (0),
                  eYes (1)
            }
    MAX-ACCESS read-write
    STATUS     current
    DESCRIPTION
            "-- empty --"
    ::= { lcsSetupNtpNetworklistEntry 2 }

-- {SCALAR} 1.3.6.1.4.1.2356.11.2.26.17
lcsSetupNtpServerWanAccess OBJECT-TYPE
    SYNTAX     INTEGER {
                  eNo (0),
                  eYes (1),
                  eVpn (2)
            }
    MAX-ACCESS read-write
    STATUS     current
    DESCRIPTION
            "-- empty --"
    ::= { lcsSetupNtp 17 }

-- {NODE} 1.3.6.1.4.1.2356.11.2.27
lcsSetupMail OBJECT IDENTIFIER ::= { lcsSetup 27 }

-- {SCALAR} 1.3.6.1.4.1.2356.11.2.27.1
lcsSetupMailSmtpServer OBJECT-TYPE
    SYNTAX     DisplayString (SIZE(0..64))
    MAX-ACCESS read-write
    STATUS     current
    DESCRIPTION
            ""
    ::= { lcsSetupMail 1 }

-- {SCALAR} 1.3.6.1.4.1.2356.11.2.27.2
lcsSetupMailSmtpPort OBJECT-TYPE
    SYNTAX     Integer32 (0..65535)
    MAX-ACCESS read-write
    STATUS     current
    DESCRIPTION
            ""
    ::= { lcsSetupMail 2 }

-- {SCALAR} 1.3.6.1.4.1.2356.11.2.27.3
lcsSetupMailPop3Server OBJECT-TYPE
    SYNTAX     DisplayString (SIZE(0..64))
    MAX-ACCESS read-write
    STATUS     current
    DESCRIPTION
            ""
    ::= { lcsSetupMail 3 }

-- {SCALAR} 1.3.6.1.4.1.2356.11.2.27.4
lcsSetupMailPop3Port OBJECT-TYPE
    SYNTAX     Integer32 (0..65535)
    MAX-ACCESS read-write
    STATUS     current
    DESCRIPTION
            ""
    ::= { lcsSetupMail 4 }

-- {SCALAR} 1.3.6.1.4.1.2356.11.2.27.5
lcsSetupMailUserName OBJECT-TYPE
    SYNTAX     DisplayString (SIZE(0..63))
    MAX-ACCESS read-write
    STATUS     current
    DESCRIPTION
            ""
    ::= { lcsSetupMail 5 }

-- {SCALAR} 1.3.6.1.4.1.2356.11.2.27.6
lcsSetupMailPassword OBJECT-TYPE
    SYNTAX     DisplayString (SIZE(0..31))
    MAX-ACCESS read-write
    STATUS     current
    DESCRIPTION
            ""
    ::= { lcsSetupMail 6 }

-- {SCALAR} 1.3.6.1.4.1.2356.11.2.27.7
lcsSetupMailEMailSender OBJECT-TYPE
    SYNTAX     DisplayString (SIZE(0..63))
    MAX-ACCESS read-write
    STATUS     current
    DESCRIPTION
            ""
    ::= { lcsSetupMail 7 }

-- {SCALAR} 1.3.6.1.4.1.2356.11.2.27.8
lcsSetupMailSendAgainMin OBJECT-TYPE
    SYNTAX     Integer32 (0..65535)
    MAX-ACCESS read-write
    STATUS     current
    DESCRIPTION
            ""
    ::= { lcsSetupMail 8 }

-- {SCALAR} 1.3.6.1.4.1.2356.11.2.27.9
lcsSetupMailHoldTimeHrs OBJECT-TYPE
    SYNTAX     Integer32 (0..65535)
    MAX-ACCESS read-write
    STATUS     current
    DESCRIPTION
            ""
    ::= { lcsSetupMail 9 }

-- {SCALAR} 1.3.6.1.4.1.2356.11.2.27.10
lcsSetupMailBuffers OBJECT-TYPE
    SYNTAX     Integer32 (0..65535)
    MAX-ACCESS read-write
    STATUS     current
    DESCRIPTION
            ""
    ::= { lcsSetupMail 10 }

-- {SCALAR} 1.3.6.1.4.1.2356.11.2.27.11
lcsSetupMailLoopbackAddr OBJECT-TYPE
    SYNTAX     DisplayString (SIZE(0..16))
    MAX-ACCESS read-write
    STATUS     current
    DESCRIPTION
            ""
    ::= { lcsSetupMail 11 }

-- {SCALAR} 1.3.6.1.4.1.2356.11.2.27.12
lcsSetupMailSmtpUseTls OBJECT-TYPE
    SYNTAX     INTEGER {
                  eNo (0),
                  eYes (1),
                  ePreferred (2),
                  eRequired (3)
            }
    MAX-ACCESS read-write
    STATUS     current
    DESCRIPTION
            "-- empty --"
    ::= { lcsSetupMail 12 }

-- {SCALAR} 1.3.6.1.4.1.2356.11.2.27.13
lcsSetupMailSmtpAuthentication OBJECT-TYPE
    SYNTAX     INTEGER {
                  eNone (0),
                  ePlainTextPreferred (1),
                  eEncrypted (2),
                  ePreferredEncrypted (3)
            }
    MAX-ACCESS read-write
    STATUS     current
    DESCRIPTION
            "-- empty --"
    ::= { lcsSetupMail 13 }

-- {NODE} 1.3.6.1.4.1.2356.11.2.27.14
lcsSetupMailSslNew OBJECT IDENTIFIER ::= { lcsSetupMail 14 }

-- {SCALAR} 1.3.6.1.4.1.2356.11.2.27.14.1
lcsSetupMailSslNewVersions OBJECT-TYPE
    SYNTAX     BITS {
                  eTlsv13 (27),
                  eTlsv12 (28),
                  eTlsv11 (29),
                  eTlsv1 (30)
            }
    MAX-ACCESS read-write
    STATUS     current
    DESCRIPTION
            "-- empty --"
    ::= { lcsSetupMailSslNew 1 }

-- {SCALAR} 1.3.6.1.4.1.2356.11.2.27.14.2
lcsSetupMailSslNewKeyexAlgorithms OBJECT-TYPE
    SYNTAX     BITS {
                  eEcdhe (27),
                  eDhe (29),
                  eRsa (31)
            }
    MAX-ACCESS read-write
    STATUS     current
    DESCRIPTION
            "-- empty --"
    ::= { lcsSetupMailSslNew 2 }

-- {SCALAR} 1.3.6.1.4.1.2356.11.2.27.14.3
lcsSetupMailSslNewCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupMailSslNew 3 }

-- {SCALAR} 1.3.6.1.4.1.2356.11.2.27.14.4
lcsSetupMailSslNewHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupMailSslNew 4 }

-- {SCALAR} 1.3.6.1.4.1.2356.11.2.27.14.5
lcsSetupMailSslNewPreferPfs OBJECT-TYPE
    SYNTAX     BITS {
                  eNo (0),
                  eYes (7)
            }
    MAX-ACCESS read-write
    STATUS     current
    DESCRIPTION
            "-- empty --"
    ::= { lcsSetupMailSslNew 5 }

-- {SCALAR} 1.3.6.1.4.1.2356.11.2.27.14.6
lcsSetupMailSslNewRenegotiations OBJECT-TYPE
    SYNTAX     INTEGER {
                  eForbidden (0),
                  eAllowed (1),
                  eIgnored (2)
            }
    MAX-ACCESS read-write
    STATUS     current
    DESCRIPTION
            "-- empty --"
    ::= { lcsSetupMailSslNew 6 }

-- {SCALAR} 1.3.6.1.4.1.2356.11.2.27.14.7
lcsSetupMailSslNewEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupMailSslNew 7 }

-- {SCALAR} 1.3.6.1.4.1.2356.11.2.27.14.21
lcsSetupMailSslNewSigHashAlgs OBJECT-TYPE
    SYNTAX     BITS {
                  eSha512Ecdsa (20),
                  eSha384Ecdsa (21),
                  eSha256Ecdsa (22),
                  eSha224Ecdsa (23),
                  eSha1Ecdsa (24),
                  eSha512Rsa (26),
                  eSha384Rsa (27),
                  eSha256Rsa (28),
                  eSha224Rsa (29),
                  eSha1Rsa (30)
            }
    MAX-ACCESS read-write
    STATUS     current
    DESCRIPTION
            "list of allowed signature/hash algorithms"
    ::= { lcsSetupMailSslNew 21 }

-- {NODE} 1.3.6.1.4.1.2356.11.2.30
lcsSetupIeee8021x OBJECT IDENTIFIER ::= { lcsSetup 30 }

-- {TABLE} 1.3.6.1.4.1.2356.11.2.30.3
lcsSetupIeee8021xRadiusServerTable OBJECT-TYPE
    SYNTAX     SEQUENCE OF LcsSetupIeee8021xRadiusServerEntry
    MAX-ACCESS not-accessible
    STATUS     current
    DESCRIPTION
            ""
    ::= { lcsSetupIeee8021x 3 }

-- {ROW} 1.3.6.1.4.1.2356.11.2.30.3.1
lcsSetupIeee8021xRadiusServerEntry OBJECT-TYPE
    SYNTAX     LcsSetupIeee8021xRadiusServerEntry
    MAX-ACCESS not-accessible
    STATUS     current
    DESCRIPTION
            ""
    INDEX {
            lcsSetupIeee8021xRadiusServerEntryName
          }
    ::= { lcsSetupIeee8021xRadiusServerTable 1 }

LcsSetupIeee8021xRadiusServerEntry ::= SEQUENCE {
            lcsSetupIeee8021xRadiusServerEntryName DisplayString,
            lcsSetupIeee8021xRadiusServerEntryIpAddress IpAddress,
            lcsSetupIeee8021xRadiusServerEntryPort Integer32,
            lcsSetupIeee8021xRadiusServerEntrySecret DisplayString,
            lcsSetupIeee8021xRadiusServerEntryBackup DisplayString,
            lcsSetupIeee8021xRadiusServerEntryLoopbackAddr DisplayString,
            lcsSetupIeee8021xRadiusServerEntryProtocol INTEGER,
            lcsSetupIeee8021xRadiusServerEntryHostName DisplayString,
            lcsSetupIeee8021xRadiusServerEntryAttributeValues DisplayString,
            lcsSetupIeee8021xRadiusServerEntrySupProfile DisplayString
    }

-- {COLUMN} 1.3.6.1.4.1.2356.11.2.30.3.1.1
lcsSetupIeee8021xRadiusServerEntryName OBJECT-TYPE
    SYNTAX     DisplayString (SIZE(0..16))
    MAX-ACCESS read-write
    STATUS     current
    DESCRIPTION
            ""
    ::= { lcsSetupIeee8021xRadiusServerEntry 1 }

-- {COLUMN} 1.3.6.1.4.1.2356.11.2.30.3.1.2
lcsSetupIeee8021xRadiusServerEntryIpAddress OBJECT-TYPE
    SYNTAX     IpAddress
    MAX-ACCESS read-write
    STATUS     current
    DESCRIPTION
            ""
    ::= { lcsSetupIeee8021xRadiusServerEntry 2 }

-- {COLUMN} 1.3.6.1.4.1.2356.11.2.30.3.1.3
lcsSetupIeee8021xRadiusServerEntryPort OBJECT-TYPE
    SYNTAX     Integer32 (0..65535)
    MAX-ACCESS read-write
    STATUS     current
    DESCRIPTION
            ""
    ::= { lcsSetupIeee8021xRadiusServerEntry 3 }

-- {COLUMN} 1.3.6.1.4.1.2356.11.2.30.3.1.4
lcsSetupIeee8021xRadiusServerEntrySecret OBJECT-TYPE
    SYNTAX     DisplayString (SIZE(0..64))
    MAX-ACCESS read-write
    STATUS     current
    DESCRIPTION
            ""
    ::= { lcsSetupIeee8021xRadiusServerEntry 4 }

-- {COLUMN} 1.3.6.1.4.1.2356.11.2.30.3.1.5
lcsSetupIeee8021xRadiusServerEntryBackup OBJECT-TYPE
    SYNTAX     DisplayString (SIZE(0..16))
    MAX-ACCESS read-write
    STATUS     current
    DESCRIPTION
            ""
    ::= { lcsSetupIeee8021xRadiusServerEntry 5 }

-- {COLUMN} 1.3.6.1.4.1.2356.11.2.30.3.1.6
lcsSetupIeee8021xRadiusServerEntryLoopbackAddr OBJECT-TYPE
    SYNTAX     DisplayString (SIZE(0..16))
    MAX-ACCESS read-write
    STATUS     current
    DESCRIPTION
            ""
    ::= { lcsSetupIeee8021xRadiusServerEntry 6 }

-- {COLUMN} 1.3.6.1.4.1.2356.11.2.30.3.1.7
lcsSetupIeee8021xRadiusServerEntryProtocol OBJECT-TYPE
    SYNTAX     INTEGER {
                  eRadius (0),
                  eRadsec (1)
            }
    MAX-ACCESS read-write
    STATUS     current
    DESCRIPTION
            ""
    ::= { lcsSetupIeee8021xRadiusServerEntry 7 }

-- {COLUMN} 1.3.6.1.4.1.2356.11.2.30.3.1.8
lcsSetupIeee8021xRadiusServerEntryHostName OBJECT-TYPE
    SYNTAX     DisplayString (SIZE(0..64))
    MAX-ACCESS read-write
    STATUS     current
    DESCRIPTION
            "-- empty --"
    ::= { lcsSetupIeee8021xRadiusServerEntry 8 }

-- {COLUMN} 1.3.6.1.4.1.2356.11.2.30.3.1.9
lcsSetupIeee8021xRadiusServerEntryAttributeValues OBJECT-TYPE
    SYNTAX     DisplayString (SIZE(0..251))
    MAX-ACCESS read-write
    STATUS     current
    DESCRIPTION
            "-- empty --"
    ::= { lcsSetupIeee8021xRadiusServerEntry 9 }

-- {COLUMN} 1.3.6.1.4.1.2356.11.2.30.3.1.10
lcsSetupIeee8021xRadiusServerEntrySupProfile OBJECT-TYPE
    SYNTAX     DisplayString (SIZE(0..8))
    MAX-ACCESS read-write
    STATUS     current
    DESCRIPTION
            "-- empty --"
    ::= { lcsSetupIeee8021xRadiusServerEntry 10 }

-- {TABLE} 1.3.6.1.4.1.2356.11.2.30.4
lcsSetupIeee8021xPortsTable OBJECT-TYPE
    SYNTAX     SEQUENCE OF LcsSetupIeee8021xPortsEntry
    MAX-ACCESS not-accessible
    STATUS     current
    DESCRIPTION
            ""
    ::= { lcsSetupIeee8021x 4 }

-- {ROW} 1.3.6.1.4.1.2356.11.2.30.4.1
lcsSetupIeee8021xPortsEntry OBJECT-TYPE
    SYNTAX     LcsSetupIeee8021xPortsEntry
    MAX-ACCESS not-accessible
    STATUS     current
    DESCRIPTION
            ""
    INDEX {
            lcsSetupIeee8021xPortsEntryPort
          }
    ::= { lcsSetupIeee8021xPortsTable 1 }

LcsSetupIeee8021xPortsEntry ::= SEQUENCE {
            lcsSetupIeee8021xPortsEntryPort DisplayString,
            lcsSetupIeee8021xPortsEntryPortControl INTEGER,
            lcsSetupIeee8021xPortsEntryReAuthMax Integer32,
            lcsSetupIeee8021xPortsEntryMaxReq Integer32,
            lcsSetupIeee8021xPortsEntryTxPeriod Integer32,
            lcsSetupIeee8021xPortsEntrySuppTimeout Integer32,
            lcsSetupIeee8021xPortsEntryServerTimeout Integer32,
            lcsSetupIeee8021xPortsEntryQuietPeriod Integer32,
            lcsSetupIeee8021xPortsEntryReAuthentication INTEGER,
            lcsSetupIeee8021xPortsEntryReAuthInterval Integer32,
            lcsSetupIeee8021xPortsEntryKeyTransmission INTEGER,
            lcsSetupIeee8021xPortsEntryKeyTxInterval Integer32,
            lcsSetupIeee8021xPortsEntryReAuthDelayPeriod Integer32
    }

-- {COLUMN} 1.3.6.1.4.1.2356.11.2.30.4.1.2
lcsSetupIeee8021xPortsEntryPort OBJECT-TYPE
    SYNTAX     DisplayString (SIZE(0..18))
    MAX-ACCESS read-only
    STATUS     current
    DESCRIPTION
            ""
    ::= { lcsSetupIeee8021xPortsEntry 2 }

-- {COLUMN} 1.3.6.1.4.1.2356.11.2.30.4.1.3
lcsSetupIeee8021xPortsEntryPortControl OBJECT-TYPE
    SYNTAX     INTEGER {
                  eForceUnauth (0),
                  eForceAuth (1),
                  eAuto (2)
            }
    MAX-ACCESS read-write
    STATUS     current
    DESCRIPTION
            ""
    ::= { lcsSetupIeee8021xPortsEntry 3 }

-- {COLUMN} 1.3.6.1.4.1.2356.11.2.30.4.1.4
lcsSetupIeee8021xPortsEntryReAuthMax OBJECT-TYPE
    SYNTAX     Integer32 (0..255)
    MAX-ACCESS read-write
    STATUS     current
    DESCRIPTION
            ""
    ::= { lcsSetupIeee8021xPortsEntry 4 }

-- {COLUMN} 1.3.6.1.4.1.2356.11.2.30.4.1.5
lcsSetupIeee8021xPortsEntryMaxReq OBJECT-TYPE
    SYNTAX     Integer32 (0..255)
    MAX-ACCESS read-write
    STATUS     current
    DESCRIPTION
            ""
    ::= { lcsSetupIeee8021xPortsEntry 5 }

-- {COLUMN} 1.3.6.1.4.1.2356.11.2.30.4.1.6
lcsSetupIeee8021xPortsEntryTxPeriod OBJECT-TYPE
    SYNTAX     Integer32 (0..65535)
    MAX-ACCESS read-write
    STATUS     current
    DESCRIPTION
            ""
    ::= { lcsSetupIeee8021xPortsEntry 6 }

-- {COLUMN} 1.3.6.1.4.1.2356.11.2.30.4.1.7
lcsSetupIeee8021xPortsEntrySuppTimeout OBJECT-TYPE
    SYNTAX     Integer32 (0..65535)
    MAX-ACCESS read-write
    STATUS     current
    DESCRIPTION
            ""
    ::= { lcsSetupIeee8021xPortsEntry 7 }

-- {COLUMN} 1.3.6.1.4.1.2356.11.2.30.4.1.8
lcsSetupIeee8021xPortsEntryServerTimeout OBJECT-TYPE
    SYNTAX     Integer32 (0..65535)
    MAX-ACCESS read-write
    STATUS     current
    DESCRIPTION
            ""
    ::= { lcsSetupIeee8021xPortsEntry 8 }

-- {COLUMN} 1.3.6.1.4.1.2356.11.2.30.4.1.9
lcsSetupIeee8021xPortsEntryQuietPeriod OBJECT-TYPE
    SYNTAX     Integer32 (0..65535)
    MAX-ACCESS read-write
    STATUS     current
    DESCRIPTION
            ""
    ::= { lcsSetupIeee8021xPortsEntry 9 }

-- {COLUMN} 1.3.6.1.4.1.2356.11.2.30.4.1.10
lcsSetupIeee8021xPortsEntryReAuthentication OBJECT-TYPE
    SYNTAX     INTEGER {
                  eNo (0),
                  eYes (1)
            }
    MAX-ACCESS read-write
    STATUS     current
    DESCRIPTION
            ""
    ::= { lcsSetupIeee8021xPortsEntry 10 }

-- {COLUMN} 1.3.6.1.4.1.2356.11.2.30.4.1.11
lcsSetupIeee8021xPortsEntryReAuthInterval OBJECT-TYPE
    SYNTAX     Integer32 (0..65535)
    MAX-ACCESS read-write
    STATUS     current
    DESCRIPTION
            ""
    ::= { lcsSetupIeee8021xPortsEntry 11 }

-- {COLUMN} 1.3.6.1.4.1.2356.11.2.30.4.1.12
lcsSetupIeee8021xPortsEntryKeyTransmission OBJECT-TYPE
    SYNTAX     INTEGER {
                  eNo (0),
                  eYes (1)
            }
    MAX-ACCESS read-write
    STATUS     current
    DESCRIPTION
            ""
    ::= { lcsSetupIeee8021xPortsEntry 12 }

-- {COLUMN} 1.3.6.1.4.1.2356.11.2.30.4.1.13
lcsSetupIeee8021xPortsEntryKeyTxInterval OBJECT-TYPE
    SYNTAX     Integer32 (0..65535)
    MAX-ACCESS read-write
    STATUS     current
    DESCRIPTION
            ""
    ::= { lcsSetupIeee8021xPortsEntry 13 }

-- {COLUMN} 1.3.6.1.4.1.2356.11.2.30.4.1.14
lcsSetupIeee8021xPortsEntryReAuthDelayPeriod OBJECT-TYPE
    SYNTAX     Integer32 (0..65535)
    MAX-ACCESS read-write
    STATUS     current
    DESCRIPTION
            "-- empty --"
    ::= { lcsSetupIeee8021xPortsEntry 14 }

-- {NODE} 1.3.6.1.4.1.2356.11.2.30.11
lcsSetupIeee8021xSupplicantSetup OBJECT IDENTIFIER ::= { lcsSetupIeee8021x 11 }

-- {NODE} 1.3.6.1.4.1.2356.11.2.30.11.13
lcsSetupIeee8021xSupplicantSetupTls OBJECT IDENTIFIER ::= { lcsSetupIeee8021xSupplicantSetup 13 }

-- {SCALAR} 1.3.6.1.4.1.2356.11.2.30.11.13.2
lcsSetupIeee8021xSupplicantSetupTlsVersions OBJECT-TYPE
    SYNTAX     BITS {
                  eTlsv12 (28),
                  eTlsv11 (29),
                  eTlsv1 (30)
            }
    MAX-ACCESS read-write
    STATUS     current
    DESCRIPTION
            "-- empty --"
    ::= { lcsSetupIeee8021xSupplicantSetupTls 2 }

-- {SCALAR} 1.3.6.1.4.1.2356.11.2.30.11.13.3
lcsSetupIeee8021xSupplicantSetupTlsKeyexAlgorithms OBJECT-TYPE
    SYNTAX     BITS {
                  eEcdhe (27),
                  eDhe (29),
                  eRsa (31)
            }
    MAX-ACCESS read-write
    STATUS     current
    DESCRIPTION
            "-- empty --"
    ::= { lcsSetupIeee8021xSupplicantSetupTls 3 }

-- {SCALAR} 1.3.6.1.4.1.2356.11.2.30.11.13.4
lcsSetupIeee8021xSupplicantSetupTlsCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupIeee8021xSupplicantSetupTls 4 }

-- {SCALAR} 1.3.6.1.4.1.2356.11.2.30.11.13.5
lcsSetupIeee8021xSupplicantSetupTlsHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupIeee8021xSupplicantSetupTls 5 }

-- {SCALAR} 1.3.6.1.4.1.2356.11.2.30.11.13.6
lcsSetupIeee8021xSupplicantSetupTlsPreferPfs OBJECT-TYPE
    SYNTAX     BITS {
                  eNo (0),
                  eYes (7)
            }
    MAX-ACCESS read-write
    STATUS     current
    DESCRIPTION
            "-- empty --"
    ::= { lcsSetupIeee8021xSupplicantSetupTls 6 }

-- {SCALAR} 1.3.6.1.4.1.2356.11.2.30.11.13.8
lcsSetupIeee8021xSupplicantSetupTlsEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupIeee8021xSupplicantSetupTls 8 }

-- {SCALAR} 1.3.6.1.4.1.2356.11.2.30.11.13.22
lcsSetupIeee8021xSupplicantSetupTlsSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupIeee8021xSupplicantSetupTls 22 }

-- {NODE} 1.3.6.1.4.1.2356.11.2.31
lcsSetupPppoeServer OBJECT IDENTIFIER ::= { lcsSetup 31 }

-- {SCALAR} 1.3.6.1.4.1.2356.11.2.31.1
lcsSetupPppoeServerOperating OBJECT-TYPE
    SYNTAX     INTEGER {
                  eNo (0),
                  eYes (1)
            }
    MAX-ACCESS read-write
    STATUS     current
    DESCRIPTION
            ""
    ::= { lcsSetupPppoeServer 1 }

-- {TABLE} 1.3.6.1.4.1.2356.11.2.31.2
lcsSetupPppoeServerNameListTable OBJECT-TYPE
    SYNTAX     SEQUENCE OF LcsSetupPppoeServerNameListEntry
    MAX-ACCESS not-accessible
    STATUS     current
    DESCRIPTION
            ""
    ::= { lcsSetupPppoeServer 2 }

-- {ROW} 1.3.6.1.4.1.2356.11.2.31.2.1
lcsSetupPppoeServerNameListEntry OBJECT-TYPE
    SYNTAX     LcsSetupPppoeServerNameListEntry
    MAX-ACCESS not-accessible
    STATUS     current
    DESCRIPTION
            ""
    INDEX {
            lcsSetupPppoeServerNameListEntryPeer
          }
    ::= { lcsSetupPppoeServerNameListTable 1 }

LcsSetupPppoeServerNameListEntry ::= SEQUENCE {
            lcsSetupPppoeServerNameListEntryPeer DisplayString,
            lcsSetupPppoeServerNameListEntryShTime Integer32,
            lcsSetupPppoeServerNameListEntryMacAddress DisplayString
    }

-- {COLUMN} 1.3.6.1.4.1.2356.11.2.31.2.1.1
lcsSetupPppoeServerNameListEntryPeer OBJECT-TYPE
    SYNTAX     DisplayString (SIZE(0..16))
    MAX-ACCESS read-write
    STATUS     current
    DESCRIPTION
            ""
    ::= { lcsSetupPppoeServerNameListEntry 1 }

-- {COLUMN} 1.3.6.1.4.1.2356.11.2.31.2.1.2
lcsSetupPppoeServerNameListEntryShTime OBJECT-TYPE
    SYNTAX     Integer32 (0..65535)
    MAX-ACCESS read-write
    STATUS     current
    DESCRIPTION
            ""
    ::= { lcsSetupPppoeServerNameListEntry 2 }

-- {COLUMN} 1.3.6.1.4.1.2356.11.2.31.2.1.3
lcsSetupPppoeServerNameListEntryMacAddress OBJECT-TYPE
    SYNTAX     DisplayString (SIZE(0..12))
    MAX-ACCESS read-write
    STATUS     current
    DESCRIPTION
            ""
    ::= { lcsSetupPppoeServerNameListEntry 3 }

-- {SCALAR} 1.3.6.1.4.1.2356.11.2.31.3
lcsSetupPppoeServerService OBJECT-TYPE
    SYNTAX     DisplayString (SIZE(0..32))
    MAX-ACCESS read-write
    STATUS     current
    DESCRIPTION
            ""
    ::= { lcsSetupPppoeServer 3 }

-- {SCALAR} 1.3.6.1.4.1.2356.11.2.31.4
lcsSetupPppoeServerSessionLimit OBJECT-TYPE
    SYNTAX     Integer32 (0..2147483647)
    MAX-ACCESS read-write
    STATUS     current
    DESCRIPTION
            ""
    ::= { lcsSetupPppoeServer 4 }

-- {TABLE} 1.3.6.1.4.1.2356.11.2.31.5
lcsSetupPppoeServerPortsTable OBJECT-TYPE
    SYNTAX     SEQUENCE OF LcsSetupPppoeServerPortsEntry
    MAX-ACCESS not-accessible
    STATUS     current
    DESCRIPTION
            ""
    ::= { lcsSetupPppoeServer 5 }

-- {ROW} 1.3.6.1.4.1.2356.11.2.31.5.1
lcsSetupPppoeServerPortsEntry OBJECT-TYPE
    SYNTAX     LcsSetupPppoeServerPortsEntry
    MAX-ACCESS not-accessible
    STATUS     current
    DESCRIPTION
            ""
    INDEX {
            lcsSetupPppoeServerPortsEntryPort
          }
    ::= { lcsSetupPppoeServerPortsTable 1 }

LcsSetupPppoeServerPortsEntry ::= SEQUENCE {
            lcsSetupPppoeServerPortsEntryPort DisplayString,
            lcsSetupPppoeServerPortsEntryEnablePppoe INTEGER
    }

-- {COLUMN} 1.3.6.1.4.1.2356.11.2.31.5.1.2
lcsSetupPppoeServerPortsEntryPort OBJECT-TYPE
    SYNTAX     DisplayString (SIZE(0..18))
    MAX-ACCESS read-only
    STATUS     current
    DESCRIPTION
            ""
    ::= { lcsSetupPppoeServerPortsEntry 2 }

-- {COLUMN} 1.3.6.1.4.1.2356.11.2.31.5.1.3
lcsSetupPppoeServerPortsEntryEnablePppoe OBJECT-TYPE
    SYNTAX     INTEGER {
                  eNo (0),
                  eYes (1)
            }
    MAX-ACCESS read-write
    STATUS     current
    DESCRIPTION
            ""
    ::= { lcsSetupPppoeServerPortsEntry 3 }

-- {SCALAR} 1.3.6.1.4.1.2356.11.2.31.6
lcsSetupPppoeServerAcName OBJECT-TYPE
    SYNTAX     DisplayString (SIZE(0..32))
    MAX-ACCESS read-write
    STATUS     current
    DESCRIPTION
            "-- empty --"
    ::= { lcsSetupPppoeServer 6 }

-- {NODE} 1.3.6.1.4.1.2356.11.2.32
lcsSetupVlan OBJECT IDENTIFIER ::= { lcsSetup 32 }

-- {TABLE} 1.3.6.1.4.1.2356.11.2.32.1
lcsSetupVlanNetworksTable OBJECT-TYPE
    SYNTAX     SEQUENCE OF LcsSetupVlanNetworksEntry
    MAX-ACCESS not-accessible
    STATUS     current
    DESCRIPTION
            ""
    ::= { lcsSetupVlan 1 }

-- {ROW} 1.3.6.1.4.1.2356.11.2.32.1.1
lcsSetupVlanNetworksEntry OBJECT-TYPE
    SYNTAX     LcsSetupVlanNetworksEntry
    MAX-ACCESS not-accessible
    STATUS     current
    DESCRIPTION
            ""
    INDEX {
            lcsSetupVlanNetworksEntryName
          }
    ::= { lcsSetupVlanNetworksTable 1 }

LcsSetupVlanNetworksEntry ::= SEQUENCE {
            lcsSetupVlanNetworksEntryName DisplayString,
            lcsSetupVlanNetworksEntryVlanId Integer32,
            lcsSetupVlanNetworksEntryPorts DisplayString,
            lcsSetupVlanNetworksEntryLldpTxTlvPpid DisplayString,
            lcsSetupVlanNetworksEntryLldpTxTlvName DisplayString
    }

-- {COLUMN} 1.3.6.1.4.1.2356.11.2.32.1.1.1
lcsSetupVlanNetworksEntryName OBJECT-TYPE
    SYNTAX     DisplayString (SIZE(0..16))
    MAX-ACCESS read-write
    STATUS     current
    DESCRIPTION
            ""
    ::= { lcsSetupVlanNetworksEntry 1 }

-- {COLUMN} 1.3.6.1.4.1.2356.11.2.32.1.1.2
lcsSetupVlanNetworksEntryVlanId OBJECT-TYPE
    SYNTAX     Integer32 (0..65535)
    MAX-ACCESS read-write
    STATUS     current
    DESCRIPTION
            ""
    ::= { lcsSetupVlanNetworksEntry 2 }

-- {COLUMN} 1.3.6.1.4.1.2356.11.2.32.1.1.4
lcsSetupVlanNetworksEntryPorts OBJECT-TYPE
    SYNTAX     DisplayString (SIZE(0..251))
    MAX-ACCESS read-write
    STATUS     current
    DESCRIPTION
            ""
    ::= { lcsSetupVlanNetworksEntry 4 }

-- {COLUMN} 1.3.6.1.4.1.2356.11.2.32.1.1.5
lcsSetupVlanNetworksEntryLldpTxTlvPpid OBJECT-TYPE
    SYNTAX     DisplayString (SIZE(0..251))
    MAX-ACCESS read-write
    STATUS     current
    DESCRIPTION
            "-- empty --"
    ::= { lcsSetupVlanNetworksEntry 5 }

-- {COLUMN} 1.3.6.1.4.1.2356.11.2.32.1.1.6
lcsSetupVlanNetworksEntryLldpTxTlvName OBJECT-TYPE
    SYNTAX     DisplayString (SIZE(0..251))
    MAX-ACCESS read-write
    STATUS     current
    DESCRIPTION
            "-- empty --"
    ::= { lcsSetupVlanNetworksEntry 6 }

-- {TABLE} 1.3.6.1.4.1.2356.11.2.32.2
lcsSetupVlanPortTableTable OBJECT-TYPE
    SYNTAX     SEQUENCE OF LcsSetupVlanPortTableEntry
    MAX-ACCESS not-accessible
    STATUS     current
    DESCRIPTION
            ""
    ::= { lcsSetupVlan 2 }

-- {ROW} 1.3.6.1.4.1.2356.11.2.32.2.1
lcsSetupVlanPortTableEntry OBJECT-TYPE
    SYNTAX     LcsSetupVlanPortTableEntry
    MAX-ACCESS not-accessible
    STATUS     current
    DESCRIPTION
            ""
    INDEX {
            lcsSetupVlanPortTableEntryPort
          }
    ::= { lcsSetupVlanPortTableTable 1 }

LcsSetupVlanPortTableEntry ::= SEQUENCE {
            lcsSetupVlanPortTableEntryPort DisplayString,
            lcsSetupVlanPortTableEntryAllowAllVlans INTEGER,
            lcsSetupVlanPortTableEntryPortVlanId Integer32,
            lcsSetupVlanPortTableEntryTaggingMode INTEGER,
            lcsSetupVlanPortTableEntryTxLldpTlvPortVlan INTEGER
    }

-- {COLUMN} 1.3.6.1.4.1.2356.11.2.32.2.1.1
lcsSetupVlanPortTableEntryPort OBJECT-TYPE
    SYNTAX     DisplayString (SIZE(0..18))
    MAX-ACCESS read-only
    STATUS     current
    DESCRIPTION
            ""
    ::= { lcsSetupVlanPortTableEntry 1 }

-- {COLUMN} 1.3.6.1.4.1.2356.11.2.32.2.1.4
lcsSetupVlanPortTableEntryAllowAllVlans OBJECT-TYPE
    SYNTAX     INTEGER {
                  eNo (0),
                  eYes (1)
            }
    MAX-ACCESS read-write
    STATUS     current
    DESCRIPTION
            ""
    ::= { lcsSetupVlanPortTableEntry 4 }

-- {COLUMN} 1.3.6.1.4.1.2356.11.2.32.2.1.5
lcsSetupVlanPortTableEntryPortVlanId OBJECT-TYPE
    SYNTAX     Integer32 (0..65535)
    MAX-ACCESS read-write
    STATUS     current
    DESCRIPTION
            ""
    ::= { lcsSetupVlanPortTableEntry 5 }

-- {COLUMN} 1.3.6.1.4.1.2356.11.2.32.2.1.6
lcsSetupVlanPortTableEntryTaggingMode OBJECT-TYPE
    SYNTAX     INTEGER {
                  eIngressMixed (0),
                  eNever (1),
                  eMixed (2),
                  eAlways (3)
            }
    MAX-ACCESS read-write
    STATUS     current
    DESCRIPTION
            ""
    ::= { lcsSetupVlanPortTableEntry 6 }

-- {COLUMN} 1.3.6.1.4.1.2356.11.2.32.2.1.7
lcsSetupVlanPortTableEntryTxLldpTlvPortVlan OBJECT-TYPE
    SYNTAX     INTEGER {
                  eNo (0),
                  eYes (1)
            }
    MAX-ACCESS read-write
    STATUS     current
    DESCRIPTION
            "-- empty --"
    ::= { lcsSetupVlanPortTableEntry 7 }

-- {SCALAR} 1.3.6.1.4.1.2356.11.2.32.4
lcsSetupVlanOperating OBJECT-TYPE
    SYNTAX     INTEGER {
                  eNo (0),
                  eYes (1)
            }
    MAX-ACCESS read-write
    STATUS     current
    DESCRIPTION
            ""
    ::= { lcsSetupVlan 4 }

-- {SCALAR} 1.3.6.1.4.1.2356.11.2.32.5
lcsSetupVlanTagValue OBJECT-TYPE
    SYNTAX     DisplayString (SIZE(0..4))
    MAX-ACCESS read-write
    STATUS     current
    DESCRIPTION
            ""
    ::= { lcsSetupVlan 5 }

-- {NODE} 1.3.6.1.4.1.2356.11.2.33
lcsSetupVcCllMngr OBJECT IDENTIFIER ::= { lcsSetup 33 }

-- {SCALAR} 1.3.6.1.4.1.2356.11.2.33.1
lcsSetupVcCllMngrOperating OBJECT-TYPE
    SYNTAX     INTEGER {
                  eNo (0),
                  eYes (1)
            }
    MAX-ACCESS read-write
    STATUS     current
    DESCRIPTION
            "-- empty --"
    ::= { lcsSetupVcCllMngr 1 }

-- {NODE} 1.3.6.1.4.1.2356.11.2.33.2
lcsSetupVcCllMngrGeneral OBJECT IDENTIFIER ::= { lcsSetupVcCllMngr 2 }

-- {SCALAR} 1.3.6.1.4.1.2356.11.2.33.2.1
lcsSetupVcCllMngrGeneralDomain OBJECT-TYPE
    SYNTAX     DisplayString (SIZE(0..63))
    MAX-ACCESS read-write
    STATUS     current
    DESCRIPTION
            "-- empty --"
    ::= { lcsSetupVcCllMngrGeneral 1 }

-- {SCALAR} 1.3.6.1.4.1.2356.11.2.33.2.2
lcsSetupVcCllMngrGeneralOverlapTimeout OBJECT-TYPE
    SYNTAX     Integer32 (0..255)
    MAX-ACCESS read-write
    STATUS     current
    DESCRIPTION
            "-- empty --"
    ::= { lcsSetupVcCllMngrGeneral 2 }

-- {SCALAR} 1.3.6.1.4.1.2356.11.2.33.2.3
lcsSetupVcCllMngrGeneralLocalAuthentication OBJECT-TYPE
    SYNTAX     INTEGER {
                  eNo (0),
                  eYes (1)
            }
    MAX-ACCESS read-write
    STATUS     current
    DESCRIPTION
            "-- empty --"
    ::= { lcsSetupVcCllMngrGeneral 3 }

-- {SCALAR} 1.3.6.1.4.1.2356.11.2.33.2.4
lcsSetupVcCllMngrGeneralEchoCanceler OBJECT-TYPE
    SYNTAX     INTEGER {
                  eNo (0),
                  eYes (1)
            }
    MAX-ACCESS read-write
    STATUS     current
    DESCRIPTION
            "-- empty --"
    ::= { lcsSetupVcCllMngrGeneral 4 }

-- {SCALAR} 1.3.6.1.4.1.2356.11.2.33.2.5
lcsSetupVcCllMngrGeneralOutgoingPacketReduction OBJECT-TYPE
    SYNTAX     INTEGER {
                  eNone (0),
                  ePmtu (1),
                  eFragmentation (2),
                  ePmtuPlusFragmentation (3)
            }
    MAX-ACCESS read-write
    STATUS     current
    DESCRIPTION
            "-- empty --"
    ::= { lcsSetupVcCllMngrGeneral 5 }

-- {SCALAR} 1.3.6.1.4.1.2356.11.2.33.2.6
lcsSetupVcCllMngrGeneralIncomingPacketReduction OBJECT-TYPE
    SYNTAX     INTEGER {
                  eNone (0),
                  ePmtu (1)
            }
    MAX-ACCESS read-write
    STATUS     current
    DESCRIPTION
            "-- empty --"
    ::= { lcsSetupVcCllMngrGeneral 6 }

-- {SCALAR} 1.3.6.1.4.1.2356.11.2.33.2.7
lcsSetupVcCllMngrGeneralReducedPacketSize OBJECT-TYPE
    SYNTAX     Integer32 (0..65535)
    MAX-ACCESS read-write
    STATUS     current
    DESCRIPTION
            "-- empty --"
    ::= { lcsSetupVcCllMngrGeneral 7 }

-- {SCALAR} 1.3.6.1.4.1.2356.11.2.33.2.9
lcsSetupVcCllMngrGeneralCountry OBJECT-TYPE
    SYNTAX     INTEGER {
                  eUnknown (0),
                  eAustria (40),
                  eBelgium (56),
                  eFrance (250),
                  eGermany (276),
                  eItaly (380),
                  eNetherlands (528),
                  eSpain (724),
                  eSwitzerland (756),
                  eUnitedKingdom (826)
            }
    MAX-ACCESS read-write
    STATUS     current
    DESCRIPTION
            "-- empty --"
    ::= { lcsSetupVcCllMngrGeneral 9 }

-- {SCALAR} 1.3.6.1.4.1.2356.11.2.33.2.11
lcsSetupVcCllMngrGeneralClnpartynumtype OBJECT-TYPE
    SYNTAX     INTEGER {
                  eSubscriber (0),
                  eUnknown (1),
                  eNational (2),
                  eAuto (255)
            }
    MAX-ACCESS read-write
    STATUS     current
    DESCRIPTION
            "-- empty --"
    ::= { lcsSetupVcCllMngrGeneral 11 }

-- {SCALAR} 1.3.6.1.4.1.2356.11.2.33.2.12
lcsSetupVcCllMngrGeneralRegisterTime OBJECT-TYPE
    SYNTAX     Integer32 (0..2147483647)
    MAX-ACCESS read-write
    STATUS     current
    DESCRIPTION
            "-- empty --"
    ::= { lcsSetupVcCllMngrGeneral 12 }

-- {SCALAR} 1.3.6.1.4.1.2356.11.2.33.2.13
lcsSetupVcCllMngrGeneralConvertCanonicals OBJECT-TYPE
    SYNTAX     INTEGER {
                  eNo (0),
                  eYes (1)
            }
    MAX-ACCESS read-write
    STATUS     current
    DESCRIPTION
            "-- empty --"
    ::= { lcsSetupVcCllMngrGeneral 13 }

-- {SCALAR} 1.3.6.1.4.1.2356.11.2.33.2.14
lcsSetupVcCllMngrGeneralSymmetricRtp OBJECT-TYPE
    SYNTAX     INTEGER {
                  eNo (0),
                  eYes (1)
            }
    MAX-ACCESS read-write
    STATUS     current
    DESCRIPTION
            "-- empty --"
    ::= { lcsSetupVcCllMngrGeneral 14 }

-- {SCALAR} 1.3.6.1.4.1.2356.11.2.33.2.15
lcsSetupVcCllMngrGeneralSipDscp OBJECT-TYPE
    SYNTAX     INTEGER {
                  eBeCs0 (0),
                  eCs1 (32),
                  eAf11 (40),
                  eAf12 (48),
                  eAf13 (56),
                  eCs2 (64),
                  eAf21 (72),
                  eAf22 (80),
                  eAf23 (88),
                  eCs3 (96),
                  eAf31 (104),
                  eAf32 (112),
                  eAf33 (120),
                  eCs4 (128),
                  eAf41 (136),
                  eAf42 (144),
                  eAf43 (152),
                  eCs5 (160),
                  eEf (184),
                  eCs6 (192),
                  eCs7 (224)
            }
    MAX-ACCESS read-write
    STATUS     current
    DESCRIPTION
            "-- empty --"
    ::= { lcsSetupVcCllMngrGeneral 15 }

-- {SCALAR} 1.3.6.1.4.1.2356.11.2.33.2.16
lcsSetupVcCllMngrGeneralRtpDscp OBJECT-TYPE
    SYNTAX     INTEGER {
                  eBeCs0 (0),
                  eCs1 (32),
                  eAf11 (40),
                  eAf12 (48),
                  eAf13 (56),
                  eCs2 (64),
                  eAf21 (72),
                  eAf22 (80),
                  eAf23 (88),
                  eCs3 (96),
                  eAf31 (104),
                  eAf32 (112),
                  eAf33 (120),
                  eCs4 (128),
                  eAf41 (136),
                  eAf42 (144),
                  eAf43 (152),
                  eCs5 (160),
                  eEf (184),
                  eCs6 (192),
                  eCs7 (224)
            }
    MAX-ACCESS read-write
    STATUS     current
    DESCRIPTION
            "-- empty --"
    ::= { lcsSetupVcCllMngrGeneral 16 }

-- {SCALAR} 1.3.6.1.4.1.2356.11.2.33.2.17
lcsSetupVcCllMngrGeneralLockMinutes OBJECT-TYPE
    SYNTAX     Integer32 (0..255)
    MAX-ACCESS read-write
    STATUS     current
    DESCRIPTION
            "-- empty --"
    ::= { lcsSetupVcCllMngrGeneral 17 }

-- {SCALAR} 1.3.6.1.4.1.2356.11.2.33.2.18
lcsSetupVcCllMngrGeneralLoginErrors OBJECT-TYPE
    SYNTAX     Integer32 (0..255)
    MAX-ACCESS read-write
    STATUS     current
    DESCRIPTION
            "-- empty --"
    ::= { lcsSetupVcCllMngrGeneral 18 }

-- {SCALAR} 1.3.6.1.4.1.2356.11.2.33.2.19
lcsSetupVcCllMngrGeneralT38 OBJECT-TYPE
    SYNTAX     INTEGER {
                  eNo (0),
                  eYes (1),
                  eIsdnPlusAnalog (2)
            }
    MAX-ACCESS read-write
    STATUS     current
    DESCRIPTION
            "-- empty --"
    ::= { lcsSetupVcCllMngrGeneral 19 }

-- {SCALAR} 1.3.6.1.4.1.2356.11.2.33.2.20
lcsSetupVcCllMngrGeneralVcmDnsResolve OBJECT-TYPE
    SYNTAX     INTEGER {
                  eNo (0),
                  eYes (1)
            }
    MAX-ACCESS read-write
    STATUS     current
    DESCRIPTION
            "-- empty --"
    ::= { lcsSetupVcCllMngrGeneral 20 }

-- {SCALAR} 1.3.6.1.4.1.2356.11.2.33.2.21
lcsSetupVcCllMngrGeneralRtpPortStart OBJECT-TYPE
    SYNTAX     Integer32 (0..65535)
    MAX-ACCESS read-write
    STATUS     current
    DESCRIPTION
            "-- empty --"
    ::= { lcsSetupVcCllMngrGeneral 21 }

-- {SCALAR} 1.3.6.1.4.1.2356.11.2.33.2.22
lcsSetupVcCllMngrGeneralRtpPortEnd OBJECT-TYPE
    SYNTAX     Integer32 (0..65535)
    MAX-ACCESS read-write
    STATUS     current
    DESCRIPTION
            "-- empty --"
    ::= { lcsSetupVcCllMngrGeneral 22 }

-- {NODE} 1.3.6.1.4.1.2356.11.2.33.2.23
lcsSetupVcCllMngrGeneralJitterBuffer OBJECT IDENTIFIER ::= { lcsSetupVcCllMngrGeneral 23 }

-- {SCALAR} 1.3.6.1.4.1.2356.11.2.33.2.23.1
lcsSetupVcCllMngrGeneralJitterBufferMeanJitterBufferFactor OBJECT-TYPE
    SYNTAX     Integer32 (0..255)
    MAX-ACCESS read-write
    STATUS     current
    DESCRIPTION
            "-- empty --"
    ::= { lcsSetupVcCllMngrGeneralJitterBuffer 1 }

-- {SCALAR} 1.3.6.1.4.1.2356.11.2.33.2.23.2
lcsSetupVcCllMngrGeneralJitterBufferMinJitterBuffer OBJECT-TYPE
    SYNTAX     Integer32 (0..255)
    MAX-ACCESS read-write
    STATUS     current
    DESCRIPTION
            "-- empty --"
    ::= { lcsSetupVcCllMngrGeneralJitterBuffer 2 }

-- {SCALAR} 1.3.6.1.4.1.2356.11.2.33.2.23.3
lcsSetupVcCllMngrGeneralJitterBufferMaxJitterBuffer OBJECT-TYPE
    SYNTAX     Integer32 (0..255)
    MAX-ACCESS read-write
    STATUS     current
    DESCRIPTION
            "-- empty --"
    ::= { lcsSetupVcCllMngrGeneralJitterBuffer 3 }

-- {SCALAR} 1.3.6.1.4.1.2356.11.2.33.2.23.4
lcsSetupVcCllMngrGeneralJitterBufferMaxJitterDiffTime OBJECT-TYPE
    SYNTAX     Integer32 (0..2147483647)
    MAX-ACCESS read-write
    STATUS     current
    DESCRIPTION
            "-- empty --"
    ::= { lcsSetupVcCllMngrGeneralJitterBuffer 4 }

-- {SCALAR} 1.3.6.1.4.1.2356.11.2.33.2.23.5
lcsSetupVcCllMngrGeneralJitterBufferLevelOverTargetPercent OBJECT-TYPE
    SYNTAX     Integer32 (0..2147483647)
    MAX-ACCESS read-write
    STATUS     current
    DESCRIPTION
            "-- empty --"
    ::= { lcsSetupVcCllMngrGeneralJitterBuffer 5 }

-- {SCALAR} 1.3.6.1.4.1.2356.11.2.33.2.23.6
lcsSetupVcCllMngrGeneralJitterBufferTargetVarianceTime OBJECT-TYPE
    SYNTAX     Integer32 (0..2147483647)
    MAX-ACCESS read-write
    STATUS     current
    DESCRIPTION
            "-- empty --"
    ::= { lcsSetupVcCllMngrGeneralJitterBuffer 6 }

-- {SCALAR} 1.3.6.1.4.1.2356.11.2.33.2.23.7
lcsSetupVcCllMngrGeneralJitterBufferAlgon OBJECT-TYPE
    SYNTAX     Integer32 (0..2147483647)
    MAX-ACCESS read-write
    STATUS     current
    DESCRIPTION
            "-- empty --"
    ::= { lcsSetupVcCllMngrGeneralJitterBuffer 7 }

-- {SCALAR} 1.3.6.1.4.1.2356.11.2.33.2.23.8
lcsSetupVcCllMngrGeneralJitterBufferLongTermDeviation OBJECT-TYPE
    SYNTAX     Integer32 (0..2147483647)
    MAX-ACCESS read-write
    STATUS     current
    DESCRIPTION
            "-- empty --"
    ::= { lcsSetupVcCllMngrGeneralJitterBuffer 8 }

-- {SCALAR} 1.3.6.1.4.1.2356.11.2.33.2.23.9
lcsSetupVcCllMngrGeneralJitterBufferLtdTime OBJECT-TYPE
    SYNTAX     Integer32 (0..2147483647)
    MAX-ACCESS read-write
    STATUS     current
    DESCRIPTION
            "-- empty --"
    ::= { lcsSetupVcCllMngrGeneralJitterBuffer 9 }

-- {NODE} 1.3.6.1.4.1.2356.11.2.33.3
lcsSetupVcCllMngrUsers OBJECT IDENTIFIER ::= { lcsSetupVcCllMngr 3 }

-- {NODE} 1.3.6.1.4.1.2356.11.2.33.3.1
lcsSetupVcCllMngrUsersSipUser OBJECT IDENTIFIER ::= { lcsSetupVcCllMngrUsers 1 }

-- {TABLE} 1.3.6.1.4.1.2356.11.2.33.3.1.1
lcsSetupVcCllMngrUsersSipUserUsersTable OBJECT-TYPE
    SYNTAX     SEQUENCE OF LcsSetupVcCllMngrUsersSipUserUsersEntry
    MAX-ACCESS not-accessible
    STATUS     current
    DESCRIPTION
            "-- empty --"
    ::= { lcsSetupVcCllMngrUsersSipUser 1 }

-- {ROW} 1.3.6.1.4.1.2356.11.2.33.3.1.1.1
lcsSetupVcCllMngrUsersSipUserUsersEntry OBJECT-TYPE
    SYNTAX     LcsSetupVcCllMngrUsersSipUserUsersEntry
    MAX-ACCESS not-accessible
    STATUS     current
    DESCRIPTION
            ""
    INDEX {
            lcsSetupVcCllMngrUsersSipUserUsersEntryNumberName
          }
    ::= { lcsSetupVcCllMngrUsersSipUserUsersTable 1 }

LcsSetupVcCllMngrUsersSipUserUsersEntry ::= SEQUENCE {
            lcsSetupVcCllMngrUsersSipUserUsersEntryNumberName DisplayString,
            lcsSetupVcCllMngrUsersSipUserUsersEntryAuthName DisplayString,
            lcsSetupVcCllMngrUsersSipUserUsersEntrySecret DisplayString,
            lcsSetupVcCllMngrUsersSipUserUsersEntryActive INTEGER,
            lcsSetupVcCllMngrUsersSipUserUsersEntryComment DisplayString,
            lcsSetupVcCllMngrUsersSipUserUsersEntryDeviceType INTEGER,
            lcsSetupVcCllMngrUsersSipUserUsersEntryClir INTEGER,
            lcsSetupVcCllMngrUsersSipUserUsersEntryAccessFromWan INTEGER,
            lcsSetupVcCllMngrUsersSipUserUsersEntryDtmfMethod INTEGER,
            lcsSetupVcCllMngrUsersSipUserUsersEntryMwiTargetLine DisplayString,
            lcsSetupVcCllMngrUsersSipUserUsersEntryTransports BITS,
            lcsSetupVcCllMngrUsersSipUserUsersEntrySrtp INTEGER,
            lcsSetupVcCllMngrUsersSipUserUsersEntrySrtpCiphers BITS,
            lcsSetupVcCllMngrUsersSipUserUsersEntrySrtpMessageAuthTags BITS,
            lcsSetupVcCllMngrUsersSipUserUsersEntryPrivacyMethod INTEGER
    }

-- {COLUMN} 1.3.6.1.4.1.2356.11.2.33.3.1.1.1.1
lcsSetupVcCllMngrUsersSipUserUsersEntryNumberName OBJECT-TYPE
    SYNTAX     DisplayString (SIZE(0..32))
    MAX-ACCESS read-write
    STATUS     current
    DESCRIPTION
            "-- empty --"
    ::= { lcsSetupVcCllMngrUsersSipUserUsersEntry 1 }

-- {COLUMN} 1.3.6.1.4.1.2356.11.2.33.3.1.1.1.2
lcsSetupVcCllMngrUsersSipUserUsersEntryAuthName OBJECT-TYPE
    SYNTAX     DisplayString (SIZE(0..63))
    MAX-ACCESS read-write
    STATUS     current
    DESCRIPTION
            "-- empty --"
    ::= { lcsSetupVcCllMngrUsersSipUserUsersEntry 2 }

-- {COLUMN} 1.3.6.1.4.1.2356.11.2.33.3.1.1.1.3
lcsSetupVcCllMngrUsersSipUserUsersEntrySecret OBJECT-TYPE
    SYNTAX     DisplayString (SIZE(0..32))
    MAX-ACCESS read-write
    STATUS     current
    DESCRIPTION
            "-- empty --"
    ::= { lcsSetupVcCllMngrUsersSipUserUsersEntry 3 }

-- {COLUMN} 1.3.6.1.4.1.2356.11.2.33.3.1.1.1.4
lcsSetupVcCllMngrUsersSipUserUsersEntryActive OBJECT-TYPE
    SYNTAX     INTEGER {
                  eYes (0),
                  eNo (1)
            }
    MAX-ACCESS read-write
    STATUS     current
    DESCRIPTION
            "-- empty --"
    ::= { lcsSetupVcCllMngrUsersSipUserUsersEntry 4 }

-- {COLUMN} 1.3.6.1.4.1.2356.11.2.33.3.1.1.1.5
lcsSetupVcCllMngrUsersSipUserUsersEntryComment OBJECT-TYPE
    SYNTAX     DisplayString (SIZE(0..63))
    MAX-ACCESS read-write
    STATUS     current
    DESCRIPTION
            "-- empty --"
    ::= { lcsSetupVcCllMngrUsersSipUserUsersEntry 5 }

-- {COLUMN} 1.3.6.1.4.1.2356.11.2.33.3.1.1.1.6
lcsSetupVcCllMngrUsersSipUserUsersEntryDeviceType OBJECT-TYPE
    SYNTAX     INTEGER {
                  ePhone (0),
                  eFax (1),
                  eAuto (2),
                  eModem (3)
            }
    MAX-ACCESS read-write
    STATUS     current
    DESCRIPTION
            "-- empty --"
    ::= { lcsSetupVcCllMngrUsersSipUserUsersEntry 6 }

-- {COLUMN} 1.3.6.1.4.1.2356.11.2.33.3.1.1.1.7
lcsSetupVcCllMngrUsersSipUserUsersEntryClir OBJECT-TYPE
    SYNTAX     INTEGER {
                  eNo (0),
                  eYes (1)
            }
    MAX-ACCESS read-write
    STATUS     current
    DESCRIPTION
            "-- empty --"
    ::= { lcsSetupVcCllMngrUsersSipUserUsersEntry 7 }

-- {COLUMN} 1.3.6.1.4.1.2356.11.2.33.3.1.1.1.8
lcsSetupVcCllMngrUsersSipUserUsersEntryAccessFromWan OBJECT-TYPE
    SYNTAX     INTEGER {
                  eVpn (1),
                  eNo (2)
            }
    MAX-ACCESS read-write
    STATUS     current
    DESCRIPTION
            "-- empty --"
    ::= { lcsSetupVcCllMngrUsersSipUserUsersEntry 8 }

-- {COLUMN} 1.3.6.1.4.1.2356.11.2.33.3.1.1.1.20
lcsSetupVcCllMngrUsersSipUserUsersEntryDtmfMethod OBJECT-TYPE
    SYNTAX     INTEGER {
                  eInband (0),
                  eSipInfo (1),
                  eRtpEvent (2),
                  eRtpEventSipInfo (3)
            }
    MAX-ACCESS read-write
    STATUS     current
    DESCRIPTION
            "-- empty --"
    ::= { lcsSetupVcCllMngrUsersSipUserUsersEntry 20 }

-- {COLUMN} 1.3.6.1.4.1.2356.11.2.33.3.1.1.1.21
lcsSetupVcCllMngrUsersSipUserUsersEntryMwiTargetLine OBJECT-TYPE
    SYNTAX     DisplayString (SIZE(0..32))
    MAX-ACCESS read-write
    STATUS     current
    DESCRIPTION
            "-- empty --"
    ::= { lcsSetupVcCllMngrUsersSipUserUsersEntry 21 }

-- {COLUMN} 1.3.6.1.4.1.2356.11.2.33.3.1.1.1.22
lcsSetupVcCllMngrUsersSipUserUsersEntryTransports OBJECT-TYPE
    SYNTAX     BITS {
                  eTls (5),
                  eTcp (6),
                  eUdp (7)
            }
    MAX-ACCESS read-write
    STATUS     current
    DESCRIPTION
            "-- empty --"
    ::= { lcsSetupVcCllMngrUsersSipUserUsersEntry 22 }

-- {COLUMN} 1.3.6.1.4.1.2356.11.2.33.3.1.1.1.23
lcsSetupVcCllMngrUsersSipUserUsersEntrySrtp OBJECT-TYPE
    SYNTAX     INTEGER {
                  eReject (0),
                  eIgnore (1),
                  ePrefer (2),
                  eForce (3)
            }
    MAX-ACCESS read-write
    STATUS     current
    DESCRIPTION
            "-- empty --"
    ::= { lcsSetupVcCllMngrUsersSipUserUsersEntry 23 }

-- {COLUMN} 1.3.6.1.4.1.2356.11.2.33.3.1.1.1.24
lcsSetupVcCllMngrUsersSipUserUsersEntrySrtpCiphers OBJECT-TYPE
    SYNTAX     BITS {
                  eF8128 (4),
                  eAesCm256 (5),
                  eAesCm192 (6),
                  eAesCm128 (7)
            }
    MAX-ACCESS read-write
    STATUS     current
    DESCRIPTION
            "-- empty --"
    ::= { lcsSetupVcCllMngrUsersSipUserUsersEntry 24 }

-- {COLUMN} 1.3.6.1.4.1.2356.11.2.33.3.1.1.1.25
lcsSetupVcCllMngrUsersSipUserUsersEntrySrtpMessageAuthTags OBJECT-TYPE
    SYNTAX     BITS {
                  eHmacSha132 (6),
                  eHmacSha180 (7)
            }
    MAX-ACCESS read-write
    STATUS     current
    DESCRIPTION
            "-- empty --"
    ::= { lcsSetupVcCllMngrUsersSipUserUsersEntry 25 }

-- {COLUMN} 1.3.6.1.4.1.2356.11.2.33.3.1.1.1.26
lcsSetupVcCllMngrUsersSipUserUsersEntryPrivacyMethod OBJECT-TYPE
    SYNTAX     INTEGER {
                  eAnonymous (0),
                  eInternalDomain (1)
            }
    MAX-ACCESS read-write
    STATUS     current
    DESCRIPTION
            "-- empty --"
    ::= { lcsSetupVcCllMngrUsersSipUserUsersEntry 26 }

-- {SCALAR} 1.3.6.1.4.1.2356.11.2.33.3.1.2
lcsSetupVcCllMngrUsersSipUserInternClnPrefix OBJECT-TYPE
    SYNTAX     DisplayString (SIZE(0..15))
    MAX-ACCESS read-write
    STATUS     current
    DESCRIPTION
            "-- empty --"
    ::= { lcsSetupVcCllMngrUsersSipUser 2 }

-- {SCALAR} 1.3.6.1.4.1.2356.11.2.33.3.1.3
lcsSetupVcCllMngrUsersSipUserExternClnPrefix OBJECT-TYPE
    SYNTAX     DisplayString (SIZE(0..15))
    MAX-ACCESS read-write
    STATUS     current
    DESCRIPTION
            "-- empty --"
    ::= { lcsSetupVcCllMngrUsersSipUser 3 }

-- {NODE} 1.3.6.1.4.1.2356.11.2.33.3.2
lcsSetupVcCllMngrUsersIsdnUser OBJECT IDENTIFIER ::= { lcsSetupVcCllMngrUsers 2 }

-- {TABLE} 1.3.6.1.4.1.2356.11.2.33.3.2.1
lcsSetupVcCllMngrUsersIsdnUserInterfacesTable OBJECT-TYPE
    SYNTAX     SEQUENCE OF LcsSetupVcCllMngrUsersIsdnUserInterfacesEntry
    MAX-ACCESS not-accessible
    STATUS     current
    DESCRIPTION
            "-- empty --"
    ::= { lcsSetupVcCllMngrUsersIsdnUser 1 }

-- {ROW} 1.3.6.1.4.1.2356.11.2.33.3.2.1.1
lcsSetupVcCllMngrUsersIsdnUserInterfacesEntry OBJECT-TYPE
    SYNTAX     LcsSetupVcCllMngrUsersIsdnUserInterfacesEntry
    MAX-ACCESS not-accessible
    STATUS     current
    DESCRIPTION
            ""
    INDEX {
            lcsSetupVcCllMngrUsersIsdnUserInterfacesEntryName
          }
    ::= { lcsSetupVcCllMngrUsersIsdnUserInterfacesTable 1 }

LcsSetupVcCllMngrUsersIsdnUserInterfacesEntry ::= SEQUENCE {
            lcsSetupVcCllMngrUsersIsdnUserInterfacesEntryName DisplayString,
            lcsSetupVcCllMngrUsersIsdnUserInterfacesEntryIfc BITS,
            lcsSetupVcCllMngrUsersIsdnUserInterfacesEntryActive INTEGER,
            lcsSetupVcCllMngrUsersIsdnUserInterfacesEntryComment DisplayString,
            lcsSetupVcCllMngrUsersIsdnUserInterfacesEntryAreaCode DisplayString
    }

-- {COLUMN} 1.3.6.1.4.1.2356.11.2.33.3.2.1.1.1
lcsSetupVcCllMngrUsersIsdnUserInterfacesEntryName OBJECT-TYPE
    SYNTAX     DisplayString (SIZE(0..4))
    MAX-ACCESS read-only
    STATUS     current
    DESCRIPTION
            "-- empty --"
    ::= { lcsSetupVcCllMngrUsersIsdnUserInterfacesEntry 1 }

-- {COLUMN} 1.3.6.1.4.1.2356.11.2.33.3.2.1.1.2
lcsSetupVcCllMngrUsersIsdnUserInterfacesEntryIfc OBJECT-TYPE
    SYNTAX     BITS {
                  eS02 (6),
                  eS01 (7)
            }
    MAX-ACCESS read-write
    STATUS     current
    DESCRIPTION
            "-- empty --"
    ::= { lcsSetupVcCllMngrUsersIsdnUserInterfacesEntry 2 }

-- {COLUMN} 1.3.6.1.4.1.2356.11.2.33.3.2.1.1.3
lcsSetupVcCllMngrUsersIsdnUserInterfacesEntryActive OBJECT-TYPE
    SYNTAX     INTEGER {
                  eYes (0),
                  eNo (1)
            }
    MAX-ACCESS read-write
    STATUS     current
    DESCRIPTION
            "-- empty --"
    ::= { lcsSetupVcCllMngrUsersIsdnUserInterfacesEntry 3 }

-- {COLUMN} 1.3.6.1.4.1.2356.11.2.33.3.2.1.1.4
lcsSetupVcCllMngrUsersIsdnUserInterfacesEntryComment OBJECT-TYPE
    SYNTAX     DisplayString (SIZE(0..63))
    MAX-ACCESS read-write
    STATUS     current
    DESCRIPTION
            "-- empty --"
    ::= { lcsSetupVcCllMngrUsersIsdnUserInterfacesEntry 4 }

-- {COLUMN} 1.3.6.1.4.1.2356.11.2.33.3.2.1.1.5
lcsSetupVcCllMngrUsersIsdnUserInterfacesEntryAreaCode OBJECT-TYPE
    SYNTAX     DisplayString (SIZE(0..19))
    MAX-ACCESS read-write
    STATUS     current
    DESCRIPTION
            "-- empty --"
    ::= { lcsSetupVcCllMngrUsersIsdnUserInterfacesEntry 5 }

-- {TABLE} 1.3.6.1.4.1.2356.11.2.33.3.2.2
lcsSetupVcCllMngrUsersIsdnUserUsersTable OBJECT-TYPE
    SYNTAX     SEQUENCE OF LcsSetupVcCllMngrUsersIsdnUserUsersEntry
    MAX-ACCESS not-accessible
    STATUS     current
    DESCRIPTION
            "-- empty --"
    ::= { lcsSetupVcCllMngrUsersIsdnUser 2 }

-- {ROW} 1.3.6.1.4.1.2356.11.2.33.3.2.2.1
lcsSetupVcCllMngrUsersIsdnUserUsersEntry OBJECT-TYPE
    SYNTAX     LcsSetupVcCllMngrUsersIsdnUserUsersEntry
    MAX-ACCESS not-accessible
    STATUS     current
    DESCRIPTION
            ""
    INDEX {
            lcsSetupVcCllMngrUsersIsdnUserUsersEntryNumberName,
            lcsSetupVcCllMngrUsersIsdnUserUsersEntryMsnDdi
          }
    ::= { lcsSetupVcCllMngrUsersIsdnUserUsersTable 1 }

LcsSetupVcCllMngrUsersIsdnUserUsersEntry ::= SEQUENCE {
            lcsSetupVcCllMngrUsersIsdnUserUsersEntryNumberName DisplayString,
            lcsSetupVcCllMngrUsersIsdnUserUsersEntryIfc BITS,
            lcsSetupVcCllMngrUsersIsdnUserUsersEntryMsnDdi DisplayString,
            lcsSetupVcCllMngrUsersIsdnUserUsersEntryDisplayName DisplayString,
            lcsSetupVcCllMngrUsersIsdnUserUsersEntryAuthName DisplayString,
            lcsSetupVcCllMngrUsersIsdnUserUsersEntrySecret DisplayString,
            lcsSetupVcCllMngrUsersIsdnUserUsersEntryDomain DisplayString,
            lcsSetupVcCllMngrUsersIsdnUserUsersEntryDialcompl INTEGER,
            lcsSetupVcCllMngrUsersIsdnUserUsersEntryActive INTEGER,
            lcsSetupVcCllMngrUsersIsdnUserUsersEntryComment DisplayString,
            lcsSetupVcCllMngrUsersIsdnUserUsersEntryDeviceType INTEGER,
            lcsSetupVcCllMngrUsersIsdnUserUsersEntryClir INTEGER,
            lcsSetupVcCllMngrUsersIsdnUserUsersEntryParallelCall INTEGER
    }

-- {COLUMN} 1.3.6.1.4.1.2356.11.2.33.3.2.2.1.1
lcsSetupVcCllMngrUsersIsdnUserUsersEntryNumberName OBJECT-TYPE
    SYNTAX     DisplayString (SIZE(0..20))
    MAX-ACCESS read-write
    STATUS     current
    DESCRIPTION
            "-- empty --"
    ::= { lcsSetupVcCllMngrUsersIsdnUserUsersEntry 1 }

-- {COLUMN} 1.3.6.1.4.1.2356.11.2.33.3.2.2.1.2
lcsSetupVcCllMngrUsersIsdnUserUsersEntryIfc OBJECT-TYPE
    SYNTAX     BITS {
                  eS02 (6),
                  eS01 (7)
            }
    MAX-ACCESS read-write
    STATUS     current
    DESCRIPTION
            "-- empty --"
    ::= { lcsSetupVcCllMngrUsersIsdnUserUsersEntry 2 }

-- {COLUMN} 1.3.6.1.4.1.2356.11.2.33.3.2.2.1.3
lcsSetupVcCllMngrUsersIsdnUserUsersEntryMsnDdi OBJECT-TYPE
    SYNTAX     DisplayString (SIZE(0..19))
    MAX-ACCESS read-write
    STATUS     current
    DESCRIPTION
            "-- empty --"
    ::= { lcsSetupVcCllMngrUsersIsdnUserUsersEntry 3 }

-- {COLUMN} 1.3.6.1.4.1.2356.11.2.33.3.2.2.1.4
lcsSetupVcCllMngrUsersIsdnUserUsersEntryDisplayName OBJECT-TYPE
    SYNTAX     DisplayString (SIZE(0..32))
    MAX-ACCESS read-write
    STATUS     current
    DESCRIPTION
            "-- empty --"
    ::= { lcsSetupVcCllMngrUsersIsdnUserUsersEntry 4 }

-- {COLUMN} 1.3.6.1.4.1.2356.11.2.33.3.2.2.1.5
lcsSetupVcCllMngrUsersIsdnUserUsersEntryAuthName OBJECT-TYPE
    SYNTAX     DisplayString (SIZE(0..63))
    MAX-ACCESS read-write
    STATUS     current
    DESCRIPTION
            "-- empty --"
    ::= { lcsSetupVcCllMngrUsersIsdnUserUsersEntry 5 }

-- {COLUMN} 1.3.6.1.4.1.2356.11.2.33.3.2.2.1.6
lcsSetupVcCllMngrUsersIsdnUserUsersEntrySecret OBJECT-TYPE
    SYNTAX     DisplayString (SIZE(0..32))
    MAX-ACCESS read-write
    STATUS     current
    DESCRIPTION
            "-- empty --"
    ::= { lcsSetupVcCllMngrUsersIsdnUserUsersEntry 6 }

-- {COLUMN} 1.3.6.1.4.1.2356.11.2.33.3.2.2.1.7
lcsSetupVcCllMngrUsersIsdnUserUsersEntryDomain OBJECT-TYPE
    SYNTAX     DisplayString (SIZE(0..63))
    MAX-ACCESS read-write
    STATUS     current
    DESCRIPTION
            "-- empty --"
    ::= { lcsSetupVcCllMngrUsersIsdnUserUsersEntry 7 }

-- {COLUMN} 1.3.6.1.4.1.2356.11.2.33.3.2.2.1.8
lcsSetupVcCllMngrUsersIsdnUserUsersEntryDialcompl OBJECT-TYPE
    SYNTAX     INTEGER {
                  eAuto (0),
                  eManual (1)
            }
    MAX-ACCESS read-write
    STATUS     current
    DESCRIPTION
            "-- empty --"
    ::= { lcsSetupVcCllMngrUsersIsdnUserUsersEntry 8 }

-- {COLUMN} 1.3.6.1.4.1.2356.11.2.33.3.2.2.1.9
lcsSetupVcCllMngrUsersIsdnUserUsersEntryActive OBJECT-TYPE
    SYNTAX     INTEGER {
                  eYes (0),
                  eNo (1)
            }
    MAX-ACCESS read-write
    STATUS     current
    DESCRIPTION
            "-- empty --"
    ::= { lcsSetupVcCllMngrUsersIsdnUserUsersEntry 9 }

-- {COLUMN} 1.3.6.1.4.1.2356.11.2.33.3.2.2.1.10
lcsSetupVcCllMngrUsersIsdnUserUsersEntryComment OBJECT-TYPE
    SYNTAX     DisplayString (SIZE(0..63))
    MAX-ACCESS read-write
    STATUS     current
    DESCRIPTION
            "-- empty --"
    ::= { lcsSetupVcCllMngrUsersIsdnUserUsersEntry 10 }

-- {COLUMN} 1.3.6.1.4.1.2356.11.2.33.3.2.2.1.11
lcsSetupVcCllMngrUsersIsdnUserUsersEntryDeviceType OBJECT-TYPE
    SYNTAX     INTEGER {
                  ePhone (0),
                  eFax (1),
                  eAuto (2),
                  eModem (3)
            }
    MAX-ACCESS read-write
    STATUS     current
    DESCRIPTION
            "-- empty --"
    ::= { lcsSetupVcCllMngrUsersIsdnUserUsersEntry 11 }

-- {COLUMN} 1.3.6.1.4.1.2356.11.2.33.3.2.2.1.12
lcsSetupVcCllMngrUsersIsdnUserUsersEntryClir OBJECT-TYPE
    SYNTAX     INTEGER {
                  eNo (0),
                  eYes (1)
            }
    MAX-ACCESS read-write
    STATUS     current
    DESCRIPTION
            "-- empty --"
    ::= { lcsSetupVcCllMngrUsersIsdnUserUsersEntry 12 }

-- {COLUMN} 1.3.6.1.4.1.2356.11.2.33.3.2.2.1.13
lcsSetupVcCllMngrUsersIsdnUserUsersEntryParallelCall OBJECT-TYPE
    SYNTAX     INTEGER {
                  eNo (0),
                  eYes (1)
            }
    MAX-ACCESS read-write
    STATUS     current
    DESCRIPTION
            "-- empty --"
    ::= { lcsSetupVcCllMngrUsersIsdnUserUsersEntry 13 }

-- {SCALAR} 1.3.6.1.4.1.2356.11.2.33.3.2.3
lcsSetupVcCllMngrUsersIsdnUserInternClnPrefix OBJECT-TYPE
    SYNTAX     DisplayString (SIZE(0..15))
    MAX-ACCESS read-write
    STATUS     current
    DESCRIPTION
            "-- empty --"
    ::= { lcsSetupVcCllMngrUsersIsdnUser 3 }

-- {SCALAR} 1.3.6.1.4.1.2356.11.2.33.3.2.4
lcsSetupVcCllMngrUsersIsdnUserExternClnPrefix OBJECT-TYPE
    SYNTAX     DisplayString (SIZE(0..15))
    MAX-ACCESS read-write
    STATUS     current
    DESCRIPTION
            "-- empty --"
    ::= { lcsSetupVcCllMngrUsersIsdnUser 4 }

-- {SCALAR} 1.3.6.1.4.1.2356.11.2.33.3.2.5
lcsSetupVcCllMngrUsersIsdnUserInternDialTone OBJECT-TYPE
    SYNTAX     INTEGER {
                  eNo (0),
                  eYes (1)
            }
    MAX-ACCESS read-write
    STATUS     current
    DESCRIPTION
            "-- empty --"
    ::= { lcsSetupVcCllMngrUsersIsdnUser 5 }

-- {SCALAR} 1.3.6.1.4.1.2356.11.2.33.3.2.6
lcsSetupVcCllMngrUsersIsdnUserCldpartynumtype OBJECT-TYPE
    SYNTAX     INTEGER {
                  eSubscriber (0),
                  eUnknown (1),
                  eNational (2),
                  eAuto (255)
            }
    MAX-ACCESS read-write
    STATUS     current
    DESCRIPTION
            "-- empty --"
    ::= { lcsSetupVcCllMngrUsersIsdnUser 6 }

-- {SCALAR} 1.3.6.1.4.1.2356.11.2.33.3.2.7
lcsSetupVcCllMngrUsersIsdnUserClnpartynumtype OBJECT-TYPE
    SYNTAX     INTEGER {
                  eSubscriber (0),
                  eUnknown (1),
                  eNational (2),
                  eAuto (255)
            }
    MAX-ACCESS read-write
    STATUS     current
    DESCRIPTION
            "-- empty --"
    ::= { lcsSetupVcCllMngrUsersIsdnUser 7 }

-- {SCALAR} 1.3.6.1.4.1.2356.11.2.33.3.2.8
lcsSetupVcCllMngrUsersIsdnUserConnectednumtype OBJECT-TYPE
    SYNTAX     INTEGER {
                  eSubscriber (0),
                  eUnknown (1),
                  eNational (2),
                  eAuto (255)
            }
    MAX-ACCESS read-write
    STATUS     current
    DESCRIPTION
            "-- empty --"
    ::= { lcsSetupVcCllMngrUsersIsdnUser 8 }

-- {NODE} 1.3.6.1.4.1.2356.11.2.33.3.3
lcsSetupVcCllMngrUsersAnalogUser OBJECT IDENTIFIER ::= { lcsSetupVcCllMngrUsers 3 }

-- {TABLE} 1.3.6.1.4.1.2356.11.2.33.3.3.1
lcsSetupVcCllMngrUsersAnalogUserInterfacesTable OBJECT-TYPE
    SYNTAX     SEQUENCE OF LcsSetupVcCllMngrUsersAnalogUserInterfacesEntry
    MAX-ACCESS not-accessible
    STATUS     current
    DESCRIPTION
            "-- empty --"
    ::= { lcsSetupVcCllMngrUsersAnalogUser 1 }

-- {ROW} 1.3.6.1.4.1.2356.11.2.33.3.3.1.1
lcsSetupVcCllMngrUsersAnalogUserInterfacesEntry OBJECT-TYPE
    SYNTAX     LcsSetupVcCllMngrUsersAnalogUserInterfacesEntry
    MAX-ACCESS not-accessible
    STATUS     current
    DESCRIPTION
            ""
    INDEX {
            lcsSetupVcCllMngrUsersAnalogUserInterfacesEntryName
          }
    ::= { lcsSetupVcCllMngrUsersAnalogUserInterfacesTable 1 }

LcsSetupVcCllMngrUsersAnalogUserInterfacesEntry ::= SEQUENCE {
            lcsSetupVcCllMngrUsersAnalogUserInterfacesEntryName DisplayString,
            lcsSetupVcCllMngrUsersAnalogUserInterfacesEntryIfc BITS,
            lcsSetupVcCllMngrUsersAnalogUserInterfacesEntryActive INTEGER,
            lcsSetupVcCllMngrUsersAnalogUserInterfacesEntryComment DisplayString
    }

-- {COLUMN} 1.3.6.1.4.1.2356.11.2.33.3.3.1.1.1
lcsSetupVcCllMngrUsersAnalogUserInterfacesEntryName OBJECT-TYPE
    SYNTAX     DisplayString (SIZE(0..6))
    MAX-ACCESS read-write
    STATUS     current
    DESCRIPTION
            "-- empty --"
    ::= { lcsSetupVcCllMngrUsersAnalogUserInterfacesEntry 1 }

-- {COLUMN} 1.3.6.1.4.1.2356.11.2.33.3.3.1.1.2
lcsSetupVcCllMngrUsersAnalogUserInterfacesEntryIfc OBJECT-TYPE
    SYNTAX     BITS {
                  eAnalog4 (4),
                  eAnalog3 (5),
                  eAnalog2 (6),
                  eAnalog1 (7)
            }
    MAX-ACCESS read-write
    STATUS     current
    DESCRIPTION
            "-- empty --"
    ::= { lcsSetupVcCllMngrUsersAnalogUserInterfacesEntry 2 }

-- {COLUMN} 1.3.6.1.4.1.2356.11.2.33.3.3.1.1.3
lcsSetupVcCllMngrUsersAnalogUserInterfacesEntryActive OBJECT-TYPE
    SYNTAX     INTEGER {
                  eYes (0),
                  eNo (1)
            }
    MAX-ACCESS read-write
    STATUS     current
    DESCRIPTION
            "-- empty --"
    ::= { lcsSetupVcCllMngrUsersAnalogUserInterfacesEntry 3 }

-- {COLUMN} 1.3.6.1.4.1.2356.11.2.33.3.3.1.1.4
lcsSetupVcCllMngrUsersAnalogUserInterfacesEntryComment OBJECT-TYPE
    SYNTAX     DisplayString (SIZE(0..63))
    MAX-ACCESS read-write
    STATUS     current
    DESCRIPTION
            "-- empty --"
    ::= { lcsSetupVcCllMngrUsersAnalogUserInterfacesEntry 4 }

-- {TABLE} 1.3.6.1.4.1.2356.11.2.33.3.3.2
lcsSetupVcCllMngrUsersAnalogUserUsersTable OBJECT-TYPE
    SYNTAX     SEQUENCE OF LcsSetupVcCllMngrUsersAnalogUserUsersEntry
    MAX-ACCESS not-accessible
    STATUS     current
    DESCRIPTION
            "-- empty --"
    ::= { lcsSetupVcCllMngrUsersAnalogUser 2 }

-- {ROW} 1.3.6.1.4.1.2356.11.2.33.3.3.2.1
lcsSetupVcCllMngrUsersAnalogUserUsersEntry OBJECT-TYPE
    SYNTAX     LcsSetupVcCllMngrUsersAnalogUserUsersEntry
    MAX-ACCESS not-accessible
    STATUS     current
    DESCRIPTION
            ""
    INDEX {
            lcsSetupVcCllMngrUsersAnalogUserUsersEntryNumberName
          }
    ::= { lcsSetupVcCllMngrUsersAnalogUserUsersTable 1 }

LcsSetupVcCllMngrUsersAnalogUserUsersEntry ::= SEQUENCE {
            lcsSetupVcCllMngrUsersAnalogUserUsersEntryNumberName DisplayString,
            lcsSetupVcCllMngrUsersAnalogUserUsersEntryIfc BITS,
            lcsSetupVcCllMngrUsersAnalogUserUsersEntryDisplayName DisplayString,
            lcsSetupVcCllMngrUsersAnalogUserUsersEntryAuthName DisplayString,
            lcsSetupVcCllMngrUsersAnalogUserUsersEntrySecret DisplayString,
            lcsSetupVcCllMngrUsersAnalogUserUsersEntryDomain DisplayString,
            lcsSetupVcCllMngrUsersAnalogUserUsersEntryClir INTEGER,
            lcsSetupVcCllMngrUsersAnalogUserUsersEntryMetering INTEGER,
            lcsSetupVcCllMngrUsersAnalogUserUsersEntryActive INTEGER,
            lcsSetupVcCllMngrUsersAnalogUserUsersEntryComment DisplayString,
            lcsSetupVcCllMngrUsersAnalogUserUsersEntryDeviceType INTEGER,
            lcsSetupVcCllMngrUsersAnalogUserUsersEntryDialifc BITS
    }

-- {COLUMN} 1.3.6.1.4.1.2356.11.2.33.3.3.2.1.1
lcsSetupVcCllMngrUsersAnalogUserUsersEntryNumberName OBJECT-TYPE
    SYNTAX     DisplayString (SIZE(0..20))
    MAX-ACCESS read-write
    STATUS     current
    DESCRIPTION
            "-- empty --"
    ::= { lcsSetupVcCllMngrUsersAnalogUserUsersEntry 1 }

-- {COLUMN} 1.3.6.1.4.1.2356.11.2.33.3.3.2.1.2
lcsSetupVcCllMngrUsersAnalogUserUsersEntryIfc OBJECT-TYPE
    SYNTAX     BITS {
                  eAnalog4 (4),
                  eAnalog3 (5),
                  eAnalog2 (6),
                  eAnalog1 (7)
            }
    MAX-ACCESS read-write
    STATUS     current
    DESCRIPTION
            "-- empty --"
    ::= { lcsSetupVcCllMngrUsersAnalogUserUsersEntry 2 }

-- {COLUMN} 1.3.6.1.4.1.2356.11.2.33.3.3.2.1.3
lcsSetupVcCllMngrUsersAnalogUserUsersEntryDisplayName OBJECT-TYPE
    SYNTAX     DisplayString (SIZE(0..32))
    MAX-ACCESS read-write
    STATUS     current
    DESCRIPTION
            "-- empty --"
    ::= { lcsSetupVcCllMngrUsersAnalogUserUsersEntry 3 }

-- {COLUMN} 1.3.6.1.4.1.2356.11.2.33.3.3.2.1.4
lcsSetupVcCllMngrUsersAnalogUserUsersEntryAuthName OBJECT-TYPE
    SYNTAX     DisplayString (SIZE(0..63))
    MAX-ACCESS read-write
    STATUS     current
    DESCRIPTION
            "-- empty --"
    ::= { lcsSetupVcCllMngrUsersAnalogUserUsersEntry 4 }

-- {COLUMN} 1.3.6.1.4.1.2356.11.2.33.3.3.2.1.5
lcsSetupVcCllMngrUsersAnalogUserUsersEntrySecret OBJECT-TYPE
    SYNTAX     DisplayString (SIZE(0..32))
    MAX-ACCESS read-write
    STATUS     current
    DESCRIPTION
            "-- empty --"
    ::= { lcsSetupVcCllMngrUsersAnalogUserUsersEntry 5 }

-- {COLUMN} 1.3.6.1.4.1.2356.11.2.33.3.3.2.1.6
lcsSetupVcCllMngrUsersAnalogUserUsersEntryDomain OBJECT-TYPE
    SYNTAX     DisplayString (SIZE(0..63))
    MAX-ACCESS read-write
    STATUS     current
    DESCRIPTION
            "-- empty --"
    ::= { lcsSetupVcCllMngrUsersAnalogUserUsersEntry 6 }

-- {COLUMN} 1.3.6.1.4.1.2356.11.2.33.3.3.2.1.8
lcsSetupVcCllMngrUsersAnalogUserUsersEntryClir OBJECT-TYPE
    SYNTAX     INTEGER {
                  eNo (0),
                  eYes (1)
            }
    MAX-ACCESS read-write
    STATUS     current
    DESCRIPTION
            "-- empty --"
    ::= { lcsSetupVcCllMngrUsersAnalogUserUsersEntry 8 }

-- {COLUMN} 1.3.6.1.4.1.2356.11.2.33.3.3.2.1.9
lcsSetupVcCllMngrUsersAnalogUserUsersEntryMetering OBJECT-TYPE
    SYNTAX     INTEGER {
                  eNo (0),
                  eYes (1)
            }
    MAX-ACCESS read-write
    STATUS     current
    DESCRIPTION
            "-- empty --"
    ::= { lcsSetupVcCllMngrUsersAnalogUserUsersEntry 9 }

-- {COLUMN} 1.3.6.1.4.1.2356.11.2.33.3.3.2.1.10
lcsSetupVcCllMngrUsersAnalogUserUsersEntryActive OBJECT-TYPE
    SYNTAX     INTEGER {
                  eYes (0),
                  eNo (1)
            }
    MAX-ACCESS read-write
    STATUS     current
    DESCRIPTION
            "-- empty --"
    ::= { lcsSetupVcCllMngrUsersAnalogUserUsersEntry 10 }

-- {COLUMN} 1.3.6.1.4.1.2356.11.2.33.3.3.2.1.11
lcsSetupVcCllMngrUsersAnalogUserUsersEntryComment OBJECT-TYPE
    SYNTAX     DisplayString (SIZE(0..63))
    MAX-ACCESS read-write
    STATUS     current
    DESCRIPTION
            "-- empty --"
    ::= { lcsSetupVcCllMngrUsersAnalogUserUsersEntry 11 }

-- {COLUMN} 1.3.6.1.4.1.2356.11.2.33.3.3.2.1.12
lcsSetupVcCllMngrUsersAnalogUserUsersEntryDeviceType OBJECT-TYPE
    SYNTAX     INTEGER {
                  ePhone (0),
                  eFax (1),
                  eAuto (2),
                  eModem (3)
            }
    MAX-ACCESS read-write
    STATUS     current
    DESCRIPTION
            "-- empty --"
    ::= { lcsSetupVcCllMngrUsersAnalogUserUsersEntry 12 }

-- {COLUMN} 1.3.6.1.4.1.2356.11.2.33.3.3.2.1.13
lcsSetupVcCllMngrUsersAnalogUserUsersEntryDialifc OBJECT-TYPE
    SYNTAX     BITS {
                  eAnalog4 (4),
                  eAnalog3 (5),
                  eAnalog2 (6),
                  eAnalog1 (7)
            }
    MAX-ACCESS read-write
    STATUS     current
    DESCRIPTION
            "-- empty --"
    ::= { lcsSetupVcCllMngrUsersAnalogUserUsersEntry 13 }

-- {SCALAR} 1.3.6.1.4.1.2356.11.2.33.3.3.3
lcsSetupVcCllMngrUsersAnalogUserInternClnPrefix OBJECT-TYPE
    SYNTAX     DisplayString (SIZE(0..15))
    MAX-ACCESS read-write
    STATUS     current
    DESCRIPTION
            "-- empty --"
    ::= { lcsSetupVcCllMngrUsersAnalogUser 3 }

-- {SCALAR} 1.3.6.1.4.1.2356.11.2.33.3.3.4
lcsSetupVcCllMngrUsersAnalogUserExternClnPrefix OBJECT-TYPE
    SYNTAX     DisplayString (SIZE(0..15))
    MAX-ACCESS read-write
    STATUS     current
    DESCRIPTION
            "-- empty --"
    ::= { lcsSetupVcCllMngrUsersAnalogUser 4 }

-- {SCALAR} 1.3.6.1.4.1.2356.11.2.33.3.3.5
lcsSetupVcCllMngrUsersAnalogUserInternDialTone OBJECT-TYPE
    SYNTAX     INTEGER {
                  eNo (0),
                  eYes (1)
            }
    MAX-ACCESS read-write
    STATUS     current
    DESCRIPTION
            "-- empty --"
    ::= { lcsSetupVcCllMngrUsersAnalogUser 5 }

-- {TABLE} 1.3.6.1.4.1.2356.11.2.33.3.4
lcsSetupVcCllMngrUsersExtensionsTable OBJECT-TYPE
    SYNTAX     SEQUENCE OF LcsSetupVcCllMngrUsersExtensionsEntry
    MAX-ACCESS not-accessible
    STATUS     current
    DESCRIPTION
            "-- empty --"
    ::= { lcsSetupVcCllMngrUsers 4 }

-- {ROW} 1.3.6.1.4.1.2356.11.2.33.3.4.1
lcsSetupVcCllMngrUsersExtensionsEntry OBJECT-TYPE
    SYNTAX     LcsSetupVcCllMngrUsersExtensionsEntry
    MAX-ACCESS not-accessible
    STATUS     current
    DESCRIPTION
            ""
    INDEX {
            lcsSetupVcCllMngrUsersExtensionsEntryName
          }
    ::= { lcsSetupVcCllMngrUsersExtensionsTable 1 }

LcsSetupVcCllMngrUsersExtensionsEntry ::= SEQUENCE {
            lcsSetupVcCllMngrUsersExtensionsEntryName DisplayString,
            lcsSetupVcCllMngrUsersExtensionsEntryUserModifiable INTEGER,
            lcsSetupVcCllMngrUsersExtensionsEntryCfuActive INTEGER,
            lcsSetupVcCllMngrUsersExtensionsEntryCfuTarget DisplayString,
            lcsSetupVcCllMngrUsersExtensionsEntryCfnrActive INTEGER,
            lcsSetupVcCllMngrUsersExtensionsEntryCfnrTarget DisplayString,
            lcsSetupVcCllMngrUsersExtensionsEntryCfnrTimeout Integer32,
            lcsSetupVcCllMngrUsersExtensionsEntryCfbActive INTEGER,
            lcsSetupVcCllMngrUsersExtensionsEntryCfbTarget DisplayString,
            lcsSetupVcCllMngrUsersExtensionsEntryActive INTEGER,
            lcsSetupVcCllMngrUsersExtensionsEntryBusyOnBusy INTEGER,
            lcsSetupVcCllMngrUsersExtensionsEntryCfSetClnId INTEGER,
            lcsSetupVcCllMngrUsersExtensionsEntryCustomId DisplayString
    }

-- {COLUMN} 1.3.6.1.4.1.2356.11.2.33.3.4.1.1
lcsSetupVcCllMngrUsersExtensionsEntryName OBJECT-TYPE
    SYNTAX     DisplayString (SIZE(0..64))
    MAX-ACCESS read-write
    STATUS     current
    DESCRIPTION
            "-- empty --"
    ::= { lcsSetupVcCllMngrUsersExtensionsEntry 1 }

-- {COLUMN} 1.3.6.1.4.1.2356.11.2.33.3.4.1.2
lcsSetupVcCllMngrUsersExtensionsEntryUserModifiable OBJECT-TYPE
    SYNTAX     INTEGER {
                  eYes (0),
                  eNo (1)
            }
    MAX-ACCESS read-write
    STATUS     current
    DESCRIPTION
            "-- empty --"
    ::= { lcsSetupVcCllMngrUsersExtensionsEntry 2 }

-- {COLUMN} 1.3.6.1.4.1.2356.11.2.33.3.4.1.3
lcsSetupVcCllMngrUsersExtensionsEntryCfuActive OBJECT-TYPE
    SYNTAX     INTEGER {
                  eNo (0),
                  eYes (1)
            }
    MAX-ACCESS read-write
    STATUS     current
    DESCRIPTION
            "-- empty --"
    ::= { lcsSetupVcCllMngrUsersExtensionsEntry 3 }

-- {COLUMN} 1.3.6.1.4.1.2356.11.2.33.3.4.1.4
lcsSetupVcCllMngrUsersExtensionsEntryCfuTarget OBJECT-TYPE
    SYNTAX     DisplayString (SIZE(0..64))
    MAX-ACCESS read-write
    STATUS     current
    DESCRIPTION
            "-- empty --"
    ::= { lcsSetupVcCllMngrUsersExtensionsEntry 4 }

-- {COLUMN} 1.3.6.1.4.1.2356.11.2.33.3.4.1.5
lcsSetupVcCllMngrUsersExtensionsEntryCfnrActive OBJECT-TYPE
    SYNTAX     INTEGER {
                  eNo (0),
                  eYes (1)
            }
    MAX-ACCESS read-write
    STATUS     current
    DESCRIPTION
            "-- empty --"
    ::= { lcsSetupVcCllMngrUsersExtensionsEntry 5 }

-- {COLUMN} 1.3.6.1.4.1.2356.11.2.33.3.4.1.6
lcsSetupVcCllMngrUsersExtensionsEntryCfnrTarget OBJECT-TYPE
    SYNTAX     DisplayString (SIZE(0..64))
    MAX-ACCESS read-write
    STATUS     current
    DESCRIPTION
            "-- empty --"
    ::= { lcsSetupVcCllMngrUsersExtensionsEntry 6 }

-- {COLUMN} 1.3.6.1.4.1.2356.11.2.33.3.4.1.7
lcsSetupVcCllMngrUsersExtensionsEntryCfnrTimeout OBJECT-TYPE
    SYNTAX     Integer32 (0..2147483647)
    MAX-ACCESS read-write
    STATUS     current
    DESCRIPTION
            "-- empty --"
    ::= { lcsSetupVcCllMngrUsersExtensionsEntry 7 }

-- {COLUMN} 1.3.6.1.4.1.2356.11.2.33.3.4.1.8
lcsSetupVcCllMngrUsersExtensionsEntryCfbActive OBJECT-TYPE
    SYNTAX     INTEGER {
                  eNo (0),
                  eYes (1)
            }
    MAX-ACCESS read-write
    STATUS     current
    DESCRIPTION
            "-- empty --"
    ::= { lcsSetupVcCllMngrUsersExtensionsEntry 8 }

-- {COLUMN} 1.3.6.1.4.1.2356.11.2.33.3.4.1.9
lcsSetupVcCllMngrUsersExtensionsEntryCfbTarget OBJECT-TYPE
    SYNTAX     DisplayString (SIZE(0..64))
    MAX-ACCESS read-write
    STATUS     current
    DESCRIPTION
            "-- empty --"
    ::= { lcsSetupVcCllMngrUsersExtensionsEntry 9 }

-- {COLUMN} 1.3.6.1.4.1.2356.11.2.33.3.4.1.10
lcsSetupVcCllMngrUsersExtensionsEntryActive OBJECT-TYPE
    SYNTAX     INTEGER {
                  eYes (0),
                  eNo (1)
            }
    MAX-ACCESS read-write
    STATUS     current
    DESCRIPTION
            "-- empty --"
    ::= { lcsSetupVcCllMngrUsersExtensionsEntry 10 }

-- {COLUMN} 1.3.6.1.4.1.2356.11.2.33.3.4.1.11
lcsSetupVcCllMngrUsersExtensionsEntryBusyOnBusy OBJECT-TYPE
    SYNTAX     INTEGER {
                  eYes (0),
                  eNo (1)
            }
    MAX-ACCESS read-write
    STATUS     current
    DESCRIPTION
            "-- empty --"
    ::= { lcsSetupVcCllMngrUsersExtensionsEntry 11 }

-- {COLUMN} 1.3.6.1.4.1.2356.11.2.33.3.4.1.12
lcsSetupVcCllMngrUsersExtensionsEntryCfSetClnId OBJECT-TYPE
    SYNTAX     INTEGER {
                  eExtensionId (0),
                  eCallingId (1),
                  eCustomId (2)
            }
    MAX-ACCESS read-write
    STATUS     current
    DESCRIPTION
            "-- empty --"
    ::= { lcsSetupVcCllMngrUsersExtensionsEntry 12 }

-- {COLUMN} 1.3.6.1.4.1.2356.11.2.33.3.4.1.13
lcsSetupVcCllMngrUsersExtensionsEntryCustomId OBJECT-TYPE
    SYNTAX     DisplayString (SIZE(0..64))
    MAX-ACCESS read-write
    STATUS     current
    DESCRIPTION
            "-- empty --"
    ::= { lcsSetupVcCllMngrUsersExtensionsEntry 13 }

-- {NODE} 1.3.6.1.4.1.2356.11.2.33.4
lcsSetupVcCllMngrLines OBJECT IDENTIFIER ::= { lcsSetupVcCllMngr 4 }

-- {NODE} 1.3.6.1.4.1.2356.11.2.33.4.1
lcsSetupVcCllMngrLinesSipProvider OBJECT IDENTIFIER ::= { lcsSetupVcCllMngrLines 1 }

-- {TABLE} 1.3.6.1.4.1.2356.11.2.33.4.1.1
lcsSetupVcCllMngrLinesSipProviderLineTable OBJECT-TYPE
    SYNTAX     SEQUENCE OF LcsSetupVcCllMngrLinesSipProviderLineEntry
    MAX-ACCESS not-accessible
    STATUS     current
    DESCRIPTION
            "-- empty --"
    ::= { lcsSetupVcCllMngrLinesSipProvider 1 }

-- {ROW} 1.3.6.1.4.1.2356.11.2.33.4.1.1.1
lcsSetupVcCllMngrLinesSipProviderLineEntry OBJECT-TYPE
    SYNTAX     LcsSetupVcCllMngrLinesSipProviderLineEntry
    MAX-ACCESS not-accessible
    STATUS     current
    DESCRIPTION
            ""
    INDEX {
            lcsSetupVcCllMngrLinesSipProviderLineEntryName
          }
    ::= { lcsSetupVcCllMngrLinesSipProviderLineTable 1 }

LcsSetupVcCllMngrLinesSipProviderLineEntry ::= SEQUENCE {
            lcsSetupVcCllMngrLinesSipProviderLineEntryName DisplayString,
            lcsSetupVcCllMngrLinesSipProviderLineEntryDomain DisplayString,
            lcsSetupVcCllMngrLinesSipProviderLineEntryPort Integer32,
            lcsSetupVcCllMngrLinesSipProviderLineEntryUserId DisplayString,
            lcsSetupVcCllMngrLinesSipProviderLineEntryAuthName DisplayString,
            lcsSetupVcCllMngrLinesSipProviderLineEntrySecret DisplayString,
            lcsSetupVcCllMngrLinesSipProviderLineEntryOutbProxy DisplayString,
            lcsSetupVcCllMngrLinesSipProviderLineEntryClnPrefix DisplayString,
            lcsSetupVcCllMngrLinesSipProviderLineEntryNumberName DisplayString,
            lcsSetupVcCllMngrLinesSipProviderLineEntryActive INTEGER,
            lcsSetupVcCllMngrLinesSipProviderLineEntryComment DisplayString,
            lcsSetupVcCllMngrLinesSipProviderLineEntryRtgTag Integer32,
            lcsSetupVcCllMngrLinesSipProviderLineEntryDisplayName DisplayString,
            lcsSetupVcCllMngrLinesSipProviderLineEntryRegistrar DisplayString,
            lcsSetupVcCllMngrLinesSipProviderLineEntryMode INTEGER,
            lcsSetupVcCllMngrLinesSipProviderLineEntryReferForwarding INTEGER,
            lcsSetupVcCllMngrLinesSipProviderLineEntryLocalPort Integer32,
            lcsSetupVcCllMngrLinesSipProviderLineEntryReRegistration INTEGER,
            lcsSetupVcCllMngrLinesSipProviderLineEntryLineControlMethod INTEGER,
            lcsSetupVcCllMngrLinesSipProviderLineEntryLineControlInterval Integer32,
            lcsSetupVcCllMngrLinesSipProviderLineEntryTrusted INTEGER,
            lcsSetupVcCllMngrLinesSipProviderLineEntryPrivacyMethod INTEGER,
            lcsSetupVcCllMngrLinesSipProviderLineEntryRemoveFromUsertype INTEGER,
            lcsSetupVcCllMngrLinesSipProviderLineEntryTrunkIncCldInToheader INTEGER,
            lcsSetupVcCllMngrLinesSipProviderLineEntryDtmfMethod INTEGER,
            lcsSetupVcCllMngrLinesSipProviderLineEntryTransport INTEGER,
            lcsSetupVcCllMngrLinesSipProviderLineEntrySrtp INTEGER,
            lcsSetupVcCllMngrLinesSipProviderLineEntryStrictMode INTEGER,
            lcsSetupVcCllMngrLinesSipProviderLineEntryVerifyServerCert INTEGER,
            lcsSetupVcCllMngrLinesSipProviderLineEntryAllowInboundUdpFrom BITS,
            lcsSetupVcCllMngrLinesSipProviderLineEntrySrtpCiphers BITS,
            lcsSetupVcCllMngrLinesSipProviderLineEntrySrtpMessageAuthTags BITS,
            lcsSetupVcCllMngrLinesSipProviderLineEntryOverlapDialing INTEGER,
            lcsSetupVcCllMngrLinesSipProviderLineEntryRegistrationInterval Integer32,
            lcsSetupVcCllMngrLinesSipProviderLineEntryFallback INTEGER,
            lcsSetupVcCllMngrLinesSipProviderLineEntryUserIdField INTEGER,
            lcsSetupVcCllMngrLinesSipProviderLineEntryLoopbackAddress DisplayString,
            lcsSetupVcCllMngrLinesSipProviderLineEntryAllowSip302Forwarding INTEGER
    }

-- {COLUMN} 1.3.6.1.4.1.2356.11.2.33.4.1.1.1.1
lcsSetupVcCllMngrLinesSipProviderLineEntryName OBJECT-TYPE
    SYNTAX     DisplayString (SIZE(0..32))
    MAX-ACCESS read-write
    STATUS     current
    DESCRIPTION
            "-- empty --"
    ::= { lcsSetupVcCllMngrLinesSipProviderLineEntry 1 }

-- {COLUMN} 1.3.6.1.4.1.2356.11.2.33.4.1.1.1.2
lcsSetupVcCllMngrLinesSipProviderLineEntryDomain OBJECT-TYPE
    SYNTAX     DisplayString (SIZE(0..63))
    MAX-ACCESS read-write
    STATUS     current
    DESCRIPTION
            "-- empty --"
    ::= { lcsSetupVcCllMngrLinesSipProviderLineEntry 2 }

-- {COLUMN} 1.3.6.1.4.1.2356.11.2.33.4.1.1.1.3
lcsSetupVcCllMngrLinesSipProviderLineEntryPort OBJECT-TYPE
    SYNTAX     Integer32 (0..65535)
    MAX-ACCESS read-write
    STATUS     current
    DESCRIPTION
            "-- empty --"
    ::= { lcsSetupVcCllMngrLinesSipProviderLineEntry 3 }

-- {COLUMN} 1.3.6.1.4.1.2356.11.2.33.4.1.1.1.4
lcsSetupVcCllMngrLinesSipProviderLineEntryUserId OBJECT-TYPE
    SYNTAX     DisplayString (SIZE(0..63))
    MAX-ACCESS read-write
    STATUS     current
    DESCRIPTION
            "-- empty --"
    ::= { lcsSetupVcCllMngrLinesSipProviderLineEntry 4 }

-- {COLUMN} 1.3.6.1.4.1.2356.11.2.33.4.1.1.1.5
lcsSetupVcCllMngrLinesSipProviderLineEntryAuthName OBJECT-TYPE
    SYNTAX     DisplayString (SIZE(0..63))
    MAX-ACCESS read-write
    STATUS     current
    DESCRIPTION
            "-- empty --"
    ::= { lcsSetupVcCllMngrLinesSipProviderLineEntry 5 }

-- {COLUMN} 1.3.6.1.4.1.2356.11.2.33.4.1.1.1.6
lcsSetupVcCllMngrLinesSipProviderLineEntrySecret OBJECT-TYPE
    SYNTAX     DisplayString (SIZE(0..64))
    MAX-ACCESS read-write
    STATUS     current
    DESCRIPTION
            "-- empty --"
    ::= { lcsSetupVcCllMngrLinesSipProviderLineEntry 6 }

-- {COLUMN} 1.3.6.1.4.1.2356.11.2.33.4.1.1.1.7
lcsSetupVcCllMngrLinesSipProviderLineEntryOutbProxy OBJECT-TYPE
    SYNTAX     DisplayString (SIZE(0..63))
    MAX-ACCESS read-write
    STATUS     current
    DESCRIPTION
            "-- empty --"
    ::= { lcsSetupVcCllMngrLinesSipProviderLineEntry 7 }

-- {COLUMN} 1.3.6.1.4.1.2356.11.2.33.4.1.1.1.8
lcsSetupVcCllMngrLinesSipProviderLineEntryClnPrefix OBJECT-TYPE
    SYNTAX     DisplayString (SIZE(0..9))
    MAX-ACCESS read-write
    STATUS     current
    DESCRIPTION
            "-- empty --"
    ::= { lcsSetupVcCllMngrLinesSipProviderLineEntry 8 }

-- {COLUMN} 1.3.6.1.4.1.2356.11.2.33.4.1.1.1.9
lcsSetupVcCllMngrLinesSipProviderLineEntryNumberName OBJECT-TYPE
    SYNTAX     DisplayString (SIZE(0..20))
    MAX-ACCESS read-write
    STATUS     current
    DESCRIPTION
            "-- empty --"
    ::= { lcsSetupVcCllMngrLinesSipProviderLineEntry 9 }

-- {COLUMN} 1.3.6.1.4.1.2356.11.2.33.4.1.1.1.10
lcsSetupVcCllMngrLinesSipProviderLineEntryActive OBJECT-TYPE
    SYNTAX     INTEGER {
                  eYes (0),
                  eNo (1)
            }
    MAX-ACCESS read-write
    STATUS     current
    DESCRIPTION
            "-- empty --"
    ::= { lcsSetupVcCllMngrLinesSipProviderLineEntry 10 }

-- {COLUMN} 1.3.6.1.4.1.2356.11.2.33.4.1.1.1.11
lcsSetupVcCllMngrLinesSipProviderLineEntryComment OBJECT-TYPE
    SYNTAX     DisplayString (SIZE(0..63))
    MAX-ACCESS read-write
    STATUS     current
    DESCRIPTION
            "-- empty --"
    ::= { lcsSetupVcCllMngrLinesSipProviderLineEntry 11 }

-- {COLUMN} 1.3.6.1.4.1.2356.11.2.33.4.1.1.1.14
lcsSetupVcCllMngrLinesSipProviderLineEntryRtgTag OBJECT-TYPE
    SYNTAX     Integer32 (0..65535)
    MAX-ACCESS read-write
    STATUS     current
    DESCRIPTION
            "-- empty --"
    ::= { lcsSetupVcCllMngrLinesSipProviderLineEntry 14 }

-- {COLUMN} 1.3.6.1.4.1.2356.11.2.33.4.1.1.1.15
lcsSetupVcCllMngrLinesSipProviderLineEntryDisplayName OBJECT-TYPE
    SYNTAX     DisplayString (SIZE(0..32))
    MAX-ACCESS read-write
    STATUS     current
    DESCRIPTION
            "-- empty --"
    ::= { lcsSetupVcCllMngrLinesSipProviderLineEntry 15 }

-- {COLUMN} 1.3.6.1.4.1.2356.11.2.33.4.1.1.1.16
lcsSetupVcCllMngrLinesSipProviderLineEntryRegistrar OBJECT-TYPE
    SYNTAX     DisplayString (SIZE(0..63))
    MAX-ACCESS read-write
    STATUS     current
    DESCRIPTION
            "-- empty --"
    ::= { lcsSetupVcCllMngrLinesSipProviderLineEntry 16 }

-- {COLUMN} 1.3.6.1.4.1.2356.11.2.33.4.1.1.1.17
lcsSetupVcCllMngrLinesSipProviderLineEntryMode OBJECT-TYPE
    SYNTAX     INTEGER {
                  eProvider (0),
                  eTrunk (1),
                  eGateway (2),
                  eLink (3),
                  eFlex (4)
            }
    MAX-ACCESS read-write
    STATUS     current
    DESCRIPTION
            "-- empty --"
    ::= { lcsSetupVcCllMngrLinesSipProviderLineEntry 17 }

-- {COLUMN} 1.3.6.1.4.1.2356.11.2.33.4.1.1.1.18
lcsSetupVcCllMngrLinesSipProviderLineEntryReferForwarding OBJECT-TYPE
    SYNTAX     INTEGER {
                  eNo (0),
                  eYes (1)
            }
    MAX-ACCESS read-write
    STATUS     current
    DESCRIPTION
            "-- empty --"
    ::= { lcsSetupVcCllMngrLinesSipProviderLineEntry 18 }

-- {COLUMN} 1.3.6.1.4.1.2356.11.2.33.4.1.1.1.19
lcsSetupVcCllMngrLinesSipProviderLineEntryLocalPort OBJECT-TYPE
    SYNTAX     Integer32 (0..65535)
    MAX-ACCESS read-write
    STATUS     current
    DESCRIPTION
            "-- empty --"
    ::= { lcsSetupVcCllMngrLinesSipProviderLineEntry 19 }

-- {COLUMN} 1.3.6.1.4.1.2356.11.2.33.4.1.1.1.20
lcsSetupVcCllMngrLinesSipProviderLineEntryReRegistration OBJECT-TYPE
    SYNTAX     INTEGER {
                  eYes (0),
                  eNo (1)
            }
    MAX-ACCESS read-write
    STATUS     current
    DESCRIPTION
            "-- empty --"
    ::= { lcsSetupVcCllMngrLinesSipProviderLineEntry 20 }

-- {COLUMN} 1.3.6.1.4.1.2356.11.2.33.4.1.1.1.21
lcsSetupVcCllMngrLinesSipProviderLineEntryLineControlMethod OBJECT-TYPE
    SYNTAX     INTEGER {
                  eAuto (0),
                  eInactive (1),
                  eRegister (2),
                  eOptions (3)
            }
    MAX-ACCESS read-write
    STATUS     current
    DESCRIPTION
            "-- empty --"
    ::= { lcsSetupVcCllMngrLinesSipProviderLineEntry 21 }

-- {COLUMN} 1.3.6.1.4.1.2356.11.2.33.4.1.1.1.22
lcsSetupVcCllMngrLinesSipProviderLineEntryLineControlInterval OBJECT-TYPE
    SYNTAX     Integer32 (0..65535)
    MAX-ACCESS read-write
    STATUS     current
    DESCRIPTION
            "-- empty --"
    ::= { lcsSetupVcCllMngrLinesSipProviderLineEntry 22 }

-- {COLUMN} 1.3.6.1.4.1.2356.11.2.33.4.1.1.1.23
lcsSetupVcCllMngrLinesSipProviderLineEntryTrusted OBJECT-TYPE
    SYNTAX     INTEGER {
                  eYes (0),
                  eNo (1)
            }
    MAX-ACCESS read-write
    STATUS     current
    DESCRIPTION
            "-- empty --"
    ::= { lcsSetupVcCllMngrLinesSipProviderLineEntry 23 }

-- {COLUMN} 1.3.6.1.4.1.2356.11.2.33.4.1.1.1.24
lcsSetupVcCllMngrLinesSipProviderLineEntryPrivacyMethod OBJECT-TYPE
    SYNTAX     INTEGER {
                  eNone (0),
                  eRfc3325 (1),
                  eIetfDraftSipPrivacy04 (2)
            }
    MAX-ACCESS read-write
    STATUS     current
    DESCRIPTION
            "-- empty --"
    ::= { lcsSetupVcCllMngrLinesSipProviderLineEntry 24 }

-- {COLUMN} 1.3.6.1.4.1.2356.11.2.33.4.1.1.1.25
lcsSetupVcCllMngrLinesSipProviderLineEntryRemoveFromUsertype OBJECT-TYPE
    SYNTAX     INTEGER {
                  eNo (0),
                  eYes (1)
            }
    MAX-ACCESS read-write
    STATUS     current
    DESCRIPTION
            "-- empty --"
    ::= { lcsSetupVcCllMngrLinesSipProviderLineEntry 25 }

-- {COLUMN} 1.3.6.1.4.1.2356.11.2.33.4.1.1.1.26
lcsSetupVcCllMngrLinesSipProviderLineEntryTrunkIncCldInToheader OBJECT-TYPE
    SYNTAX     INTEGER {
                  eNo (0),
                  eYes (1)
            }
    MAX-ACCESS read-write
    STATUS     current
    DESCRIPTION
            "-- empty --"
    ::= { lcsSetupVcCllMngrLinesSipProviderLineEntry 26 }

-- {COLUMN} 1.3.6.1.4.1.2356.11.2.33.4.1.1.1.27
lcsSetupVcCllMngrLinesSipProviderLineEntryDtmfMethod OBJECT-TYPE
    SYNTAX     INTEGER {
                  eInband (0),
                  eSipInfo (1),
                  eRtpEvent (2),
                  eRtpEventSipInfo (3)
            }
    MAX-ACCESS read-write
    STATUS     current
    DESCRIPTION
            "-- empty --"
    ::= { lcsSetupVcCllMngrLinesSipProviderLineEntry 27 }

-- {COLUMN} 1.3.6.1.4.1.2356.11.2.33.4.1.1.1.28
lcsSetupVcCllMngrLinesSipProviderLineEntryTransport OBJECT-TYPE
    SYNTAX     INTEGER {
                  eUdp (0),
                  eTcp (1),
                  eTlsv1 (2),
                  eTlsv11 (3),
                  eTlsv12 (4)
            }
    MAX-ACCESS read-write
    STATUS     current
    DESCRIPTION
            "-- empty --"
    ::= { lcsSetupVcCllMngrLinesSipProviderLineEntry 28 }

-- {COLUMN} 1.3.6.1.4.1.2356.11.2.33.4.1.1.1.29
lcsSetupVcCllMngrLinesSipProviderLineEntrySrtp OBJECT-TYPE
    SYNTAX     INTEGER {
                  eReject (0),
                  eIgnore (1),
                  ePrefer (2),
                  eForce (3)
            }
    MAX-ACCESS read-write
    STATUS     current
    DESCRIPTION
            "-- empty --"
    ::= { lcsSetupVcCllMngrLinesSipProviderLineEntry 29 }

-- {COLUMN} 1.3.6.1.4.1.2356.11.2.33.4.1.1.1.30
lcsSetupVcCllMngrLinesSipProviderLineEntryStrictMode OBJECT-TYPE
    SYNTAX     INTEGER {
                  eNo (0),
                  eYes (1)
            }
    MAX-ACCESS read-write
    STATUS     current
    DESCRIPTION
            "-- empty --"
    ::= { lcsSetupVcCllMngrLinesSipProviderLineEntry 30 }

-- {COLUMN} 1.3.6.1.4.1.2356.11.2.33.4.1.1.1.32
lcsSetupVcCllMngrLinesSipProviderLineEntryVerifyServerCert OBJECT-TYPE
    SYNTAX     INTEGER {
                  eNoVerification (0),
                  eSipTrustedCaSlot1 (1),
                  eSipTrustedCaSlot2 (2),
                  eSipTrustedCaSlot3 (3),
                  eTelekomSharedBusinessCa4 (10),
                  eAcceptTrusted (99)
            }
    MAX-ACCESS read-write
    STATUS     current
    DESCRIPTION
            ""
    ::= { lcsSetupVcCllMngrLinesSipProviderLineEntry 32 }

-- {COLUMN} 1.3.6.1.4.1.2356.11.2.33.4.1.1.1.33
lcsSetupVcCllMngrLinesSipProviderLineEntryAllowInboundUdpFrom OBJECT-TYPE
    SYNTAX     BITS {
                  eWan (5),
                  eVpn (6),
                  eLan (7)
            }
    MAX-ACCESS read-write
    STATUS     current
    DESCRIPTION
            "-- empty --"
    ::= { lcsSetupVcCllMngrLinesSipProviderLineEntry 33 }

-- {COLUMN} 1.3.6.1.4.1.2356.11.2.33.4.1.1.1.34
lcsSetupVcCllMngrLinesSipProviderLineEntrySrtpCiphers OBJECT-TYPE
    SYNTAX     BITS {
                  eF8128 (4),
                  eAesCm256 (5),
                  eAesCm192 (6),
                  eAesCm128 (7)
            }
    MAX-ACCESS read-write
    STATUS     current
    DESCRIPTION
            "-- empty --"
    ::= { lcsSetupVcCllMngrLinesSipProviderLineEntry 34 }

-- {COLUMN} 1.3.6.1.4.1.2356.11.2.33.4.1.1.1.35
lcsSetupVcCllMngrLinesSipProviderLineEntrySrtpMessageAuthTags OBJECT-TYPE
    SYNTAX     BITS {
                  eHmacSha132 (6),
                  eHmacSha180 (7)
            }
    MAX-ACCESS read-write
    STATUS     current
    DESCRIPTION
            "-- empty --"
    ::= { lcsSetupVcCllMngrLinesSipProviderLineEntry 35 }

-- {COLUMN} 1.3.6.1.4.1.2356.11.2.33.4.1.1.1.36
lcsSetupVcCllMngrLinesSipProviderLineEntryOverlapDialing OBJECT-TYPE
    SYNTAX     INTEGER {
                  eNo (0),
                  eYes (1)
            }
    MAX-ACCESS read-write
    STATUS     current
    DESCRIPTION
            "-- empty --"
    ::= { lcsSetupVcCllMngrLinesSipProviderLineEntry 36 }

-- {COLUMN} 1.3.6.1.4.1.2356.11.2.33.4.1.1.1.37
lcsSetupVcCllMngrLinesSipProviderLineEntryRegistrationInterval OBJECT-TYPE
    SYNTAX     Integer32 (0..65535)
    MAX-ACCESS read-write
    STATUS     current
    DESCRIPTION
            "-- empty --"
    ::= { lcsSetupVcCllMngrLinesSipProviderLineEntry 37 }

-- {COLUMN} 1.3.6.1.4.1.2356.11.2.33.4.1.1.1.38
lcsSetupVcCllMngrLinesSipProviderLineEntryFallback OBJECT-TYPE
    SYNTAX     INTEGER {
                  eNo (0),
                  eUdp (1),
                  eComplete (2)
            }
    MAX-ACCESS read-write
    STATUS     current
    DESCRIPTION
            "-- empty --"
    ::= { lcsSetupVcCllMngrLinesSipProviderLineEntry 38 }

-- {COLUMN} 1.3.6.1.4.1.2356.11.2.33.4.1.1.1.39
lcsSetupVcCllMngrLinesSipProviderLineEntryUserIdField OBJECT-TYPE
    SYNTAX     INTEGER {
                  ePpi (0),
                  eFrom (1),
                  eNone (2),
                  ePpiWoddi (3)
            }
    MAX-ACCESS read-write
    STATUS     current
    DESCRIPTION
            "-- empty --"
    ::= { lcsSetupVcCllMngrLinesSipProviderLineEntry 39 }

-- {COLUMN} 1.3.6.1.4.1.2356.11.2.33.4.1.1.1.40
lcsSetupVcCllMngrLinesSipProviderLineEntryLoopbackAddress OBJECT-TYPE
    SYNTAX     DisplayString (SIZE(0..20))
    MAX-ACCESS read-write
    STATUS     current
    DESCRIPTION
            "-- empty --"
    ::= { lcsSetupVcCllMngrLinesSipProviderLineEntry 40 }

-- {COLUMN} 1.3.6.1.4.1.2356.11.2.33.4.1.1.1.41
lcsSetupVcCllMngrLinesSipProviderLineEntryAllowSip302Forwarding OBJECT-TYPE
    SYNTAX     INTEGER {
                  eNo (0),
                  eYes (1)
            }
    MAX-ACCESS read-write
    STATUS     current
    DESCRIPTION
            "-- empty --"
    ::= { lcsSetupVcCllMngrLinesSipProviderLineEntry 41 }

-- {TABLE} 1.3.6.1.4.1.2356.11.2.33.4.1.2
lcsSetupVcCllMngrLinesSipProviderMappingTable OBJECT-TYPE
    SYNTAX     SEQUENCE OF LcsSetupVcCllMngrLinesSipProviderMappingEntry
    MAX-ACCESS not-accessible
    STATUS     current
    DESCRIPTION
            "-- empty --"
    ::= { lcsSetupVcCllMngrLinesSipProvider 2 }

-- {ROW} 1.3.6.1.4.1.2356.11.2.33.4.1.2.1
lcsSetupVcCllMngrLinesSipProviderMappingEntry OBJECT-TYPE
    SYNTAX     LcsSetupVcCllMngrLinesSipProviderMappingEntry
    MAX-ACCESS not-accessible
    STATUS     current
    DESCRIPTION
            ""
    INDEX {
            lcsSetupVcCllMngrLinesSipProviderMappingEntrySipProvider,
            lcsSetupVcCllMngrLinesSipProviderMappingEntryExtNumberName,
            lcsSetupVcCllMngrLinesSipProviderMappingEntryNumberName
          }
    ::= { lcsSetupVcCllMngrLinesSipProviderMappingTable 1 }

LcsSetupVcCllMngrLinesSipProviderMappingEntry ::= SEQUENCE {
            lcsSetupVcCllMngrLinesSipProviderMappingEntrySipProvider DisplayString,
            lcsSetupVcCllMngrLinesSipProviderMappingEntryExtNumberName DisplayString,
            lcsSetupVcCllMngrLinesSipProviderMappingEntryNumberName DisplayString,
            lcsSetupVcCllMngrLinesSipProviderMappingEntryLength Integer32,
            lcsSetupVcCllMngrLinesSipProviderMappingEntryActive INTEGER,
            lcsSetupVcCllMngrLinesSipProviderMappingEntryComment DisplayString,
            lcsSetupVcCllMngrLinesSipProviderMappingEntryClir INTEGER
    }

-- {COLUMN} 1.3.6.1.4.1.2356.11.2.33.4.1.2.1.1
lcsSetupVcCllMngrLinesSipProviderMappingEntrySipProvider OBJECT-TYPE
    SYNTAX     DisplayString (SIZE(0..32))
    MAX-ACCESS read-write
    STATUS     current
    DESCRIPTION
            "-- empty --"
    ::= { lcsSetupVcCllMngrLinesSipProviderMappingEntry 1 }

-- {COLUMN} 1.3.6.1.4.1.2356.11.2.33.4.1.2.1.2
lcsSetupVcCllMngrLinesSipProviderMappingEntryExtNumberName OBJECT-TYPE
    SYNTAX     DisplayString (SIZE(0..19))
    MAX-ACCESS read-write
    STATUS     current
    DESCRIPTION
            "-- empty --"
    ::= { lcsSetupVcCllMngrLinesSipProviderMappingEntry 2 }

-- {COLUMN} 1.3.6.1.4.1.2356.11.2.33.4.1.2.1.3
lcsSetupVcCllMngrLinesSipProviderMappingEntryNumberName OBJECT-TYPE
    SYNTAX     DisplayString (SIZE(0..20))
    MAX-ACCESS read-write
    STATUS     current
    DESCRIPTION
            "-- empty --"
    ::= { lcsSetupVcCllMngrLinesSipProviderMappingEntry 3 }

-- {COLUMN} 1.3.6.1.4.1.2356.11.2.33.4.1.2.1.4
lcsSetupVcCllMngrLinesSipProviderMappingEntryLength OBJECT-TYPE
    SYNTAX     Integer32 (0..255)
    MAX-ACCESS read-write
    STATUS     current
    DESCRIPTION
            "-- empty --"
    ::= { lcsSetupVcCllMngrLinesSipProviderMappingEntry 4 }

-- {COLUMN} 1.3.6.1.4.1.2356.11.2.33.4.1.2.1.5
lcsSetupVcCllMngrLinesSipProviderMappingEntryActive OBJECT-TYPE
    SYNTAX     INTEGER {
                  eYes (0),
                  eNo (1)
            }
    MAX-ACCESS read-write
    STATUS     current
    DESCRIPTION
            "-- empty --"
    ::= { lcsSetupVcCllMngrLinesSipProviderMappingEntry 5 }

-- {COLUMN} 1.3.6.1.4.1.2356.11.2.33.4.1.2.1.6
lcsSetupVcCllMngrLinesSipProviderMappingEntryComment OBJECT-TYPE
    SYNTAX     DisplayString (SIZE(0..63))
    MAX-ACCESS read-write
    STATUS     current
    DESCRIPTION
            "-- empty --"
    ::= { lcsSetupVcCllMngrLinesSipProviderMappingEntry 6 }

-- {COLUMN} 1.3.6.1.4.1.2356.11.2.33.4.1.2.1.7
lcsSetupVcCllMngrLinesSipProviderMappingEntryClir OBJECT-TYPE
    SYNTAX     INTEGER {
                  eNo (0),
                  eYes (1)
            }
    MAX-ACCESS read-write
    STATUS     current
    DESCRIPTION
            "-- empty --"
    ::= { lcsSetupVcCllMngrLinesSipProviderMappingEntry 7 }

-- {TABLE} 1.3.6.1.4.1.2356.11.2.33.4.1.3
lcsSetupVcCllMngrLinesSipProviderDynamicLineTable OBJECT-TYPE
    SYNTAX     SEQUENCE OF LcsSetupVcCllMngrLinesSipProviderDynamicLineEntry
    MAX-ACCESS not-accessible
    STATUS     current
    DESCRIPTION
            "-- empty --"
    ::= { lcsSetupVcCllMngrLinesSipProvider 3 }

-- {ROW} 1.3.6.1.4.1.2356.11.2.33.4.1.3.1
lcsSetupVcCllMngrLinesSipProviderDynamicLineEntry OBJECT-TYPE
    SYNTAX     LcsSetupVcCllMngrLinesSipProviderDynamicLineEntry
    MAX-ACCESS not-accessible
    STATUS     current
    DESCRIPTION
            ""
    INDEX {
            lcsSetupVcCllMngrLinesSipProviderDynamicLineEntryDynamicLineName,
            lcsSetupVcCllMngrLinesSipProviderDynamicLineEntrySipLineName
          }
    ::= { lcsSetupVcCllMngrLinesSipProviderDynamicLineTable 1 }

LcsSetupVcCllMngrLinesSipProviderDynamicLineEntry ::= SEQUENCE {
            lcsSetupVcCllMngrLinesSipProviderDynamicLineEntryDynamicLineName DisplayString,
            lcsSetupVcCllMngrLinesSipProviderDynamicLineEntrySipLineName DisplayString,
            lcsSetupVcCllMngrLinesSipProviderDynamicLineEntryPriority Integer32,
            lcsSetupVcCllMngrLinesSipProviderDynamicLineEntryWeight Integer32,
            lcsSetupVcCllMngrLinesSipProviderDynamicLineEntryAlgorithm INTEGER,
            lcsSetupVcCllMngrLinesSipProviderDynamicLineEntryMaxCalls Integer32
    }

-- {COLUMN} 1.3.6.1.4.1.2356.11.2.33.4.1.3.1.1
lcsSetupVcCllMngrLinesSipProviderDynamicLineEntryDynamicLineName OBJECT-TYPE
    SYNTAX     DisplayString (SIZE(0..32))
    MAX-ACCESS read-write
    STATUS     current
    DESCRIPTION
            "-- empty --"
    ::= { lcsSetupVcCllMngrLinesSipProviderDynamicLineEntry 1 }

-- {COLUMN} 1.3.6.1.4.1.2356.11.2.33.4.1.3.1.2
lcsSetupVcCllMngrLinesSipProviderDynamicLineEntrySipLineName OBJECT-TYPE
    SYNTAX     DisplayString (SIZE(0..32))
    MAX-ACCESS read-write
    STATUS     current
    DESCRIPTION
            "-- empty --"
    ::= { lcsSetupVcCllMngrLinesSipProviderDynamicLineEntry 2 }

-- {COLUMN} 1.3.6.1.4.1.2356.11.2.33.4.1.3.1.3
lcsSetupVcCllMngrLinesSipProviderDynamicLineEntryPriority OBJECT-TYPE
    SYNTAX     Integer32 (0..2147483647)
    MAX-ACCESS read-write
    STATUS     current
    DESCRIPTION
            "-- empty --"
    ::= { lcsSetupVcCllMngrLinesSipProviderDynamicLineEntry 3 }

-- {COLUMN} 1.3.6.1.4.1.2356.11.2.33.4.1.3.1.4
lcsSetupVcCllMngrLinesSipProviderDynamicLineEntryWeight OBJECT-TYPE
    SYNTAX     Integer32 (0..2147483647)
    MAX-ACCESS read-write
    STATUS     current
    DESCRIPTION
            "-- empty --"
    ::= { lcsSetupVcCllMngrLinesSipProviderDynamicLineEntry 4 }

-- {COLUMN} 1.3.6.1.4.1.2356.11.2.33.4.1.3.1.5
lcsSetupVcCllMngrLinesSipProviderDynamicLineEntryAlgorithm OBJECT-TYPE
    SYNTAX     INTEGER {
                  eWeight (0),
                  eRoundRobin (1),
                  ePriority (2)
            }
    MAX-ACCESS read-write
    STATUS     current
    DESCRIPTION
            "-- empty --"
    ::= { lcsSetupVcCllMngrLinesSipProviderDynamicLineEntry 5 }

-- {COLUMN} 1.3.6.1.4.1.2356.11.2.33.4.1.3.1.6
lcsSetupVcCllMngrLinesSipProviderDynamicLineEntryMaxCalls OBJECT-TYPE
    SYNTAX     Integer32 (0..2147483647)
    MAX-ACCESS read-write
    STATUS     current
    DESCRIPTION
            "-- empty --"
    ::= { lcsSetupVcCllMngrLinesSipProviderDynamicLineEntry 6 }

-- {NODE} 1.3.6.1.4.1.2356.11.2.33.4.2
lcsSetupVcCllMngrLinesSipPbx OBJECT IDENTIFIER ::= { lcsSetupVcCllMngrLines 2 }

-- {TABLE} 1.3.6.1.4.1.2356.11.2.33.4.2.1
lcsSetupVcCllMngrLinesSipPbxPbxTable OBJECT-TYPE
    SYNTAX     SEQUENCE OF LcsSetupVcCllMngrLinesSipPbxPbxEntry
    MAX-ACCESS not-accessible
    STATUS     current
    DESCRIPTION
            "-- empty --"
    ::= { lcsSetupVcCllMngrLinesSipPbx 1 }

-- {ROW} 1.3.6.1.4.1.2356.11.2.33.4.2.1.1
lcsSetupVcCllMngrLinesSipPbxPbxEntry OBJECT-TYPE
    SYNTAX     LcsSetupVcCllMngrLinesSipPbxPbxEntry
    MAX-ACCESS not-accessible
    STATUS     current
    DESCRIPTION
            ""
    INDEX {
            lcsSetupVcCllMngrLinesSipPbxPbxEntryName
          }
    ::= { lcsSetupVcCllMngrLinesSipPbxPbxTable 1 }

LcsSetupVcCllMngrLinesSipPbxPbxEntry ::= SEQUENCE {
            lcsSetupVcCllMngrLinesSipPbxPbxEntryName DisplayString,
            lcsSetupVcCllMngrLinesSipPbxPbxEntryDomain DisplayString,
            lcsSetupVcCllMngrLinesSipPbxPbxEntryPort Integer32,
            lcsSetupVcCllMngrLinesSipPbxPbxEntrySecret DisplayString,
            lcsSetupVcCllMngrLinesSipPbxPbxEntryOutbProxy DisplayString,
            lcsSetupVcCllMngrLinesSipPbxPbxEntryActive INTEGER,
            lcsSetupVcCllMngrLinesSipPbxPbxEntryComment DisplayString,
            lcsSetupVcCllMngrLinesSipPbxPbxEntryClnPrefix DisplayString,
            lcsSetupVcCllMngrLinesSipPbxPbxEntryLinePrefix DisplayString,
            lcsSetupVcCllMngrLinesSipPbxPbxEntryRtgTag Integer32,
            lcsSetupVcCllMngrLinesSipPbxPbxEntryRegistrar DisplayString,
            lcsSetupVcCllMngrLinesSipPbxPbxEntryLocalPort Integer32,
            lcsSetupVcCllMngrLinesSipPbxPbxEntryReRegistration INTEGER,
            lcsSetupVcCllMngrLinesSipPbxPbxEntryLineControlMethod INTEGER,
            lcsSetupVcCllMngrLinesSipPbxPbxEntryLineControlInterval Integer32,
            lcsSetupVcCllMngrLinesSipPbxPbxEntryTrusted INTEGER,
            lcsSetupVcCllMngrLinesSipPbxPbxEntryPrivacyMethod INTEGER,
            lcsSetupVcCllMngrLinesSipPbxPbxEntryDtmfMethod INTEGER,
            lcsSetupVcCllMngrLinesSipPbxPbxEntryStrictMode INTEGER,
            lcsSetupVcCllMngrLinesSipPbxPbxEntryAllowInboundUdpFrom BITS,
            lcsSetupVcCllMngrLinesSipPbxPbxEntryOverlapDialing INTEGER
    }

-- {COLUMN} 1.3.6.1.4.1.2356.11.2.33.4.2.1.1.1
lcsSetupVcCllMngrLinesSipPbxPbxEntryName OBJECT-TYPE
    SYNTAX     DisplayString (SIZE(0..16))
    MAX-ACCESS read-write
    STATUS     current
    DESCRIPTION
            "-- empty --"
    ::= { lcsSetupVcCllMngrLinesSipPbxPbxEntry 1 }

-- {COLUMN} 1.3.6.1.4.1.2356.11.2.33.4.2.1.1.2
lcsSetupVcCllMngrLinesSipPbxPbxEntryDomain OBJECT-TYPE
    SYNTAX     DisplayString (SIZE(0..63))
    MAX-ACCESS read-write
    STATUS     current
    DESCRIPTION
            "-- empty --"
    ::= { lcsSetupVcCllMngrLinesSipPbxPbxEntry 2 }

-- {COLUMN} 1.3.6.1.4.1.2356.11.2.33.4.2.1.1.3
lcsSetupVcCllMngrLinesSipPbxPbxEntryPort OBJECT-TYPE
    SYNTAX     Integer32 (0..65535)
    MAX-ACCESS read-write
    STATUS     current
    DESCRIPTION
            "-- empty --"
    ::= { lcsSetupVcCllMngrLinesSipPbxPbxEntry 3 }

-- {COLUMN} 1.3.6.1.4.1.2356.11.2.33.4.2.1.1.4
lcsSetupVcCllMngrLinesSipPbxPbxEntrySecret OBJECT-TYPE
    SYNTAX     DisplayString (SIZE(0..32))
    MAX-ACCESS read-write
    STATUS     current
    DESCRIPTION
            "-- empty --"
    ::= { lcsSetupVcCllMngrLinesSipPbxPbxEntry 4 }

-- {COLUMN} 1.3.6.1.4.1.2356.11.2.33.4.2.1.1.5
lcsSetupVcCllMngrLinesSipPbxPbxEntryOutbProxy OBJECT-TYPE
    SYNTAX     DisplayString (SIZE(0..63))
    MAX-ACCESS read-write
    STATUS     current
    DESCRIPTION
            "-- empty --"
    ::= { lcsSetupVcCllMngrLinesSipPbxPbxEntry 5 }

-- {COLUMN} 1.3.6.1.4.1.2356.11.2.33.4.2.1.1.6
lcsSetupVcCllMngrLinesSipPbxPbxEntryActive OBJECT-TYPE
    SYNTAX     INTEGER {
                  eYes (0),
                  eNo (1)
            }
    MAX-ACCESS read-write
    STATUS     current
    DESCRIPTION
            "-- empty --"
    ::= { lcsSetupVcCllMngrLinesSipPbxPbxEntry 6 }

-- {COLUMN} 1.3.6.1.4.1.2356.11.2.33.4.2.1.1.7
lcsSetupVcCllMngrLinesSipPbxPbxEntryComment OBJECT-TYPE
    SYNTAX     DisplayString (SIZE(0..63))
    MAX-ACCESS read-write
    STATUS     current
    DESCRIPTION
            "-- empty --"
    ::= { lcsSetupVcCllMngrLinesSipPbxPbxEntry 7 }

-- {COLUMN} 1.3.6.1.4.1.2356.11.2.33.4.2.1.1.8
lcsSetupVcCllMngrLinesSipPbxPbxEntryClnPrefix OBJECT-TYPE
    SYNTAX     DisplayString (SIZE(0..9))
    MAX-ACCESS read-write
    STATUS     current
    DESCRIPTION
            "-- empty --"
    ::= { lcsSetupVcCllMngrLinesSipPbxPbxEntry 8 }

-- {COLUMN} 1.3.6.1.4.1.2356.11.2.33.4.2.1.1.9
lcsSetupVcCllMngrLinesSipPbxPbxEntryLinePrefix OBJECT-TYPE
    SYNTAX     DisplayString (SIZE(0..19))
    MAX-ACCESS read-write
    STATUS     current
    DESCRIPTION
            "-- empty --"
    ::= { lcsSetupVcCllMngrLinesSipPbxPbxEntry 9 }

-- {COLUMN} 1.3.6.1.4.1.2356.11.2.33.4.2.1.1.12
lcsSetupVcCllMngrLinesSipPbxPbxEntryRtgTag OBJECT-TYPE
    SYNTAX     Integer32 (0..65535)
    MAX-ACCESS read-write
    STATUS     current
    DESCRIPTION
            "-- empty --"
    ::= { lcsSetupVcCllMngrLinesSipPbxPbxEntry 12 }

-- {COLUMN} 1.3.6.1.4.1.2356.11.2.33.4.2.1.1.13
lcsSetupVcCllMngrLinesSipPbxPbxEntryRegistrar OBJECT-TYPE
    SYNTAX     DisplayString (SIZE(0..63))
    MAX-ACCESS read-write
    STATUS     current
    DESCRIPTION
            "-- empty --"
    ::= { lcsSetupVcCllMngrLinesSipPbxPbxEntry 13 }

-- {COLUMN} 1.3.6.1.4.1.2356.11.2.33.4.2.1.1.14
lcsSetupVcCllMngrLinesSipPbxPbxEntryLocalPort OBJECT-TYPE
    SYNTAX     Integer32 (0..65535)
    MAX-ACCESS read-write
    STATUS     current
    DESCRIPTION
            "-- empty --"
    ::= { lcsSetupVcCllMngrLinesSipPbxPbxEntry 14 }

-- {COLUMN} 1.3.6.1.4.1.2356.11.2.33.4.2.1.1.15
lcsSetupVcCllMngrLinesSipPbxPbxEntryReRegistration OBJECT-TYPE
    SYNTAX     INTEGER {
                  eYes (0),
                  eNo (1)
            }
    MAX-ACCESS read-write
    STATUS     current
    DESCRIPTION
            "-- empty --"
    ::= { lcsSetupVcCllMngrLinesSipPbxPbxEntry 15 }

-- {COLUMN} 1.3.6.1.4.1.2356.11.2.33.4.2.1.1.16
lcsSetupVcCllMngrLinesSipPbxPbxEntryLineControlMethod OBJECT-TYPE
    SYNTAX     INTEGER {
                  eAuto (0),
                  eInactive (1),
                  eRegister (2),
                  eOptions (3)
            }
    MAX-ACCESS read-write
    STATUS     current
    DESCRIPTION
            "-- empty --"
    ::= { lcsSetupVcCllMngrLinesSipPbxPbxEntry 16 }

-- {COLUMN} 1.3.6.1.4.1.2356.11.2.33.4.2.1.1.17
lcsSetupVcCllMngrLinesSipPbxPbxEntryLineControlInterval OBJECT-TYPE
    SYNTAX     Integer32 (0..65535)
    MAX-ACCESS read-write
    STATUS     current
    DESCRIPTION
            "-- empty --"
    ::= { lcsSetupVcCllMngrLinesSipPbxPbxEntry 17 }

-- {COLUMN} 1.3.6.1.4.1.2356.11.2.33.4.2.1.1.18
lcsSetupVcCllMngrLinesSipPbxPbxEntryTrusted OBJECT-TYPE
    SYNTAX     INTEGER {
                  eYes (0),
                  eNo (1)
            }
    MAX-ACCESS read-write
    STATUS     current
    DESCRIPTION
            "-- empty --"
    ::= { lcsSetupVcCllMngrLinesSipPbxPbxEntry 18 }

-- {COLUMN} 1.3.6.1.4.1.2356.11.2.33.4.2.1.1.19
lcsSetupVcCllMngrLinesSipPbxPbxEntryPrivacyMethod OBJECT-TYPE
    SYNTAX     INTEGER {
                  eNone (0),
                  eRfc3325 (1),
                  eIetfDraftSipPrivacy04 (2)
            }
    MAX-ACCESS read-write
    STATUS     current
    DESCRIPTION
            "-- empty --"
    ::= { lcsSetupVcCllMngrLinesSipPbxPbxEntry 19 }

-- {COLUMN} 1.3.6.1.4.1.2356.11.2.33.4.2.1.1.20
lcsSetupVcCllMngrLinesSipPbxPbxEntryDtmfMethod OBJECT-TYPE
    SYNTAX     INTEGER {
                  eInband (0),
                  eSipInfo (1),
                  eRtpEvent (2),
                  eRtpEventSipInfo (3)
            }
    MAX-ACCESS read-write
    STATUS     current
    DESCRIPTION
            "-- empty --"
    ::= { lcsSetupVcCllMngrLinesSipPbxPbxEntry 20 }

-- {COLUMN} 1.3.6.1.4.1.2356.11.2.33.4.2.1.1.21
lcsSetupVcCllMngrLinesSipPbxPbxEntryStrictMode OBJECT-TYPE
    SYNTAX     INTEGER {
                  eNo (0),
                  eYes (1)
            }
    MAX-ACCESS read-write
    STATUS     current
    DESCRIPTION
            "-- empty --"
    ::= { lcsSetupVcCllMngrLinesSipPbxPbxEntry 21 }

-- {COLUMN} 1.3.6.1.4.1.2356.11.2.33.4.2.1.1.22
lcsSetupVcCllMngrLinesSipPbxPbxEntryAllowInboundUdpFrom OBJECT-TYPE
    SYNTAX     BITS {
                  eWan (5),
                  eVpn (6),
                  eLan (7)
            }
    MAX-ACCESS read-write
    STATUS     current
    DESCRIPTION
            "-- empty --"
    ::= { lcsSetupVcCllMngrLinesSipPbxPbxEntry 22 }

-- {COLUMN} 1.3.6.1.4.1.2356.11.2.33.4.2.1.1.23
lcsSetupVcCllMngrLinesSipPbxPbxEntryOverlapDialing OBJECT-TYPE
    SYNTAX     INTEGER {
                  eNo (0),
                  eYes (1)
            }
    MAX-ACCESS read-write
    STATUS     current
    DESCRIPTION
            "-- empty --"
    ::= { lcsSetupVcCllMngrLinesSipPbxPbxEntry 23 }

-- {NODE} 1.3.6.1.4.1.2356.11.2.33.4.3
lcsSetupVcCllMngrLinesIsdn OBJECT IDENTIFIER ::= { lcsSetupVcCllMngrLines 3 }

-- {TABLE} 1.3.6.1.4.1.2356.11.2.33.4.3.1
lcsSetupVcCllMngrLinesIsdnInterfacesTable OBJECT-TYPE
    SYNTAX     SEQUENCE OF LcsSetupVcCllMngrLinesIsdnInterfacesEntry
    MAX-ACCESS not-accessible
    STATUS     current
    DESCRIPTION
            "-- empty --"
    ::= { lcsSetupVcCllMngrLinesIsdn 1 }

-- {ROW} 1.3.6.1.4.1.2356.11.2.33.4.3.1.1
lcsSetupVcCllMngrLinesIsdnInterfacesEntry OBJECT-TYPE
    SYNTAX     LcsSetupVcCllMngrLinesIsdnInterfacesEntry
    MAX-ACCESS not-accessible
    STATUS     current
    DESCRIPTION
            ""
    INDEX {
            lcsSetupVcCllMngrLinesIsdnInterfacesEntryName
          }
    ::= { lcsSetupVcCllMngrLinesIsdnInterfacesTable 1 }

LcsSetupVcCllMngrLinesIsdnInterfacesEntry ::= SEQUENCE {
            lcsSetupVcCllMngrLinesIsdnInterfacesEntryName DisplayString,
            lcsSetupVcCllMngrLinesIsdnInterfacesEntryIfc BITS,
            lcsSetupVcCllMngrLinesIsdnInterfacesEntryDomain DisplayString,
            lcsSetupVcCllMngrLinesIsdnInterfacesEntryClnPrefix DisplayString,
            lcsSetupVcCllMngrLinesIsdnInterfacesEntryActive INTEGER,
            lcsSetupVcCllMngrLinesIsdnInterfacesEntryComment DisplayString
    }

-- {COLUMN} 1.3.6.1.4.1.2356.11.2.33.4.3.1.1.1
lcsSetupVcCllMngrLinesIsdnInterfacesEntryName OBJECT-TYPE
    SYNTAX     DisplayString (SIZE(0..16))
    MAX-ACCESS read-write
    STATUS     current
    DESCRIPTION
            "-- empty --"
    ::= { lcsSetupVcCllMngrLinesIsdnInterfacesEntry 1 }

-- {COLUMN} 1.3.6.1.4.1.2356.11.2.33.4.3.1.1.2
lcsSetupVcCllMngrLinesIsdnInterfacesEntryIfc OBJECT-TYPE
    SYNTAX     BITS {
                  eS02 (6),
                  eS01 (7)
            }
    MAX-ACCESS read-write
    STATUS     current
    DESCRIPTION
            "-- empty --"
    ::= { lcsSetupVcCllMngrLinesIsdnInterfacesEntry 2 }

-- {COLUMN} 1.3.6.1.4.1.2356.11.2.33.4.3.1.1.3
lcsSetupVcCllMngrLinesIsdnInterfacesEntryDomain OBJECT-TYPE
    SYNTAX     DisplayString (SIZE(0..63))
    MAX-ACCESS read-write
    STATUS     current
    DESCRIPTION
            "-- empty --"
    ::= { lcsSetupVcCllMngrLinesIsdnInterfacesEntry 3 }

-- {COLUMN} 1.3.6.1.4.1.2356.11.2.33.4.3.1.1.4
lcsSetupVcCllMngrLinesIsdnInterfacesEntryClnPrefix OBJECT-TYPE
    SYNTAX     DisplayString (SIZE(0..9))
    MAX-ACCESS read-write
    STATUS     current
    DESCRIPTION
            "-- empty --"
    ::= { lcsSetupVcCllMngrLinesIsdnInterfacesEntry 4 }

-- {COLUMN} 1.3.6.1.4.1.2356.11.2.33.4.3.1.1.5
lcsSetupVcCllMngrLinesIsdnInterfacesEntryActive OBJECT-TYPE
    SYNTAX     INTEGER {
                  eYes (0),
                  eNo (1)
            }
    MAX-ACCESS read-write
    STATUS     current
    DESCRIPTION
            "-- empty --"
    ::= { lcsSetupVcCllMngrLinesIsdnInterfacesEntry 5 }

-- {COLUMN} 1.3.6.1.4.1.2356.11.2.33.4.3.1.1.6
lcsSetupVcCllMngrLinesIsdnInterfacesEntryComment OBJECT-TYPE
    SYNTAX     DisplayString (SIZE(0..63))
    MAX-ACCESS read-write
    STATUS     current
    DESCRIPTION
            "-- empty --"
    ::= { lcsSetupVcCllMngrLinesIsdnInterfacesEntry 6 }

-- {TABLE} 1.3.6.1.4.1.2356.11.2.33.4.3.2
lcsSetupVcCllMngrLinesIsdnMappingTable OBJECT-TYPE
    SYNTAX     SEQUENCE OF LcsSetupVcCllMngrLinesIsdnMappingEntry
    MAX-ACCESS not-accessible
    STATUS     current
    DESCRIPTION
            "-- empty --"
    ::= { lcsSetupVcCllMngrLinesIsdn 2 }

-- {ROW} 1.3.6.1.4.1.2356.11.2.33.4.3.2.1
lcsSetupVcCllMngrLinesIsdnMappingEntry OBJECT-TYPE
    SYNTAX     LcsSetupVcCllMngrLinesIsdnMappingEntry
    MAX-ACCESS not-accessible
    STATUS     current
    DESCRIPTION
            ""
    INDEX {
            lcsSetupVcCllMngrLinesIsdnMappingEntryMsnDdi,
            lcsSetupVcCllMngrLinesIsdnMappingEntryNumberName
          }
    ::= { lcsSetupVcCllMngrLinesIsdnMappingTable 1 }

LcsSetupVcCllMngrLinesIsdnMappingEntry ::= SEQUENCE {
            lcsSetupVcCllMngrLinesIsdnMappingEntryMsnDdi DisplayString,
            lcsSetupVcCllMngrLinesIsdnMappingEntryIfc BITS,
            lcsSetupVcCllMngrLinesIsdnMappingEntryNumberName DisplayString,
            lcsSetupVcCllMngrLinesIsdnMappingEntryClir INTEGER,
            lcsSetupVcCllMngrLinesIsdnMappingEntryActive INTEGER,
            lcsSetupVcCllMngrLinesIsdnMappingEntryComment DisplayString
    }

-- {COLUMN} 1.3.6.1.4.1.2356.11.2.33.4.3.2.1.1
lcsSetupVcCllMngrLinesIsdnMappingEntryMsnDdi OBJECT-TYPE
    SYNTAX     DisplayString (SIZE(0..19))
    MAX-ACCESS read-write
    STATUS     current
    DESCRIPTION
            "-- empty --"
    ::= { lcsSetupVcCllMngrLinesIsdnMappingEntry 1 }

-- {COLUMN} 1.3.6.1.4.1.2356.11.2.33.4.3.2.1.2
lcsSetupVcCllMngrLinesIsdnMappingEntryIfc OBJECT-TYPE
    SYNTAX     BITS {
                  eS02 (6),
                  eS01 (7)
            }
    MAX-ACCESS read-write
    STATUS     current
    DESCRIPTION
            "-- empty --"
    ::= { lcsSetupVcCllMngrLinesIsdnMappingEntry 2 }

-- {COLUMN} 1.3.6.1.4.1.2356.11.2.33.4.3.2.1.3
lcsSetupVcCllMngrLinesIsdnMappingEntryNumberName OBJECT-TYPE
    SYNTAX     DisplayString (SIZE(0..20))
    MAX-ACCESS read-write
    STATUS     current
    DESCRIPTION
            "-- empty --"
    ::= { lcsSetupVcCllMngrLinesIsdnMappingEntry 3 }

-- {COLUMN} 1.3.6.1.4.1.2356.11.2.33.4.3.2.1.4
lcsSetupVcCllMngrLinesIsdnMappingEntryClir OBJECT-TYPE
    SYNTAX     INTEGER {
                  eNo (0),
                  eYes (1)
            }
    MAX-ACCESS read-write
    STATUS     current
    DESCRIPTION
            "-- empty --"
    ::= { lcsSetupVcCllMngrLinesIsdnMappingEntry 4 }

-- {COLUMN} 1.3.6.1.4.1.2356.11.2.33.4.3.2.1.5
lcsSetupVcCllMngrLinesIsdnMappingEntryActive OBJECT-TYPE
    SYNTAX     INTEGER {
                  eYes (0),
                  eNo (1)
            }
    MAX-ACCESS read-write
    STATUS     current
    DESCRIPTION
            "-- empty --"
    ::= { lcsSetupVcCllMngrLinesIsdnMappingEntry 5 }

-- {COLUMN} 1.3.6.1.4.1.2356.11.2.33.4.3.2.1.6
lcsSetupVcCllMngrLinesIsdnMappingEntryComment OBJECT-TYPE
    SYNTAX     DisplayString (SIZE(0..63))
    MAX-ACCESS read-write
    STATUS     current
    DESCRIPTION
            "-- empty --"
    ::= { lcsSetupVcCllMngrLinesIsdnMappingEntry 6 }

-- {TABLE} 1.3.6.1.4.1.2356.11.2.33.4.4
lcsSetupVcCllMngrLinesPredefDestTable OBJECT-TYPE
    SYNTAX     SEQUENCE OF LcsSetupVcCllMngrLinesPredefDestEntry
    MAX-ACCESS not-accessible
    STATUS     current
    DESCRIPTION
            "-- empty --"
    ::= { lcsSetupVcCllMngrLines 4 }

-- {ROW} 1.3.6.1.4.1.2356.11.2.33.4.4.1
lcsSetupVcCllMngrLinesPredefDestEntry OBJECT-TYPE
    SYNTAX     LcsSetupVcCllMngrLinesPredefDestEntry
    MAX-ACCESS not-accessible
    STATUS     current
    DESCRIPTION
            ""
    INDEX {
            lcsSetupVcCllMngrLinesPredefDestEntryName
          }
    ::= { lcsSetupVcCllMngrLinesPredefDestTable 1 }

LcsSetupVcCllMngrLinesPredefDestEntry ::= SEQUENCE {
            lcsSetupVcCllMngrLinesPredefDestEntryName DisplayString
    }

-- {COLUMN} 1.3.6.1.4.1.2356.11.2.33.4.4.1.1
lcsSetupVcCllMngrLinesPredefDestEntryName OBJECT-TYPE
    SYNTAX     DisplayString (SIZE(0..15))
    MAX-ACCESS read-only
    STATUS     current
    DESCRIPTION
            "-- empty --"
    ::= { lcsSetupVcCllMngrLinesPredefDestEntry 1 }

-- {TABLE} 1.3.6.1.4.1.2356.11.2.33.4.5
lcsSetupVcCllMngrLinesSourceFiltersTable OBJECT-TYPE
    SYNTAX     SEQUENCE OF LcsSetupVcCllMngrLinesSourceFiltersEntry
    MAX-ACCESS not-accessible
    STATUS     current
    DESCRIPTION
            "-- empty --"
    ::= { lcsSetupVcCllMngrLines 5 }

-- {ROW} 1.3.6.1.4.1.2356.11.2.33.4.5.1
lcsSetupVcCllMngrLinesSourceFiltersEntry OBJECT-TYPE
    SYNTAX     LcsSetupVcCllMngrLinesSourceFiltersEntry
    MAX-ACCESS not-accessible
    STATUS     current
    DESCRIPTION
            ""
    INDEX {
            lcsSetupVcCllMngrLinesSourceFiltersEntryName
          }
    ::= { lcsSetupVcCllMngrLinesSourceFiltersTable 1 }

LcsSetupVcCllMngrLinesSourceFiltersEntry ::= SEQUENCE {
            lcsSetupVcCllMngrLinesSourceFiltersEntryName DisplayString
    }

-- {COLUMN} 1.3.6.1.4.1.2356.11.2.33.4.5.1.1
lcsSetupVcCllMngrLinesSourceFiltersEntryName OBJECT-TYPE
    SYNTAX     DisplayString (SIZE(0..15))
    MAX-ACCESS read-only
    STATUS     current
    DESCRIPTION
            "-- empty --"
    ::= { lcsSetupVcCllMngrLinesSourceFiltersEntry 1 }

-- {NODE} 1.3.6.1.4.1.2356.11.2.33.5
lcsSetupVcCllMngrCallRouter OBJECT IDENTIFIER ::= { lcsSetupVcCllMngr 5 }

-- {TABLE} 1.3.6.1.4.1.2356.11.2.33.5.1
lcsSetupVcCllMngrCallRouterCallRoutingTable OBJECT-TYPE
    SYNTAX     SEQUENCE OF LcsSetupVcCllMngrCallRouterCallRoutingEntry
    MAX-ACCESS not-accessible
    STATUS     current
    DESCRIPTION
            "-- empty --"
    ::= { lcsSetupVcCllMngrCallRouter 1 }

-- {ROW} 1.3.6.1.4.1.2356.11.2.33.5.1.1
lcsSetupVcCllMngrCallRouterCallRoutingEntry OBJECT-TYPE
    SYNTAX     LcsSetupVcCllMngrCallRouterCallRoutingEntry
    MAX-ACCESS not-accessible
    STATUS     current
    DESCRIPTION
            ""
    INDEX {
            lcsSetupVcCllMngrCallRouterCallRoutingEntryCalledId,
            lcsSetupVcCllMngrCallRouterCallRoutingEntryCldDomain,
            lcsSetupVcCllMngrCallRouterCallRoutingEntryCallingId,
            lcsSetupVcCllMngrCallRouterCallRoutingEntryClnDomain,
            lcsSetupVcCllMngrCallRouterCallRoutingEntrySrcLine
          }
    ::= { lcsSetupVcCllMngrCallRouterCallRoutingTable 1 }

LcsSetupVcCllMngrCallRouterCallRoutingEntry ::= SEQUENCE {
            lcsSetupVcCllMngrCallRouterCallRoutingEntryCalledId DisplayString,
            lcsSetupVcCllMngrCallRouterCallRoutingEntryCldDomain DisplayString,
            lcsSetupVcCllMngrCallRouterCallRoutingEntryCallingId DisplayString,
            lcsSetupVcCllMngrCallRouterCallRoutingEntryClnDomain DisplayString,
            lcsSetupVcCllMngrCallRouterCallRoutingEntrySrcLine DisplayString,
            lcsSetupVcCllMngrCallRouterCallRoutingEntryDestId1 DisplayString,
            lcsSetupVcCllMngrCallRouterCallRoutingEntryDestLine1 DisplayString,
            lcsSetupVcCllMngrCallRouterCallRoutingEntryActive INTEGER,
            lcsSetupVcCllMngrCallRouterCallRoutingEntryComment DisplayString,
            lcsSetupVcCllMngrCallRouterCallRoutingEntryDestId2 DisplayString,
            lcsSetupVcCllMngrCallRouterCallRoutingEntryDestLine2 DisplayString,
            lcsSetupVcCllMngrCallRouterCallRoutingEntryDestId3 DisplayString,
            lcsSetupVcCllMngrCallRouterCallRoutingEntryDestLine3 DisplayString,
            lcsSetupVcCllMngrCallRouterCallRoutingEntryPrio Integer32,
            lcsSetupVcCllMngrCallRouterCallRoutingEntryDestCallingId DisplayString
    }

-- {COLUMN} 1.3.6.1.4.1.2356.11.2.33.5.1.1.1
lcsSetupVcCllMngrCallRouterCallRoutingEntryCalledId OBJECT-TYPE
    SYNTAX     DisplayString (SIZE(0..19))
    MAX-ACCESS read-write
    STATUS     current
    DESCRIPTION
            "-- empty --"
    ::= { lcsSetupVcCllMngrCallRouterCallRoutingEntry 1 }

-- {COLUMN} 1.3.6.1.4.1.2356.11.2.33.5.1.1.2
lcsSetupVcCllMngrCallRouterCallRoutingEntryCldDomain OBJECT-TYPE
    SYNTAX     DisplayString (SIZE(0..63))
    MAX-ACCESS read-write
    STATUS     current
    DESCRIPTION
            "-- empty --"
    ::= { lcsSetupVcCllMngrCallRouterCallRoutingEntry 2 }

-- {COLUMN} 1.3.6.1.4.1.2356.11.2.33.5.1.1.3
lcsSetupVcCllMngrCallRouterCallRoutingEntryCallingId OBJECT-TYPE
    SYNTAX     DisplayString (SIZE(0..19))
    MAX-ACCESS read-write
    STATUS     current
    DESCRIPTION
            "-- empty --"
    ::= { lcsSetupVcCllMngrCallRouterCallRoutingEntry 3 }

-- {COLUMN} 1.3.6.1.4.1.2356.11.2.33.5.1.1.4
lcsSetupVcCllMngrCallRouterCallRoutingEntryClnDomain OBJECT-TYPE
    SYNTAX     DisplayString (SIZE(0..63))
    MAX-ACCESS read-write
    STATUS     current
    DESCRIPTION
            "-- empty --"
    ::= { lcsSetupVcCllMngrCallRouterCallRoutingEntry 4 }

-- {COLUMN} 1.3.6.1.4.1.2356.11.2.33.5.1.1.5
lcsSetupVcCllMngrCallRouterCallRoutingEntrySrcLine OBJECT-TYPE
    SYNTAX     DisplayString (SIZE(0..32))
    MAX-ACCESS read-write
    STATUS     current
    DESCRIPTION
            "-- empty --"
    ::= { lcsSetupVcCllMngrCallRouterCallRoutingEntry 5 }

-- {COLUMN} 1.3.6.1.4.1.2356.11.2.33.5.1.1.7
lcsSetupVcCllMngrCallRouterCallRoutingEntryDestId1 OBJECT-TYPE
    SYNTAX     DisplayString (SIZE(0..38))
    MAX-ACCESS read-write
    STATUS     current
    DESCRIPTION
            "-- empty --"
    ::= { lcsSetupVcCllMngrCallRouterCallRoutingEntry 7 }

-- {COLUMN} 1.3.6.1.4.1.2356.11.2.33.5.1.1.8
lcsSetupVcCllMngrCallRouterCallRoutingEntryDestLine1 OBJECT-TYPE
    SYNTAX     DisplayString (SIZE(0..32))
    MAX-ACCESS read-write
    STATUS     current
    DESCRIPTION
            "-- empty --"
    ::= { lcsSetupVcCllMngrCallRouterCallRoutingEntry 8 }

-- {COLUMN} 1.3.6.1.4.1.2356.11.2.33.5.1.1.9
lcsSetupVcCllMngrCallRouterCallRoutingEntryActive OBJECT-TYPE
    SYNTAX     INTEGER {
                  eYes (0),
                  eDefault (1),
                  eNo (2)
            }
    MAX-ACCESS read-write
    STATUS     current
    DESCRIPTION
            "-- empty --"
    ::= { lcsSetupVcCllMngrCallRouterCallRoutingEntry 9 }

-- {COLUMN} 1.3.6.1.4.1.2356.11.2.33.5.1.1.10
lcsSetupVcCllMngrCallRouterCallRoutingEntryComment OBJECT-TYPE
    SYNTAX     DisplayString (SIZE(0..63))
    MAX-ACCESS read-write
    STATUS     current
    DESCRIPTION
            "-- empty --"
    ::= { lcsSetupVcCllMngrCallRouterCallRoutingEntry 10 }

-- {COLUMN} 1.3.6.1.4.1.2356.11.2.33.5.1.1.11
lcsSetupVcCllMngrCallRouterCallRoutingEntryDestId2 OBJECT-TYPE
    SYNTAX     DisplayString (SIZE(0..19))
    MAX-ACCESS read-write
    STATUS     current
    DESCRIPTION
            "-- empty --"
    ::= { lcsSetupVcCllMngrCallRouterCallRoutingEntry 11 }

-- {COLUMN} 1.3.6.1.4.1.2356.11.2.33.5.1.1.12
lcsSetupVcCllMngrCallRouterCallRoutingEntryDestLine2 OBJECT-TYPE
    SYNTAX     DisplayString (SIZE(0..32))
    MAX-ACCESS read-write
    STATUS     current
    DESCRIPTION
            "-- empty --"
    ::= { lcsSetupVcCllMngrCallRouterCallRoutingEntry 12 }

-- {COLUMN} 1.3.6.1.4.1.2356.11.2.33.5.1.1.13
lcsSetupVcCllMngrCallRouterCallRoutingEntryDestId3 OBJECT-TYPE
    SYNTAX     DisplayString (SIZE(0..19))
    MAX-ACCESS read-write
    STATUS     current
    DESCRIPTION
            "-- empty --"
    ::= { lcsSetupVcCllMngrCallRouterCallRoutingEntry 13 }

-- {COLUMN} 1.3.6.1.4.1.2356.11.2.33.5.1.1.14
lcsSetupVcCllMngrCallRouterCallRoutingEntryDestLine3 OBJECT-TYPE
    SYNTAX     DisplayString (SIZE(0..32))
    MAX-ACCESS read-write
    STATUS     current
    DESCRIPTION
            "-- empty --"
    ::= { lcsSetupVcCllMngrCallRouterCallRoutingEntry 14 }

-- {COLUMN} 1.3.6.1.4.1.2356.11.2.33.5.1.1.15
lcsSetupVcCllMngrCallRouterCallRoutingEntryPrio OBJECT-TYPE
    SYNTAX     Integer32 (0..255)
    MAX-ACCESS read-write
    STATUS     current
    DESCRIPTION
            "-- empty --"
    ::= { lcsSetupVcCllMngrCallRouterCallRoutingEntry 15 }

-- {COLUMN} 1.3.6.1.4.1.2356.11.2.33.5.1.1.16
lcsSetupVcCllMngrCallRouterCallRoutingEntryDestCallingId OBJECT-TYPE
    SYNTAX     DisplayString (SIZE(0..38))
    MAX-ACCESS read-write
    STATUS     current
    DESCRIPTION
            "-- empty --"
    ::= { lcsSetupVcCllMngrCallRouterCallRoutingEntry 16 }

-- {NODE} 1.3.6.1.4.1.2356.11.2.33.7
lcsSetupVcCllMngrGroups OBJECT IDENTIFIER ::= { lcsSetupVcCllMngr 7 }

-- {TABLE} 1.3.6.1.4.1.2356.11.2.33.7.1
lcsSetupVcCllMngrGroupsGroupsTable OBJECT-TYPE
    SYNTAX     SEQUENCE OF LcsSetupVcCllMngrGroupsGroupsEntry
    MAX-ACCESS not-accessible
    STATUS     current
    DESCRIPTION
            "-- empty --"
    ::= { lcsSetupVcCllMngrGroups 1 }

-- {ROW} 1.3.6.1.4.1.2356.11.2.33.7.1.1
lcsSetupVcCllMngrGroupsGroupsEntry OBJECT-TYPE
    SYNTAX     LcsSetupVcCllMngrGroupsGroupsEntry
    MAX-ACCESS not-accessible
    STATUS     current
    DESCRIPTION
            ""
    INDEX {
            lcsSetupVcCllMngrGroupsGroupsEntryName
          }
    ::= { lcsSetupVcCllMngrGroupsGroupsTable 1 }

LcsSetupVcCllMngrGroupsGroupsEntry ::= SEQUENCE {
            lcsSetupVcCllMngrGroupsGroupsEntryName DisplayString,
            lcsSetupVcCllMngrGroupsGroupsEntryMembers DisplayString,
            lcsSetupVcCllMngrGroupsGroupsEntryDistributionMethod INTEGER,
            lcsSetupVcCllMngrGroupsGroupsEntryForwardingTime Integer32,
            lcsSetupVcCllMngrGroupsGroupsEntryForwardingTarget DisplayString,
            lcsSetupVcCllMngrGroupsGroupsEntryActive INTEGER,
            lcsSetupVcCllMngrGroupsGroupsEntryComment DisplayString
    }

-- {COLUMN} 1.3.6.1.4.1.2356.11.2.33.7.1.1.1
lcsSetupVcCllMngrGroupsGroupsEntryName OBJECT-TYPE
    SYNTAX     DisplayString (SIZE(0..64))
    MAX-ACCESS read-write
    STATUS     current
    DESCRIPTION
            "-- empty --"
    ::= { lcsSetupVcCllMngrGroupsGroupsEntry 1 }

-- {COLUMN} 1.3.6.1.4.1.2356.11.2.33.7.1.1.2
lcsSetupVcCllMngrGroupsGroupsEntryMembers OBJECT-TYPE
    SYNTAX     DisplayString (SIZE(0..128))
    MAX-ACCESS read-write
    STATUS     current
    DESCRIPTION
            "-- empty --"
    ::= { lcsSetupVcCllMngrGroupsGroupsEntry 2 }

-- {COLUMN} 1.3.6.1.4.1.2356.11.2.33.7.1.1.3
lcsSetupVcCllMngrGroupsGroupsEntryDistributionMethod OBJECT-TYPE
    SYNTAX     INTEGER {
                  eSimultaneous (0),
                  eSequential (1)
            }
    MAX-ACCESS read-write
    STATUS     current
    DESCRIPTION
            "-- empty --"
    ::= { lcsSetupVcCllMngrGroupsGroupsEntry 3 }

-- {COLUMN} 1.3.6.1.4.1.2356.11.2.33.7.1.1.4
lcsSetupVcCllMngrGroupsGroupsEntryForwardingTime OBJECT-TYPE
    SYNTAX     Integer32 (0..255)
    MAX-ACCESS read-write
    STATUS     current
    DESCRIPTION
            "-- empty --"
    ::= { lcsSetupVcCllMngrGroupsGroupsEntry 4 }

-- {COLUMN} 1.3.6.1.4.1.2356.11.2.33.7.1.1.5
lcsSetupVcCllMngrGroupsGroupsEntryForwardingTarget OBJECT-TYPE
    SYNTAX     DisplayString (SIZE(0..64))
    MAX-ACCESS read-write
    STATUS     current
    DESCRIPTION
            "-- empty --"
    ::= { lcsSetupVcCllMngrGroupsGroupsEntry 5 }

-- {COLUMN} 1.3.6.1.4.1.2356.11.2.33.7.1.1.6
lcsSetupVcCllMngrGroupsGroupsEntryActive OBJECT-TYPE
    SYNTAX     INTEGER {
                  eYes (0),
                  eNo (1)
            }
    MAX-ACCESS read-write
    STATUS     current
    DESCRIPTION
            "-- empty --"
    ::= { lcsSetupVcCllMngrGroupsGroupsEntry 6 }

-- {COLUMN} 1.3.6.1.4.1.2356.11.2.33.7.1.1.7
lcsSetupVcCllMngrGroupsGroupsEntryComment OBJECT-TYPE
    SYNTAX     DisplayString (SIZE(0..63))
    MAX-ACCESS read-write
    STATUS     current
    DESCRIPTION
            "-- empty --"
    ::= { lcsSetupVcCllMngrGroupsGroupsEntry 7 }

-- {NODE} 1.3.6.1.4.1.2356.11.2.33.8
lcsSetupVcCllMngrLogging OBJECT IDENTIFIER ::= { lcsSetupVcCllMngr 8 }

-- {NODE} 1.3.6.1.4.1.2356.11.2.33.8.1
lcsSetupVcCllMngrLoggingCallDataRecords OBJECT IDENTIFIER ::= { lcsSetupVcCllMngrLogging 1 }

-- {SCALAR} 1.3.6.1.4.1.2356.11.2.33.8.1.1
lcsSetupVcCllMngrLoggingCallDataRecordsEMailNotification OBJECT-TYPE
    SYNTAX     INTEGER {
                  eNo (0),
                  eYes (1)
            }
    MAX-ACCESS read-write
    STATUS     current
    DESCRIPTION
            "-- empty --"
    ::= { lcsSetupVcCllMngrLoggingCallDataRecords 1 }

-- {SCALAR} 1.3.6.1.4.1.2356.11.2.33.8.1.2
lcsSetupVcCllMngrLoggingCallDataRecordsEMailAddress OBJECT-TYPE
    SYNTAX     DisplayString (SIZE(0..63))
    MAX-ACCESS read-write
    STATUS     current
    DESCRIPTION
            "-- empty --"
    ::= { lcsSetupVcCllMngrLoggingCallDataRecords 2 }

-- {SCALAR} 1.3.6.1.4.1.2356.11.2.33.8.1.3
lcsSetupVcCllMngrLoggingCallDataRecordsSyslog OBJECT-TYPE
    SYNTAX     INTEGER {
                  eNo (0),
                  eYes (1)
            }
    MAX-ACCESS read-write
    STATUS     current
    DESCRIPTION
            "-- empty --"
    ::= { lcsSetupVcCllMngrLoggingCallDataRecords 3 }

-- {NODE} 1.3.6.1.4.1.2356.11.2.33.10
lcsSetupVcCllMngrDect OBJECT IDENTIFIER ::= { lcsSetupVcCllMngr 10 }

-- {TABLE} 1.3.6.1.4.1.2356.11.2.33.10.1
lcsSetupVcCllMngrDectBasestationsTable OBJECT-TYPE
    SYNTAX     SEQUENCE OF LcsSetupVcCllMngrDectBasestationsEntry
    MAX-ACCESS not-accessible
    STATUS     current
    DESCRIPTION
            "-- empty --"
    ::= { lcsSetupVcCllMngrDect 1 }

-- {ROW} 1.3.6.1.4.1.2356.11.2.33.10.1.1
lcsSetupVcCllMngrDectBasestationsEntry OBJECT-TYPE
    SYNTAX     LcsSetupVcCllMngrDectBasestationsEntry
    MAX-ACCESS not-accessible
    STATUS     current
    DESCRIPTION
            ""
    INDEX {
            lcsSetupVcCllMngrDectBasestationsEntryName
          }
    ::= { lcsSetupVcCllMngrDectBasestationsTable 1 }

LcsSetupVcCllMngrDectBasestationsEntry ::= SEQUENCE {
            lcsSetupVcCllMngrDectBasestationsEntryName DisplayString,
            lcsSetupVcCllMngrDectBasestationsEntryMacAddress MacAddress,
            lcsSetupVcCllMngrDectBasestationsEntryRoutingTag Integer32,
            lcsSetupVcCllMngrDectBasestationsEntryRemoteConfiguration INTEGER
    }

-- {COLUMN} 1.3.6.1.4.1.2356.11.2.33.10.1.1.1
lcsSetupVcCllMngrDectBasestationsEntryName OBJECT-TYPE
    SYNTAX     DisplayString (SIZE(0..15))
    MAX-ACCESS read-write
    STATUS     current
    DESCRIPTION
            "-- empty --"
    ::= { lcsSetupVcCllMngrDectBasestationsEntry 1 }

-- {COLUMN} 1.3.6.1.4.1.2356.11.2.33.10.1.1.2
lcsSetupVcCllMngrDectBasestationsEntryMacAddress OBJECT-TYPE
    SYNTAX     MacAddress
    MAX-ACCESS read-write
    STATUS     current
    DESCRIPTION
            "-- empty --"
    ::= { lcsSetupVcCllMngrDectBasestationsEntry 2 }

-- {COLUMN} 1.3.6.1.4.1.2356.11.2.33.10.1.1.4
lcsSetupVcCllMngrDectBasestationsEntryRoutingTag OBJECT-TYPE
    SYNTAX     Integer32 (0..2147483647)
    MAX-ACCESS read-write
    STATUS     current
    DESCRIPTION
            "-- empty --"
    ::= { lcsSetupVcCllMngrDectBasestationsEntry 4 }

-- {COLUMN} 1.3.6.1.4.1.2356.11.2.33.10.1.1.5
lcsSetupVcCllMngrDectBasestationsEntryRemoteConfiguration OBJECT-TYPE
    SYNTAX     INTEGER {
                  eNo (0),
                  eYes (1)
            }
    MAX-ACCESS read-write
    STATUS     current
    DESCRIPTION
            "-- empty --"
    ::= { lcsSetupVcCllMngrDectBasestationsEntry 5 }

-- {TABLE} 1.3.6.1.4.1.2356.11.2.33.10.2
lcsSetupVcCllMngrDectHandsetsTable OBJECT-TYPE
    SYNTAX     SEQUENCE OF LcsSetupVcCllMngrDectHandsetsEntry
    MAX-ACCESS not-accessible
    STATUS     current
    DESCRIPTION
            "-- empty --"
    ::= { lcsSetupVcCllMngrDect 2 }

-- {ROW} 1.3.6.1.4.1.2356.11.2.33.10.2.1
lcsSetupVcCllMngrDectHandsetsEntry OBJECT-TYPE
    SYNTAX     LcsSetupVcCllMngrDectHandsetsEntry
    MAX-ACCESS not-accessible
    STATUS     current
    DESCRIPTION
            ""
    INDEX {
            lcsSetupVcCllMngrDectHandsetsEntryBasestationName,
            lcsSetupVcCllMngrDectHandsetsEntryIndex
          }
    ::= { lcsSetupVcCllMngrDectHandsetsTable 1 }

LcsSetupVcCllMngrDectHandsetsEntry ::= SEQUENCE {
            lcsSetupVcCllMngrDectHandsetsEntryBasestationName DisplayString,
            lcsSetupVcCllMngrDectHandsetsEntryIndex Integer32,
            lcsSetupVcCllMngrDectHandsetsEntrySipUser DisplayString,
            lcsSetupVcCllMngrDectHandsetsEntryHandsetName DisplayString,
            lcsSetupVcCllMngrDectHandsetsEntryDisplayName DisplayString,
            lcsSetupVcCllMngrDectHandsetsEntryVoiceMailbox DisplayString
    }

-- {COLUMN} 1.3.6.1.4.1.2356.11.2.33.10.2.1.1
lcsSetupVcCllMngrDectHandsetsEntryBasestationName OBJECT-TYPE
    SYNTAX     DisplayString (SIZE(0..15))
    MAX-ACCESS read-write
    STATUS     current
    DESCRIPTION
            "-- empty --"
    ::= { lcsSetupVcCllMngrDectHandsetsEntry 1 }

-- {COLUMN} 1.3.6.1.4.1.2356.11.2.33.10.2.1.2
lcsSetupVcCllMngrDectHandsetsEntryIndex OBJECT-TYPE
    SYNTAX     Integer32 (0..2147483647)
    MAX-ACCESS read-write
    STATUS     current
    DESCRIPTION
            "-- empty --"
    ::= { lcsSetupVcCllMngrDectHandsetsEntry 2 }

-- {COLUMN} 1.3.6.1.4.1.2356.11.2.33.10.2.1.3
lcsSetupVcCllMngrDectHandsetsEntrySipUser OBJECT-TYPE
    SYNTAX     DisplayString (SIZE(0..20))
    MAX-ACCESS read-write
    STATUS     current
    DESCRIPTION
            "-- empty --"
    ::= { lcsSetupVcCllMngrDectHandsetsEntry 3 }

-- {COLUMN} 1.3.6.1.4.1.2356.11.2.33.10.2.1.4
lcsSetupVcCllMngrDectHandsetsEntryHandsetName OBJECT-TYPE
    SYNTAX     DisplayString (SIZE(0..10))
    MAX-ACCESS read-write
    STATUS     current
    DESCRIPTION
            "-- empty --"
    ::= { lcsSetupVcCllMngrDectHandsetsEntry 4 }

-- {COLUMN} 1.3.6.1.4.1.2356.11.2.33.10.2.1.5
lcsSetupVcCllMngrDectHandsetsEntryDisplayName OBJECT-TYPE
    SYNTAX     DisplayString (SIZE(0..32))
    MAX-ACCESS read-write
    STATUS     current
    DESCRIPTION
            "-- empty --"
    ::= { lcsSetupVcCllMngrDectHandsetsEntry 5 }

-- {COLUMN} 1.3.6.1.4.1.2356.11.2.33.10.2.1.6
lcsSetupVcCllMngrDectHandsetsEntryVoiceMailbox OBJECT-TYPE
    SYNTAX     DisplayString (SIZE(0..20))
    MAX-ACCESS read-write
    STATUS     current
    DESCRIPTION
            "-- empty --"
    ::= { lcsSetupVcCllMngrDectHandsetsEntry 6 }

-- {NODE} 1.3.6.1.4.1.2356.11.2.33.11
lcsSetupVcCllMngrSipServer OBJECT IDENTIFIER ::= { lcsSetupVcCllMngr 11 }

-- {NODE} 1.3.6.1.4.1.2356.11.2.33.11.1
lcsSetupVcCllMngrSipServerTlsServer OBJECT IDENTIFIER ::= { lcsSetupVcCllMngrSipServer 1 }

-- {SCALAR} 1.3.6.1.4.1.2356.11.2.33.11.1.1
lcsSetupVcCllMngrSipServerTlsServerOperating OBJECT-TYPE
    SYNTAX     INTEGER {
                  eNo (0),
                  eYes (1)
            }
    MAX-ACCESS read-write
    STATUS     current
    DESCRIPTION
            "-- empty --"
    ::= { lcsSetupVcCllMngrSipServerTlsServer 1 }

-- {SCALAR} 1.3.6.1.4.1.2356.11.2.33.11.1.2
lcsSetupVcCllMngrSipServerTlsServerPort OBJECT-TYPE
    SYNTAX     Integer32 (0..65535)
    MAX-ACCESS read-write
    STATUS     current
    DESCRIPTION
            "-- empty --"
    ::= { lcsSetupVcCllMngrSipServerTlsServer 2 }

-- {SCALAR} 1.3.6.1.4.1.2356.11.2.33.11.1.10
lcsSetupVcCllMngrSipServerTlsServerVersions OBJECT-TYPE
    SYNTAX     BITS {
                  eTlsv12 (28),
                  eTlsv11 (29),
                  eTlsv1 (30)
            }
    MAX-ACCESS read-write
    STATUS     current
    DESCRIPTION
            "-- empty --"
    ::= { lcsSetupVcCllMngrSipServerTlsServer 10 }

-- {SCALAR} 1.3.6.1.4.1.2356.11.2.33.11.1.11
lcsSetupVcCllMngrSipServerTlsServerKeyexAlgorithms OBJECT-TYPE
    SYNTAX     BITS {
                  eEcdhe (27),
                  eDhe (29),
                  eRsa (31)
            }
    MAX-ACCESS read-write
    STATUS     current
    DESCRIPTION
            "-- empty --"
    ::= { lcsSetupVcCllMngrSipServerTlsServer 11 }

-- {SCALAR} 1.3.6.1.4.1.2356.11.2.33.11.1.12
lcsSetupVcCllMngrSipServerTlsServerCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupVcCllMngrSipServerTlsServer 12 }

-- {SCALAR} 1.3.6.1.4.1.2356.11.2.33.11.1.13
lcsSetupVcCllMngrSipServerTlsServerHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupVcCllMngrSipServerTlsServer 13 }

-- {SCALAR} 1.3.6.1.4.1.2356.11.2.33.11.1.14
lcsSetupVcCllMngrSipServerTlsServerPreferPfs OBJECT-TYPE
    SYNTAX     BITS {
                  eNo (0),
                  eYes (7)
            }
    MAX-ACCESS read-write
    STATUS     current
    DESCRIPTION
            "-- empty --"
    ::= { lcsSetupVcCllMngrSipServerTlsServer 14 }

-- {SCALAR} 1.3.6.1.4.1.2356.11.2.33.11.1.15
lcsSetupVcCllMngrSipServerTlsServerRenegotiations OBJECT-TYPE
    SYNTAX     INTEGER {
                  eForbidden (0),
                  eAllowed (1),
                  eIgnored (2)
            }
    MAX-ACCESS read-write
    STATUS     current
    DESCRIPTION
            "-- empty --"
    ::= { lcsSetupVcCllMngrSipServerTlsServer 15 }

-- {SCALAR} 1.3.6.1.4.1.2356.11.2.33.11.1.16
lcsSetupVcCllMngrSipServerTlsServerEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupVcCllMngrSipServerTlsServer 16 }

-- {SCALAR} 1.3.6.1.4.1.2356.11.2.33.11.1.30
lcsSetupVcCllMngrSipServerTlsServerSigHashAlgs OBJECT-TYPE
    SYNTAX     BITS {
                  eSha512Ecdsa (20),
                  eSha384Ecdsa (21),
                  eSha256Ecdsa (22),
                  eSha224Ecdsa (23),
                  eSha1Ecdsa (24),
                  eSha512Rsa (26),
                  eSha384Rsa (27),
                  eSha256Rsa (28),
                  eSha224Rsa (29),
                  eSha1Rsa (30)
            }
    MAX-ACCESS read-write
    STATUS     current
    DESCRIPTION
            "list of allowed signature/hash algorithms"
    ::= { lcsSetupVcCllMngrSipServerTlsServer 30 }

-- {SCALAR} 1.3.6.1.4.1.2356.11.2.33.11.2
lcsSetupVcCllMngrSipServerUdpServerOperating OBJECT-TYPE
    SYNTAX     INTEGER {
                  eNo (0),
                  eYes (1)
            }
    MAX-ACCESS read-write
    STATUS     current
    DESCRIPTION
            "-- empty --"
    ::= { lcsSetupVcCllMngrSipServer 2 }

-- {SCALAR} 1.3.6.1.4.1.2356.11.2.33.11.3
lcsSetupVcCllMngrSipServerUdpServerPort OBJECT-TYPE
    SYNTAX     Integer32 (0..65535)
    MAX-ACCESS read-write
    STATUS     current
    DESCRIPTION
            "-- empty --"
    ::= { lcsSetupVcCllMngrSipServer 3 }

-- {SCALAR} 1.3.6.1.4.1.2356.11.2.33.11.4
lcsSetupVcCllMngrSipServerTcpServerOperating OBJECT-TYPE
    SYNTAX     INTEGER {
                  eNo (0),
                  eYes (1)
            }
    MAX-ACCESS read-write
    STATUS     current
    DESCRIPTION
            "-- empty --"
    ::= { lcsSetupVcCllMngrSipServer 4 }

-- {SCALAR} 1.3.6.1.4.1.2356.11.2.33.11.5
lcsSetupVcCllMngrSipServerTcpServerPort OBJECT-TYPE
    SYNTAX     Integer32 (0..65535)
    MAX-ACCESS read-write
    STATUS     current
    DESCRIPTION
            "-- empty --"
    ::= { lcsSetupVcCllMngrSipServer 5 }

-- {NODE} 1.3.6.1.4.1.2356.11.2.33.12
lcsSetupVcCllMngrCallHandling OBJECT IDENTIFIER ::= { lcsSetupVcCllMngr 12 }

-- {TABLE} 1.3.6.1.4.1.2356.11.2.33.12.1
lcsSetupVcCllMngrCallHandlingPreferredNumbersTable OBJECT-TYPE
    SYNTAX     SEQUENCE OF LcsSetupVcCllMngrCallHandlingPreferredNumbersEntry
    MAX-ACCESS not-accessible
    STATUS     current
    DESCRIPTION
            "-- empty --"
    ::= { lcsSetupVcCllMngrCallHandling 1 }

-- {ROW} 1.3.6.1.4.1.2356.11.2.33.12.1.1
lcsSetupVcCllMngrCallHandlingPreferredNumbersEntry OBJECT-TYPE
    SYNTAX     LcsSetupVcCllMngrCallHandlingPreferredNumbersEntry
    MAX-ACCESS not-accessible
    STATUS     current
    DESCRIPTION
            ""
    INDEX {
            lcsSetupVcCllMngrCallHandlingPreferredNumbersEntryCalledNumber
          }
    ::= { lcsSetupVcCllMngrCallHandlingPreferredNumbersTable 1 }

LcsSetupVcCllMngrCallHandlingPreferredNumbersEntry ::= SEQUENCE {
            lcsSetupVcCllMngrCallHandlingPreferredNumbersEntryCalledNumber DisplayString,
            lcsSetupVcCllMngrCallHandlingPreferredNumbersEntryType INTEGER,
            lcsSetupVcCllMngrCallHandlingPreferredNumbersEntryComment DisplayString
    }

-- {COLUMN} 1.3.6.1.4.1.2356.11.2.33.12.1.1.1
lcsSetupVcCllMngrCallHandlingPreferredNumbersEntryCalledNumber OBJECT-TYPE
    SYNTAX     DisplayString (SIZE(0..19))
    MAX-ACCESS read-write
    STATUS     current
    DESCRIPTION
            "-- empty --"
    ::= { lcsSetupVcCllMngrCallHandlingPreferredNumbersEntry 1 }

-- {COLUMN} 1.3.6.1.4.1.2356.11.2.33.12.1.1.2
lcsSetupVcCllMngrCallHandlingPreferredNumbersEntryType OBJECT-TYPE
    SYNTAX     INTEGER {
                  eEmergency (0),
                  ePrivate (1)
            }
    MAX-ACCESS read-write
    STATUS     current
    DESCRIPTION
            "-- empty --"
    ::= { lcsSetupVcCllMngrCallHandlingPreferredNumbersEntry 2 }

-- {COLUMN} 1.3.6.1.4.1.2356.11.2.33.12.1.1.4
lcsSetupVcCllMngrCallHandlingPreferredNumbersEntryComment OBJECT-TYPE
    SYNTAX     DisplayString (SIZE(0..63))
    MAX-ACCESS read-write
    STATUS     current
    DESCRIPTION
            "-- empty --"
    ::= { lcsSetupVcCllMngrCallHandlingPreferredNumbersEntry 4 }

-- {SCALAR} 1.3.6.1.4.1.2356.11.2.33.12.2
lcsSetupVcCllMngrCallHandlingRtpThreshold OBJECT-TYPE
    SYNTAX     Integer32 (0..2147483647)
    MAX-ACCESS read-write
    STATUS     current
    DESCRIPTION
            "-- empty --"
    ::= { lcsSetupVcCllMngrCallHandling 2 }

-- {NODE} 1.3.6.1.4.1.2356.11.2.34
lcsSetupPrinter OBJECT IDENTIFIER ::= { lcsSetup 34 }

-- {TABLE} 1.3.6.1.4.1.2356.11.2.34.1
lcsSetupPrinterPrinterTable OBJECT-TYPE
    SYNTAX     SEQUENCE OF LcsSetupPrinterPrinterEntry
    MAX-ACCESS not-accessible
    STATUS     current
    DESCRIPTION
            ""
    ::= { lcsSetupPrinter 1 }

-- {ROW} 1.3.6.1.4.1.2356.11.2.34.1.1
lcsSetupPrinterPrinterEntry OBJECT-TYPE
    SYNTAX     LcsSetupPrinterPrinterEntry
    MAX-ACCESS not-accessible
    STATUS     current
    DESCRIPTION
            ""
    INDEX {
            lcsSetupPrinterPrinterEntryPrinter
          }
    ::= { lcsSetupPrinterPrinterTable 1 }

LcsSetupPrinterPrinterEntry ::= SEQUENCE {
            lcsSetupPrinterPrinterEntryPrinter DisplayString,
            lcsSetupPrinterPrinterEntryRawipPort Integer32,
            lcsSetupPrinterPrinterEntryLpdPort Integer32,
            lcsSetupPrinterPrinterEntryActiv INTEGER,
            lcsSetupPrinterPrinterEntryBidirectional INTEGER,
            lcsSetupPrinterPrinterEntryResetOnOpen INTEGER
    }

-- {COLUMN} 1.3.6.1.4.1.2356.11.2.34.1.1.1
lcsSetupPrinterPrinterEntryPrinter OBJECT-TYPE
    SYNTAX     DisplayString (SIZE(0..15))
    MAX-ACCESS read-write
    STATUS     current
    DESCRIPTION
            ""
    ::= { lcsSetupPrinterPrinterEntry 1 }

-- {COLUMN} 1.3.6.1.4.1.2356.11.2.34.1.1.2
lcsSetupPrinterPrinterEntryRawipPort OBJECT-TYPE
    SYNTAX     Integer32 (0..2147483647)
    MAX-ACCESS read-write
    STATUS     current
    DESCRIPTION
            ""
    ::= { lcsSetupPrinterPrinterEntry 2 }

-- {COLUMN} 1.3.6.1.4.1.2356.11.2.34.1.1.3
lcsSetupPrinterPrinterEntryLpdPort OBJECT-TYPE
    SYNTAX     Integer32 (0..2147483647)
    MAX-ACCESS read-write
    STATUS     current
    DESCRIPTION
            ""
    ::= { lcsSetupPrinterPrinterEntry 3 }

-- {COLUMN} 1.3.6.1.4.1.2356.11.2.34.1.1.4
lcsSetupPrinterPrinterEntryActiv OBJECT-TYPE
    SYNTAX     INTEGER {
                  eNo (0),
                  eYes (1)
            }
    MAX-ACCESS read-write
    STATUS     current
    DESCRIPTION
            ""
    ::= { lcsSetupPrinterPrinterEntry 4 }

-- {COLUMN} 1.3.6.1.4.1.2356.11.2.34.1.1.5
lcsSetupPrinterPrinterEntryBidirectional OBJECT-TYPE
    SYNTAX     INTEGER {
                  eNo (0),
                  eYes (1)
            }
    MAX-ACCESS read-write
    STATUS     current
    DESCRIPTION
            ""
    ::= { lcsSetupPrinterPrinterEntry 5 }

-- {COLUMN} 1.3.6.1.4.1.2356.11.2.34.1.1.6
lcsSetupPrinterPrinterEntryResetOnOpen OBJECT-TYPE
    SYNTAX     INTEGER {
                  eNo (0),
                  eYes (1)
            }
    MAX-ACCESS read-write
    STATUS     current
    DESCRIPTION
            ""
    ::= { lcsSetupPrinterPrinterEntry 6 }

-- {TABLE} 1.3.6.1.4.1.2356.11.2.34.2
lcsSetupPrinterAccessListTable OBJECT-TYPE
    SYNTAX     SEQUENCE OF LcsSetupPrinterAccessListEntry
    MAX-ACCESS not-accessible
    STATUS     current
    DESCRIPTION
            ""
    ::= { lcsSetupPrinter 2 }

-- {ROW} 1.3.6.1.4.1.2356.11.2.34.2.1
lcsSetupPrinterAccessListEntry OBJECT-TYPE
    SYNTAX     LcsSetupPrinterAccessListEntry
    MAX-ACCESS not-accessible
    STATUS     current
    DESCRIPTION
            ""
    INDEX {
            lcsSetupPrinterAccessListEntryIpAddress,
            lcsSetupPrinterAccessListEntryIpNetmask,
            lcsSetupPrinterAccessListEntryRtgTag
          }
    ::= { lcsSetupPrinterAccessListTable 1 }

LcsSetupPrinterAccessListEntry ::= SEQUENCE {
            lcsSetupPrinterAccessListEntryIpAddress IpAddress,
            lcsSetupPrinterAccessListEntryIpNetmask IpAddress,
            lcsSetupPrinterAccessListEntryRtgTag Integer32
    }

-- {COLUMN} 1.3.6.1.4.1.2356.11.2.34.2.1.1
lcsSetupPrinterAccessListEntryIpAddress OBJECT-TYPE
    SYNTAX     IpAddress
    MAX-ACCESS read-write
    STATUS     current
    DESCRIPTION
            ""
    ::= { lcsSetupPrinterAccessListEntry 1 }

-- {COLUMN} 1.3.6.1.4.1.2356.11.2.34.2.1.2
lcsSetupPrinterAccessListEntryIpNetmask OBJECT-TYPE
    SYNTAX     IpAddress
    MAX-ACCESS read-write
    STATUS     current
    DESCRIPTION
            ""
    ::= { lcsSetupPrinterAccessListEntry 2 }

-- {COLUMN} 1.3.6.1.4.1.2356.11.2.34.2.1.3
lcsSetupPrinterAccessListEntryRtgTag OBJECT-TYPE
    SYNTAX     Integer32 (0..65535)
    MAX-ACCESS read-write
    STATUS     current
    DESCRIPTION
            ""
    ::= { lcsSetupPrinterAccessListEntry 3 }

-- {NODE} 1.3.6.1.4.1.2356.11.2.35
lcsSetupEchoServer OBJECT IDENTIFIER ::= { lcsSetup 35 }

-- {SCALAR} 1.3.6.1.4.1.2356.11.2.35.1
lcsSetupEchoServerOperating OBJECT-TYPE
    SYNTAX     INTEGER {
                  eNo (0),
                  eYes (1)
            }
    MAX-ACCESS read-write
    STATUS     current
    DESCRIPTION
            ""
    ::= { lcsSetupEchoServer 1 }

-- {TABLE} 1.3.6.1.4.1.2356.11.2.35.2
lcsSetupEchoServerAccessTableTable OBJECT-TYPE
    SYNTAX     SEQUENCE OF LcsSetupEchoServerAccessTableEntry
    MAX-ACCESS not-accessible
    STATUS     current
    DESCRIPTION
            ""
    ::= { lcsSetupEchoServer 2 }

-- {ROW} 1.3.6.1.4.1.2356.11.2.35.2.1
lcsSetupEchoServerAccessTableEntry OBJECT-TYPE
    SYNTAX     LcsSetupEchoServerAccessTableEntry
    MAX-ACCESS not-accessible
    STATUS     current
    DESCRIPTION
            ""
    INDEX {
            lcsSetupEchoServerAccessTableEntryIpAddress,
            lcsSetupEchoServerAccessTableEntryNetmask
          }
    ::= { lcsSetupEchoServerAccessTableTable 1 }

LcsSetupEchoServerAccessTableEntry ::= SEQUENCE {
            lcsSetupEchoServerAccessTableEntryIpAddress IpAddress,
            lcsSetupEchoServerAccessTableEntryNetmask IpAddress,
            lcsSetupEchoServerAccessTableEntryProtokoll INTEGER,
            lcsSetupEchoServerAccessTableEntryActive INTEGER,
            lcsSetupEchoServerAccessTableEntryComment DisplayString
    }

-- {COLUMN} 1.3.6.1.4.1.2356.11.2.35.2.1.1
lcsSetupEchoServerAccessTableEntryIpAddress OBJECT-TYPE
    SYNTAX     IpAddress
    MAX-ACCESS read-write
    STATUS     current
    DESCRIPTION
            ""
    ::= { lcsSetupEchoServerAccessTableEntry 1 }

-- {COLUMN} 1.3.6.1.4.1.2356.11.2.35.2.1.2
lcsSetupEchoServerAccessTableEntryNetmask OBJECT-TYPE
    SYNTAX     IpAddress
    MAX-ACCESS read-write
    STATUS     current
    DESCRIPTION
            ""
    ::= { lcsSetupEchoServerAccessTableEntry 2 }

-- {COLUMN} 1.3.6.1.4.1.2356.11.2.35.2.1.3
lcsSetupEchoServerAccessTableEntryProtokoll OBJECT-TYPE
    SYNTAX     INTEGER {
                  eNone (0),
                  eTcp (1),
                  eUdp (2),
                  eTcpPlusUdp (3)
            }
    MAX-ACCESS read-write
    STATUS     current
    DESCRIPTION
            ""
    ::= { lcsSetupEchoServerAccessTableEntry 3 }

-- {COLUMN} 1.3.6.1.4.1.2356.11.2.35.2.1.4
lcsSetupEchoServerAccessTableEntryActive OBJECT-TYPE
    SYNTAX     INTEGER {
                  eYes (0),
                  eNo (1)
            }
    MAX-ACCESS read-write
    STATUS     current
    DESCRIPTION
            ""
    ::= { lcsSetupEchoServerAccessTableEntry 4 }

-- {COLUMN} 1.3.6.1.4.1.2356.11.2.35.2.1.5
lcsSetupEchoServerAccessTableEntryComment OBJECT-TYPE
    SYNTAX     DisplayString (SIZE(0..31))
    MAX-ACCESS read-write
    STATUS     current
    DESCRIPTION
            ""
    ::= { lcsSetupEchoServerAccessTableEntry 5 }

-- {SCALAR} 1.3.6.1.4.1.2356.11.2.35.3
lcsSetupEchoServerTcpTimeout OBJECT-TYPE
    SYNTAX     Integer32 (0..2147483647)
    MAX-ACCESS read-write
    STATUS     current
    DESCRIPTION
            ""
    ::= { lcsSetupEchoServer 3 }

-- {NODE} 1.3.6.1.4.1.2356.11.2.36
lcsSetupPerfmon OBJECT IDENTIFIER ::= { lcsSetup 36 }

-- {TABLE} 1.3.6.1.4.1.2356.11.2.36.2
lcsSetupPerfmonRttmonadminTable OBJECT-TYPE
    SYNTAX     SEQUENCE OF LcsSetupPerfmonRttmonadminEntry
    MAX-ACCESS not-accessible
    STATUS     current
    DESCRIPTION
            ""
    ::= { lcsSetupPerfmon 2 }

-- {ROW} 1.3.6.1.4.1.2356.11.2.36.2.1
lcsSetupPerfmonRttmonadminEntry OBJECT-TYPE
    SYNTAX     LcsSetupPerfmonRttmonadminEntry
    MAX-ACCESS not-accessible
    STATUS     current
    DESCRIPTION
            ""
    INDEX {
            lcsSetupPerfmonRttmonadminEntryIndex
          }
    ::= { lcsSetupPerfmonRttmonadminTable 1 }

LcsSetupPerfmonRttmonadminEntry ::= SEQUENCE {
            lcsSetupPerfmonRttmonadminEntryIndex Integer32,
            lcsSetupPerfmonRttmonadminEntryType INTEGER,
            lcsSetupPerfmonRttmonadminEntryFrequency Integer32,
            lcsSetupPerfmonRttmonadminEntryTimeout Integer32,
            lcsSetupPerfmonRttmonadminEntryStatus INTEGER
    }

-- {COLUMN} 1.3.6.1.4.1.2356.11.2.36.2.1.1
lcsSetupPerfmonRttmonadminEntryIndex OBJECT-TYPE
    SYNTAX     Integer32 (0..2147483647)
    MAX-ACCESS read-write
    STATUS     current
    DESCRIPTION
            ""
    ::= { lcsSetupPerfmonRttmonadminEntry 1 }

-- {COLUMN} 1.3.6.1.4.1.2356.11.2.36.2.1.4
lcsSetupPerfmonRttmonadminEntryType OBJECT-TYPE
    SYNTAX     INTEGER {
                  eJitter (9)
            }
    MAX-ACCESS read-write
    STATUS     current
    DESCRIPTION
            ""
    ::= { lcsSetupPerfmonRttmonadminEntry 4 }

-- {COLUMN} 1.3.6.1.4.1.2356.11.2.36.2.1.6
lcsSetupPerfmonRttmonadminEntryFrequency OBJECT-TYPE
    SYNTAX     Integer32 (0..2147483647)
    MAX-ACCESS read-write
    STATUS     current
    DESCRIPTION
            ""
    ::= { lcsSetupPerfmonRttmonadminEntry 6 }

-- {COLUMN} 1.3.6.1.4.1.2356.11.2.36.2.1.7
lcsSetupPerfmonRttmonadminEntryTimeout OBJECT-TYPE
    SYNTAX     Integer32 (0..2147483647)
    MAX-ACCESS read-write
    STATUS     current
    DESCRIPTION
            ""
    ::= { lcsSetupPerfmonRttmonadminEntry 7 }

-- {COLUMN} 1.3.6.1.4.1.2356.11.2.36.2.1.9
lcsSetupPerfmonRttmonadminEntryStatus OBJECT-TYPE
    SYNTAX     INTEGER {
                  eActive (1),
                  eNotInService (2),
                  eNotReady (3),
                  eCreate (5),
                  eDestroy (6)
            }
    MAX-ACCESS read-write
    STATUS     current
    DESCRIPTION
            ""
    ::= { lcsSetupPerfmonRttmonadminEntry 9 }

-- {TABLE} 1.3.6.1.4.1.2356.11.2.36.3
lcsSetupPerfmonRttmonechoadminTable OBJECT-TYPE
    SYNTAX     SEQUENCE OF LcsSetupPerfmonRttmonechoadminEntry
    MAX-ACCESS not-accessible
    STATUS     current
    DESCRIPTION
            ""
    ::= { lcsSetupPerfmon 3 }

-- {ROW} 1.3.6.1.4.1.2356.11.2.36.3.1
lcsSetupPerfmonRttmonechoadminEntry OBJECT-TYPE
    SYNTAX     LcsSetupPerfmonRttmonechoadminEntry
    MAX-ACCESS not-accessible
    STATUS     current
    DESCRIPTION
            ""
    INDEX {
            lcsSetupPerfmonRttmonechoadminEntryIndex
          }
    ::= { lcsSetupPerfmonRttmonechoadminTable 1 }

LcsSetupPerfmonRttmonechoadminEntry ::= SEQUENCE {
            lcsSetupPerfmonRttmonechoadminEntryProtocol INTEGER,
            lcsSetupPerfmonRttmonechoadminEntryDestinationAddress IpAddress,
            lcsSetupPerfmonRttmonechoadminEntryPacketSize Integer32,
            lcsSetupPerfmonRttmonechoadminEntryDestinationPort Integer32,
            lcsSetupPerfmonRttmonechoadminEntryInterval Integer32,
            lcsSetupPerfmonRttmonechoadminEntryPacketCount Integer32,
            lcsSetupPerfmonRttmonechoadminEntryIndex Integer32
    }

-- {COLUMN} 1.3.6.1.4.1.2356.11.2.36.3.1.1
lcsSetupPerfmonRttmonechoadminEntryProtocol OBJECT-TYPE
    SYNTAX     INTEGER {
                  eEcho (3)
            }
    MAX-ACCESS read-write
    STATUS     current
    DESCRIPTION
            ""
    ::= { lcsSetupPerfmonRttmonechoadminEntry 1 }

-- {COLUMN} 1.3.6.1.4.1.2356.11.2.36.3.1.2
lcsSetupPerfmonRttmonechoadminEntryDestinationAddress OBJECT-TYPE
    SYNTAX     IpAddress
    MAX-ACCESS read-write
    STATUS     current
    DESCRIPTION
            ""
    ::= { lcsSetupPerfmonRttmonechoadminEntry 2 }

-- {COLUMN} 1.3.6.1.4.1.2356.11.2.36.3.1.3
lcsSetupPerfmonRttmonechoadminEntryPacketSize OBJECT-TYPE
    SYNTAX     Integer32 (0..65535)
    MAX-ACCESS read-write
    STATUS     current
    DESCRIPTION
            ""
    ::= { lcsSetupPerfmonRttmonechoadminEntry 3 }

-- {COLUMN} 1.3.6.1.4.1.2356.11.2.36.3.1.5
lcsSetupPerfmonRttmonechoadminEntryDestinationPort OBJECT-TYPE
    SYNTAX     Integer32 (0..65535)
    MAX-ACCESS read-write
    STATUS     current
    DESCRIPTION
            ""
    ::= { lcsSetupPerfmonRttmonechoadminEntry 5 }

-- {COLUMN} 1.3.6.1.4.1.2356.11.2.36.3.1.17
lcsSetupPerfmonRttmonechoadminEntryInterval OBJECT-TYPE
    SYNTAX     Integer32 (0..2147483647)
    MAX-ACCESS read-write
    STATUS     current
    DESCRIPTION
            ""
    ::= { lcsSetupPerfmonRttmonechoadminEntry 17 }

-- {COLUMN} 1.3.6.1.4.1.2356.11.2.36.3.1.18
lcsSetupPerfmonRttmonechoadminEntryPacketCount OBJECT-TYPE
    SYNTAX     Integer32 (0..2147483647)
    MAX-ACCESS read-write
    STATUS     current
    DESCRIPTION
            ""
    ::= { lcsSetupPerfmonRttmonechoadminEntry 18 }

-- {COLUMN} 1.3.6.1.4.1.2356.11.2.36.3.1.255
lcsSetupPerfmonRttmonechoadminEntryIndex OBJECT-TYPE
    SYNTAX     Integer32 (0..2147483647)
    MAX-ACCESS read-only
    STATUS     current
    DESCRIPTION
            ""
    ::= { lcsSetupPerfmonRttmonechoadminEntry 255 }

-- {TABLE} 1.3.6.1.4.1.2356.11.2.36.4
lcsSetupPerfmonRttmonstatisticsTable OBJECT-TYPE
    SYNTAX     SEQUENCE OF LcsSetupPerfmonRttmonstatisticsEntry
    MAX-ACCESS not-accessible
    STATUS     current
    DESCRIPTION
            ""
    ::= { lcsSetupPerfmon 4 }

-- {ROW} 1.3.6.1.4.1.2356.11.2.36.4.1
lcsSetupPerfmonRttmonstatisticsEntry OBJECT-TYPE
    SYNTAX     LcsSetupPerfmonRttmonstatisticsEntry
    MAX-ACCESS not-accessible
    STATUS     current
    DESCRIPTION
            ""
    INDEX {
            lcsSetupPerfmonRttmonstatisticsEntryIndex
          }
    ::= { lcsSetupPerfmonRttmonstatisticsTable 1 }

LcsSetupPerfmonRttmonstatisticsEntry ::= SEQUENCE {
            lcsSetupPerfmonRttmonstatisticsEntryCompletions Integer32,
            lcsSetupPerfmonRttmonstatisticsEntryRttCount Integer32,
            lcsSetupPerfmonRttmonstatisticsEntryRttSum Integer32,
            lcsSetupPerfmonRttmonstatisticsEntryRttMin Integer32,
            lcsSetupPerfmonRttmonstatisticsEntryRttMax Integer32,
            lcsSetupPerfmonRttmonstatisticsEntryJitterMinPosSd Integer32,
            lcsSetupPerfmonRttmonstatisticsEntryJitterMaxPosSd Integer32,
            lcsSetupPerfmonRttmonstatisticsEntryJitterCountPosSd Integer32,
            lcsSetupPerfmonRttmonstatisticsEntryJitterSumPosSd Integer32,
            lcsSetupPerfmonRttmonstatisticsEntryJitterMinPosDs Integer32,
            lcsSetupPerfmonRttmonstatisticsEntryJitterMaxPosDs Integer32,
            lcsSetupPerfmonRttmonstatisticsEntryJitterCountPosDs Integer32,
            lcsSetupPerfmonRttmonstatisticsEntryJitterSumPosDs Integer32,
            lcsSetupPerfmonRttmonstatisticsEntryJitterMinNegSd Integer32,
            lcsSetupPerfmonRttmonstatisticsEntryJitterMaxNegSd Integer32,
            lcsSetupPerfmonRttmonstatisticsEntryJitterCountNegSd Integer32,
            lcsSetupPerfmonRttmonstatisticsEntryJitterSumNegSd Integer32,
            lcsSetupPerfmonRttmonstatisticsEntryJitterMinNegDs Integer32,
            lcsSetupPerfmonRttmonstatisticsEntryJitterMaxNegDs Integer32,
            lcsSetupPerfmonRttmonstatisticsEntryJitterCountNegDs Integer32,
            lcsSetupPerfmonRttmonstatisticsEntryJitterSumNegDs Integer32,
            lcsSetupPerfmonRttmonstatisticsEntryPacketLossSd Integer32,
            lcsSetupPerfmonRttmonstatisticsEntryPacketLossDs Integer32,
            lcsSetupPerfmonRttmonstatisticsEntryAverageJitter Integer32,
            lcsSetupPerfmonRttmonstatisticsEntryAverageJitterSd Integer32,
            lcsSetupPerfmonRttmonstatisticsEntryAverageJitterDs Integer32,
            lcsSetupPerfmonRttmonstatisticsEntryIndex Integer32
    }

-- {COLUMN} 1.3.6.1.4.1.2356.11.2.36.4.1.2
lcsSetupPerfmonRttmonstatisticsEntryCompletions OBJECT-TYPE
    SYNTAX     Integer32 (0..2147483647)
    MAX-ACCESS read-only
    STATUS     current
    DESCRIPTION
            ""
    ::= { lcsSetupPerfmonRttmonstatisticsEntry 2 }

-- {COLUMN} 1.3.6.1.4.1.2356.11.2.36.4.1.4
lcsSetupPerfmonRttmonstatisticsEntryRttCount OBJECT-TYPE
    SYNTAX     Integer32 (0..2147483647)
    MAX-ACCESS read-only
    STATUS     current
    DESCRIPTION
            ""
    ::= { lcsSetupPerfmonRttmonstatisticsEntry 4 }

-- {COLUMN} 1.3.6.1.4.1.2356.11.2.36.4.1.5
lcsSetupPerfmonRttmonstatisticsEntryRttSum OBJECT-TYPE
    SYNTAX     Integer32 (0..2147483647)
    MAX-ACCESS read-only
    STATUS     current
    DESCRIPTION
            ""
    ::= { lcsSetupPerfmonRttmonstatisticsEntry 5 }

-- {COLUMN} 1.3.6.1.4.1.2356.11.2.36.4.1.8
lcsSetupPerfmonRttmonstatisticsEntryRttMin OBJECT-TYPE
    SYNTAX     Integer32 (0..2147483647)
    MAX-ACCESS read-only
    STATUS     current
    DESCRIPTION
            ""
    ::= { lcsSetupPerfmonRttmonstatisticsEntry 8 }

-- {COLUMN} 1.3.6.1.4.1.2356.11.2.36.4.1.9
lcsSetupPerfmonRttmonstatisticsEntryRttMax OBJECT-TYPE
    SYNTAX     Integer32 (0..2147483647)
    MAX-ACCESS read-only
    STATUS     current
    DESCRIPTION
            ""
    ::= { lcsSetupPerfmonRttmonstatisticsEntry 9 }

-- {COLUMN} 1.3.6.1.4.1.2356.11.2.36.4.1.10
lcsSetupPerfmonRttmonstatisticsEntryJitterMinPosSd OBJECT-TYPE
    SYNTAX     Integer32 (0..2147483647)
    MAX-ACCESS read-only
    STATUS     current
    DESCRIPTION
            ""
    ::= { lcsSetupPerfmonRttmonstatisticsEntry 10 }

-- {COLUMN} 1.3.6.1.4.1.2356.11.2.36.4.1.11
lcsSetupPerfmonRttmonstatisticsEntryJitterMaxPosSd OBJECT-TYPE
    SYNTAX     Integer32 (0..2147483647)
    MAX-ACCESS read-only
    STATUS     current
    DESCRIPTION
            ""
    ::= { lcsSetupPerfmonRttmonstatisticsEntry 11 }

-- {COLUMN} 1.3.6.1.4.1.2356.11.2.36.4.1.12
lcsSetupPerfmonRttmonstatisticsEntryJitterCountPosSd OBJECT-TYPE
    SYNTAX     Integer32 (0..2147483647)
    MAX-ACCESS read-only
    STATUS     current
    DESCRIPTION
            ""
    ::= { lcsSetupPerfmonRttmonstatisticsEntry 12 }

-- {COLUMN} 1.3.6.1.4.1.2356.11.2.36.4.1.13
lcsSetupPerfmonRttmonstatisticsEntryJitterSumPosSd OBJECT-TYPE
    SYNTAX     Integer32 (0..2147483647)
    MAX-ACCESS read-only
    STATUS     current
    DESCRIPTION
            ""
    ::= { lcsSetupPerfmonRttmonstatisticsEntry 13 }

-- {COLUMN} 1.3.6.1.4.1.2356.11.2.36.4.1.16
lcsSetupPerfmonRttmonstatisticsEntryJitterMinPosDs OBJECT-TYPE
    SYNTAX     Integer32 (0..2147483647)
    MAX-ACCESS read-only
    STATUS     current
    DESCRIPTION
            ""
    ::= { lcsSetupPerfmonRttmonstatisticsEntry 16 }

-- {COLUMN} 1.3.6.1.4.1.2356.11.2.36.4.1.17
lcsSetupPerfmonRttmonstatisticsEntryJitterMaxPosDs OBJECT-TYPE
    SYNTAX     Integer32 (0..2147483647)
    MAX-ACCESS read-only
    STATUS     current
    DESCRIPTION
            ""
    ::= { lcsSetupPerfmonRttmonstatisticsEntry 17 }

-- {COLUMN} 1.3.6.1.4.1.2356.11.2.36.4.1.18
lcsSetupPerfmonRttmonstatisticsEntryJitterCountPosDs OBJECT-TYPE
    SYNTAX     Integer32 (0..2147483647)
    MAX-ACCESS read-only
    STATUS     current
    DESCRIPTION
            ""
    ::= { lcsSetupPerfmonRttmonstatisticsEntry 18 }

-- {COLUMN} 1.3.6.1.4.1.2356.11.2.36.4.1.19
lcsSetupPerfmonRttmonstatisticsEntryJitterSumPosDs OBJECT-TYPE
    SYNTAX     Integer32 (0..2147483647)
    MAX-ACCESS read-only
    STATUS     current
    DESCRIPTION
            ""
    ::= { lcsSetupPerfmonRttmonstatisticsEntry 19 }

-- {COLUMN} 1.3.6.1.4.1.2356.11.2.36.4.1.22
lcsSetupPerfmonRttmonstatisticsEntryJitterMinNegSd OBJECT-TYPE
    SYNTAX     Integer32 (0..2147483647)
    MAX-ACCESS read-only
    STATUS     current
    DESCRIPTION
            ""
    ::= { lcsSetupPerfmonRttmonstatisticsEntry 22 }

-- {COLUMN} 1.3.6.1.4.1.2356.11.2.36.4.1.23
lcsSetupPerfmonRttmonstatisticsEntryJitterMaxNegSd OBJECT-TYPE
    SYNTAX     Integer32 (0..2147483647)
    MAX-ACCESS read-only
    STATUS     current
    DESCRIPTION
            ""
    ::= { lcsSetupPerfmonRttmonstatisticsEntry 23 }

-- {COLUMN} 1.3.6.1.4.1.2356.11.2.36.4.1.24
lcsSetupPerfmonRttmonstatisticsEntryJitterCountNegSd OBJECT-TYPE
    SYNTAX     Integer32 (0..2147483647)
    MAX-ACCESS read-only
    STATUS     current
    DESCRIPTION
            ""
    ::= { lcsSetupPerfmonRttmonstatisticsEntry 24 }

-- {COLUMN} 1.3.6.1.4.1.2356.11.2.36.4.1.25
lcsSetupPerfmonRttmonstatisticsEntryJitterSumNegSd OBJECT-TYPE
    SYNTAX     Integer32 (0..2147483647)
    MAX-ACCESS read-only
    STATUS     current
    DESCRIPTION
            ""
    ::= { lcsSetupPerfmonRttmonstatisticsEntry 25 }

-- {COLUMN} 1.3.6.1.4.1.2356.11.2.36.4.1.28
lcsSetupPerfmonRttmonstatisticsEntryJitterMinNegDs OBJECT-TYPE
    SYNTAX     Integer32 (0..2147483647)
    MAX-ACCESS read-only
    STATUS     current
    DESCRIPTION
            ""
    ::= { lcsSetupPerfmonRttmonstatisticsEntry 28 }

-- {COLUMN} 1.3.6.1.4.1.2356.11.2.36.4.1.29
lcsSetupPerfmonRttmonstatisticsEntryJitterMaxNegDs OBJECT-TYPE
    SYNTAX     Integer32 (0..2147483647)
    MAX-ACCESS read-only
    STATUS     current
    DESCRIPTION
            ""
    ::= { lcsSetupPerfmonRttmonstatisticsEntry 29 }

-- {COLUMN} 1.3.6.1.4.1.2356.11.2.36.4.1.30
lcsSetupPerfmonRttmonstatisticsEntryJitterCountNegDs OBJECT-TYPE
    SYNTAX     Integer32 (0..2147483647)
    MAX-ACCESS read-only
    STATUS     current
    DESCRIPTION
            ""
    ::= { lcsSetupPerfmonRttmonstatisticsEntry 30 }

-- {COLUMN} 1.3.6.1.4.1.2356.11.2.36.4.1.31
lcsSetupPerfmonRttmonstatisticsEntryJitterSumNegDs OBJECT-TYPE
    SYNTAX     Integer32 (0..2147483647)
    MAX-ACCESS read-only
    STATUS     current
    DESCRIPTION
            ""
    ::= { lcsSetupPerfmonRttmonstatisticsEntry 31 }

-- {COLUMN} 1.3.6.1.4.1.2356.11.2.36.4.1.34
lcsSetupPerfmonRttmonstatisticsEntryPacketLossSd OBJECT-TYPE
    SYNTAX     Integer32 (0..2147483647)
    MAX-ACCESS read-only
    STATUS     current
    DESCRIPTION
            ""
    ::= { lcsSetupPerfmonRttmonstatisticsEntry 34 }

-- {COLUMN} 1.3.6.1.4.1.2356.11.2.36.4.1.35
lcsSetupPerfmonRttmonstatisticsEntryPacketLossDs OBJECT-TYPE
    SYNTAX     Integer32 (0..2147483647)
    MAX-ACCESS read-only
    STATUS     current
    DESCRIPTION
            ""
    ::= { lcsSetupPerfmonRttmonstatisticsEntry 35 }

-- {COLUMN} 1.3.6.1.4.1.2356.11.2.36.4.1.62
lcsSetupPerfmonRttmonstatisticsEntryAverageJitter OBJECT-TYPE
    SYNTAX     Integer32 (0..2147483647)
    MAX-ACCESS read-only
    STATUS     current
    DESCRIPTION
            ""
    ::= { lcsSetupPerfmonRttmonstatisticsEntry 62 }

-- {COLUMN} 1.3.6.1.4.1.2356.11.2.36.4.1.63
lcsSetupPerfmonRttmonstatisticsEntryAverageJitterSd OBJECT-TYPE
    SYNTAX     Integer32 (0..2147483647)
    MAX-ACCESS read-only
    STATUS     current
    DESCRIPTION
            ""
    ::= { lcsSetupPerfmonRttmonstatisticsEntry 63 }

-- {COLUMN} 1.3.6.1.4.1.2356.11.2.36.4.1.64
lcsSetupPerfmonRttmonstatisticsEntryAverageJitterDs OBJECT-TYPE
    SYNTAX     Integer32 (0..2147483647)
    MAX-ACCESS read-only
    STATUS     current
    DESCRIPTION
            ""
    ::= { lcsSetupPerfmonRttmonstatisticsEntry 64 }

-- {COLUMN} 1.3.6.1.4.1.2356.11.2.36.4.1.255
lcsSetupPerfmonRttmonstatisticsEntryIndex OBJECT-TYPE
    SYNTAX     Integer32 (0..2147483647)
    MAX-ACCESS read-only
    STATUS     current
    DESCRIPTION
            ""
    ::= { lcsSetupPerfmonRttmonstatisticsEntry 255 }

-- {NODE} 1.3.6.1.4.1.2356.11.2.37
lcsSetupWlanMngmt OBJECT IDENTIFIER ::= { lcsSetup 37 }

-- {NODE} 1.3.6.1.4.1.2356.11.2.37.1
lcsSetupWlanMngmtApConf OBJECT IDENTIFIER ::= { lcsSetupWlanMngmt 1 }

-- {TABLE} 1.3.6.1.4.1.2356.11.2.37.1.1
lcsSetupWlanMngmtApConfNetwprofilsTable OBJECT-TYPE
    SYNTAX     SEQUENCE OF LcsSetupWlanMngmtApConfNetwprofilsEntry
    MAX-ACCESS not-accessible
    STATUS     current
    DESCRIPTION
            "network profiles"
    ::= { lcsSetupWlanMngmtApConf 1 }

-- {ROW} 1.3.6.1.4.1.2356.11.2.37.1.1.1
lcsSetupWlanMngmtApConfNetwprofilsEntry OBJECT-TYPE
    SYNTAX     LcsSetupWlanMngmtApConfNetwprofilsEntry
    MAX-ACCESS not-accessible
    STATUS     current
    DESCRIPTION
            ""
    INDEX {
            lcsSetupWlanMngmtApConfNetwprofilsEntryName
          }
    ::= { lcsSetupWlanMngmtApConfNetwprofilsTable 1 }

LcsSetupWlanMngmtApConfNetwprofilsEntry ::= SEQUENCE {
            lcsSetupWlanMngmtApConfNetwprofilsEntryName DisplayString,
            lcsSetupWlanMngmtApConfNetwprofilsEntryParentName DisplayString,
            lcsSetupWlanMngmtApConfNetwprofilsEntryLocVal DisplayString,
            lcsSetupWlanMngmtApConfNetwprofilsEntryOperating INTEGER,
            lcsSetupWlanMngmtApConfNetwprofilsEntryVlanId Integer32,
            lcsSetupWlanMngmtApConfNetwprofilsEntryEncryption INTEGER,
            lcsSetupWlanMngmtApConfNetwprofilsEntryWpa1SessionKeytypes INTEGER,
            lcsSetupWlanMngmtApConfNetwprofilsEntryWpaVersion INTEGER,
            lcsSetupWlanMngmtApConfNetwprofilsEntryKey DisplayString,
            lcsSetupWlanMngmtApConfNetwprofilsEntryRadioBand INTEGER,
            lcsSetupWlanMngmtApConfNetwprofilsEntryContinuation Integer32,
            lcsSetupWlanMngmtApConfNetwprofilsEntryMinTxRate INTEGER,
            lcsSetupWlanMngmtApConfNetwprofilsEntryMaxTxRate INTEGER,
            lcsSetupWlanMngmtApConfNetwprofilsEntryBasicRate INTEGER,
            lcsSetupWlanMngmtApConfNetwprofilsEntry11bPreamble INTEGER,
            lcsSetupWlanMngmtApConfNetwprofilsEntryMacFilter INTEGER,
            lcsSetupWlanMngmtApConfNetwprofilsEntryClBrgSupport INTEGER,
            lcsSetupWlanMngmtApConfNetwprofilsEntryMaxStations Integer32,
            lcsSetupWlanMngmtApConfNetwprofilsEntrySsidBroadcast INTEGER,
            lcsSetupWlanMngmtApConfNetwprofilsEntrySsid DisplayString,
            lcsSetupWlanMngmtApConfNetwprofilsEntryMinHtMcs INTEGER,
            lcsSetupWlanMngmtApConfNetwprofilsEntryMaxHtMcs INTEGER,
            lcsSetupWlanMngmtApConfNetwprofilsEntryShortGuardInterval INTEGER,
            lcsSetupWlanMngmtApConfNetwprofilsEntryMaxSpatialStreams INTEGER,
            lcsSetupWlanMngmtApConfNetwprofilsEntrySendAggregates INTEGER,
            lcsSetupWlanMngmtApConfNetwprofilsEntryWpa2SessionKeytypes INTEGER,
            lcsSetupWlanMngmtApConfNetwprofilsEntryRadiusAccounting INTEGER,
            lcsSetupWlanMngmtApConfNetwprofilsEntryVlanMode INTEGER,
            lcsSetupWlanMngmtApConfNetwprofilsEntryConnectSsidTo INTEGER,
            lcsSetupWlanMngmtApConfNetwprofilsEntryInterStationTraffic INTEGER,
            lcsSetupWlanMngmtApConfNetwprofilsEntryVlanIdnew Integer32,
            lcsSetupWlanMngmtApConfNetwprofilsEntryRadiusProfile DisplayString,
            lcsSetupWlanMngmtApConfNetwprofilsEntryStbcActivated INTEGER,
            lcsSetupWlanMngmtApConfNetwprofilsEntryLdpcActivated INTEGER,
            lcsSetupWlanMngmtApConfNetwprofilsEntryMinClientStrength Integer32,
            lcsSetupWlanMngmtApConfNetwprofilsEntryIeee80211uNetworkProfile DisplayString,
            lcsSetupWlanMngmtApConfNetwprofilsEntryOkc INTEGER,
            lcsSetupWlanMngmtApConfNetwprofilsEntryWpa2KeyManagement BITS,
            lcsSetupWlanMngmtApConfNetwprofilsEntryApsd INTEGER,
            lcsSetupWlanMngmtApConfNetwprofilsEntryProtMgmtFrames INTEGER,
            lcsSetupWlanMngmtApConfNetwprofilsEntryTxLimit Integer32,
            lcsSetupWlanMngmtApConfNetwprofilsEntryRxLimit Integer32,
            lcsSetupWlanMngmtApConfNetwprofilsEntryLbsTracking INTEGER,
            lcsSetupWlanMngmtApConfNetwprofilsEntryLbsTrackingList DisplayString,
            lcsSetupWlanMngmtApConfNetwprofilsEntry11acBeamforming INTEGER,
            lcsSetupWlanMngmtApConfNetwprofilsEntryConvertToUnicast BITS,
            lcsSetupWlanMngmtApConfNetwprofilsEntryTransmitOnlyUnicasts INTEGER,
            lcsSetupWlanMngmtApConfNetwprofilsEntryContinuationUseDef INTEGER,
            lcsSetupWlanMngmtApConfNetwprofilsEntryWpa23SessionKeytypes BITS,
            lcsSetupWlanMngmtApConfNetwprofilsEntryWpa8021xSecurityLevel INTEGER,
            lcsSetupWlanMngmtApConfNetwprofilsEntryPerClientTxLimit Integer32,
            lcsSetupWlanMngmtApConfNetwprofilsEntryPerClientRxLimit Integer32,
            lcsSetupWlanMngmtApConfNetwprofilsEntryTimeframe DisplayString,
            lcsSetupWlanMngmtApConfNetwprofilsEntryMinClDisStr Integer32
    }

-- {COLUMN} 1.3.6.1.4.1.2356.11.2.37.1.1.1.1
lcsSetupWlanMngmtApConfNetwprofilsEntryName OBJECT-TYPE
    SYNTAX     DisplayString (SIZE(0..31))
    MAX-ACCESS read-write
    STATUS     current
    DESCRIPTION
            ""
    ::= { lcsSetupWlanMngmtApConfNetwprofilsEntry 1 }

-- {COLUMN} 1.3.6.1.4.1.2356.11.2.37.1.1.1.2
lcsSetupWlanMngmtApConfNetwprofilsEntryParentName OBJECT-TYPE
    SYNTAX     DisplayString (SIZE(0..31))
    MAX-ACCESS read-write
    STATUS     current
    DESCRIPTION
            ""
    ::= { lcsSetupWlanMngmtApConfNetwprofilsEntry 2 }

-- {COLUMN} 1.3.6.1.4.1.2356.11.2.37.1.1.1.3
lcsSetupWlanMngmtApConfNetwprofilsEntryLocVal OBJECT-TYPE
    SYNTAX     DisplayString (SIZE(0..16))
    MAX-ACCESS read-write
    STATUS     current
    DESCRIPTION
            "local values"
    ::= { lcsSetupWlanMngmtApConfNetwprofilsEntry 3 }

-- {COLUMN} 1.3.6.1.4.1.2356.11.2.37.1.1.1.4
lcsSetupWlanMngmtApConfNetwprofilsEntryOperating OBJECT-TYPE
    SYNTAX     INTEGER {
                  eYes (0),
                  eNo (1)
            }
    MAX-ACCESS read-write
    STATUS     current
    DESCRIPTION
            ""
    ::= { lcsSetupWlanMngmtApConfNetwprofilsEntry 4 }

-- {COLUMN} 1.3.6.1.4.1.2356.11.2.37.1.1.1.5
lcsSetupWlanMngmtApConfNetwprofilsEntryVlanId OBJECT-TYPE
    SYNTAX     Integer32 (0..65535)
    MAX-ACCESS read-write
    STATUS     obsolete
    DESCRIPTION
            ""
    ::= { lcsSetupWlanMngmtApConfNetwprofilsEntry 5 }

-- {COLUMN} 1.3.6.1.4.1.2356.11.2.37.1.1.1.6
lcsSetupWlanMngmtApConfNetwprofilsEntryEncryption OBJECT-TYPE
    SYNTAX     INTEGER {
                  e80211iWpaPsk (0),
                  e80211iWpa8021x (1),
                  eWep104Bits (2),
                  eWep40Bits (3),
                  eWep104Bits8021x (4),
                  eWep40Bits8021x (5),
                  eNone (6),
                  eWPA-OWE (7),
                  eEnhancedOpenTransitional (8)
            }
    MAX-ACCESS read-write
    STATUS     current
    DESCRIPTION
            ""
    ::= { lcsSetupWlanMngmtApConfNetwprofilsEntry 6 }

-- {COLUMN} 1.3.6.1.4.1.2356.11.2.37.1.1.1.7
lcsSetupWlanMngmtApConfNetwprofilsEntryWpa1SessionKeytypes OBJECT-TYPE
    SYNTAX     INTEGER {
                  eTkipAes (0),
                  eAes (1),
                  eTkip (2)
            }
    MAX-ACCESS read-write
    STATUS     current
    DESCRIPTION
            ""
    ::= { lcsSetupWlanMngmtApConfNetwprofilsEntry 7 }

-- {COLUMN} 1.3.6.1.4.1.2356.11.2.37.1.1.1.8
lcsSetupWlanMngmtApConfNetwprofilsEntryWpaVersion OBJECT-TYPE
    SYNTAX     INTEGER {
                  eWpa12 (0),
                  eWpa1 (1),
                  eWpa2 (2),
                  eWpa3 (3),
                  eWpa23 (4),
                  eWpa123 (5)
            }
    MAX-ACCESS read-write
    STATUS     current
    DESCRIPTION
            ""
    ::= { lcsSetupWlanMngmtApConfNetwprofilsEntry 8 }

-- {COLUMN} 1.3.6.1.4.1.2356.11.2.37.1.1.1.9
lcsSetupWlanMngmtApConfNetwprofilsEntryKey OBJECT-TYPE
    SYNTAX     DisplayString (SIZE(0..63))
    MAX-ACCESS read-write
    STATUS     current
    DESCRIPTION
            ""
    ::= { lcsSetupWlanMngmtApConfNetwprofilsEntry 9 }

-- {COLUMN} 1.3.6.1.4.1.2356.11.2.37.1.1.1.10
lcsSetupWlanMngmtApConfNetwprofilsEntryRadioBand OBJECT-TYPE
    SYNTAX     INTEGER {
                  e24ghz5ghz (0),
                  e24ghz (1),
                  e5ghz (2)
            }
    MAX-ACCESS read-write
    STATUS     current
    DESCRIPTION
            ""
    ::= { lcsSetupWlanMngmtApConfNetwprofilsEntry 10 }

-- {COLUMN} 1.3.6.1.4.1.2356.11.2.37.1.1.1.11
lcsSetupWlanMngmtApConfNetwprofilsEntryContinuation OBJECT-TYPE
    SYNTAX     Integer32 (0..65535)
    MAX-ACCESS read-write
    STATUS     current
    DESCRIPTION
            ""
    ::= { lcsSetupWlanMngmtApConfNetwprofilsEntry 11 }

-- {COLUMN} 1.3.6.1.4.1.2356.11.2.37.1.1.1.12
lcsSetupWlanMngmtApConfNetwprofilsEntryMinTxRate OBJECT-TYPE
    SYNTAX     INTEGER {
                  eAuto (0),
                  e1M (1),
                  e2M (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-write
    STATUS     current
    DESCRIPTION
            ""
    ::= { lcsSetupWlanMngmtApConfNetwprofilsEntry 12 }

-- {COLUMN} 1.3.6.1.4.1.2356.11.2.37.1.1.1.13
lcsSetupWlanMngmtApConfNetwprofilsEntryMaxTxRate OBJECT-TYPE
    SYNTAX     INTEGER {
                  eAuto (0),
                  e1M (1),
                  e2M (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-write
    STATUS     current
    DESCRIPTION
            ""
    ::= { lcsSetupWlanMngmtApConfNetwprofilsEntry 13 }

-- {COLUMN} 1.3.6.1.4.1.2356.11.2.37.1.1.1.14
lcsSetupWlanMngmtApConfNetwprofilsEntryBasicRate OBJECT-TYPE
    SYNTAX     INTEGER {
                  e2M (0),
                  e1M (1),
                  eAuto (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-write
    STATUS     current
    DESCRIPTION
            ""
    ::= { lcsSetupWlanMngmtApConfNetwprofilsEntry 14 }

-- {COLUMN} 1.3.6.1.4.1.2356.11.2.37.1.1.1.15
lcsSetupWlanMngmtApConfNetwprofilsEntry11bPreamble OBJECT-TYPE
    SYNTAX     INTEGER {
                  eAuto (0),
                  eLong (1)
            }
    MAX-ACCESS read-write
    STATUS     current
    DESCRIPTION
            ""
    ::= { lcsSetupWlanMngmtApConfNetwprofilsEntry 15 }

-- {COLUMN} 1.3.6.1.4.1.2356.11.2.37.1.1.1.16
lcsSetupWlanMngmtApConfNetwprofilsEntryMacFilter OBJECT-TYPE
    SYNTAX     INTEGER {
                  eNo (0),
                  eYes (1)
            }
    MAX-ACCESS read-write
    STATUS     current
    DESCRIPTION
            ""
    ::= { lcsSetupWlanMngmtApConfNetwprofilsEntry 16 }

-- {COLUMN} 1.3.6.1.4.1.2356.11.2.37.1.1.1.17
lcsSetupWlanMngmtApConfNetwprofilsEntryClBrgSupport OBJECT-TYPE
    SYNTAX     INTEGER {
                  eNo (0),
                  eYes (1),
                  eExclusive (2)
            }
    MAX-ACCESS read-write
    STATUS     current
    DESCRIPTION
            ""
    ::= { lcsSetupWlanMngmtApConfNetwprofilsEntry 17 }

-- {COLUMN} 1.3.6.1.4.1.2356.11.2.37.1.1.1.18
lcsSetupWlanMngmtApConfNetwprofilsEntryMaxStations OBJECT-TYPE
    SYNTAX     Integer32 (0..65535)
    MAX-ACCESS read-write
    STATUS     current
    DESCRIPTION
            ""
    ::= { lcsSetupWlanMngmtApConfNetwprofilsEntry 18 }

-- {COLUMN} 1.3.6.1.4.1.2356.11.2.37.1.1.1.19
lcsSetupWlanMngmtApConfNetwprofilsEntrySsidBroadcast OBJECT-TYPE
    SYNTAX     INTEGER {
                  eYes (0),
                  eNo (1),
                  eTightened (2)
            }
    MAX-ACCESS read-write
    STATUS     current
    DESCRIPTION
            ""
    ::= { lcsSetupWlanMngmtApConfNetwprofilsEntry 19 }

-- {COLUMN} 1.3.6.1.4.1.2356.11.2.37.1.1.1.21
lcsSetupWlanMngmtApConfNetwprofilsEntrySsid OBJECT-TYPE
    SYNTAX     DisplayString (SIZE(0..32))
    MAX-ACCESS read-write
    STATUS     current
    DESCRIPTION
            ""
    ::= { lcsSetupWlanMngmtApConfNetwprofilsEntry 21 }

-- {COLUMN} 1.3.6.1.4.1.2356.11.2.37.1.1.1.22
lcsSetupWlanMngmtApConfNetwprofilsEntryMinHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-write
    STATUS     current
    DESCRIPTION
            ""
    ::= { lcsSetupWlanMngmtApConfNetwprofilsEntry 22 }

-- {COLUMN} 1.3.6.1.4.1.2356.11.2.37.1.1.1.23
lcsSetupWlanMngmtApConfNetwprofilsEntryMaxHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-write
    STATUS     current
    DESCRIPTION
            ""
    ::= { lcsSetupWlanMngmtApConfNetwprofilsEntry 23 }

-- {COLUMN} 1.3.6.1.4.1.2356.11.2.37.1.1.1.24
lcsSetupWlanMngmtApConfNetwprofilsEntryShortGuardInterval OBJECT-TYPE
    SYNTAX     INTEGER {
                  eAuto (0),
                  eNo (1)
            }
    MAX-ACCESS read-write
    STATUS     current
    DESCRIPTION
            ""
    ::= { lcsSetupWlanMngmtApConfNetwprofilsEntry 24 }

-- {COLUMN} 1.3.6.1.4.1.2356.11.2.37.1.1.1.25
lcsSetupWlanMngmtApConfNetwprofilsEntryMaxSpatialStreams OBJECT-TYPE
    SYNTAX     INTEGER {
                  eAuto (0),
                  eOne (1),
                  eTwo (2),
                  eThree (3),
                  eFour (4)
            }
    MAX-ACCESS read-write
    STATUS     current
    DESCRIPTION
            ""
    ::= { lcsSetupWlanMngmtApConfNetwprofilsEntry 25 }

-- {COLUMN} 1.3.6.1.4.1.2356.11.2.37.1.1.1.26
lcsSetupWlanMngmtApConfNetwprofilsEntrySendAggregates OBJECT-TYPE
    SYNTAX     INTEGER {
                  eNo (0),
                  eYes (1)
            }
    MAX-ACCESS read-write
    STATUS     current
    DESCRIPTION
            ""
    ::= { lcsSetupWlanMngmtApConfNetwprofilsEntry 26 }

-- {COLUMN} 1.3.6.1.4.1.2356.11.2.37.1.1.1.27
lcsSetupWlanMngmtApConfNetwprofilsEntryWpa2SessionKeytypes OBJECT-TYPE
    SYNTAX     INTEGER {
                  eTkipAes (0),
                  eAes (1),
                  eTkip (2)
            }
    MAX-ACCESS read-write
    STATUS     current
    DESCRIPTION
            ""
    ::= { lcsSetupWlanMngmtApConfNetwprofilsEntry 27 }

-- {COLUMN} 1.3.6.1.4.1.2356.11.2.37.1.1.1.28
lcsSetupWlanMngmtApConfNetwprofilsEntryRadiusAccounting OBJECT-TYPE
    SYNTAX     INTEGER {
                  eNo (0),
                  eYes (1)
            }
    MAX-ACCESS read-write
    STATUS     current
    DESCRIPTION
            ""
    ::= { lcsSetupWlanMngmtApConfNetwprofilsEntry 28 }

-- {COLUMN} 1.3.6.1.4.1.2356.11.2.37.1.1.1.30
lcsSetupWlanMngmtApConfNetwprofilsEntryVlanMode OBJECT-TYPE
    SYNTAX     INTEGER {
                  eUntagged (0),
                  eTagged (1)
            }
    MAX-ACCESS read-write
    STATUS     current
    DESCRIPTION
            ""
    ::= { lcsSetupWlanMngmtApConfNetwprofilsEntry 30 }

-- {COLUMN} 1.3.6.1.4.1.2356.11.2.37.1.1.1.32
lcsSetupWlanMngmtApConfNetwprofilsEntryConnectSsidTo OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-write
    STATUS     current
    DESCRIPTION
            ""
    ::= { lcsSetupWlanMngmtApConfNetwprofilsEntry 32 }

-- {COLUMN} 1.3.6.1.4.1.2356.11.2.37.1.1.1.33
lcsSetupWlanMngmtApConfNetwprofilsEntryInterStationTraffic OBJECT-TYPE
    SYNTAX     INTEGER {
                  eNo (0),
                  eYes (1)
            }
    MAX-ACCESS read-write
    STATUS     current
    DESCRIPTION
            ""
    ::= { lcsSetupWlanMngmtApConfNetwprofilsEntry 33 }

-- {COLUMN} 1.3.6.1.4.1.2356.11.2.37.1.1.1.34
lcsSetupWlanMngmtApConfNetwprofilsEntryVlanIdnew OBJECT-TYPE
    SYNTAX     Integer32 (0..65535)
    MAX-ACCESS read-write
    STATUS     current
    DESCRIPTION
            ""
    ::= { lcsSetupWlanMngmtApConfNetwprofilsEntry 34 }

-- {COLUMN} 1.3.6.1.4.1.2356.11.2.37.1.1.1.35
lcsSetupWlanMngmtApConfNetwprofilsEntryRadiusProfile OBJECT-TYPE
    SYNTAX     DisplayString (SIZE(0..16))
    MAX-ACCESS read-write
    STATUS     current
    DESCRIPTION
            "-- empty --"
    ::= { lcsSetupWlanMngmtApConfNetwprofilsEntry 35 }

-- {COLUMN} 1.3.6.1.4.1.2356.11.2.37.1.1.1.36
lcsSetupWlanMngmtApConfNetwprofilsEntryStbcActivated OBJECT-TYPE
    SYNTAX     INTEGER {
                  eNo (0),
                  eYes (1)
            }
    MAX-ACCESS read-write
    STATUS     current
    DESCRIPTION
            "-- empty --"
    ::= { lcsSetupWlanMngmtApConfNetwprofilsEntry 36 }

-- {COLUMN} 1.3.6.1.4.1.2356.11.2.37.1.1.1.37
lcsSetupWlanMngmtApConfNetwprofilsEntryLdpcActivated OBJECT-TYPE
    SYNTAX     INTEGER {
                  eNo (0),
                  eYes (1)
            }
    MAX-ACCESS read-write
    STATUS     current
    DESCRIPTION
            "-- empty --"
    ::= { lcsSetupWlanMngmtApConfNetwprofilsEntry 37 }

-- {COLUMN} 1.3.6.1.4.1.2356.11.2.37.1.1.1.38
lcsSetupWlanMngmtApConfNetwprofilsEntryMinClientStrength OBJECT-TYPE
    SYNTAX     Integer32 (0..255)
    MAX-ACCESS read-write
    STATUS     current
    DESCRIPTION
            "-- empty --"
    ::= { lcsSetupWlanMngmtApConfNetwprofilsEntry 38 }

-- {COLUMN} 1.3.6.1.4.1.2356.11.2.37.1.1.1.39
lcsSetupWlanMngmtApConfNetwprofilsEntryIeee80211uNetworkProfile OBJECT-TYPE
    SYNTAX     DisplayString (SIZE(0..32))
    MAX-ACCESS read-write
    STATUS     current
    DESCRIPTION
            "-- empty --"
    ::= { lcsSetupWlanMngmtApConfNetwprofilsEntry 39 }

-- {COLUMN} 1.3.6.1.4.1.2356.11.2.37.1.1.1.40
lcsSetupWlanMngmtApConfNetwprofilsEntryOkc OBJECT-TYPE
    SYNTAX     INTEGER {
                  eNo (0),
                  eYes (1)
            }
    MAX-ACCESS read-write
    STATUS     current
    DESCRIPTION
            "-- empty --"
    ::= { lcsSetupWlanMngmtApConfNetwprofilsEntry 40 }

-- {COLUMN} 1.3.6.1.4.1.2356.11.2.37.1.1.1.41
lcsSetupWlanMngmtApConfNetwprofilsEntryWpa2KeyManagement OBJECT-TYPE
    SYNTAX     BITS {
                  eSha256 (5),
                  eFastRoaming (6),
                  eStandard (7)
            }
    MAX-ACCESS read-write
    STATUS     current
    DESCRIPTION
            "-- empty --"
    ::= { lcsSetupWlanMngmtApConfNetwprofilsEntry 41 }

-- {COLUMN} 1.3.6.1.4.1.2356.11.2.37.1.1.1.42
lcsSetupWlanMngmtApConfNetwprofilsEntryApsd OBJECT-TYPE
    SYNTAX     INTEGER {
                  eNo (0),
                  eYes (1)
            }
    MAX-ACCESS read-write
    STATUS     current
    DESCRIPTION
            "-- empty --"
    ::= { lcsSetupWlanMngmtApConfNetwprofilsEntry 42 }

-- {COLUMN} 1.3.6.1.4.1.2356.11.2.37.1.1.1.43
lcsSetupWlanMngmtApConfNetwprofilsEntryProtMgmtFrames OBJECT-TYPE
    SYNTAX     INTEGER {
                  eNo (0),
                  eOptional (1),
                  eMandatory (2)
            }
    MAX-ACCESS read-write
    STATUS     current
    DESCRIPTION
            "-- empty --"
    ::= { lcsSetupWlanMngmtApConfNetwprofilsEntry 43 }

-- {COLUMN} 1.3.6.1.4.1.2356.11.2.37.1.1.1.44
lcsSetupWlanMngmtApConfNetwprofilsEntryTxLimit OBJECT-TYPE
    SYNTAX     Integer32 (0..2147483647)
    MAX-ACCESS read-write
    STATUS     current
    DESCRIPTION
            "-- empty --"
    ::= { lcsSetupWlanMngmtApConfNetwprofilsEntry 44 }

-- {COLUMN} 1.3.6.1.4.1.2356.11.2.37.1.1.1.45
lcsSetupWlanMngmtApConfNetwprofilsEntryRxLimit OBJECT-TYPE
    SYNTAX     Integer32 (0..2147483647)
    MAX-ACCESS read-write
    STATUS     current
    DESCRIPTION
            "-- empty --"
    ::= { lcsSetupWlanMngmtApConfNetwprofilsEntry 45 }

-- {COLUMN} 1.3.6.1.4.1.2356.11.2.37.1.1.1.46
lcsSetupWlanMngmtApConfNetwprofilsEntryLbsTracking OBJECT-TYPE
    SYNTAX     INTEGER {
                  eNo (0),
                  eYes (1)
            }
    MAX-ACCESS read-write
    STATUS     current
    DESCRIPTION
            "-- empty --"
    ::= { lcsSetupWlanMngmtApConfNetwprofilsEntry 46 }

-- {COLUMN} 1.3.6.1.4.1.2356.11.2.37.1.1.1.47
lcsSetupWlanMngmtApConfNetwprofilsEntryLbsTrackingList OBJECT-TYPE
    SYNTAX     DisplayString (SIZE(0..32))
    MAX-ACCESS read-write
    STATUS     current
    DESCRIPTION
            "-- empty --"
    ::= { lcsSetupWlanMngmtApConfNetwprofilsEntry 47 }

-- {COLUMN} 1.3.6.1.4.1.2356.11.2.37.1.1.1.49
lcsSetupWlanMngmtApConfNetwprofilsEntry11acBeamforming OBJECT-TYPE
    SYNTAX     INTEGER {
                  eAuto (0),
                  eNo (1),
                  eSuMimo (2),
                  eMuMimo (3)
            }
    MAX-ACCESS read-write
    STATUS     current
    DESCRIPTION
            "-- empty --"
    ::= { lcsSetupWlanMngmtApConfNetwprofilsEntry 49 }

-- {COLUMN} 1.3.6.1.4.1.2356.11.2.37.1.1.1.50
lcsSetupWlanMngmtApConfNetwprofilsEntryConvertToUnicast OBJECT-TYPE
    SYNTAX     BITS {
                  eMulticast (14),
                  eDhcp (15)
            }
    MAX-ACCESS read-write
    STATUS     current
    DESCRIPTION
            "-- empty --"
    ::= { lcsSetupWlanMngmtApConfNetwprofilsEntry 50 }

-- {COLUMN} 1.3.6.1.4.1.2356.11.2.37.1.1.1.51
lcsSetupWlanMngmtApConfNetwprofilsEntryTransmitOnlyUnicasts OBJECT-TYPE
    SYNTAX     INTEGER {
                  eNo (0),
                  eYes (1)
            }
    MAX-ACCESS read-write
    STATUS     current
    DESCRIPTION
            "-- empty --"
    ::= { lcsSetupWlanMngmtApConfNetwprofilsEntry 51 }

-- {COLUMN} 1.3.6.1.4.1.2356.11.2.37.1.1.1.52
lcsSetupWlanMngmtApConfNetwprofilsEntryContinuationUseDef OBJECT-TYPE
    SYNTAX     INTEGER {
                  eNo (0),
                  eYes (1)
            }
    MAX-ACCESS read-write
    STATUS     current
    DESCRIPTION
            ""
    ::= { lcsSetupWlanMngmtApConfNetwprofilsEntry 52 }

-- {COLUMN} 1.3.6.1.4.1.2356.11.2.37.1.1.1.53
lcsSetupWlanMngmtApConfNetwprofilsEntryWpa23SessionKeytypes OBJECT-TYPE
    SYNTAX     BITS {
                  eAesGcmp256 (2),
                  eAesGcmp128 (3),
                  eAesCcmp256 (4),
                  eAesCcm (5),
                  eTkip (6)
            }
    MAX-ACCESS read-write
    STATUS     current
    DESCRIPTION
            "-- empty --"
    ::= { lcsSetupWlanMngmtApConfNetwprofilsEntry 53 }

-- {COLUMN} 1.3.6.1.4.1.2356.11.2.37.1.1.1.54
lcsSetupWlanMngmtApConfNetwprofilsEntryWpa8021xSecurityLevel OBJECT-TYPE
    SYNTAX     INTEGER {
                  eStandard (0),
                  eSuiteB128Bits (1),
                  eSuiteB192Bits (2)
            }
    MAX-ACCESS read-write
    STATUS     current
    DESCRIPTION
            "-- empty --"
    ::= { lcsSetupWlanMngmtApConfNetwprofilsEntry 54 }

-- {COLUMN} 1.3.6.1.4.1.2356.11.2.37.1.1.1.55
lcsSetupWlanMngmtApConfNetwprofilsEntryPerClientTxLimit OBJECT-TYPE
    SYNTAX     Integer32 (0..2147483647)
    MAX-ACCESS read-write
    STATUS     current
    DESCRIPTION
            "-- empty --"
    ::= { lcsSetupWlanMngmtApConfNetwprofilsEntry 55 }

-- {COLUMN} 1.3.6.1.4.1.2356.11.2.37.1.1.1.56
lcsSetupWlanMngmtApConfNetwprofilsEntryPerClientRxLimit OBJECT-TYPE
    SYNTAX     Integer32 (0..2147483647)
    MAX-ACCESS read-write
    STATUS     current
    DESCRIPTION
            "-- empty --"
    ::= { lcsSetupWlanMngmtApConfNetwprofilsEntry 56 }

-- {COLUMN} 1.3.6.1.4.1.2356.11.2.37.1.1.1.57
lcsSetupWlanMngmtApConfNetwprofilsEntryTimeframe OBJECT-TYPE
    SYNTAX     DisplayString (SIZE(0..31))
    MAX-ACCESS read-write
    STATUS     current
    DESCRIPTION
            "-- empty --"
    ::= { lcsSetupWlanMngmtApConfNetwprofilsEntry 57 }

-- {COLUMN} 1.3.6.1.4.1.2356.11.2.37.1.1.1.58
lcsSetupWlanMngmtApConfNetwprofilsEntryMinClDisStr OBJECT-TYPE
    SYNTAX     Integer32 (0..255)
    MAX-ACCESS read-write
    STATUS     current
    DESCRIPTION
            ""
    ::= { lcsSetupWlanMngmtApConfNetwprofilsEntry 58 }

-- {TABLE} 1.3.6.1.4.1.2356.11.2.37.1.2
lcsSetupWlanMngmtApConfRadioprofilsTable OBJECT-TYPE
    SYNTAX     SEQUENCE OF LcsSetupWlanMngmtApConfRadioprofilsEntry
    MAX-ACCESS not-accessible
    STATUS     current
    DESCRIPTION
            ""
    ::= { lcsSetupWlanMngmtApConf 2 }

-- {ROW} 1.3.6.1.4.1.2356.11.2.37.1.2.1
lcsSetupWlanMngmtApConfRadioprofilsEntry OBJECT-TYPE
    SYNTAX     LcsSetupWlanMngmtApConfRadioprofilsEntry
    MAX-ACCESS not-accessible
    STATUS     current
    DESCRIPTION
            ""
    INDEX {
            lcsSetupWlanMngmtApConfRadioprofilsEntryName
          }
    ::= { lcsSetupWlanMngmtApConfRadioprofilsTable 1 }

LcsSetupWlanMngmtApConfRadioprofilsEntry ::= SEQUENCE {
            lcsSetupWlanMngmtApConfRadioprofilsEntryName DisplayString,
            lcsSetupWlanMngmtApConfRadioprofilsEntryParentName DisplayString,
            lcsSetupWlanMngmtApConfRadioprofilsEntryLocVal DisplayString,
            lcsSetupWlanMngmtApConfRadioprofilsEntryCountry INTEGER,
            lcsSetupWlanMngmtApConfRadioprofilsEntryChannelList DisplayString,
            lcsSetupWlanMngmtApConfRadioprofilsEntry24ghzMode INTEGER,
            lcsSetupWlanMngmtApConfRadioprofilsEntry5ghzMode INTEGER,
            lcsSetupWlanMngmtApConfRadioprofilsEntrySubbands INTEGER,
            lcsSetupWlanMngmtApConfRadioprofilsEntryQos INTEGER,
            lcsSetupWlanMngmtApConfRadioprofilsEntryDtimPeriod Integer32,
            lcsSetupWlanMngmtApConfRadioprofilsEntryBackgroundScan Integer32,
            lcsSetupWlanMngmtApConfRadioprofilsEntryAntennaGain Integer32,
            lcsSetupWlanMngmtApConfRadioprofilsEntryTxPowerReduction Integer32,
            lcsSetupWlanMngmtApConfRadioprofilsEntryMgmtVLANId Integer32,
            lcsSetupWlanMngmtApConfRadioprofilsEntryIndoorOnlyOperation INTEGER,
            lcsSetupWlanMngmtApConfRadioprofilsEntryActVlanModOfMngdAps INTEGER,
            lcsSetupWlanMngmtApConfRadioprofilsEntryMgmtVlanMode INTEGER,
            lcsSetupWlanMngmtApConfRadioprofilsEntryMgmtVLANIdnew Integer32,
            lcsSetupWlanMngmtApConfRadioprofilsEntryReportSeenClients INTEGER,
            lcsSetupWlanMngmtApConfRadioprofilsEntryClientSteering INTEGER,
            lcsSetupWlanMngmtApConfRadioprofilsEntryPreferredBand INTEGER,
            lcsSetupWlanMngmtApConfRadioprofilsEntryPrReqAgeO Integer32,
            lcsSetupWlanMngmtApConfRadioprofilsEntryAdaptiveRfOptimization INTEGER,
            lcsSetupWlanMngmtApConfRadioprofilsEntryRxPacketSensReduction Integer32
    }

-- {COLUMN} 1.3.6.1.4.1.2356.11.2.37.1.2.1.1
lcsSetupWlanMngmtApConfRadioprofilsEntryName OBJECT-TYPE
    SYNTAX     DisplayString (SIZE(0..31))
    MAX-ACCESS read-write
    STATUS     current
    DESCRIPTION
            ""
    ::= { lcsSetupWlanMngmtApConfRadioprofilsEntry 1 }

-- {COLUMN} 1.3.6.1.4.1.2356.11.2.37.1.2.1.2
lcsSetupWlanMngmtApConfRadioprofilsEntryParentName OBJECT-TYPE
    SYNTAX     DisplayString (SIZE(0..31))
    MAX-ACCESS read-write
    STATUS     current
    DESCRIPTION
            ""
    ::= { lcsSetupWlanMngmtApConfRadioprofilsEntry 2 }

-- {COLUMN} 1.3.6.1.4.1.2356.11.2.37.1.2.1.3
lcsSetupWlanMngmtApConfRadioprofilsEntryLocVal OBJECT-TYPE
    SYNTAX     DisplayString (SIZE(0..8))
    MAX-ACCESS read-write
    STATUS     current
    DESCRIPTION
            "local values"
    ::= { lcsSetupWlanMngmtApConfRadioprofilsEntry 3 }

-- {COLUMN} 1.3.6.1.4.1.2356.11.2.37.1.2.1.4
lcsSetupWlanMngmtApConfRadioprofilsEntryCountry OBJECT-TYPE
    SYNTAX     INTEGER {
                  eDefault (0),
                  eAlbania (8),
                  eAlgeria (12),
                  eArgentina (32),
                  eAustralia (36),
                  eAustria (40),
                  eBahrain (48),
                  eBangladesh (50),
                  eBelgium (56),
                  eBosniaHerzegovina (70),
                  eBrazil (76),
                  eBruneiDarussalam (96),
                  eBulgaria (100),
                  eBelarus (112),
                  eCanada (124),
                  eChile (152),
                  eChina (156),
                  eTaiwan (158),
                  eColombia (170),
                  eCostaRica (188),
                  eCroatia (191),
                  eCyprus (196),
                  eCzech (203),
                  eDenmark (208),
                  eEcuador (218),
                  eEstonia (233),
                  eFinland (246),
                  eFrance (250),
                  eGermany (276),
                  eGhana (288),
                  eGreece (300),
                  eGuatemala (320),
                  eHonduras (340),
                  eHongKong (344),
                  eHungary (348),
                  eIceland (352),
                  eIndia (356),
                  eIndonesia (360),
                  eIreland (372),
                  eIsrael (376),
                  eItaly (380),
                  eJapan (392),
                  eJordan (400),
                  eSouthKorea (410),
                  eKuwait (414),
                  eLebanon (422),
                  eLatvia (428),
                  eLiechtenstein (438),
                  eLithuania (440),
                  eLuxembourg (442),
                  eMacau (446),
                  eMalaysia (458),
                  eMalta (470),
                  eMexico (484),
                  eMoldavia (498),
                  eMorocco (504),
                  eOman (512),
                  eNetherlands (528),
                  eNewZealand (554),
                  eNicaragua (558),
                  eNorway (578),
                  ePakistan (586),
                  ePanama (591),
                  eParaguay (600),
                  ePeru (604),
                  ePhilippines (608),
                  ePoland (616),
                  ePortugal (620),
                  ePuertoRico (630),
                  eQatar (634),
                  eRomania (642),
                  eRussia (643),
                  eSaudiArabia (682),
                  eSingapore (702),
                  eSlovak (703),
                  eSlovenia (705),
                  eSouthAfrica (710),
                  eSpain (724),
                  eSweden (752),
                  eSwitzerland (756),
                  eThailand (764),
                  eUnitedArabEmirates (784),
                  eTunisia (788),
                  eTurkey (792),
                  eUganda (800),
                  eUkraine (804),
                  eMacedonia (807),
                  eEgypt (818),
                  eUnitedKingdom (826),
                  eTanzania (834),
                  eUnitedStatesFcc (840),
                  eUruguay (858),
                  eVenezuela (862),
                  eEurope (998),
                  eEgalistan (999)
            }
    MAX-ACCESS read-write
    STATUS     current
    DESCRIPTION
            ""
    ::= { lcsSetupWlanMngmtApConfRadioprofilsEntry 4 }

-- {COLUMN} 1.3.6.1.4.1.2356.11.2.37.1.2.1.5
lcsSetupWlanMngmtApConfRadioprofilsEntryChannelList OBJECT-TYPE
    SYNTAX     DisplayString (SIZE(0..48))
    MAX-ACCESS read-write
    STATUS     current
    DESCRIPTION
            ""
    ::= { lcsSetupWlanMngmtApConfRadioprofilsEntry 5 }

-- {COLUMN} 1.3.6.1.4.1.2356.11.2.37.1.2.1.6
lcsSetupWlanMngmtApConfRadioprofilsEntry24ghzMode OBJECT-TYPE
    SYNTAX     INTEGER {
                  e11bgMixed (0),
                  e11gOnly (1),
                  e11bOnly (2),
                  e108mbps (3),
                  e11bgnMixed (4),
                  e11gnMixed (5),
                  eGreenfield (6),
                  eAuto (255)
            }
    MAX-ACCESS read-write
    STATUS     current
    DESCRIPTION
            ""
    ::= { lcsSetupWlanMngmtApConfRadioprofilsEntry 6 }

-- {COLUMN} 1.3.6.1.4.1.2356.11.2.37.1.2.1.7
lcsSetupWlanMngmtApConfRadioprofilsEntry5ghzMode OBJECT-TYPE
    SYNTAX     INTEGER {
                  eNormal (0),
                  e108mbps (3),
                  e11anMixed (4),
                  eGreenfield (5),
                  e11anacMixed (6),
                  e11nacMixed (7),
                  e11acOnly (8),
                  eAuto (255)
            }
    MAX-ACCESS read-write
    STATUS     current
    DESCRIPTION
            ""
    ::= { lcsSetupWlanMngmtApConfRadioprofilsEntry 7 }

-- {COLUMN} 1.3.6.1.4.1.2356.11.2.37.1.2.1.8
lcsSetupWlanMngmtApConfRadioprofilsEntrySubbands OBJECT-TYPE
    SYNTAX     INTEGER {
                  eBand1Plus2Plus3 (0),
                  eBand1 (1),
                  eBand2 (2),
                  eBand3 (3),
                  eBand1Plus2 (4),
                  eBand1Plus3 (5),
                  eBand2Plus3 (6)
            }
    MAX-ACCESS read-write
    STATUS     current
    DESCRIPTION
            ""
    ::= { lcsSetupWlanMngmtApConfRadioprofilsEntry 8 }

-- {COLUMN} 1.3.6.1.4.1.2356.11.2.37.1.2.1.9
lcsSetupWlanMngmtApConfRadioprofilsEntryQos OBJECT-TYPE
    SYNTAX     INTEGER {
                  eNo (0),
                  eYes (1)
            }
    MAX-ACCESS read-write
    STATUS     current
    DESCRIPTION
            ""
    ::= { lcsSetupWlanMngmtApConfRadioprofilsEntry 9 }

-- {COLUMN} 1.3.6.1.4.1.2356.11.2.37.1.2.1.10
lcsSetupWlanMngmtApConfRadioprofilsEntryDtimPeriod OBJECT-TYPE
    SYNTAX     Integer32 (0..255)
    MAX-ACCESS read-write
    STATUS     current
    DESCRIPTION
            ""
    ::= { lcsSetupWlanMngmtApConfRadioprofilsEntry 10 }

-- {COLUMN} 1.3.6.1.4.1.2356.11.2.37.1.2.1.11
lcsSetupWlanMngmtApConfRadioprofilsEntryBackgroundScan OBJECT-TYPE
    SYNTAX     Integer32 (0..2147483647)
    MAX-ACCESS read-write
    STATUS     current
    DESCRIPTION
            ""
    ::= { lcsSetupWlanMngmtApConfRadioprofilsEntry 11 }

-- {COLUMN} 1.3.6.1.4.1.2356.11.2.37.1.2.1.12
lcsSetupWlanMngmtApConfRadioprofilsEntryAntennaGain OBJECT-TYPE
    SYNTAX     Integer32 (-128..127)
    MAX-ACCESS read-write
    STATUS     current
    DESCRIPTION
            ""
    ::= { lcsSetupWlanMngmtApConfRadioprofilsEntry 12 }

-- {COLUMN} 1.3.6.1.4.1.2356.11.2.37.1.2.1.13
lcsSetupWlanMngmtApConfRadioprofilsEntryTxPowerReduction OBJECT-TYPE
    SYNTAX     Integer32 (0..255)
    MAX-ACCESS read-write
    STATUS     current
    DESCRIPTION
            ""
    ::= { lcsSetupWlanMngmtApConfRadioprofilsEntry 13 }

-- {COLUMN} 1.3.6.1.4.1.2356.11.2.37.1.2.1.14
lcsSetupWlanMngmtApConfRadioprofilsEntryMgmtVLANId OBJECT-TYPE
    SYNTAX     Integer32 (0..65535)
    MAX-ACCESS read-write
    STATUS     obsolete
    DESCRIPTION
            ""
    ::= { lcsSetupWlanMngmtApConfRadioprofilsEntry 14 }

-- {COLUMN} 1.3.6.1.4.1.2356.11.2.37.1.2.1.16
lcsSetupWlanMngmtApConfRadioprofilsEntryIndoorOnlyOperation OBJECT-TYPE
    SYNTAX     INTEGER {
                  eNo (0),
                  eYes (1)
            }
    MAX-ACCESS read-write
    STATUS     current
    DESCRIPTION
            ""
    ::= { lcsSetupWlanMngmtApConfRadioprofilsEntry 16 }

-- {COLUMN} 1.3.6.1.4.1.2356.11.2.37.1.2.1.17
lcsSetupWlanMngmtApConfRadioprofilsEntryActVlanModOfMngdAps OBJECT-TYPE
    SYNTAX     INTEGER {
                  eNo (0),
                  eYes (1)
            }
    MAX-ACCESS read-write
    STATUS     current
    DESCRIPTION
            ""
    ::= { lcsSetupWlanMngmtApConfRadioprofilsEntry 17 }

-- {COLUMN} 1.3.6.1.4.1.2356.11.2.37.1.2.1.18
lcsSetupWlanMngmtApConfRadioprofilsEntryMgmtVlanMode OBJECT-TYPE
    SYNTAX     INTEGER {
                  eUntagged (0),
                  eTagged (1)
            }
    MAX-ACCESS read-write
    STATUS     current
    DESCRIPTION
            ""
    ::= { lcsSetupWlanMngmtApConfRadioprofilsEntry 18 }

-- {COLUMN} 1.3.6.1.4.1.2356.11.2.37.1.2.1.19
lcsSetupWlanMngmtApConfRadioprofilsEntryMgmtVLANIdnew OBJECT-TYPE
    SYNTAX     Integer32 (0..65535)
    MAX-ACCESS read-write
    STATUS     current
    DESCRIPTION
            ""
    ::= { lcsSetupWlanMngmtApConfRadioprofilsEntry 19 }

-- {COLUMN} 1.3.6.1.4.1.2356.11.2.37.1.2.1.20
lcsSetupWlanMngmtApConfRadioprofilsEntryReportSeenClients OBJECT-TYPE
    SYNTAX     INTEGER {
                  eNo (0),
                  eYes (1)
            }
    MAX-ACCESS read-write
    STATUS     current
    DESCRIPTION
            ""
    ::= { lcsSetupWlanMngmtApConfRadioprofilsEntry 20 }

-- {COLUMN} 1.3.6.1.4.1.2356.11.2.37.1.2.1.21
lcsSetupWlanMngmtApConfRadioprofilsEntryClientSteering OBJECT-TYPE
    SYNTAX     INTEGER {
                  eOff (0),
                  eYes (1),
                  eOn (2),
                  eClientManagement (3)
            }
    MAX-ACCESS read-write
    STATUS     current
    DESCRIPTION
            "-- empty --"
    ::= { lcsSetupWlanMngmtApConfRadioprofilsEntry 21 }

-- {COLUMN} 1.3.6.1.4.1.2356.11.2.37.1.2.1.22
lcsSetupWlanMngmtApConfRadioprofilsEntryPreferredBand OBJECT-TYPE
    SYNTAX     INTEGER {
                  e24ghz (1),
                  e5ghz (2)
            }
    MAX-ACCESS read-write
    STATUS     current
    DESCRIPTION
            "-- empty --"
    ::= { lcsSetupWlanMngmtApConfRadioprofilsEntry 22 }

-- {COLUMN} 1.3.6.1.4.1.2356.11.2.37.1.2.1.23
lcsSetupWlanMngmtApConfRadioprofilsEntryPrReqAgeO OBJECT-TYPE
    SYNTAX     Integer32 (0..2147483647)
    MAX-ACCESS read-write
    STATUS     current
    DESCRIPTION
            ""
    ::= { lcsSetupWlanMngmtApConfRadioprofilsEntry 23 }

-- {COLUMN} 1.3.6.1.4.1.2356.11.2.37.1.2.1.24
lcsSetupWlanMngmtApConfRadioprofilsEntryAdaptiveRfOptimization OBJECT-TYPE
    SYNTAX     INTEGER {
                  eNo (0),
                  eYes (1)
            }
    MAX-ACCESS read-write
    STATUS     current
    DESCRIPTION
            "-- empty --"
    ::= { lcsSetupWlanMngmtApConfRadioprofilsEntry 24 }

-- {COLUMN} 1.3.6.1.4.1.2356.11.2.37.1.2.1.25
lcsSetupWlanMngmtApConfRadioprofilsEntryRxPacketSensReduction OBJECT-TYPE
    SYNTAX     Integer32 (0..255)
    MAX-ACCESS read-write
    STATUS     current
    DESCRIPTION
            "-- empty --"
    ::= { lcsSetupWlanMngmtApConfRadioprofilsEntry 25 }

-- {TABLE} 1.3.6.1.4.1.2356.11.2.37.1.3
lcsSetupWlanMngmtApConfCommonprofilsTable OBJECT-TYPE
    SYNTAX     SEQUENCE OF LcsSetupWlanMngmtApConfCommonprofilsEntry
    MAX-ACCESS not-accessible
    STATUS     current
    DESCRIPTION
            ""
    ::= { lcsSetupWlanMngmtApConf 3 }

-- {ROW} 1.3.6.1.4.1.2356.11.2.37.1.3.1
lcsSetupWlanMngmtApConfCommonprofilsEntry OBJECT-TYPE
    SYNTAX     LcsSetupWlanMngmtApConfCommonprofilsEntry
    MAX-ACCESS not-accessible
    STATUS     current
    DESCRIPTION
            ""
    INDEX {
            lcsSetupWlanMngmtApConfCommonprofilsEntryName
          }
    ::= { lcsSetupWlanMngmtApConfCommonprofilsTable 1 }

LcsSetupWlanMngmtApConfCommonprofilsEntry ::= SEQUENCE {
            lcsSetupWlanMngmtApConfCommonprofilsEntryName DisplayString,
            lcsSetupWlanMngmtApConfCommonprofilsEntryNetw DisplayString,
            lcsSetupWlanMngmtApConfCommonprofilsEntryApParams DisplayString,
            lcsSetupWlanMngmtApConfCommonprofilsEntryContr DisplayString,
            lcsSetupWlanMngmtApConfCommonprofilsEntryIeee80211uGeneral DisplayString,
            lcsSetupWlanMngmtApConfCommonprofilsEntryConfigurationDelay Integer32,
            lcsSetupWlanMngmtApConfCommonprofilsEntryLedProfile DisplayString,
            lcsSetupWlanMngmtApConfCommonprofilsEntryLbsGeneralProfile DisplayString,
            lcsSetupWlanMngmtApConfCommonprofilsEntryWirelessEpaperProfile DisplayString,
            lcsSetupWlanMngmtApConfCommonprofilsEntryEventTimeout Integer32,
            lcsSetupWlanMngmtApConfCommonprofilsEntryWirelessIdsProfile DisplayString
    }

-- {COLUMN} 1.3.6.1.4.1.2356.11.2.37.1.3.1.1
lcsSetupWlanMngmtApConfCommonprofilsEntryName OBJECT-TYPE
    SYNTAX     DisplayString (SIZE(0..31))
    MAX-ACCESS read-write
    STATUS     current
    DESCRIPTION
            ""
    ::= { lcsSetupWlanMngmtApConfCommonprofilsEntry 1 }

-- {COLUMN} 1.3.6.1.4.1.2356.11.2.37.1.3.1.2
lcsSetupWlanMngmtApConfCommonprofilsEntryNetw OBJECT-TYPE
    SYNTAX     DisplayString (SIZE(0..251))
    MAX-ACCESS read-write
    STATUS     current
    DESCRIPTION
            ""
    ::= { lcsSetupWlanMngmtApConfCommonprofilsEntry 2 }

-- {COLUMN} 1.3.6.1.4.1.2356.11.2.37.1.3.1.3
lcsSetupWlanMngmtApConfCommonprofilsEntryApParams OBJECT-TYPE
    SYNTAX     DisplayString (SIZE(0..31))
    MAX-ACCESS read-write
    STATUS     current
    DESCRIPTION
            ""
    ::= { lcsSetupWlanMngmtApConfCommonprofilsEntry 3 }

-- {COLUMN} 1.3.6.1.4.1.2356.11.2.37.1.3.1.4
lcsSetupWlanMngmtApConfCommonprofilsEntryContr OBJECT-TYPE
    SYNTAX     DisplayString (SIZE(0..159))
    MAX-ACCESS read-write
    STATUS     current
    DESCRIPTION
            ""
    ::= { lcsSetupWlanMngmtApConfCommonprofilsEntry 4 }

-- {COLUMN} 1.3.6.1.4.1.2356.11.2.37.1.3.1.6
lcsSetupWlanMngmtApConfCommonprofilsEntryIeee80211uGeneral OBJECT-TYPE
    SYNTAX     DisplayString (SIZE(0..31))
    MAX-ACCESS read-write
    STATUS     current
    DESCRIPTION
            "-- empty --"
    ::= { lcsSetupWlanMngmtApConfCommonprofilsEntry 6 }

-- {COLUMN} 1.3.6.1.4.1.2356.11.2.37.1.3.1.7
lcsSetupWlanMngmtApConfCommonprofilsEntryConfigurationDelay OBJECT-TYPE
    SYNTAX     Integer32 (0..2147483647)
    MAX-ACCESS read-write
    STATUS     current
    DESCRIPTION
            "-- empty --"
    ::= { lcsSetupWlanMngmtApConfCommonprofilsEntry 7 }

-- {COLUMN} 1.3.6.1.4.1.2356.11.2.37.1.3.1.8
lcsSetupWlanMngmtApConfCommonprofilsEntryLedProfile OBJECT-TYPE
    SYNTAX     DisplayString (SIZE(0..31))
    MAX-ACCESS read-write
    STATUS     current
    DESCRIPTION
            "-- empty --"
    ::= { lcsSetupWlanMngmtApConfCommonprofilsEntry 8 }

-- {COLUMN} 1.3.6.1.4.1.2356.11.2.37.1.3.1.9
lcsSetupWlanMngmtApConfCommonprofilsEntryLbsGeneralProfile OBJECT-TYPE
    SYNTAX     DisplayString (SIZE(0..31))
    MAX-ACCESS read-write
    STATUS     current
    DESCRIPTION
            "-- empty --"
    ::= { lcsSetupWlanMngmtApConfCommonprofilsEntry 9 }

-- {COLUMN} 1.3.6.1.4.1.2356.11.2.37.1.3.1.10
lcsSetupWlanMngmtApConfCommonprofilsEntryWirelessEpaperProfile OBJECT-TYPE
    SYNTAX     DisplayString (SIZE(0..31))
    MAX-ACCESS read-write
    STATUS     current
    DESCRIPTION
            "-- empty --"
    ::= { lcsSetupWlanMngmtApConfCommonprofilsEntry 10 }

-- {COLUMN} 1.3.6.1.4.1.2356.11.2.37.1.3.1.11
lcsSetupWlanMngmtApConfCommonprofilsEntryEventTimeout OBJECT-TYPE
    SYNTAX     Integer32 (0..2147483647)
    MAX-ACCESS read-write
    STATUS     current
    DESCRIPTION
            "-- empty --"
    ::= { lcsSetupWlanMngmtApConfCommonprofilsEntry 11 }

-- {COLUMN} 1.3.6.1.4.1.2356.11.2.37.1.3.1.248
lcsSetupWlanMngmtApConfCommonprofilsEntryWirelessIdsProfile OBJECT-TYPE
    SYNTAX     DisplayString (SIZE(0..31))
    MAX-ACCESS read-write
    STATUS     current
    DESCRIPTION
            "-- empty --"
    ::= { lcsSetupWlanMngmtApConfCommonprofilsEntry 248 }

-- {TABLE} 1.3.6.1.4.1.2356.11.2.37.1.4
lcsSetupWlanMngmtApConfApsTable OBJECT-TYPE
    SYNTAX     SEQUENCE OF LcsSetupWlanMngmtApConfApsEntry
    MAX-ACCESS not-accessible
    STATUS     current
    DESCRIPTION
            "accesspoints"
    ::= { lcsSetupWlanMngmtApConf 4 }

-- {ROW} 1.3.6.1.4.1.2356.11.2.37.1.4.1
lcsSetupWlanMngmtApConfApsEntry OBJECT-TYPE
    SYNTAX     LcsSetupWlanMngmtApConfApsEntry
    MAX-ACCESS not-accessible
    STATUS     current
    DESCRIPTION
            ""
    INDEX {
            lcsSetupWlanMngmtApConfApsEntryMacAddress
          }
    ::= { lcsSetupWlanMngmtApConfApsTable 1 }

LcsSetupWlanMngmtApConfApsEntry ::= SEQUENCE {
            lcsSetupWlanMngmtApConfApsEntryMacAddress DisplayString,
            lcsSetupWlanMngmtApConfApsEntryName DisplayString,
            lcsSetupWlanMngmtApConfApsEntryLocation DisplayString,
            lcsSetupWlanMngmtApConfApsEntryProfile DisplayString,
            lcsSetupWlanMngmtApConfApsEntryDeviceParameters DisplayString,
            lcsSetupWlanMngmtApConfApsEntryEncryption INTEGER,
            lcsSetupWlanMngmtApConfApsEntryWlanModule1 INTEGER,
            lcsSetupWlanMngmtApConfApsEntryWlanModule2 INTEGER,
            lcsSetupWlanMngmtApConfApsEntryModule1ChannelList DisplayString,
            lcsSetupWlanMngmtApConfApsEntryModule2ChannelList DisplayString,
            lcsSetupWlanMngmtApConfApsEntryOperating INTEGER,
            lcsSetupWlanMngmtApConfApsEntryIpAddress IpAddress,
            lcsSetupWlanMngmtApConfApsEntryNetmask IpAddress,
            lcsSetupWlanMngmtApConfApsEntryGateway IpAddress,
            lcsSetupWlanMngmtApConfApsEntryAllow40mhz INTEGER,
            lcsSetupWlanMngmtApConfApsEntryAntennaMask INTEGER,
            lcsSetupWlanMngmtApConfApsEntryApIntranet DisplayString,
            lcsSetupWlanMngmtApConfApsEntryManageFirmware INTEGER,
            lcsSetupWlanMngmtApConfApsEntryMngmtFwAddInfo INTEGER,
            lcsSetupWlanMngmtApConfApsEntryModule1AntGain DisplayString,
            lcsSetupWlanMngmtApConfApsEntryModule2AntGain DisplayString,
            lcsSetupWlanMngmtApConfApsEntryModule1TxReduct DisplayString,
            lcsSetupWlanMngmtApConfApsEntryModule2TxReduct DisplayString,
            lcsSetupWlanMngmtApConfApsEntryGroups DisplayString,
            lcsSetupWlanMngmtApConfApsEntryModule2MaxChannelBandwidth INTEGER,
            lcsSetupWlanMngmtApConfApsEntryModule1MaxChannelBandwidth INTEGER,
            lcsSetupWlanMngmtApConfApsEntryClientSteeringProfile DisplayString,
            lcsSetupWlanMngmtApConfApsEntryLbsDeviceLocationProfile DisplayString,
            lcsSetupWlanMngmtApConfApsEntryWirelessEpaperChannel INTEGER,
            lcsSetupWlanMngmtApConfApsEntryIbeaconProfile DisplayString,
            lcsSetupWlanMngmtApConfApsEntryIbeaconChannel BITS,
            lcsSetupWlanMngmtApConfApsEntryMinor Integer32,
            lcsSetupWlanMngmtApConfApsEntryIbeaconTransmitPower INTEGER,
            lcsSetupWlanMngmtApConfApsEntrySnmpComment DisplayString,
            lcsSetupWlanMngmtApConfApsEntryModule1AntGainMode INTEGER,
            lcsSetupWlanMngmtApConfApsEntryModule2AntGainMode INTEGER,
            lcsSetupWlanMngmtApConfApsEntryModule1RxPacketSensReduction DisplayString,
            lcsSetupWlanMngmtApConfApsEntryModule2RxPacketSensReduction DisplayString
    }

-- {COLUMN} 1.3.6.1.4.1.2356.11.2.37.1.4.1.1
lcsSetupWlanMngmtApConfApsEntryMacAddress OBJECT-TYPE
    SYNTAX     DisplayString (SIZE(0..12))
    MAX-ACCESS read-write
    STATUS     current
    DESCRIPTION
            ""
    ::= { lcsSetupWlanMngmtApConfApsEntry 1 }

-- {COLUMN} 1.3.6.1.4.1.2356.11.2.37.1.4.1.2
lcsSetupWlanMngmtApConfApsEntryName OBJECT-TYPE
    SYNTAX     DisplayString (SIZE(0..64))
    MAX-ACCESS read-write
    STATUS     current
    DESCRIPTION
            ""
    ::= { lcsSetupWlanMngmtApConfApsEntry 2 }

-- {COLUMN} 1.3.6.1.4.1.2356.11.2.37.1.4.1.3
lcsSetupWlanMngmtApConfApsEntryLocation OBJECT-TYPE
    SYNTAX     DisplayString (SIZE(0..251))
    MAX-ACCESS read-write
    STATUS     current
    DESCRIPTION
            ""
    ::= { lcsSetupWlanMngmtApConfApsEntry 3 }

-- {COLUMN} 1.3.6.1.4.1.2356.11.2.37.1.4.1.4
lcsSetupWlanMngmtApConfApsEntryProfile OBJECT-TYPE
    SYNTAX     DisplayString (SIZE(0..31))
    MAX-ACCESS read-write
    STATUS     current
    DESCRIPTION
            ""
    ::= { lcsSetupWlanMngmtApConfApsEntry 4 }

-- {COLUMN} 1.3.6.1.4.1.2356.11.2.37.1.4.1.5
lcsSetupWlanMngmtApConfApsEntryDeviceParameters OBJECT-TYPE
    SYNTAX     DisplayString (SIZE(0..31))
    MAX-ACCESS read-write
    STATUS     current
    DESCRIPTION
            ""
    ::= { lcsSetupWlanMngmtApConfApsEntry 5 }

-- {COLUMN} 1.3.6.1.4.1.2356.11.2.37.1.4.1.6
lcsSetupWlanMngmtApConfApsEntryEncryption OBJECT-TYPE
    SYNTAX     INTEGER {
                  eDefault (0),
                  eDtls (1),
                  eNo (2)
            }
    MAX-ACCESS read-write
    STATUS     current
    DESCRIPTION
            ""
    ::= { lcsSetupWlanMngmtApConfApsEntry 6 }

-- {COLUMN} 1.3.6.1.4.1.2356.11.2.37.1.4.1.7
lcsSetupWlanMngmtApConfApsEntryWlanModule1 OBJECT-TYPE
    SYNTAX     INTEGER {
                  eDefault (0),
                  e24ghz (1),
                  e5ghz (2),
                  eOff (3),
                  eAuto (255)
            }
    MAX-ACCESS read-write
    STATUS     current
    DESCRIPTION
            ""
    ::= { lcsSetupWlanMngmtApConfApsEntry 7 }

-- {COLUMN} 1.3.6.1.4.1.2356.11.2.37.1.4.1.8
lcsSetupWlanMngmtApConfApsEntryWlanModule2 OBJECT-TYPE
    SYNTAX     INTEGER {
                  eDefault (0),
                  e24ghz (1),
                  e5ghz (2),
                  eOff (3),
                  eAuto (255)
            }
    MAX-ACCESS read-write
    STATUS     current
    DESCRIPTION
            ""
    ::= { lcsSetupWlanMngmtApConfApsEntry 8 }

-- {COLUMN} 1.3.6.1.4.1.2356.11.2.37.1.4.1.9
lcsSetupWlanMngmtApConfApsEntryModule1ChannelList OBJECT-TYPE
    SYNTAX     DisplayString (SIZE(0..48))
    MAX-ACCESS read-write
    STATUS     current
    DESCRIPTION
            ""
    ::= { lcsSetupWlanMngmtApConfApsEntry 9 }

-- {COLUMN} 1.3.6.1.4.1.2356.11.2.37.1.4.1.10
lcsSetupWlanMngmtApConfApsEntryModule2ChannelList OBJECT-TYPE
    SYNTAX     DisplayString (SIZE(0..48))
    MAX-ACCESS read-write
    STATUS     current
    DESCRIPTION
            ""
    ::= { lcsSetupWlanMngmtApConfApsEntry 10 }

-- {COLUMN} 1.3.6.1.4.1.2356.11.2.37.1.4.1.11
lcsSetupWlanMngmtApConfApsEntryOperating OBJECT-TYPE
    SYNTAX     INTEGER {
                  eYes (0),
                  eNo (1)
            }
    MAX-ACCESS read-write
    STATUS     current
    DESCRIPTION
            ""
    ::= { lcsSetupWlanMngmtApConfApsEntry 11 }

-- {COLUMN} 1.3.6.1.4.1.2356.11.2.37.1.4.1.12
lcsSetupWlanMngmtApConfApsEntryIpAddress OBJECT-TYPE
    SYNTAX     IpAddress
    MAX-ACCESS read-write
    STATUS     current
    DESCRIPTION
            ""
    ::= { lcsSetupWlanMngmtApConfApsEntry 12 }

-- {COLUMN} 1.3.6.1.4.1.2356.11.2.37.1.4.1.13
lcsSetupWlanMngmtApConfApsEntryNetmask OBJECT-TYPE
    SYNTAX     IpAddress
    MAX-ACCESS read-write
    STATUS     current
    DESCRIPTION
            ""
    ::= { lcsSetupWlanMngmtApConfApsEntry 13 }

-- {COLUMN} 1.3.6.1.4.1.2356.11.2.37.1.4.1.14
lcsSetupWlanMngmtApConfApsEntryGateway OBJECT-TYPE
    SYNTAX     IpAddress
    MAX-ACCESS read-write
    STATUS     current
    DESCRIPTION
            ""
    ::= { lcsSetupWlanMngmtApConfApsEntry 14 }

-- {COLUMN} 1.3.6.1.4.1.2356.11.2.37.1.4.1.15
lcsSetupWlanMngmtApConfApsEntryAllow40mhz OBJECT-TYPE
    SYNTAX     INTEGER {
                  eAuto (0),
                  eNo (1)
            }
    MAX-ACCESS read-write
    STATUS     current
    DESCRIPTION
            ""
    ::= { lcsSetupWlanMngmtApConfApsEntry 15 }

-- {COLUMN} 1.3.6.1.4.1.2356.11.2.37.1.4.1.16
lcsSetupWlanMngmtApConfApsEntryAntennaMask OBJECT-TYPE
    SYNTAX     INTEGER {
                  eAuto (0),
                  eAntenna1 (1),
                  eAntenna1Plus2 (3),
                  eAntenna1Plus3 (5),
                  eAntenna1Plus2Plus3 (7),
                  eAntenna1Plus2Plus3Plus4 (15)
            }
    MAX-ACCESS read-write
    STATUS     current
    DESCRIPTION
            ""
    ::= { lcsSetupWlanMngmtApConfApsEntry 16 }

-- {COLUMN} 1.3.6.1.4.1.2356.11.2.37.1.4.1.17
lcsSetupWlanMngmtApConfApsEntryApIntranet OBJECT-TYPE
    SYNTAX     DisplayString (SIZE(0..31))
    MAX-ACCESS read-write
    STATUS     current
    DESCRIPTION
            ""
    ::= { lcsSetupWlanMngmtApConfApsEntry 17 }

-- {COLUMN} 1.3.6.1.4.1.2356.11.2.37.1.4.1.18
lcsSetupWlanMngmtApConfApsEntryManageFirmware OBJECT-TYPE
    SYNTAX     INTEGER {
                  eYes (0),
                  eNo (1)
            }
    MAX-ACCESS read-write
    STATUS     current
    DESCRIPTION
            ""
    ::= { lcsSetupWlanMngmtApConfApsEntry 18 }

-- {COLUMN} 1.3.6.1.4.1.2356.11.2.37.1.4.1.19
lcsSetupWlanMngmtApConfApsEntryMngmtFwAddInfo OBJECT-TYPE
    SYNTAX     INTEGER {
                  eDisabledDueToErrorDuringUpdate (1),
                  eDisabledByManualUpload (2)
            }
    MAX-ACCESS read-write
    STATUS     current
    DESCRIPTION
            ""
    ::= { lcsSetupWlanMngmtApConfApsEntry 19 }

-- {COLUMN} 1.3.6.1.4.1.2356.11.2.37.1.4.1.20
lcsSetupWlanMngmtApConfApsEntryModule1AntGain OBJECT-TYPE
    SYNTAX     DisplayString (SIZE(0..4))
    MAX-ACCESS read-write
    STATUS     current
    DESCRIPTION
            ""
    ::= { lcsSetupWlanMngmtApConfApsEntry 20 }

-- {COLUMN} 1.3.6.1.4.1.2356.11.2.37.1.4.1.21
lcsSetupWlanMngmtApConfApsEntryModule2AntGain OBJECT-TYPE
    SYNTAX     DisplayString (SIZE(0..4))
    MAX-ACCESS read-write
    STATUS     current
    DESCRIPTION
            ""
    ::= { lcsSetupWlanMngmtApConfApsEntry 21 }

-- {COLUMN} 1.3.6.1.4.1.2356.11.2.37.1.4.1.22
lcsSetupWlanMngmtApConfApsEntryModule1TxReduct OBJECT-TYPE
    SYNTAX     DisplayString (SIZE(0..3))
    MAX-ACCESS read-write
    STATUS     current
    DESCRIPTION
            ""
    ::= { lcsSetupWlanMngmtApConfApsEntry 22 }

-- {COLUMN} 1.3.6.1.4.1.2356.11.2.37.1.4.1.23
lcsSetupWlanMngmtApConfApsEntryModule2TxReduct OBJECT-TYPE
    SYNTAX     DisplayString (SIZE(0..3))
    MAX-ACCESS read-write
    STATUS     current
    DESCRIPTION
            ""
    ::= { lcsSetupWlanMngmtApConfApsEntry 23 }

-- {COLUMN} 1.3.6.1.4.1.2356.11.2.37.1.4.1.24
lcsSetupWlanMngmtApConfApsEntryGroups OBJECT-TYPE
    SYNTAX     DisplayString (SIZE(0..251))
    MAX-ACCESS read-write
    STATUS     current
    DESCRIPTION
            "-- empty --"
    ::= { lcsSetupWlanMngmtApConfApsEntry 24 }

-- {COLUMN} 1.3.6.1.4.1.2356.11.2.37.1.4.1.25
lcsSetupWlanMngmtApConfApsEntryModule2MaxChannelBandwidth OBJECT-TYPE
    SYNTAX     INTEGER {
                  e20mhz (0),
                  e40mhz (1),
                  e80mhz (2),
                  e160mhz (3),
                  e80Plus80mhz (4),
                  eAuto (255)
            }
    MAX-ACCESS read-write
    STATUS     current
    DESCRIPTION
            "-- empty --"
    ::= { lcsSetupWlanMngmtApConfApsEntry 25 }

-- {COLUMN} 1.3.6.1.4.1.2356.11.2.37.1.4.1.26
lcsSetupWlanMngmtApConfApsEntryModule1MaxChannelBandwidth OBJECT-TYPE
    SYNTAX     INTEGER {
                  e20mhz (0),
                  e40mhz (1),
                  e80mhz (2),
                  e160mhz (3),
                  e80Plus80mhz (4),
                  eAuto (255)
            }
    MAX-ACCESS read-write
    STATUS     current
    DESCRIPTION
            "-- empty --"
    ::= { lcsSetupWlanMngmtApConfApsEntry 26 }

-- {COLUMN} 1.3.6.1.4.1.2356.11.2.37.1.4.1.27
lcsSetupWlanMngmtApConfApsEntryClientSteeringProfile OBJECT-TYPE
    SYNTAX     DisplayString (SIZE(0..31))
    MAX-ACCESS read-write
    STATUS     current
    DESCRIPTION
            "-- empty --"
    ::= { lcsSetupWlanMngmtApConfApsEntry 27 }

-- {COLUMN} 1.3.6.1.4.1.2356.11.2.37.1.4.1.28
lcsSetupWlanMngmtApConfApsEntryLbsDeviceLocationProfile OBJECT-TYPE
    SYNTAX     DisplayString (SIZE(0..32))
    MAX-ACCESS read-write
    STATUS     current
    DESCRIPTION
            "-- empty --"
    ::= { lcsSetupWlanMngmtApConfApsEntry 28 }

-- {COLUMN} 1.3.6.1.4.1.2356.11.2.37.1.4.1.29
lcsSetupWlanMngmtApConfApsEntryWirelessEpaperChannel OBJECT-TYPE
    SYNTAX     INTEGER {
                  e2404mhz (0),
                  e2410mhz (1),
                  e2422mhz (2),
                  e2425mhz (3),
                  e2442mhz (4),
                  e2450mhz (5),
                  e2462mhz (6),
                  e2470mhz (7),
                  e2474mhz (8),
                  e2477mhz (9),
                  e2480mhz (10),
                  eAuto (255)
            }
    MAX-ACCESS read-write
    STATUS     current
    DESCRIPTION
            "-- empty --"
    ::= { lcsSetupWlanMngmtApConfApsEntry 29 }

-- {COLUMN} 1.3.6.1.4.1.2356.11.2.37.1.4.1.30
lcsSetupWlanMngmtApConfApsEntryIbeaconProfile OBJECT-TYPE
    SYNTAX     DisplayString (SIZE(0..31))
    MAX-ACCESS read-write
    STATUS     current
    DESCRIPTION
            "-- empty --"
    ::= { lcsSetupWlanMngmtApConfApsEntry 30 }

-- {COLUMN} 1.3.6.1.4.1.2356.11.2.37.1.4.1.31
lcsSetupWlanMngmtApConfApsEntryIbeaconChannel OBJECT-TYPE
    SYNTAX     BITS {
                  e2480mhz (5),
                  e2426mhz (6),
                  e2402mhz (7)
            }
    MAX-ACCESS read-write
    STATUS     current
    DESCRIPTION
            "-- empty --"
    ::= { lcsSetupWlanMngmtApConfApsEntry 31 }

-- {COLUMN} 1.3.6.1.4.1.2356.11.2.37.1.4.1.32
lcsSetupWlanMngmtApConfApsEntryMinor OBJECT-TYPE
    SYNTAX     Integer32 (0..65535)
    MAX-ACCESS read-write
    STATUS     current
    DESCRIPTION
            "-- empty --"
    ::= { lcsSetupWlanMngmtApConfApsEntry 32 }

-- {COLUMN} 1.3.6.1.4.1.2356.11.2.37.1.4.1.33
lcsSetupWlanMngmtApConfApsEntryIbeaconTransmitPower OBJECT-TYPE
    SYNTAX     INTEGER {
                  eLow (0),
                  eMedium (1),
                  eHigh (2)
            }
    MAX-ACCESS read-write
    STATUS     current
    DESCRIPTION
            "-- empty --"
    ::= { lcsSetupWlanMngmtApConfApsEntry 33 }

-- {COLUMN} 1.3.6.1.4.1.2356.11.2.37.1.4.1.34
lcsSetupWlanMngmtApConfApsEntrySnmpComment OBJECT-TYPE
    SYNTAX     DisplayString (SIZE(0..251))
    MAX-ACCESS read-write
    STATUS     current
    DESCRIPTION
            "-- empty --"
    ::= { lcsSetupWlanMngmtApConfApsEntry 34 }

-- {COLUMN} 1.3.6.1.4.1.2356.11.2.37.1.4.1.35
lcsSetupWlanMngmtApConfApsEntryModule1AntGainMode OBJECT-TYPE
    SYNTAX     INTEGER {
                  eStandard (0),
                  eUserDefined (1)
            }
    MAX-ACCESS read-write
    STATUS     current
    DESCRIPTION
            "-- empty --"
    ::= { lcsSetupWlanMngmtApConfApsEntry 35 }

-- {COLUMN} 1.3.6.1.4.1.2356.11.2.37.1.4.1.36
lcsSetupWlanMngmtApConfApsEntryModule2AntGainMode OBJECT-TYPE
    SYNTAX     INTEGER {
                  eStandard (0),
                  eUserDefined (1)
            }
    MAX-ACCESS read-write
    STATUS     current
    DESCRIPTION
            "-- empty --"
    ::= { lcsSetupWlanMngmtApConfApsEntry 36 }

-- {COLUMN} 1.3.6.1.4.1.2356.11.2.37.1.4.1.37
lcsSetupWlanMngmtApConfApsEntryModule1RxPacketSensReduction OBJECT-TYPE
    SYNTAX     DisplayString (SIZE(0..3))
    MAX-ACCESS read-write
    STATUS     current
    DESCRIPTION
            "-- empty --"
    ::= { lcsSetupWlanMngmtApConfApsEntry 37 }

-- {COLUMN} 1.3.6.1.4.1.2356.11.2.37.1.4.1.38
lcsSetupWlanMngmtApConfApsEntryModule2RxPacketSensReduction OBJECT-TYPE
    SYNTAX     DisplayString (SIZE(0..3))
    MAX-ACCESS read-write
    STATUS     current
    DESCRIPTION
            "-- empty --"
    ::= { lcsSetupWlanMngmtApConfApsEntry 38 }

-- {SCALAR} 1.3.6.1.4.1.2356.11.2.37.1.5
lcsSetupWlanMngmtApConfWlanModul1Default OBJECT-TYPE
    SYNTAX     INTEGER {
                  e24ghz (1),
                  e5ghz (2),
                  eOff (3),
                  eAuto (255)
            }
    MAX-ACCESS read-write
    STATUS     current
    DESCRIPTION
            ""
    ::= { lcsSetupWlanMngmtApConf 5 }

-- {SCALAR} 1.3.6.1.4.1.2356.11.2.37.1.6
lcsSetupWlanMngmtApConfWlanModul2Default OBJECT-TYPE
    SYNTAX     INTEGER {
                  e24ghz (1),
                  e5ghz (2),
                  eOff (3),
                  eAuto (255)
            }
    MAX-ACCESS read-write
    STATUS     current
    DESCRIPTION
            ""
    ::= { lcsSetupWlanMngmtApConf 6 }

-- {SCALAR} 1.3.6.1.4.1.2356.11.2.37.1.7
lcsSetupWlanMngmtApConfControlConnectionEncryptionDefault OBJECT-TYPE
    SYNTAX     INTEGER {
                  eDtls (1),
                  eNo (2)
            }
    MAX-ACCESS read-write
    STATUS     current
    DESCRIPTION
            ""
    ::= { lcsSetupWlanMngmtApConf 7 }

-- {SCALAR} 1.3.6.1.4.1.2356.11.2.37.1.8
lcsSetupWlanMngmtApConfCountryDefault OBJECT-TYPE
    SYNTAX     INTEGER {
                  eAlbania (8),
                  eAlgeria (12),
                  eArgentina (32),
                  eAustralia (36),
                  eAustria (40),
                  eBahrain (48),
                  eBangladesh (50),
                  eBelgium (56),
                  eBosniaHerzegovina (70),
                  eBrazil (76),
                  eBruneiDarussalam (96),
                  eBulgaria (100),
                  eBelarus (112),
                  eCanada (124),
                  eChile (152),
                  eChina (156),
                  eTaiwan (158),
                  eColombia (170),
                  eCostaRica (188),
                  eCroatia (191),
                  eCyprus (196),
                  eCzech (203),
                  eDenmark (208),
                  eEcuador (218),
                  eEstonia (233),
                  eFinland (246),
                  eFrance (250),
                  eGermany (276),
                  eGhana (288),
                  eGreece (300),
                  eGuatemala (320),
                  eHonduras (340),
                  eHongKong (344),
                  eHungary (348),
                  eIceland (352),
                  eIndia (356),
                  eIndonesia (360),
                  eIreland (372),
                  eIsrael (376),
                  eItaly (380),
                  eJapan (392),
                  eJordan (400),
                  eSouthKorea (410),
                  eKuwait (414),
                  eLebanon (422),
                  eLatvia (428),
                  eLiechtenstein (438),
                  eLithuania (440),
                  eLuxembourg (442),
                  eMacau (446),
                  eMalaysia (458),
                  eMalta (470),
                  eMexico (484),
                  eMoldavia (498),
                  eMorocco (504),
                  eOman (512),
                  eNetherlands (528),
                  eNewZealand (554),
                  eNicaragua (558),
                  eNorway (578),
                  ePakistan (586),
                  ePanama (591),
                  eParaguay (600),
                  ePeru (604),
                  ePhilippines (608),
                  ePoland (616),
                  ePortugal (620),
                  ePuertoRico (630),
                  eQatar (634),
                  eRomania (642),
                  eRussia (643),
                  eSaudiArabia (682),
                  eSingapore (702),
                  eSlovak (703),
                  eSlovenia (705),
                  eSouthAfrica (710),
                  eSpain (724),
                  eSweden (752),
                  eSwitzerland (756),
                  eThailand (764),
                  eUnitedArabEmirates (784),
                  eTunisia (788),
                  eTurkey (792),
                  eUganda (800),
                  eUkraine (804),
                  eMacedonia (807),
                  eEgypt (818),
                  eUnitedKingdom (826),
                  eTanzania (834),
                  eUnitedStatesFcc (840),
                  eUruguay (858),
                  eVenezuela (862),
                  eEurope (998),
                  eEgalistan (999)
            }
    MAX-ACCESS read-write
    STATUS     current
    DESCRIPTION
            ""
    ::= { lcsSetupWlanMngmtApConf 8 }

-- {TABLE} 1.3.6.1.4.1.2356.11.2.37.1.9
lcsSetupWlanMngmtApConfApIntranetsTable OBJECT-TYPE
    SYNTAX     SEQUENCE OF LcsSetupWlanMngmtApConfApIntranetsEntry
    MAX-ACCESS not-accessible
    STATUS     current
    DESCRIPTION
            ""
    ::= { lcsSetupWlanMngmtApConf 9 }

-- {ROW} 1.3.6.1.4.1.2356.11.2.37.1.9.1
lcsSetupWlanMngmtApConfApIntranetsEntry OBJECT-TYPE
    SYNTAX     LcsSetupWlanMngmtApConfApIntranetsEntry
    MAX-ACCESS not-accessible
    STATUS     current
    DESCRIPTION
            ""
    INDEX {
            lcsSetupWlanMngmtApConfApIntranetsEntryName
          }
    ::= { lcsSetupWlanMngmtApConfApIntranetsTable 1 }

LcsSetupWlanMngmtApConfApIntranetsEntry ::= SEQUENCE {
            lcsSetupWlanMngmtApConfApIntranetsEntryName DisplayString,
            lcsSetupWlanMngmtApConfApIntranetsEntryParentName DisplayString,
            lcsSetupWlanMngmtApConfApIntranetsEntryLocVal DisplayString,
            lcsSetupWlanMngmtApConfApIntranetsEntryDomainName DisplayString,
            lcsSetupWlanMngmtApConfApIntranetsEntryNetmask IpAddress,
            lcsSetupWlanMngmtApConfApIntranetsEntryGateway IpAddress,
            lcsSetupWlanMngmtApConfApIntranetsEntryPrimaryDnsSrv IpAddress,
            lcsSetupWlanMngmtApConfApIntranetsEntrySecondaryDnsSrv IpAddress,
            lcsSetupWlanMngmtApConfApIntranetsEntryIpv4ConfigPoolStart DisplayString,
            lcsSetupWlanMngmtApConfApIntranetsEntryIpv4ConfigPoolEnd DisplayString
    }

-- {COLUMN} 1.3.6.1.4.1.2356.11.2.37.1.9.1.1
lcsSetupWlanMngmtApConfApIntranetsEntryName OBJECT-TYPE
    SYNTAX     DisplayString (SIZE(0..31))
    MAX-ACCESS read-write
    STATUS     current
    DESCRIPTION
            ""
    ::= { lcsSetupWlanMngmtApConfApIntranetsEntry 1 }

-- {COLUMN} 1.3.6.1.4.1.2356.11.2.37.1.9.1.2
lcsSetupWlanMngmtApConfApIntranetsEntryParentName OBJECT-TYPE
    SYNTAX     DisplayString (SIZE(0..31))
    MAX-ACCESS read-write
    STATUS     current
    DESCRIPTION
            ""
    ::= { lcsSetupWlanMngmtApConfApIntranetsEntry 2 }

-- {COLUMN} 1.3.6.1.4.1.2356.11.2.37.1.9.1.3
lcsSetupWlanMngmtApConfApIntranetsEntryLocVal OBJECT-TYPE
    SYNTAX     DisplayString (SIZE(0..2))
    MAX-ACCESS read-write
    STATUS     current
    DESCRIPTION
            "local values"
    ::= { lcsSetupWlanMngmtApConfApIntranetsEntry 3 }

-- {COLUMN} 1.3.6.1.4.1.2356.11.2.37.1.9.1.4
lcsSetupWlanMngmtApConfApIntranetsEntryDomainName OBJECT-TYPE
    SYNTAX     DisplayString (SIZE(0..63))
    MAX-ACCESS read-write
    STATUS     current
    DESCRIPTION
            ""
    ::= { lcsSetupWlanMngmtApConfApIntranetsEntry 4 }

-- {COLUMN} 1.3.6.1.4.1.2356.11.2.37.1.9.1.5
lcsSetupWlanMngmtApConfApIntranetsEntryNetmask OBJECT-TYPE
    SYNTAX     IpAddress
    MAX-ACCESS read-write
    STATUS     current
    DESCRIPTION
            ""
    ::= { lcsSetupWlanMngmtApConfApIntranetsEntry 5 }

-- {COLUMN} 1.3.6.1.4.1.2356.11.2.37.1.9.1.6
lcsSetupWlanMngmtApConfApIntranetsEntryGateway OBJECT-TYPE
    SYNTAX     IpAddress
    MAX-ACCESS read-write
    STATUS     current
    DESCRIPTION
            ""
    ::= { lcsSetupWlanMngmtApConfApIntranetsEntry 6 }

-- {COLUMN} 1.3.6.1.4.1.2356.11.2.37.1.9.1.7
lcsSetupWlanMngmtApConfApIntranetsEntryPrimaryDnsSrv OBJECT-TYPE
    SYNTAX     IpAddress
    MAX-ACCESS read-write
    STATUS     current
    DESCRIPTION
            ""
    ::= { lcsSetupWlanMngmtApConfApIntranetsEntry 7 }

-- {COLUMN} 1.3.6.1.4.1.2356.11.2.37.1.9.1.8
lcsSetupWlanMngmtApConfApIntranetsEntrySecondaryDnsSrv OBJECT-TYPE
    SYNTAX     IpAddress
    MAX-ACCESS read-write
    STATUS     current
    DESCRIPTION
            ""
    ::= { lcsSetupWlanMngmtApConfApIntranetsEntry 8 }

-- {COLUMN} 1.3.6.1.4.1.2356.11.2.37.1.9.1.9
lcsSetupWlanMngmtApConfApIntranetsEntryIpv4ConfigPoolStart OBJECT-TYPE
    SYNTAX     DisplayString (SIZE(0..15))
    MAX-ACCESS read-write
    STATUS     current
    DESCRIPTION
            "-- empty --"
    ::= { lcsSetupWlanMngmtApConfApIntranetsEntry 9 }

-- {COLUMN} 1.3.6.1.4.1.2356.11.2.37.1.9.1.10
lcsSetupWlanMngmtApConfApIntranetsEntryIpv4ConfigPoolEnd OBJECT-TYPE
    SYNTAX     DisplayString (SIZE(0..15))
    MAX-ACCESS read-write
    STATUS     current
    DESCRIPTION
            "-- empty --"
    ::= { lcsSetupWlanMngmtApConfApIntranetsEntry 10 }

-- {TABLE} 1.3.6.1.4.1.2356.11.2.37.1.10
lcsSetupWlanMngmtApConfPredefIntranetsTable OBJECT-TYPE
    SYNTAX     SEQUENCE OF LcsSetupWlanMngmtApConfPredefIntranetsEntry
    MAX-ACCESS not-accessible
    STATUS     current
    DESCRIPTION
            ""
    ::= { lcsSetupWlanMngmtApConf 10 }

-- {ROW} 1.3.6.1.4.1.2356.11.2.37.1.10.1
lcsSetupWlanMngmtApConfPredefIntranetsEntry OBJECT-TYPE
    SYNTAX     LcsSetupWlanMngmtApConfPredefIntranetsEntry
    MAX-ACCESS not-accessible
    STATUS     current
    DESCRIPTION
            ""
    INDEX {
            lcsSetupWlanMngmtApConfPredefIntranetsEntryName
          }
    ::= { lcsSetupWlanMngmtApConfPredefIntranetsTable 1 }

LcsSetupWlanMngmtApConfPredefIntranetsEntry ::= SEQUENCE {
            lcsSetupWlanMngmtApConfPredefIntranetsEntryName DisplayString
    }

-- {COLUMN} 1.3.6.1.4.1.2356.11.2.37.1.10.1.1
lcsSetupWlanMngmtApConfPredefIntranetsEntryName OBJECT-TYPE
    SYNTAX     DisplayString (SIZE(0..15))
    MAX-ACCESS read-only
    STATUS     current
    DESCRIPTION
            ""
    ::= { lcsSetupWlanMngmtApConfPredefIntranetsEntry 1 }

-- {SCALAR} 1.3.6.1.4.1.2356.11.2.37.1.12
lcsSetupWlanMngmtApConfDscpForControlPackets OBJECT-TYPE
    SYNTAX     INTEGER {
                  eBestEffort (0),
                  eAssuredForwarding11 (40),
                  eAssuredForwarding12 (48),
                  eAssuredForwarding13 (56),
                  eAssuredForwarding21 (72),
                  eAssuredForwarding22 (80),
                  eAssuredForwarding23 (88),
                  eAssuredForwarding31 (104),
                  eAssuredForwarding32 (112),
                  eAssuredForwarding33 (120),
                  eAssuredForwarding41 (136),
                  eAssuredForwarding42 (144),
                  eAssuredForwarding43 (152),
                  eExpeditedForwarding (184)
            }
    MAX-ACCESS read-write
    STATUS     current
    DESCRIPTION
            ""
    ::= { lcsSetupWlanMngmtApConf 12 }

-- {SCALAR} 1.3.6.1.4.1.2356.11.2.37.1.13
lcsSetupWlanMngmtApConfDscpForDataPackets OBJECT-TYPE
    SYNTAX     INTEGER {
                  eBestEffort (0),
                  eAssuredForwarding11 (40),
                  eAssuredForwarding12 (48),
                  eAssuredForwarding13 (56),
                  eAssuredForwarding21 (72),
                  eAssuredForwarding22 (80),
                  eAssuredForwarding23 (88),
                  eAssuredForwarding31 (104),
                  eAssuredForwarding32 (112),
                  eAssuredForwarding33 (120),
                  eAssuredForwarding41 (136),
                  eAssuredForwarding42 (144),
                  eAssuredForwarding43 (152),
                  eExpeditedForwarding (184)
            }
    MAX-ACCESS read-write
    STATUS     current
    DESCRIPTION
            ""
    ::= { lcsSetupWlanMngmtApConf 13 }

-- {TABLE} 1.3.6.1.4.1.2356.11.2.37.1.14
lcsSetupWlanMngmtApConfMulticastNetworksTable OBJECT-TYPE
    SYNTAX     SEQUENCE OF LcsSetupWlanMngmtApConfMulticastNetworksEntry
    MAX-ACCESS not-accessible
    STATUS     current
    DESCRIPTION
            ""
    ::= { lcsSetupWlanMngmtApConf 14 }

-- {ROW} 1.3.6.1.4.1.2356.11.2.37.1.14.1
lcsSetupWlanMngmtApConfMulticastNetworksEntry OBJECT-TYPE
    SYNTAX     LcsSetupWlanMngmtApConfMulticastNetworksEntry
    MAX-ACCESS not-accessible
    STATUS     current
    DESCRIPTION
            ""
    INDEX {
            lcsSetupWlanMngmtApConfMulticastNetworksEntryBridgeInterface
          }
    ::= { lcsSetupWlanMngmtApConfMulticastNetworksTable 1 }

LcsSetupWlanMngmtApConfMulticastNetworksEntry ::= SEQUENCE {
            lcsSetupWlanMngmtApConfMulticastNetworksEntryBridgeInterface INTEGER,
            lcsSetupWlanMngmtApConfMulticastNetworksEntryActive INTEGER,
            lcsSetupWlanMngmtApConfMulticastNetworksEntryMulticastAddress IpAddress,
            lcsSetupWlanMngmtApConfMulticastNetworksEntryMulticastPort Integer32,
            lcsSetupWlanMngmtApConfMulticastNetworksEntryLoopbackAddr DisplayString
    }

-- {COLUMN} 1.3.6.1.4.1.2356.11.2.37.1.14.1.1
lcsSetupWlanMngmtApConfMulticastNetworksEntryBridgeInterface OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-only
    STATUS     current
    DESCRIPTION
            ""
    ::= { lcsSetupWlanMngmtApConfMulticastNetworksEntry 1 }

-- {COLUMN} 1.3.6.1.4.1.2356.11.2.37.1.14.1.2
lcsSetupWlanMngmtApConfMulticastNetworksEntryActive OBJECT-TYPE
    SYNTAX     INTEGER {
                  eNo (0),
                  eYes (1)
            }
    MAX-ACCESS read-write
    STATUS     current
    DESCRIPTION
            ""
    ::= { lcsSetupWlanMngmtApConfMulticastNetworksEntry 2 }

-- {COLUMN} 1.3.6.1.4.1.2356.11.2.37.1.14.1.3
lcsSetupWlanMngmtApConfMulticastNetworksEntryMulticastAddress OBJECT-TYPE
    SYNTAX     IpAddress
    MAX-ACCESS read-write
    STATUS     current
    DESCRIPTION
            ""
    ::= { lcsSetupWlanMngmtApConfMulticastNetworksEntry 3 }

-- {COLUMN} 1.3.6.1.4.1.2356.11.2.37.1.14.1.4
lcsSetupWlanMngmtApConfMulticastNetworksEntryMulticastPort OBJECT-TYPE
    SYNTAX     Integer32 (0..65535)
    MAX-ACCESS read-write
    STATUS     current
    DESCRIPTION
            ""
    ::= { lcsSetupWlanMngmtApConfMulticastNetworksEntry 4 }

-- {COLUMN} 1.3.6.1.4.1.2356.11.2.37.1.14.1.5
lcsSetupWlanMngmtApConfMulticastNetworksEntryLoopbackAddr OBJECT-TYPE
    SYNTAX     DisplayString (SIZE(0..16))
    MAX-ACCESS read-write
    STATUS     current
    DESCRIPTION
            ""
    ::= { lcsSetupWlanMngmtApConfMulticastNetworksEntry 5 }

-- {TABLE} 1.3.6.1.4.1.2356.11.2.37.1.15
lcsSetupWlanMngmtApConfAutowdsProfilesTable OBJECT-TYPE
    SYNTAX     SEQUENCE OF LcsSetupWlanMngmtApConfAutowdsProfilesEntry
    MAX-ACCESS not-accessible
    STATUS     current
    DESCRIPTION
            "-- empty --"
    ::= { lcsSetupWlanMngmtApConf 15 }

-- {ROW} 1.3.6.1.4.1.2356.11.2.37.1.15.1
lcsSetupWlanMngmtApConfAutowdsProfilesEntry OBJECT-TYPE
    SYNTAX     LcsSetupWlanMngmtApConfAutowdsProfilesEntry
    MAX-ACCESS not-accessible
    STATUS     current
    DESCRIPTION
            ""
    INDEX {
            lcsSetupWlanMngmtApConfAutowdsProfilesEntryName
          }
    ::= { lcsSetupWlanMngmtApConfAutowdsProfilesTable 1 }

LcsSetupWlanMngmtApConfAutowdsProfilesEntry ::= SEQUENCE {
            lcsSetupWlanMngmtApConfAutowdsProfilesEntryName DisplayString,
            lcsSetupWlanMngmtApConfAutowdsProfilesEntryCommonprofile DisplayString,
            lcsSetupWlanMngmtApConfAutowdsProfilesEntrySsid DisplayString,
            lcsSetupWlanMngmtApConfAutowdsProfilesEntryKey DisplayString,
            lcsSetupWlanMngmtApConfAutowdsProfilesEntryEnabled INTEGER,
            lcsSetupWlanMngmtApConfAutowdsProfilesEntryAllowExprInt INTEGER,
            lcsSetupWlanMngmtApConfAutowdsProfilesEntryTopologyManagement INTEGER,
            lcsSetupWlanMngmtApConfAutowdsProfilesEntrySlaveTxLimit Integer32,
            lcsSetupWlanMngmtApConfAutowdsProfilesEntryMasterTxLimit Integer32,
            lcsSetupWlanMngmtApConfAutowdsProfilesEntryLinkLossTimeout Integer32,
            lcsSetupWlanMngmtApConfAutowdsProfilesEntryContinuation Integer32,
            lcsSetupWlanMngmtApConfAutowdsProfilesEntryTimeTillPreconfScan Integer32,
            lcsSetupWlanMngmtApConfAutowdsProfilesEntryTimeTillExpressScan Integer32,
            lcsSetupWlanMngmtApConfAutowdsProfilesEntryInterfacePairing INTEGER,
            lcsSetupWlanMngmtApConfAutowdsProfilesEntrySlaveRadioMultiHop INTEGER,
            lcsSetupWlanMngmtApConfAutowdsProfilesEntryRadioBand INTEGER,
            lcsSetupWlanMngmtApConfAutowdsProfilesEntrySsidBroadcast INTEGER
    }

-- {COLUMN} 1.3.6.1.4.1.2356.11.2.37.1.15.1.1
lcsSetupWlanMngmtApConfAutowdsProfilesEntryName OBJECT-TYPE
    SYNTAX     DisplayString (SIZE(0..15))
    MAX-ACCESS read-only
    STATUS     current
    DESCRIPTION
            "-- empty --"
    ::= { lcsSetupWlanMngmtApConfAutowdsProfilesEntry 1 }

-- {COLUMN} 1.3.6.1.4.1.2356.11.2.37.1.15.1.2
lcsSetupWlanMngmtApConfAutowdsProfilesEntryCommonprofile OBJECT-TYPE
    SYNTAX     DisplayString (SIZE(0..31))
    MAX-ACCESS read-write
    STATUS     current
    DESCRIPTION
            "-- empty --"
    ::= { lcsSetupWlanMngmtApConfAutowdsProfilesEntry 2 }

-- {COLUMN} 1.3.6.1.4.1.2356.11.2.37.1.15.1.3
lcsSetupWlanMngmtApConfAutowdsProfilesEntrySsid OBJECT-TYPE
    SYNTAX     DisplayString (SIZE(0..32))
    MAX-ACCESS read-write
    STATUS     current
    DESCRIPTION
            "-- empty --"
    ::= { lcsSetupWlanMngmtApConfAutowdsProfilesEntry 3 }

-- {COLUMN} 1.3.6.1.4.1.2356.11.2.37.1.15.1.4
lcsSetupWlanMngmtApConfAutowdsProfilesEntryKey OBJECT-TYPE
    SYNTAX     DisplayString (SIZE(0..63))
    MAX-ACCESS read-write
    STATUS     current
    DESCRIPTION
            "-- empty --"
    ::= { lcsSetupWlanMngmtApConfAutowdsProfilesEntry 4 }

-- {COLUMN} 1.3.6.1.4.1.2356.11.2.37.1.15.1.6
lcsSetupWlanMngmtApConfAutowdsProfilesEntryEnabled OBJECT-TYPE
    SYNTAX     INTEGER {
                  eNo (0),
                  eYes (1)
            }
    MAX-ACCESS read-write
    STATUS     current
    DESCRIPTION
            "-- empty --"
    ::= { lcsSetupWlanMngmtApConfAutowdsProfilesEntry 6 }

-- {COLUMN} 1.3.6.1.4.1.2356.11.2.37.1.15.1.7
lcsSetupWlanMngmtApConfAutowdsProfilesEntryAllowExprInt OBJECT-TYPE
    SYNTAX     INTEGER {
                  eNo (0),
                  eYes (1)
            }
    MAX-ACCESS read-write
    STATUS     current
    DESCRIPTION
            "Allow-Express-Integration"
    ::= { lcsSetupWlanMngmtApConfAutowdsProfilesEntry 7 }

-- {COLUMN} 1.3.6.1.4.1.2356.11.2.37.1.15.1.8
lcsSetupWlanMngmtApConfAutowdsProfilesEntryTopologyManagement OBJECT-TYPE
    SYNTAX     INTEGER {
                  eAutomatic (0),
                  eSemiAutomatic (1),
                  eManual (2)
            }
    MAX-ACCESS read-write
    STATUS     current
    DESCRIPTION
            "-- empty --"
    ::= { lcsSetupWlanMngmtApConfAutowdsProfilesEntry 8 }

-- {COLUMN} 1.3.6.1.4.1.2356.11.2.37.1.15.1.10
lcsSetupWlanMngmtApConfAutowdsProfilesEntrySlaveTxLimit OBJECT-TYPE
    SYNTAX     Integer32 (0..2147483647)
    MAX-ACCESS read-write
    STATUS     current
    DESCRIPTION
            "-- empty --"
    ::= { lcsSetupWlanMngmtApConfAutowdsProfilesEntry 10 }

-- {COLUMN} 1.3.6.1.4.1.2356.11.2.37.1.15.1.11
lcsSetupWlanMngmtApConfAutowdsProfilesEntryMasterTxLimit OBJECT-TYPE
    SYNTAX     Integer32 (0..2147483647)
    MAX-ACCESS read-write
    STATUS     current
    DESCRIPTION
            "-- empty --"
    ::= { lcsSetupWlanMngmtApConfAutowdsProfilesEntry 11 }

-- {COLUMN} 1.3.6.1.4.1.2356.11.2.37.1.15.1.12
lcsSetupWlanMngmtApConfAutowdsProfilesEntryLinkLossTimeout OBJECT-TYPE
    SYNTAX     Integer32 (0..2147483647)
    MAX-ACCESS read-write
    STATUS     current
    DESCRIPTION
            "-- empty --"
    ::= { lcsSetupWlanMngmtApConfAutowdsProfilesEntry 12 }

-- {COLUMN} 1.3.6.1.4.1.2356.11.2.37.1.15.1.14
lcsSetupWlanMngmtApConfAutowdsProfilesEntryContinuation OBJECT-TYPE
    SYNTAX     Integer32 (0..65535)
    MAX-ACCESS read-write
    STATUS     current
    DESCRIPTION
            ""
    ::= { lcsSetupWlanMngmtApConfAutowdsProfilesEntry 14 }

-- {COLUMN} 1.3.6.1.4.1.2356.11.2.37.1.15.1.15
lcsSetupWlanMngmtApConfAutowdsProfilesEntryTimeTillPreconfScan OBJECT-TYPE
    SYNTAX     Integer32 (0..2147483647)
    MAX-ACCESS read-write
    STATUS     current
    DESCRIPTION
            "-- empty --"
    ::= { lcsSetupWlanMngmtApConfAutowdsProfilesEntry 15 }

-- {COLUMN} 1.3.6.1.4.1.2356.11.2.37.1.15.1.16
lcsSetupWlanMngmtApConfAutowdsProfilesEntryTimeTillExpressScan OBJECT-TYPE
    SYNTAX     Integer32 (0..2147483647)
    MAX-ACCESS read-write
    STATUS     current
    DESCRIPTION
            "-- empty --"
    ::= { lcsSetupWlanMngmtApConfAutowdsProfilesEntry 16 }

-- {COLUMN} 1.3.6.1.4.1.2356.11.2.37.1.15.1.17
lcsSetupWlanMngmtApConfAutowdsProfilesEntryInterfacePairing OBJECT-TYPE
    SYNTAX     INTEGER {
                  eAutomatic (0),
                  eStrict (1),
                  eMixed (2)
            }
    MAX-ACCESS read-write
    STATUS     current
    DESCRIPTION
            "-- empty --"
    ::= { lcsSetupWlanMngmtApConfAutowdsProfilesEntry 17 }

-- {COLUMN} 1.3.6.1.4.1.2356.11.2.37.1.15.1.18
lcsSetupWlanMngmtApConfAutowdsProfilesEntrySlaveRadioMultiHop OBJECT-TYPE
    SYNTAX     INTEGER {
                  eNo (0),
                  eYes (1),
                  eSingleRadioApOnly (2)
            }
    MAX-ACCESS read-write
    STATUS     current
    DESCRIPTION
            "-- empty --"
    ::= { lcsSetupWlanMngmtApConfAutowdsProfilesEntry 18 }

-- {COLUMN} 1.3.6.1.4.1.2356.11.2.37.1.15.1.19
lcsSetupWlanMngmtApConfAutowdsProfilesEntryRadioBand OBJECT-TYPE
    SYNTAX     INTEGER {
                  e24ghz5ghz (0),
                  e24ghz (1),
                  e5ghz (2)
            }
    MAX-ACCESS read-write
    STATUS     current
    DESCRIPTION
            "-- empty --"
    ::= { lcsSetupWlanMngmtApConfAutowdsProfilesEntry 19 }

-- {COLUMN} 1.3.6.1.4.1.2356.11.2.37.1.15.1.20
lcsSetupWlanMngmtApConfAutowdsProfilesEntrySsidBroadcast OBJECT-TYPE
    SYNTAX     INTEGER {
                  eNo (0),
                  eYes (1)
            }
    MAX-ACCESS read-write
    STATUS     current
    DESCRIPTION
            "-- empty --"
    ::= { lcsSetupWlanMngmtApConfAutowdsProfilesEntry 20 }

-- {TABLE} 1.3.6.1.4.1.2356.11.2.37.1.16
lcsSetupWlanMngmtApConfAutowdsTopologyTable OBJECT-TYPE
    SYNTAX     SEQUENCE OF LcsSetupWlanMngmtApConfAutowdsTopologyEntry
    MAX-ACCESS not-accessible
    STATUS     current
    DESCRIPTION
            "-- empty --"
    ::= { lcsSetupWlanMngmtApConf 16 }

-- {ROW} 1.3.6.1.4.1.2356.11.2.37.1.16.1
lcsSetupWlanMngmtApConfAutowdsTopologyEntry OBJECT-TYPE
    SYNTAX     LcsSetupWlanMngmtApConfAutowdsTopologyEntry
    MAX-ACCESS not-accessible
    STATUS     current
    DESCRIPTION
            ""
    INDEX {
            lcsSetupWlanMngmtApConfAutowdsTopologyEntryAutowdsProfile,
            lcsSetupWlanMngmtApConfAutowdsTopologyEntryPriority,
            lcsSetupWlanMngmtApConfAutowdsTopologyEntrySlaveApName,
            lcsSetupWlanMngmtApConfAutowdsTopologyEntrySlaveApWlanIfc
          }
    ::= { lcsSetupWlanMngmtApConfAutowdsTopologyTable 1 }

LcsSetupWlanMngmtApConfAutowdsTopologyEntry ::= SEQUENCE {
            lcsSetupWlanMngmtApConfAutowdsTopologyEntryAutowdsProfile DisplayString,
            lcsSetupWlanMngmtApConfAutowdsTopologyEntryPriority Integer32,
            lcsSetupWlanMngmtApConfAutowdsTopologyEntrySlaveApName DisplayString,
            lcsSetupWlanMngmtApConfAutowdsTopologyEntrySlaveApWlanIfc INTEGER,
            lcsSetupWlanMngmtApConfAutowdsTopologyEntryMasterApName DisplayString,
            lcsSetupWlanMngmtApConfAutowdsTopologyEntryMasterApWlanIfc INTEGER,
            lcsSetupWlanMngmtApConfAutowdsTopologyEntryKey DisplayString,
            lcsSetupWlanMngmtApConfAutowdsTopologyEntryEnabled INTEGER,
            lcsSetupWlanMngmtApConfAutowdsTopologyEntrySlaveTxLimit Integer32,
            lcsSetupWlanMngmtApConfAutowdsTopologyEntryMasterTxLimit Integer32,
            lcsSetupWlanMngmtApConfAutowdsTopologyEntryLinkLossTimeout Integer32,
            lcsSetupWlanMngmtApConfAutowdsTopologyEntryContinuation Integer32
    }

-- {COLUMN} 1.3.6.1.4.1.2356.11.2.37.1.16.1.1
lcsSetupWlanMngmtApConfAutowdsTopologyEntryAutowdsProfile OBJECT-TYPE
    SYNTAX     DisplayString (SIZE(0..15))
    MAX-ACCESS read-write
    STATUS     current
    DESCRIPTION
            "-- empty --"
    ::= { lcsSetupWlanMngmtApConfAutowdsTopologyEntry 1 }

-- {COLUMN} 1.3.6.1.4.1.2356.11.2.37.1.16.1.2
lcsSetupWlanMngmtApConfAutowdsTopologyEntryPriority OBJECT-TYPE
    SYNTAX     Integer32 (0..65535)
    MAX-ACCESS read-write
    STATUS     current
    DESCRIPTION
            "-- empty --"
    ::= { lcsSetupWlanMngmtApConfAutowdsTopologyEntry 2 }

-- {COLUMN} 1.3.6.1.4.1.2356.11.2.37.1.16.1.3
lcsSetupWlanMngmtApConfAutowdsTopologyEntrySlaveApName OBJECT-TYPE
    SYNTAX     DisplayString (SIZE(0..64))
    MAX-ACCESS read-write
    STATUS     current
    DESCRIPTION
            "-- empty --"
    ::= { lcsSetupWlanMngmtApConfAutowdsTopologyEntry 3 }

-- {COLUMN} 1.3.6.1.4.1.2356.11.2.37.1.16.1.4
lcsSetupWlanMngmtApConfAutowdsTopologyEntrySlaveApWlanIfc OBJECT-TYPE
    SYNTAX     INTEGER {
                  eWlan1 (1),
                  eWlan2 (2)
            }
    MAX-ACCESS read-write
    STATUS     current
    DESCRIPTION
            "-- empty --"
    ::= { lcsSetupWlanMngmtApConfAutowdsTopologyEntry 4 }

-- {COLUMN} 1.3.6.1.4.1.2356.11.2.37.1.16.1.6
lcsSetupWlanMngmtApConfAutowdsTopologyEntryMasterApName OBJECT-TYPE
    SYNTAX     DisplayString (SIZE(0..64))
    MAX-ACCESS read-write
    STATUS     current
    DESCRIPTION
            "-- empty --"
    ::= { lcsSetupWlanMngmtApConfAutowdsTopologyEntry 6 }

-- {COLUMN} 1.3.6.1.4.1.2356.11.2.37.1.16.1.7
lcsSetupWlanMngmtApConfAutowdsTopologyEntryMasterApWlanIfc OBJECT-TYPE
    SYNTAX     INTEGER {
                  eWlan1 (1),
                  eWlan2 (2)
            }
    MAX-ACCESS read-write
    STATUS     current
    DESCRIPTION
            "-- empty --"
    ::= { lcsSetupWlanMngmtApConfAutowdsTopologyEntry 7 }

-- {COLUMN} 1.3.6.1.4.1.2356.11.2.37.1.16.1.9
lcsSetupWlanMngmtApConfAutowdsTopologyEntryKey OBJECT-TYPE
    SYNTAX     DisplayString (SIZE(0..63))
    MAX-ACCESS read-write
    STATUS     current
    DESCRIPTION
            "-- empty --"
    ::= { lcsSetupWlanMngmtApConfAutowdsTopologyEntry 9 }

-- {COLUMN} 1.3.6.1.4.1.2356.11.2.37.1.16.1.10
lcsSetupWlanMngmtApConfAutowdsTopologyEntryEnabled OBJECT-TYPE
    SYNTAX     INTEGER {
                  eNo (0),
                  eYes (1)
            }
    MAX-ACCESS read-write
    STATUS     current
    DESCRIPTION
            "-- empty --"
    ::= { lcsSetupWlanMngmtApConfAutowdsTopologyEntry 10 }

-- {COLUMN} 1.3.6.1.4.1.2356.11.2.37.1.16.1.12
lcsSetupWlanMngmtApConfAutowdsTopologyEntrySlaveTxLimit OBJECT-TYPE
    SYNTAX     Integer32 (0..2147483647)
    MAX-ACCESS read-write
    STATUS     current
    DESCRIPTION
            "-- empty --"
    ::= { lcsSetupWlanMngmtApConfAutowdsTopologyEntry 12 }

-- {COLUMN} 1.3.6.1.4.1.2356.11.2.37.1.16.1.13
lcsSetupWlanMngmtApConfAutowdsTopologyEntryMasterTxLimit OBJECT-TYPE
    SYNTAX     Integer32 (0..2147483647)
    MAX-ACCESS read-write
    STATUS     current
    DESCRIPTION
            "-- empty --"
    ::= { lcsSetupWlanMngmtApConfAutowdsTopologyEntry 13 }

-- {COLUMN} 1.3.6.1.4.1.2356.11.2.37.1.16.1.14
lcsSetupWlanMngmtApConfAutowdsTopologyEntryLinkLossTimeout OBJECT-TYPE
    SYNTAX     Integer32 (0..2147483647)
    MAX-ACCESS read-write
    STATUS     current
    DESCRIPTION
            "-- empty --"
    ::= { lcsSetupWlanMngmtApConfAutowdsTopologyEntry 14 }

-- {COLUMN} 1.3.6.1.4.1.2356.11.2.37.1.16.1.16
lcsSetupWlanMngmtApConfAutowdsTopologyEntryContinuation OBJECT-TYPE
    SYNTAX     Integer32 (0..65535)
    MAX-ACCESS read-write
    STATUS     current
    DESCRIPTION
            ""
    ::= { lcsSetupWlanMngmtApConfAutowdsTopologyEntry 16 }

-- {NODE} 1.3.6.1.4.1.2356.11.2.37.1.17
lcsSetupWlanMngmtApConf11u OBJECT IDENTIFIER ::= { lcsSetupWlanMngmtApConf 17 }

-- {TABLE} 1.3.6.1.4.1.2356.11.2.37.1.17.1
lcsSetupWlanMngmtApConf11u11u-NwTable OBJECT-TYPE
    SYNTAX     SEQUENCE OF LcsSetupWlanMngmtApConf11u11u-NwEntry
    MAX-ACCESS not-accessible
    STATUS     current
    DESCRIPTION
            "IEEE802.11u-Networks"
    ::= { lcsSetupWlanMngmtApConf11u 1 }

-- {ROW} 1.3.6.1.4.1.2356.11.2.37.1.17.1.1
lcsSetupWlanMngmtApConf11u11u-NwEntry OBJECT-TYPE
    SYNTAX     LcsSetupWlanMngmtApConf11u11u-NwEntry
    MAX-ACCESS not-accessible
    STATUS     current
    DESCRIPTION
            ""
    INDEX {
            lcsSetupWlanMngmtApConf11u11u-NwEntryName
          }
    ::= { lcsSetupWlanMngmtApConf11u11u-NwTable 1 }

LcsSetupWlanMngmtApConf11u11u-NwEntry ::= SEQUENCE {
            lcsSetupWlanMngmtApConf11u11u-NwEntryName DisplayString,
            lcsSetupWlanMngmtApConf11u11u-NwEntryOper INTEGER,
            lcsSetupWlanMngmtApConf11u11u-NwEntryHs20 INTEGER,
            lcsSetupWlanMngmtApConf11u11u-NwEntryInet INTEGER,
            lcsSetupWlanMngmtApConf11u11u-NwEntryNwType INTEGER,
            lcsSetupWlanMngmtApConf11u11u-NwEntryAsra INTEGER,
            lcsSetupWlanMngmtApConf11u11u-NwEntryHESSIDT INTEGER,
            lcsSetupWlanMngmtApConf11u11u-NwEntryHESSIDM MacAddress,
            lcsSetupWlanMngmtApConf11u11u-NwEntryANQP-Prof DisplayString,
            lcsSetupWlanMngmtApConf11u11u-NwEntryHs20-Prof DisplayString
    }

-- {COLUMN} 1.3.6.1.4.1.2356.11.2.37.1.17.1.1.1
lcsSetupWlanMngmtApConf11u11u-NwEntryName OBJECT-TYPE
    SYNTAX     DisplayString (SIZE(0..32))
    MAX-ACCESS read-write
    STATUS     current
    DESCRIPTION
            "-- empty --"
    ::= { lcsSetupWlanMngmtApConf11u11u-NwEntry 1 }

-- {COLUMN} 1.3.6.1.4.1.2356.11.2.37.1.17.1.1.2
lcsSetupWlanMngmtApConf11u11u-NwEntryOper OBJECT-TYPE
    SYNTAX     INTEGER {
                  eNo (0),
                  eYes (1)
            }
    MAX-ACCESS read-write
    STATUS     current
    DESCRIPTION
            "Operating"
    ::= { lcsSetupWlanMngmtApConf11u11u-NwEntry 2 }

-- {COLUMN} 1.3.6.1.4.1.2356.11.2.37.1.17.1.1.3
lcsSetupWlanMngmtApConf11u11u-NwEntryHs20 OBJECT-TYPE
    SYNTAX     INTEGER {
                  eNo (0),
                  eYes (1)
            }
    MAX-ACCESS read-write
    STATUS     current
    DESCRIPTION
            "Hotspot2.0"
    ::= { lcsSetupWlanMngmtApConf11u11u-NwEntry 3 }

-- {COLUMN} 1.3.6.1.4.1.2356.11.2.37.1.17.1.1.4
lcsSetupWlanMngmtApConf11u11u-NwEntryInet OBJECT-TYPE
    SYNTAX     INTEGER {
                  eNo (0),
                  eYes (1)
            }
    MAX-ACCESS read-write
    STATUS     current
    DESCRIPTION
            "Internet"
    ::= { lcsSetupWlanMngmtApConf11u11u-NwEntry 4 }

-- {COLUMN} 1.3.6.1.4.1.2356.11.2.37.1.17.1.1.5
lcsSetupWlanMngmtApConf11u11u-NwEntryNwType OBJECT-TYPE
    SYNTAX     INTEGER {
                  ePrivate (0),
                  ePrivateGuestacc (1),
                  ePublicCharge (2),
                  ePublicFree (3),
                  ePersonalDev (4),
                  eEmergency (5),
                  eExperimental (14),
                  eWildcard (15)
            }
    MAX-ACCESS read-write
    STATUS     current
    DESCRIPTION
            "Network-Type"
    ::= { lcsSetupWlanMngmtApConf11u11u-NwEntry 5 }

-- {COLUMN} 1.3.6.1.4.1.2356.11.2.37.1.17.1.1.6
lcsSetupWlanMngmtApConf11u11u-NwEntryAsra OBJECT-TYPE
    SYNTAX     INTEGER {
                  eNo (0),
                  eYes (1)
            }
    MAX-ACCESS read-write
    STATUS     current
    DESCRIPTION
            "Asra"
    ::= { lcsSetupWlanMngmtApConf11u11u-NwEntry 6 }

-- {COLUMN} 1.3.6.1.4.1.2356.11.2.37.1.17.1.1.7
lcsSetupWlanMngmtApConf11u11u-NwEntryHESSIDT OBJECT-TYPE
    SYNTAX     INTEGER {
                  eAuto (0),
                  eUser (1),
                  eNone (2)
            }
    MAX-ACCESS read-write
    STATUS     current
    DESCRIPTION
            "HESSID-Type"
    ::= { lcsSetupWlanMngmtApConf11u11u-NwEntry 7 }

-- {COLUMN} 1.3.6.1.4.1.2356.11.2.37.1.17.1.1.8
lcsSetupWlanMngmtApConf11u11u-NwEntryHESSIDM OBJECT-TYPE
    SYNTAX     MacAddress
    MAX-ACCESS read-write
    STATUS     current
    DESCRIPTION
            "HESSID-MAC"
    ::= { lcsSetupWlanMngmtApConf11u11u-NwEntry 8 }

-- {COLUMN} 1.3.6.1.4.1.2356.11.2.37.1.17.1.1.10
lcsSetupWlanMngmtApConf11u11u-NwEntryANQP-Prof OBJECT-TYPE
    SYNTAX     DisplayString (SIZE(0..32))
    MAX-ACCESS read-write
    STATUS     current
    DESCRIPTION
            "ANQP-Profile"
    ::= { lcsSetupWlanMngmtApConf11u11u-NwEntry 10 }

-- {COLUMN} 1.3.6.1.4.1.2356.11.2.37.1.17.1.1.12
lcsSetupWlanMngmtApConf11u11u-NwEntryHs20-Prof OBJECT-TYPE
    SYNTAX     DisplayString (SIZE(0..32))
    MAX-ACCESS read-write
    STATUS     current
    DESCRIPTION
            "HS20-Profile"
    ::= { lcsSetupWlanMngmtApConf11u11u-NwEntry 12 }

-- {TABLE} 1.3.6.1.4.1.2356.11.2.37.1.17.2
lcsSetupWlanMngmtApConf11uANQP-ProfsTable OBJECT-TYPE
    SYNTAX     SEQUENCE OF LcsSetupWlanMngmtApConf11uANQP-ProfsEntry
    MAX-ACCESS not-accessible
    STATUS     current
    DESCRIPTION
            "ANQP-Profiles"
    ::= { lcsSetupWlanMngmtApConf11u 2 }

-- {ROW} 1.3.6.1.4.1.2356.11.2.37.1.17.2.1
lcsSetupWlanMngmtApConf11uANQP-ProfsEntry OBJECT-TYPE
    SYNTAX     LcsSetupWlanMngmtApConf11uANQP-ProfsEntry
    MAX-ACCESS not-accessible
    STATUS     current
    DESCRIPTION
            ""
    INDEX {
            lcsSetupWlanMngmtApConf11uANQP-ProfsEntryName
          }
    ::= { lcsSetupWlanMngmtApConf11uANQP-ProfsTable 1 }

LcsSetupWlanMngmtApConf11uANQP-ProfsEntry ::= SEQUENCE {
            lcsSetupWlanMngmtApConf11uANQP-ProfsEntryName DisplayString,
            lcsSetupWlanMngmtApConf11uANQP-ProfsEntryIncOUI DisplayString,
            lcsSetupWlanMngmtApConf11uANQP-ProfsEntryAddOUI DisplayString,
            lcsSetupWlanMngmtApConf11uANQP-ProfsEntryDomainList DisplayString,
            lcsSetupWlanMngmtApConf11uANQP-ProfsEntryNaiRealmList DisplayString,
            lcsSetupWlanMngmtApConf11uANQP-ProfsEntryCellularList DisplayString,
            lcsSetupWlanMngmtApConf11uANQP-ProfsEntryNetList DisplayString
    }

-- {COLUMN} 1.3.6.1.4.1.2356.11.2.37.1.17.2.1.1
lcsSetupWlanMngmtApConf11uANQP-ProfsEntryName OBJECT-TYPE
    SYNTAX     DisplayString (SIZE(0..32))
    MAX-ACCESS read-write
    STATUS     current
    DESCRIPTION
            "-- empty --"
    ::= { lcsSetupWlanMngmtApConf11uANQP-ProfsEntry 1 }

-- {COLUMN} 1.3.6.1.4.1.2356.11.2.37.1.17.2.1.2
lcsSetupWlanMngmtApConf11uANQP-ProfsEntryIncOUI OBJECT-TYPE
    SYNTAX     DisplayString (SIZE(0..65))
    MAX-ACCESS read-write
    STATUS     current
    DESCRIPTION
            "Include-in-Beacon-OUI"
    ::= { lcsSetupWlanMngmtApConf11uANQP-ProfsEntry 2 }

-- {COLUMN} 1.3.6.1.4.1.2356.11.2.37.1.17.2.1.3
lcsSetupWlanMngmtApConf11uANQP-ProfsEntryAddOUI OBJECT-TYPE
    SYNTAX     DisplayString (SIZE(0..65))
    MAX-ACCESS read-write
    STATUS     current
    DESCRIPTION
            "Additional-OUI"
    ::= { lcsSetupWlanMngmtApConf11uANQP-ProfsEntry 3 }

-- {COLUMN} 1.3.6.1.4.1.2356.11.2.37.1.17.2.1.4
lcsSetupWlanMngmtApConf11uANQP-ProfsEntryDomainList OBJECT-TYPE
    SYNTAX     DisplayString (SIZE(0..65))
    MAX-ACCESS read-write
    STATUS     current
    DESCRIPTION
            "-- empty --"
    ::= { lcsSetupWlanMngmtApConf11uANQP-ProfsEntry 4 }

-- {COLUMN} 1.3.6.1.4.1.2356.11.2.37.1.17.2.1.5
lcsSetupWlanMngmtApConf11uANQP-ProfsEntryNaiRealmList OBJECT-TYPE
    SYNTAX     DisplayString (SIZE(0..65))
    MAX-ACCESS read-write
    STATUS     current
    DESCRIPTION
            "-- empty --"
    ::= { lcsSetupWlanMngmtApConf11uANQP-ProfsEntry 5 }

-- {COLUMN} 1.3.6.1.4.1.2356.11.2.37.1.17.2.1.6
lcsSetupWlanMngmtApConf11uANQP-ProfsEntryCellularList OBJECT-TYPE
    SYNTAX     DisplayString (SIZE(0..65))
    MAX-ACCESS read-write
    STATUS     current
    DESCRIPTION
            "-- empty --"
    ::= { lcsSetupWlanMngmtApConf11uANQP-ProfsEntry 6 }

-- {COLUMN} 1.3.6.1.4.1.2356.11.2.37.1.17.2.1.7
lcsSetupWlanMngmtApConf11uANQP-ProfsEntryNetList OBJECT-TYPE
    SYNTAX     DisplayString (SIZE(0..65))
    MAX-ACCESS read-write
    STATUS     current
    DESCRIPTION
            "Network-Auth-Type-List"
    ::= { lcsSetupWlanMngmtApConf11uANQP-ProfsEntry 7 }

-- {TABLE} 1.3.6.1.4.1.2356.11.2.37.1.17.3
lcsSetupWlanMngmtApConf11uHs20-ProfsTable OBJECT-TYPE
    SYNTAX     SEQUENCE OF LcsSetupWlanMngmtApConf11uHs20-ProfsEntry
    MAX-ACCESS not-accessible
    STATUS     current
    DESCRIPTION
            "Hotspot2.0-Profiles"
    ::= { lcsSetupWlanMngmtApConf11u 3 }

-- {ROW} 1.3.6.1.4.1.2356.11.2.37.1.17.3.1
lcsSetupWlanMngmtApConf11uHs20-ProfsEntry OBJECT-TYPE
    SYNTAX     LcsSetupWlanMngmtApConf11uHs20-ProfsEntry
    MAX-ACCESS not-accessible
    STATUS     current
    DESCRIPTION
            ""
    INDEX {
            lcsSetupWlanMngmtApConf11uHs20-ProfsEntryName
          }
    ::= { lcsSetupWlanMngmtApConf11uHs20-ProfsTable 1 }

LcsSetupWlanMngmtApConf11uHs20-ProfsEntry ::= SEQUENCE {
            lcsSetupWlanMngmtApConf11uHs20-ProfsEntryName DisplayString,
            lcsSetupWlanMngmtApConf11uHs20-ProfsEntryOperatorName DisplayString,
            lcsSetupWlanMngmtApConf11uHs20-ProfsEntryConnCaps DisplayString,
            lcsSetupWlanMngmtApConf11uHs20-ProfsEntryOpClass DisplayString
    }

-- {COLUMN} 1.3.6.1.4.1.2356.11.2.37.1.17.3.1.1
lcsSetupWlanMngmtApConf11uHs20-ProfsEntryName OBJECT-TYPE
    SYNTAX     DisplayString (SIZE(0..32))
    MAX-ACCESS read-write
    STATUS     current
    DESCRIPTION
            "-- empty --"
    ::= { lcsSetupWlanMngmtApConf11uHs20-ProfsEntry 1 }

-- {COLUMN} 1.3.6.1.4.1.2356.11.2.37.1.17.3.1.2
lcsSetupWlanMngmtApConf11uHs20-ProfsEntryOperatorName OBJECT-TYPE
    SYNTAX     DisplayString (SIZE(0..65))
    MAX-ACCESS read-write
    STATUS     current
    DESCRIPTION
            "-- empty --"
    ::= { lcsSetupWlanMngmtApConf11uHs20-ProfsEntry 2 }

-- {COLUMN} 1.3.6.1.4.1.2356.11.2.37.1.17.3.1.3
lcsSetupWlanMngmtApConf11uHs20-ProfsEntryConnCaps OBJECT-TYPE
    SYNTAX     DisplayString (SIZE(0..250))
    MAX-ACCESS read-write
    STATUS     current
    DESCRIPTION
            "Connection-Capabilities"
    ::= { lcsSetupWlanMngmtApConf11uHs20-ProfsEntry 3 }

-- {COLUMN} 1.3.6.1.4.1.2356.11.2.37.1.17.3.1.4
lcsSetupWlanMngmtApConf11uHs20-ProfsEntryOpClass OBJECT-TYPE
    SYNTAX     DisplayString (SIZE(0..32))
    MAX-ACCESS read-write
    STATUS     current
    DESCRIPTION
            "Operating-Class"
    ::= { lcsSetupWlanMngmtApConf11uHs20-ProfsEntry 4 }

-- {TABLE} 1.3.6.1.4.1.2356.11.2.37.1.17.4
lcsSetupWlanMngmtApConf11uNetAuthTable OBJECT-TYPE
    SYNTAX     SEQUENCE OF LcsSetupWlanMngmtApConf11uNetAuthEntry
    MAX-ACCESS not-accessible
    STATUS     current
    DESCRIPTION
            "Network-Authentication-Type"
    ::= { lcsSetupWlanMngmtApConf11u 4 }

-- {ROW} 1.3.6.1.4.1.2356.11.2.37.1.17.4.1
lcsSetupWlanMngmtApConf11uNetAuthEntry OBJECT-TYPE
    SYNTAX     LcsSetupWlanMngmtApConf11uNetAuthEntry
    MAX-ACCESS not-accessible
    STATUS     current
    DESCRIPTION
            ""
    INDEX {
            lcsSetupWlanMngmtApConf11uNetAuthEntryName
          }
    ::= { lcsSetupWlanMngmtApConf11uNetAuthTable 1 }

LcsSetupWlanMngmtApConf11uNetAuthEntry ::= SEQUENCE {
            lcsSetupWlanMngmtApConf11uNetAuthEntryName DisplayString,
            lcsSetupWlanMngmtApConf11uNetAuthEntryNetType INTEGER,
            lcsSetupWlanMngmtApConf11uNetAuthEntryReUrl DisplayString
    }

-- {COLUMN} 1.3.6.1.4.1.2356.11.2.37.1.17.4.1.1
lcsSetupWlanMngmtApConf11uNetAuthEntryName OBJECT-TYPE
    SYNTAX     DisplayString (SIZE(0..32))
    MAX-ACCESS read-write
    STATUS     current
    DESCRIPTION
            "-- empty --"
    ::= { lcsSetupWlanMngmtApConf11uNetAuthEntry 1 }

-- {COLUMN} 1.3.6.1.4.1.2356.11.2.37.1.17.4.1.2
lcsSetupWlanMngmtApConf11uNetAuthEntryNetType OBJECT-TYPE
    SYNTAX     INTEGER {
                  eAcceptTermsCond (0),
                  eOnlineEnrollment (1),
                  eHttpRedirection (2),
                  eDnsRedirection (3)
            }
    MAX-ACCESS read-write
    STATUS     current
    DESCRIPTION
            "Network-Auth-Type"
    ::= { lcsSetupWlanMngmtApConf11uNetAuthEntry 2 }

-- {COLUMN} 1.3.6.1.4.1.2356.11.2.37.1.17.4.1.3
lcsSetupWlanMngmtApConf11uNetAuthEntryReUrl OBJECT-TYPE
    SYNTAX     DisplayString (SIZE(0..65))
    MAX-ACCESS read-write
    STATUS     current
    DESCRIPTION
            "Redirect-URL"
    ::= { lcsSetupWlanMngmtApConf11uNetAuthEntry 3 }

-- {TABLE} 1.3.6.1.4.1.2356.11.2.37.1.17.5
lcsSetupWlanMngmtApConf11uCellListTable OBJECT-TYPE
    SYNTAX     SEQUENCE OF LcsSetupWlanMngmtApConf11uCellListEntry
    MAX-ACCESS not-accessible
    STATUS     current
    DESCRIPTION
            "Cellular-Network-Information-List"
    ::= { lcsSetupWlanMngmtApConf11u 5 }

-- {ROW} 1.3.6.1.4.1.2356.11.2.37.1.17.5.1
lcsSetupWlanMngmtApConf11uCellListEntry OBJECT-TYPE
    SYNTAX     LcsSetupWlanMngmtApConf11uCellListEntry
    MAX-ACCESS not-accessible
    STATUS     current
    DESCRIPTION
            ""
    INDEX {
            lcsSetupWlanMngmtApConf11uCellListEntryName
          }
    ::= { lcsSetupWlanMngmtApConf11uCellListTable 1 }

LcsSetupWlanMngmtApConf11uCellListEntry ::= SEQUENCE {
            lcsSetupWlanMngmtApConf11uCellListEntryName DisplayString,
            lcsSetupWlanMngmtApConf11uCellListEntryCountry DisplayString,
            lcsSetupWlanMngmtApConf11uCellListEntryNetwork DisplayString
    }

-- {COLUMN} 1.3.6.1.4.1.2356.11.2.37.1.17.5.1.1
lcsSetupWlanMngmtApConf11uCellListEntryName OBJECT-TYPE
    SYNTAX     DisplayString (SIZE(0..32))
    MAX-ACCESS read-write
    STATUS     current
    DESCRIPTION
            "-- empty --"
    ::= { lcsSetupWlanMngmtApConf11uCellListEntry 1 }

-- {COLUMN} 1.3.6.1.4.1.2356.11.2.37.1.17.5.1.2
lcsSetupWlanMngmtApConf11uCellListEntryCountry OBJECT-TYPE
    SYNTAX     DisplayString (SIZE(0..3))
    MAX-ACCESS read-write
    STATUS     current
    DESCRIPTION
            "Country-Code"
    ::= { lcsSetupWlanMngmtApConf11uCellListEntry 2 }

-- {COLUMN} 1.3.6.1.4.1.2356.11.2.37.1.17.5.1.3
lcsSetupWlanMngmtApConf11uCellListEntryNetwork OBJECT-TYPE
    SYNTAX     DisplayString (SIZE(0..3))
    MAX-ACCESS read-write
    STATUS     current
    DESCRIPTION
            "Network-Code"
    ::= { lcsSetupWlanMngmtApConf11uCellListEntry 3 }

-- {TABLE} 1.3.6.1.4.1.2356.11.2.37.1.17.6
lcsSetupWlanMngmtApConf11uVenueNameTable OBJECT-TYPE
    SYNTAX     SEQUENCE OF LcsSetupWlanMngmtApConf11uVenueNameEntry
    MAX-ACCESS not-accessible
    STATUS     current
    DESCRIPTION
            "-- empty --"
    ::= { lcsSetupWlanMngmtApConf11u 6 }

-- {ROW} 1.3.6.1.4.1.2356.11.2.37.1.17.6.1
lcsSetupWlanMngmtApConf11uVenueNameEntry OBJECT-TYPE
    SYNTAX     LcsSetupWlanMngmtApConf11uVenueNameEntry
    MAX-ACCESS not-accessible
    STATUS     current
    DESCRIPTION
            ""
    INDEX {
            lcsSetupWlanMngmtApConf11uVenueNameEntryName,
            lcsSetupWlanMngmtApConf11uVenueNameEntryLanguage
          }
    ::= { lcsSetupWlanMngmtApConf11uVenueNameTable 1 }

LcsSetupWlanMngmtApConf11uVenueNameEntry ::= SEQUENCE {
            lcsSetupWlanMngmtApConf11uVenueNameEntryName DisplayString,
            lcsSetupWlanMngmtApConf11uVenueNameEntryLanguage INTEGER,
            lcsSetupWlanMngmtApConf11uVenueNameEntryVenueName DisplayString
    }

-- {COLUMN} 1.3.6.1.4.1.2356.11.2.37.1.17.6.1.1
lcsSetupWlanMngmtApConf11uVenueNameEntryName OBJECT-TYPE
    SYNTAX     DisplayString (SIZE(0..32))
    MAX-ACCESS read-write
    STATUS     current
    DESCRIPTION
            "-- empty --"
    ::= { lcsSetupWlanMngmtApConf11uVenueNameEntry 1 }

-- {COLUMN} 1.3.6.1.4.1.2356.11.2.37.1.17.6.1.2
lcsSetupWlanMngmtApConf11uVenueNameEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13)
            }
    MAX-ACCESS read-write
    STATUS     current
    DESCRIPTION
            "-- empty --"
    ::= { lcsSetupWlanMngmtApConf11uVenueNameEntry 2 }

-- {COLUMN} 1.3.6.1.4.1.2356.11.2.37.1.17.6.1.3
lcsSetupWlanMngmtApConf11uVenueNameEntryVenueName OBJECT-TYPE
    SYNTAX     DisplayString (SIZE(0..65))
    MAX-ACCESS read-write
    STATUS     current
    DESCRIPTION
            "-- empty --"
    ::= { lcsSetupWlanMngmtApConf11uVenueNameEntry 3 }

-- {TABLE} 1.3.6.1.4.1.2356.11.2.37.1.17.7
lcsSetupWlanMngmtApConf11uNAIsTable OBJECT-TYPE
    SYNTAX     SEQUENCE OF LcsSetupWlanMngmtApConf11uNAIsEntry
    MAX-ACCESS not-accessible
    STATUS     current
    DESCRIPTION
            "NAI-Realms"
    ::= { lcsSetupWlanMngmtApConf11u 7 }

-- {ROW} 1.3.6.1.4.1.2356.11.2.37.1.17.7.1
lcsSetupWlanMngmtApConf11uNAIsEntry OBJECT-TYPE
    SYNTAX     LcsSetupWlanMngmtApConf11uNAIsEntry
    MAX-ACCESS not-accessible
    STATUS     current
    DESCRIPTION
            ""
    INDEX {
            lcsSetupWlanMngmtApConf11uNAIsEntryName
          }
    ::= { lcsSetupWlanMngmtApConf11uNAIsTable 1 }

LcsSetupWlanMngmtApConf11uNAIsEntry ::= SEQUENCE {
            lcsSetupWlanMngmtApConf11uNAIsEntryName DisplayString,
            lcsSetupWlanMngmtApConf11uNAIsEntryNaiRealm DisplayString,
            lcsSetupWlanMngmtApConf11uNAIsEntryEapMethod INTEGER,
            lcsSetupWlanMngmtApConf11uNAIsEntryAuthPar DisplayString
    }

-- {COLUMN} 1.3.6.1.4.1.2356.11.2.37.1.17.7.1.1
lcsSetupWlanMngmtApConf11uNAIsEntryName OBJECT-TYPE
    SYNTAX     DisplayString (SIZE(0..32))
    MAX-ACCESS read-write
    STATUS     current
    DESCRIPTION
            "-- empty --"
    ::= { lcsSetupWlanMngmtApConf11uNAIsEntry 1 }

-- {COLUMN} 1.3.6.1.4.1.2356.11.2.37.1.17.7.1.2
lcsSetupWlanMngmtApConf11uNAIsEntryNaiRealm OBJECT-TYPE
    SYNTAX     DisplayString (SIZE(0..32))
    MAX-ACCESS read-write
    STATUS     current
    DESCRIPTION
            "-- empty --"
    ::= { lcsSetupWlanMngmtApConf11uNAIsEntry 2 }

-- {COLUMN} 1.3.6.1.4.1.2356.11.2.37.1.17.7.1.3
lcsSetupWlanMngmtApConf11uNAIsEntryEapMethod OBJECT-TYPE
    SYNTAX     INTEGER {
                  eNone (0),
                  eEapTls (13),
                  eEapSim (18),
                  eEapTtls (21),
                  eEapAka (23)
            }
    MAX-ACCESS read-write
    STATUS     current
    DESCRIPTION
            "-- empty --"
    ::= { lcsSetupWlanMngmtApConf11uNAIsEntry 3 }

-- {COLUMN} 1.3.6.1.4.1.2356.11.2.37.1.17.7.1.4
lcsSetupWlanMngmtApConf11uNAIsEntryAuthPar OBJECT-TYPE
    SYNTAX     DisplayString (SIZE(0..65))
    MAX-ACCESS read-write
    STATUS     current
    DESCRIPTION
            "Auth-Parameter-List"
    ::= { lcsSetupWlanMngmtApConf11uNAIsEntry 4 }

-- {TABLE} 1.3.6.1.4.1.2356.11.2.37.1.17.8
lcsSetupWlanMngmtApConf11uOperatorListTable OBJECT-TYPE
    SYNTAX     SEQUENCE OF LcsSetupWlanMngmtApConf11uOperatorListEntry
    MAX-ACCESS not-accessible
    STATUS     current
    DESCRIPTION
            "-- empty --"
    ::= { lcsSetupWlanMngmtApConf11u 8 }

-- {ROW} 1.3.6.1.4.1.2356.11.2.37.1.17.8.1
lcsSetupWlanMngmtApConf11uOperatorListEntry OBJECT-TYPE
    SYNTAX     LcsSetupWlanMngmtApConf11uOperatorListEntry
    MAX-ACCESS not-accessible
    STATUS     current
    DESCRIPTION
            ""
    INDEX {
            lcsSetupWlanMngmtApConf11uOperatorListEntryName,
            lcsSetupWlanMngmtApConf11uOperatorListEntryLanguage
          }
    ::= { lcsSetupWlanMngmtApConf11uOperatorListTable 1 }

LcsSetupWlanMngmtApConf11uOperatorListEntry ::= SEQUENCE {
            lcsSetupWlanMngmtApConf11uOperatorListEntryName DisplayString,
            lcsSetupWlanMngmtApConf11uOperatorListEntryLanguage INTEGER,
            lcsSetupWlanMngmtApConf11uOperatorListEntryOperatorName DisplayString
    }

-- {COLUMN} 1.3.6.1.4.1.2356.11.2.37.1.17.8.1.1
lcsSetupWlanMngmtApConf11uOperatorListEntryName OBJECT-TYPE
    SYNTAX     DisplayString (SIZE(0..32))
    MAX-ACCESS read-write
    STATUS     current
    DESCRIPTION
            "-- empty --"
    ::= { lcsSetupWlanMngmtApConf11uOperatorListEntry 1 }

-- {COLUMN} 1.3.6.1.4.1.2356.11.2.37.1.17.8.1.2
lcsSetupWlanMngmtApConf11uOperatorListEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13)
            }
    MAX-ACCESS read-write
    STATUS     current
    DESCRIPTION
            "-- empty --"
    ::= { lcsSetupWlanMngmtApConf11uOperatorListEntry 2 }

-- {COLUMN} 1.3.6.1.4.1.2356.11.2.37.1.17.8.1.3
lcsSetupWlanMngmtApConf11uOperatorListEntryOperatorName OBJECT-TYPE
    SYNTAX     DisplayString (SIZE(0..65))
    MAX-ACCESS read-write
    STATUS     current
    DESCRIPTION
            "-- empty --"
    ::= { lcsSetupWlanMngmtApConf11uOperatorListEntry 3 }

-- {TABLE} 1.3.6.1.4.1.2356.11.2.37.1.17.9
lcsSetupWlanMngmtApConf11uGeneralTable OBJECT-TYPE
    SYNTAX     SEQUENCE OF LcsSetupWlanMngmtApConf11uGeneralEntry
    MAX-ACCESS not-accessible
    STATUS     current
    DESCRIPTION
            "-- empty --"
    ::= { lcsSetupWlanMngmtApConf11u 9 }

-- {ROW} 1.3.6.1.4.1.2356.11.2.37.1.17.9.1
lcsSetupWlanMngmtApConf11uGeneralEntry OBJECT-TYPE
    SYNTAX     LcsSetupWlanMngmtApConf11uGeneralEntry
    MAX-ACCESS not-accessible
    STATUS     current
    DESCRIPTION
            ""
    INDEX {
            lcsSetupWlanMngmtApConf11uGeneralEntryName
          }
    ::= { lcsSetupWlanMngmtApConf11uGeneralTable 1 }

LcsSetupWlanMngmtApConf11uGeneralEntry ::= SEQUENCE {
            lcsSetupWlanMngmtApConf11uGeneralEntryName DisplayString,
            lcsSetupWlanMngmtApConf11uGeneralEntryLinkStatus INTEGER,
            lcsSetupWlanMngmtApConf11uGeneralEntryDownlinkSpeed Integer32,
            lcsSetupWlanMngmtApConf11uGeneralEntryUplinkSpeed Integer32,
            lcsSetupWlanMngmtApConf11uGeneralEntryIpv4AddrType INTEGER,
            lcsSetupWlanMngmtApConf11uGeneralEntryIpv6AddrType INTEGER,
            lcsSetupWlanMngmtApConf11uGeneralEntryVenueGroup INTEGER,
            lcsSetupWlanMngmtApConf11uGeneralEntryVenueType Integer32,
            lcsSetupWlanMngmtApConf11uGeneralEntryVenueName DisplayString
    }

-- {COLUMN} 1.3.6.1.4.1.2356.11.2.37.1.17.9.1.1
lcsSetupWlanMngmtApConf11uGeneralEntryName OBJECT-TYPE
    SYNTAX     DisplayString (SIZE(0..32))
    MAX-ACCESS read-write
    STATUS     current
    DESCRIPTION
            "-- empty --"
    ::= { lcsSetupWlanMngmtApConf11uGeneralEntry 1 }

-- {COLUMN} 1.3.6.1.4.1.2356.11.2.37.1.17.9.1.2
lcsSetupWlanMngmtApConf11uGeneralEntryLinkStatus OBJECT-TYPE
    SYNTAX     INTEGER {
                  eAuto (0),
                  eLinkUp (1),
                  eLinkDown (2),
                  eLinkTest (3)
            }
    MAX-ACCESS read-write
    STATUS     current
    DESCRIPTION
            "-- empty --"
    ::= { lcsSetupWlanMngmtApConf11uGeneralEntry 2 }

-- {COLUMN} 1.3.6.1.4.1.2356.11.2.37.1.17.9.1.3
lcsSetupWlanMngmtApConf11uGeneralEntryDownlinkSpeed OBJECT-TYPE
    SYNTAX     Integer32 (0..2147483647)
    MAX-ACCESS read-write
    STATUS     current
    DESCRIPTION
            "-- empty --"
    ::= { lcsSetupWlanMngmtApConf11uGeneralEntry 3 }

-- {COLUMN} 1.3.6.1.4.1.2356.11.2.37.1.17.9.1.4
lcsSetupWlanMngmtApConf11uGeneralEntryUplinkSpeed OBJECT-TYPE
    SYNTAX     Integer32 (0..2147483647)
    MAX-ACCESS read-write
    STATUS     current
    DESCRIPTION
            "-- empty --"
    ::= { lcsSetupWlanMngmtApConf11uGeneralEntry 4 }

-- {COLUMN} 1.3.6.1.4.1.2356.11.2.37.1.17.9.1.5
lcsSetupWlanMngmtApConf11uGeneralEntryIpv4AddrType OBJECT-TYPE
    SYNTAX     INTEGER {
                  eNotAvailable (0),
                  ePublicAddrAvailable (1),
                  ePortRestrAddrAvail (2),
                  eSingleNatPrivAddrAvail (3),
                  eDoubleNatPrivAddrAvail (4),
                  ePortRestrSingleNatAddrAvail (5),
                  ePortRestrDoubleNatAddrAvail (6),
                  eAvailabilityNotKnown (7)
            }
    MAX-ACCESS read-write
    STATUS     current
    DESCRIPTION
            "-- empty --"
    ::= { lcsSetupWlanMngmtApConf11uGeneralEntry 5 }

-- {COLUMN} 1.3.6.1.4.1.2356.11.2.37.1.17.9.1.6
lcsSetupWlanMngmtApConf11uGeneralEntryIpv6AddrType OBJECT-TYPE
    SYNTAX     INTEGER {
                  eNotAvailable (0),
                  eAvailable (1),
                  eAvailabilityNotKnown (2)
            }
    MAX-ACCESS read-write
    STATUS     current
    DESCRIPTION
            "-- empty --"
    ::= { lcsSetupWlanMngmtApConf11uGeneralEntry 6 }

-- {COLUMN} 1.3.6.1.4.1.2356.11.2.37.1.17.9.1.7
lcsSetupWlanMngmtApConf11uGeneralEntryVenueGroup OBJECT-TYPE
    SYNTAX     INTEGER {
                  eUnspecified (0),
                  eAssembly (1),
                  eBusiness (2),
                  eEducational (3),
                  eFactoryAndIndustrial (4),
                  eInstitutional (5),
                  eMercantile (6),
                  eResindential (7),
                  eStorage (8),
                  eUtilityAndMiscellaneous (9),
                  eVehicular (10),
                  eOutdoor (11)
            }
    MAX-ACCESS read-write
    STATUS     current
    DESCRIPTION
            "-- empty --"
    ::= { lcsSetupWlanMngmtApConf11uGeneralEntry 7 }

-- {COLUMN} 1.3.6.1.4.1.2356.11.2.37.1.17.9.1.8
lcsSetupWlanMngmtApConf11uGeneralEntryVenueType OBJECT-TYPE
    SYNTAX     Integer32 (0..255)
    MAX-ACCESS read-write
    STATUS     current
    DESCRIPTION
            "-- empty --"
    ::= { lcsSetupWlanMngmtApConf11uGeneralEntry 8 }

-- {COLUMN} 1.3.6.1.4.1.2356.11.2.37.1.17.9.1.9
lcsSetupWlanMngmtApConf11uGeneralEntryVenueName OBJECT-TYPE
    SYNTAX     DisplayString (SIZE(0..32))
    MAX-ACCESS read-write
    STATUS     current
    DESCRIPTION
            "-- empty --"
    ::= { lcsSetupWlanMngmtApConf11uGeneralEntry 9 }

-- {TABLE} 1.3.6.1.4.1.2356.11.2.37.1.17.10
lcsSetupWlanMngmtApConf11uAuthParameterTable OBJECT-TYPE
    SYNTAX     SEQUENCE OF LcsSetupWlanMngmtApConf11uAuthParameterEntry
    MAX-ACCESS not-accessible
    STATUS     current
    DESCRIPTION
            "-- empty --"
    ::= { lcsSetupWlanMngmtApConf11u 10 }

-- {ROW} 1.3.6.1.4.1.2356.11.2.37.1.17.10.1
lcsSetupWlanMngmtApConf11uAuthParameterEntry OBJECT-TYPE
    SYNTAX     LcsSetupWlanMngmtApConf11uAuthParameterEntry
    MAX-ACCESS not-accessible
    STATUS     current
    DESCRIPTION
            ""
    INDEX {
            lcsSetupWlanMngmtApConf11uAuthParameterEntryName
          }
    ::= { lcsSetupWlanMngmtApConf11uAuthParameterTable 1 }

LcsSetupWlanMngmtApConf11uAuthParameterEntry ::= SEQUENCE {
            lcsSetupWlanMngmtApConf11uAuthParameterEntryName DisplayString
    }

-- {COLUMN} 1.3.6.1.4.1.2356.11.2.37.1.17.10.1.1
lcsSetupWlanMngmtApConf11uAuthParameterEntryName OBJECT-TYPE
    SYNTAX     DisplayString (SIZE(0..32))
    MAX-ACCESS read-only
    STATUS     current
    DESCRIPTION
            "-- empty --"
    ::= { lcsSetupWlanMngmtApConf11uAuthParameterEntry 1 }

-- {TABLE} 1.3.6.1.4.1.2356.11.2.37.1.17.11
lcsSetupWlanMngmtApConf11uConnCapTable OBJECT-TYPE
    SYNTAX     SEQUENCE OF LcsSetupWlanMngmtApConf11uConnCapEntry
    MAX-ACCESS not-accessible
    STATUS     current
    DESCRIPTION
            "Connection-Capability"
    ::= { lcsSetupWlanMngmtApConf11u 11 }

-- {ROW} 1.3.6.1.4.1.2356.11.2.37.1.17.11.1
lcsSetupWlanMngmtApConf11uConnCapEntry OBJECT-TYPE
    SYNTAX     LcsSetupWlanMngmtApConf11uConnCapEntry
    MAX-ACCESS not-accessible
    STATUS     current
    DESCRIPTION
            ""
    INDEX {
            lcsSetupWlanMngmtApConf11uConnCapEntryName
          }
    ::= { lcsSetupWlanMngmtApConf11uConnCapTable 1 }

LcsSetupWlanMngmtApConf11uConnCapEntry ::= SEQUENCE {
            lcsSetupWlanMngmtApConf11uConnCapEntryName DisplayString
    }

-- {COLUMN} 1.3.6.1.4.1.2356.11.2.37.1.17.11.1.1
lcsSetupWlanMngmtApConf11uConnCapEntryName OBJECT-TYPE
    SYNTAX     DisplayString (SIZE(0..32))
    MAX-ACCESS read-only
    STATUS     current
    DESCRIPTION
            "-- empty --"
    ::= { lcsSetupWlanMngmtApConf11uConnCapEntry 1 }

-- {TABLE} 1.3.6.1.4.1.2356.11.2.37.1.18
lcsSetupWlanMngmtApConfCfgAsgGrpTable OBJECT-TYPE
    SYNTAX     SEQUENCE OF LcsSetupWlanMngmtApConfCfgAsgGrpEntry
    MAX-ACCESS not-accessible
    STATUS     current
    DESCRIPTION
            ""
    ::= { lcsSetupWlanMngmtApConf 18 }

-- {ROW} 1.3.6.1.4.1.2356.11.2.37.1.18.1
lcsSetupWlanMngmtApConfCfgAsgGrpEntry OBJECT-TYPE
    SYNTAX     LcsSetupWlanMngmtApConfCfgAsgGrpEntry
    MAX-ACCESS not-accessible
    STATUS     current
    DESCRIPTION
            ""
    INDEX {
            lcsSetupWlanMngmtApConfCfgAsgGrpEntryName
          }
    ::= { lcsSetupWlanMngmtApConfCfgAsgGrpTable 1 }

LcsSetupWlanMngmtApConfCfgAsgGrpEntry ::= SEQUENCE {
            lcsSetupWlanMngmtApConfCfgAsgGrpEntryName DisplayString,
            lcsSetupWlanMngmtApConfCfgAsgGrpEntryProfile DisplayString,
            lcsSetupWlanMngmtApConfCfgAsgGrpEntryApIntranet DisplayString,
            lcsSetupWlanMngmtApConfCfgAsgGrpEntryIpv4ReferencePoolStart DisplayString,
            lcsSetupWlanMngmtApConfCfgAsgGrpEntryIpv4ReferencePoolEnd DisplayString,
            lcsSetupWlanMngmtApConfCfgAsgGrpEntryClientSteeringProfile DisplayString,
            lcsSetupWlanMngmtApConfCfgAsgGrpEntryIbeaconProfile DisplayString
    }

-- {COLUMN} 1.3.6.1.4.1.2356.11.2.37.1.18.1.1
lcsSetupWlanMngmtApConfCfgAsgGrpEntryName OBJECT-TYPE
    SYNTAX     DisplayString (SIZE(0..31))
    MAX-ACCESS read-write
    STATUS     current
    DESCRIPTION
            "-- empty --"
    ::= { lcsSetupWlanMngmtApConfCfgAsgGrpEntry 1 }

-- {COLUMN} 1.3.6.1.4.1.2356.11.2.37.1.18.1.2
lcsSetupWlanMngmtApConfCfgAsgGrpEntryProfile OBJECT-TYPE
    SYNTAX     DisplayString (SIZE(0..31))
    MAX-ACCESS read-write
    STATUS     current
    DESCRIPTION
            "-- empty --"
    ::= { lcsSetupWlanMngmtApConfCfgAsgGrpEntry 2 }

-- {COLUMN} 1.3.6.1.4.1.2356.11.2.37.1.18.1.3
lcsSetupWlanMngmtApConfCfgAsgGrpEntryApIntranet OBJECT-TYPE
    SYNTAX     DisplayString (SIZE(0..31))
    MAX-ACCESS read-write
    STATUS     current
    DESCRIPTION
            "-- empty --"
    ::= { lcsSetupWlanMngmtApConfCfgAsgGrpEntry 3 }

-- {COLUMN} 1.3.6.1.4.1.2356.11.2.37.1.18.1.4
lcsSetupWlanMngmtApConfCfgAsgGrpEntryIpv4ReferencePoolStart OBJECT-TYPE
    SYNTAX     DisplayString (SIZE(0..15))
    MAX-ACCESS read-write
    STATUS     current
    DESCRIPTION
            "-- empty --"
    ::= { lcsSetupWlanMngmtApConfCfgAsgGrpEntry 4 }

-- {COLUMN} 1.3.6.1.4.1.2356.11.2.37.1.18.1.5
lcsSetupWlanMngmtApConfCfgAsgGrpEntryIpv4ReferencePoolEnd OBJECT-TYPE
    SYNTAX     DisplayString (SIZE(0..15))
    MAX-ACCESS read-write
    STATUS     current
    DESCRIPTION
            "-- empty --"
    ::= { lcsSetupWlanMngmtApConfCfgAsgGrpEntry 5 }

-- {COLUMN} 1.3.6.1.4.1.2356.11.2.37.1.18.1.6
lcsSetupWlanMngmtApConfCfgAsgGrpEntryClientSteeringProfile OBJECT-TYPE
    SYNTAX     DisplayString (SIZE(0..31))
    MAX-ACCESS read-write
    STATUS     current
    DESCRIPTION
            "-- empty --"
    ::= { lcsSetupWlanMngmtApConfCfgAsgGrpEntry 6 }

-- {COLUMN} 1.3.6.1.4.1.2356.11.2.37.1.18.1.7
lcsSetupWlanMngmtApConfCfgAsgGrpEntryIbeaconProfile OBJECT-TYPE
    SYNTAX     DisplayString (SIZE(0..31))
    MAX-ACCESS read-write
    STATUS     current
    DESCRIPTION
            "-- empty --"
    ::= { lcsSetupWlanMngmtApConfCfgAsgGrpEntry 7 }

-- {TABLE} 1.3.6.1.4.1.2356.11.2.37.1.20
lcsSetupWlanMngmtApConfTagGroupsTable OBJECT-TYPE
    SYNTAX     SEQUENCE OF LcsSetupWlanMngmtApConfTagGroupsEntry
    MAX-ACCESS not-accessible
    STATUS     current
    DESCRIPTION
            "-- empty --"
    ::= { lcsSetupWlanMngmtApConf 20 }

-- {ROW} 1.3.6.1.4.1.2356.11.2.37.1.20.1
lcsSetupWlanMngmtApConfTagGroupsEntry OBJECT-TYPE
    SYNTAX     LcsSetupWlanMngmtApConfTagGroupsEntry
    MAX-ACCESS not-accessible
    STATUS     current
    DESCRIPTION
            ""
    INDEX {
            lcsSetupWlanMngmtApConfTagGroupsEntryName
          }
    ::= { lcsSetupWlanMngmtApConfTagGroupsTable 1 }

LcsSetupWlanMngmtApConfTagGroupsEntry ::= SEQUENCE {
            lcsSetupWlanMngmtApConfTagGroupsEntryName DisplayString
    }

-- {COLUMN} 1.3.6.1.4.1.2356.11.2.37.1.20.1.1
lcsSetupWlanMngmtApConfTagGroupsEntryName OBJECT-TYPE
    SYNTAX     DisplayString (SIZE(0..31))
    MAX-ACCESS read-write
    STATUS     current
    DESCRIPTION
            "-- empty --"
    ::= { lcsSetupWlanMngmtApConfTagGroupsEntry 1 }

-- {TABLE} 1.3.6.1.4.1.2356.11.2.37.1.21
lcsSetupWlanMngmtApConfLedProfilesTable OBJECT-TYPE
    SYNTAX     SEQUENCE OF LcsSetupWlanMngmtApConfLedProfilesEntry
    MAX-ACCESS not-accessible
    STATUS     current
    DESCRIPTION
            "-- empty --"
    ::= { lcsSetupWlanMngmtApConf 21 }

-- {ROW} 1.3.6.1.4.1.2356.11.2.37.1.21.1
lcsSetupWlanMngmtApConfLedProfilesEntry OBJECT-TYPE
    SYNTAX     LcsSetupWlanMngmtApConfLedProfilesEntry
    MAX-ACCESS not-accessible
    STATUS     current
    DESCRIPTION
            ""
    INDEX {
            lcsSetupWlanMngmtApConfLedProfilesEntryName
          }
    ::= { lcsSetupWlanMngmtApConfLedProfilesTable 1 }

LcsSetupWlanMngmtApConfLedProfilesEntry ::= SEQUENCE {
            lcsSetupWlanMngmtApConfLedProfilesEntryName DisplayString,
            lcsSetupWlanMngmtApConfLedProfilesEntryLedMode INTEGER,
            lcsSetupWlanMngmtApConfLedProfilesEntryLedOffSeconds Integer32
    }

-- {COLUMN} 1.3.6.1.4.1.2356.11.2.37.1.21.1.1
lcsSetupWlanMngmtApConfLedProfilesEntryName OBJECT-TYPE
    SYNTAX     DisplayString (SIZE(0..31))
    MAX-ACCESS read-write
    STATUS     current
    DESCRIPTION
            "-- empty --"
    ::= { lcsSetupWlanMngmtApConfLedProfilesEntry 1 }

-- {COLUMN} 1.3.6.1.4.1.2356.11.2.37.1.21.1.4
lcsSetupWlanMngmtApConfLedProfilesEntryLedMode OBJECT-TYPE
    SYNTAX     INTEGER {
                  eOn (0),
                  eOff (1),
                  eTimedOff (2)
            }
    MAX-ACCESS read-write
    STATUS     current
    DESCRIPTION
            "-- empty --"
    ::= { lcsSetupWlanMngmtApConfLedProfilesEntry 4 }

-- {COLUMN} 1.3.6.1.4.1.2356.11.2.37.1.21.1.5
lcsSetupWlanMngmtApConfLedProfilesEntryLedOffSeconds OBJECT-TYPE
    SYNTAX     Integer32 (0..2147483647)
    MAX-ACCESS read-write
    STATUS     current
    DESCRIPTION
            "-- empty --"
    ::= { lcsSetupWlanMngmtApConfLedProfilesEntry 5 }

-- {NODE} 1.3.6.1.4.1.2356.11.2.37.1.22
lcsSetupWlanMngmtApConfLbs OBJECT IDENTIFIER ::= { lcsSetupWlanMngmtApConf 22 }

-- {TABLE} 1.3.6.1.4.1.2356.11.2.37.1.22.1
lcsSetupWlanMngmtApConfLbsGeneralTable OBJECT-TYPE
    SYNTAX     SEQUENCE OF LcsSetupWlanMngmtApConfLbsGeneralEntry
    MAX-ACCESS not-accessible
    STATUS     current
    DESCRIPTION
            "-- empty --"
    ::= { lcsSetupWlanMngmtApConfLbs 1 }

-- {ROW} 1.3.6.1.4.1.2356.11.2.37.1.22.1.1
lcsSetupWlanMngmtApConfLbsGeneralEntry OBJECT-TYPE
    SYNTAX     LcsSetupWlanMngmtApConfLbsGeneralEntry
    MAX-ACCESS not-accessible
    STATUS     current
    DESCRIPTION
            ""
    INDEX {
            lcsSetupWlanMngmtApConfLbsGeneralEntryName
          }
    ::= { lcsSetupWlanMngmtApConfLbsGeneralTable 1 }

LcsSetupWlanMngmtApConfLbsGeneralEntry ::= SEQUENCE {
            lcsSetupWlanMngmtApConfLbsGeneralEntryName DisplayString,
            lcsSetupWlanMngmtApConfLbsGeneralEntryOperating INTEGER,
            lcsSetupWlanMngmtApConfLbsGeneralEntryUseTlsConnection INTEGER,
            lcsSetupWlanMngmtApConfLbsGeneralEntryLbsServerAddress DisplayString,
            lcsSetupWlanMngmtApConfLbsGeneralEntryLbsServerPort Integer32,
            lcsSetupWlanMngmtApConfLbsGeneralEntryUserName DisplayString,
            lcsSetupWlanMngmtApConfLbsGeneralEntryPassword DisplayString,
            lcsSetupWlanMngmtApConfLbsGeneralEntryAggregation INTEGER,
            lcsSetupWlanMngmtApConfLbsGeneralEntrySequenceNumberTransmit INTEGER,
            lcsSetupWlanMngmtApConfLbsGeneralEntrySsidTransmit INTEGER,
            lcsSetupWlanMngmtApConfLbsGeneralEntryIfcTrans INTEGER,
            lcsSetupWlanMngmtApConfLbsGeneralEntryBssidTransmit INTEGER,
            lcsSetupWlanMngmtApConfLbsGeneralEntrySignalLevelTransmit INTEGER,
            lcsSetupWlanMngmtApConfLbsGeneralEntryFrequencyTransmit INTEGER,
            lcsSetupWlanMngmtApConfLbsGeneralEntryNoiseTransmit INTEGER,
            lcsSetupWlanMngmtApConfLbsGeneralEntryWlanFrameTypeTransmit INTEGER
    }

-- {COLUMN} 1.3.6.1.4.1.2356.11.2.37.1.22.1.1.1
lcsSetupWlanMngmtApConfLbsGeneralEntryName OBJECT-TYPE
    SYNTAX     DisplayString (SIZE(0..31))
    MAX-ACCESS read-write
    STATUS     current
    DESCRIPTION
            "-- empty --"
    ::= { lcsSetupWlanMngmtApConfLbsGeneralEntry 1 }

-- {COLUMN} 1.3.6.1.4.1.2356.11.2.37.1.22.1.1.2
lcsSetupWlanMngmtApConfLbsGeneralEntryOperating OBJECT-TYPE
    SYNTAX     INTEGER {
                  eNo (0),
                  eYes (1)
            }
    MAX-ACCESS read-write
    STATUS     current
    DESCRIPTION
            "-- empty --"
    ::= { lcsSetupWlanMngmtApConfLbsGeneralEntry 2 }

-- {COLUMN} 1.3.6.1.4.1.2356.11.2.37.1.22.1.1.3
lcsSetupWlanMngmtApConfLbsGeneralEntryUseTlsConnection OBJECT-TYPE
    SYNTAX     INTEGER {
                  eNo (0),
                  eYes (1)
            }
    MAX-ACCESS read-write
    STATUS     current
    DESCRIPTION
            "-- empty --"
    ::= { lcsSetupWlanMngmtApConfLbsGeneralEntry 3 }

-- {COLUMN} 1.3.6.1.4.1.2356.11.2.37.1.22.1.1.4
lcsSetupWlanMngmtApConfLbsGeneralEntryLbsServerAddress OBJECT-TYPE
    SYNTAX     DisplayString (SIZE(0..64))
    MAX-ACCESS read-write
    STATUS     current
    DESCRIPTION
            "-- empty --"
    ::= { lcsSetupWlanMngmtApConfLbsGeneralEntry 4 }

-- {COLUMN} 1.3.6.1.4.1.2356.11.2.37.1.22.1.1.5
lcsSetupWlanMngmtApConfLbsGeneralEntryLbsServerPort OBJECT-TYPE
    SYNTAX     Integer32 (0..65535)
    MAX-ACCESS read-write
    STATUS     current
    DESCRIPTION
            "-- empty --"
    ::= { lcsSetupWlanMngmtApConfLbsGeneralEntry 5 }

-- {COLUMN} 1.3.6.1.4.1.2356.11.2.37.1.22.1.1.6
lcsSetupWlanMngmtApConfLbsGeneralEntryUserName OBJECT-TYPE
    SYNTAX     DisplayString (SIZE(0..64))
    MAX-ACCESS read-write
    STATUS     current
    DESCRIPTION
            "-- empty --"
    ::= { lcsSetupWlanMngmtApConfLbsGeneralEntry 6 }

-- {COLUMN} 1.3.6.1.4.1.2356.11.2.37.1.22.1.1.7
lcsSetupWlanMngmtApConfLbsGeneralEntryPassword OBJECT-TYPE
    SYNTAX     DisplayString (SIZE(0..32))
    MAX-ACCESS read-write
    STATUS     current
    DESCRIPTION
            "-- empty --"
    ::= { lcsSetupWlanMngmtApConfLbsGeneralEntry 7 }

-- {COLUMN} 1.3.6.1.4.1.2356.11.2.37.1.22.1.1.8
lcsSetupWlanMngmtApConfLbsGeneralEntryAggregation OBJECT-TYPE
    SYNTAX     INTEGER {
                  eNo (0),
                  eYes (1)
            }
    MAX-ACCESS read-write
    STATUS     current
    DESCRIPTION
            "-- empty --"
    ::= { lcsSetupWlanMngmtApConfLbsGeneralEntry 8 }

-- {COLUMN} 1.3.6.1.4.1.2356.11.2.37.1.22.1.1.9
lcsSetupWlanMngmtApConfLbsGeneralEntrySequenceNumberTransmit OBJECT-TYPE
    SYNTAX     INTEGER {
                  eNo (0),
                  eYes (1)
            }
    MAX-ACCESS read-write
    STATUS     current
    DESCRIPTION
            "-- empty --"
    ::= { lcsSetupWlanMngmtApConfLbsGeneralEntry 9 }

-- {COLUMN} 1.3.6.1.4.1.2356.11.2.37.1.22.1.1.10
lcsSetupWlanMngmtApConfLbsGeneralEntrySsidTransmit OBJECT-TYPE
    SYNTAX     INTEGER {
                  eNo (0),
                  eYes (1)
            }
    MAX-ACCESS read-write
    STATUS     current
    DESCRIPTION
            "-- empty --"
    ::= { lcsSetupWlanMngmtApConfLbsGeneralEntry 10 }

-- {COLUMN} 1.3.6.1.4.1.2356.11.2.37.1.22.1.1.11
lcsSetupWlanMngmtApConfLbsGeneralEntryIfcTrans OBJECT-TYPE
    SYNTAX     INTEGER {
                  eNo (0),
                  eYes (1)
            }
    MAX-ACCESS read-write
    STATUS     current
    DESCRIPTION
            ""
    ::= { lcsSetupWlanMngmtApConfLbsGeneralEntry 11 }

-- {COLUMN} 1.3.6.1.4.1.2356.11.2.37.1.22.1.1.12
lcsSetupWlanMngmtApConfLbsGeneralEntryBssidTransmit OBJECT-TYPE
    SYNTAX     INTEGER {
                  eNo (0),
                  eYes (1)
            }
    MAX-ACCESS read-write
    STATUS     current
    DESCRIPTION
            "-- empty --"
    ::= { lcsSetupWlanMngmtApConfLbsGeneralEntry 12 }

-- {COLUMN} 1.3.6.1.4.1.2356.11.2.37.1.22.1.1.13
lcsSetupWlanMngmtApConfLbsGeneralEntrySignalLevelTransmit OBJECT-TYPE
    SYNTAX     INTEGER {
                  eNo (0),
                  eYes (1)
            }
    MAX-ACCESS read-write
    STATUS     current
    DESCRIPTION
            "-- empty --"
    ::= { lcsSetupWlanMngmtApConfLbsGeneralEntry 13 }

-- {COLUMN} 1.3.6.1.4.1.2356.11.2.37.1.22.1.1.14
lcsSetupWlanMngmtApConfLbsGeneralEntryFrequencyTransmit OBJECT-TYPE
    SYNTAX     INTEGER {
                  eNo (0),
                  eYes (1)
            }
    MAX-ACCESS read-write
    STATUS     current
    DESCRIPTION
            "-- empty --"
    ::= { lcsSetupWlanMngmtApConfLbsGeneralEntry 14 }

-- {COLUMN} 1.3.6.1.4.1.2356.11.2.37.1.22.1.1.15
lcsSetupWlanMngmtApConfLbsGeneralEntryNoiseTransmit OBJECT-TYPE
    SYNTAX     INTEGER {
                  eNo (0),
                  eYes (1)
            }
    MAX-ACCESS read-write
    STATUS     current
    DESCRIPTION
            "-- empty --"
    ::= { lcsSetupWlanMngmtApConfLbsGeneralEntry 15 }

-- {COLUMN} 1.3.6.1.4.1.2356.11.2.37.1.22.1.1.16
lcsSetupWlanMngmtApConfLbsGeneralEntryWlanFrameTypeTransmit OBJECT-TYPE
    SYNTAX     INTEGER {
                  eNo (0),
                  eYes (1)
            }
    MAX-ACCESS read-write
    STATUS     current
    DESCRIPTION
            "-- empty --"
    ::= { lcsSetupWlanMngmtApConfLbsGeneralEntry 16 }

-- {TABLE} 1.3.6.1.4.1.2356.11.2.37.1.22.2
lcsSetupWlanMngmtApConfLbsDevLocTable OBJECT-TYPE
    SYNTAX     SEQUENCE OF LcsSetupWlanMngmtApConfLbsDevLocEntry
    MAX-ACCESS not-accessible
    STATUS     current
    DESCRIPTION
            ""
    ::= { lcsSetupWlanMngmtApConfLbs 2 }

-- {ROW} 1.3.6.1.4.1.2356.11.2.37.1.22.2.1
lcsSetupWlanMngmtApConfLbsDevLocEntry OBJECT-TYPE
    SYNTAX     LcsSetupWlanMngmtApConfLbsDevLocEntry
    MAX-ACCESS not-accessible
    STATUS     current
    DESCRIPTION
            ""
    INDEX {
            lcsSetupWlanMngmtApConfLbsDevLocEntryName
          }
    ::= { lcsSetupWlanMngmtApConfLbsDevLocTable 1 }

LcsSetupWlanMngmtApConfLbsDevLocEntry ::= SEQUENCE {
            lcsSetupWlanMngmtApConfLbsDevLocEntryName DisplayString,
            lcsSetupWlanMngmtApConfLbsDevLocEntryFloor Integer32,
            lcsSetupWlanMngmtApConfLbsDevLocEntryHeight Integer32,
            lcsSetupWlanMngmtApConfLbsDevLocEntryLatDeg Integer32,
            lcsSetupWlanMngmtApConfLbsDevLocEntryLatMin Integer32,
            lcsSetupWlanMngmtApConfLbsDevLocEntryLatSec Integer32,
            lcsSetupWlanMngmtApConfLbsDevLocEntryLatHemi INTEGER,
            lcsSetupWlanMngmtApConfLbsDevLocEntryLongDeg Integer32,
            lcsSetupWlanMngmtApConfLbsDevLocEntryLongMin Integer32,
            lcsSetupWlanMngmtApConfLbsDevLocEntryLongSec Integer32,
            lcsSetupWlanMngmtApConfLbsDevLocEntryLongHemi INTEGER,
            lcsSetupWlanMngmtApConfLbsDevLocEntryDescription DisplayString,
            lcsSetupWlanMngmtApConfLbsDevLocEntryLatDecDeg DisplayString,
            lcsSetupWlanMngmtApConfLbsDevLocEntryLongDecDeg DisplayString
    }

-- {COLUMN} 1.3.6.1.4.1.2356.11.2.37.1.22.2.1.1
lcsSetupWlanMngmtApConfLbsDevLocEntryName OBJECT-TYPE
    SYNTAX     DisplayString (SIZE(0..31))
    MAX-ACCESS read-write
    STATUS     current
    DESCRIPTION
            "-- empty --"
    ::= { lcsSetupWlanMngmtApConfLbsDevLocEntry 1 }

-- {COLUMN} 1.3.6.1.4.1.2356.11.2.37.1.22.2.1.2
lcsSetupWlanMngmtApConfLbsDevLocEntryFloor OBJECT-TYPE
    SYNTAX     Integer32 (-32768..32767)
    MAX-ACCESS read-write
    STATUS     current
    DESCRIPTION
            "-- empty --"
    ::= { lcsSetupWlanMngmtApConfLbsDevLocEntry 2 }

-- {COLUMN} 1.3.6.1.4.1.2356.11.2.37.1.22.2.1.3
lcsSetupWlanMngmtApConfLbsDevLocEntryHeight OBJECT-TYPE
    SYNTAX     Integer32 (-32768..32767)
    MAX-ACCESS read-write
    STATUS     current
    DESCRIPTION
            "-- empty --"
    ::= { lcsSetupWlanMngmtApConfLbsDevLocEntry 3 }

-- {COLUMN} 1.3.6.1.4.1.2356.11.2.37.1.22.2.1.4
lcsSetupWlanMngmtApConfLbsDevLocEntryLatDeg OBJECT-TYPE
    SYNTAX     Integer32 (0..255)
    MAX-ACCESS read-write
    STATUS     current
    DESCRIPTION
            ""
    ::= { lcsSetupWlanMngmtApConfLbsDevLocEntry 4 }

-- {COLUMN} 1.3.6.1.4.1.2356.11.2.37.1.22.2.1.5
lcsSetupWlanMngmtApConfLbsDevLocEntryLatMin OBJECT-TYPE
    SYNTAX     Integer32 (0..255)
    MAX-ACCESS read-write
    STATUS     current
    DESCRIPTION
            ""
    ::= { lcsSetupWlanMngmtApConfLbsDevLocEntry 5 }

-- {COLUMN} 1.3.6.1.4.1.2356.11.2.37.1.22.2.1.6
lcsSetupWlanMngmtApConfLbsDevLocEntryLatSec OBJECT-TYPE
    SYNTAX     Integer32 (0..2147483647)
    MAX-ACCESS read-write
    STATUS     current
    DESCRIPTION
            ""
    ::= { lcsSetupWlanMngmtApConfLbsDevLocEntry 6 }

-- {COLUMN} 1.3.6.1.4.1.2356.11.2.37.1.22.2.1.7
lcsSetupWlanMngmtApConfLbsDevLocEntryLatHemi OBJECT-TYPE
    SYNTAX     INTEGER {
                  eN (0),
                  eS (1)
            }
    MAX-ACCESS read-write
    STATUS     current
    DESCRIPTION
            ""
    ::= { lcsSetupWlanMngmtApConfLbsDevLocEntry 7 }

-- {COLUMN} 1.3.6.1.4.1.2356.11.2.37.1.22.2.1.8
lcsSetupWlanMngmtApConfLbsDevLocEntryLongDeg OBJECT-TYPE
    SYNTAX     Integer32 (0..255)
    MAX-ACCESS read-write
    STATUS     current
    DESCRIPTION
            ""
    ::= { lcsSetupWlanMngmtApConfLbsDevLocEntry 8 }

-- {COLUMN} 1.3.6.1.4.1.2356.11.2.37.1.22.2.1.9
lcsSetupWlanMngmtApConfLbsDevLocEntryLongMin OBJECT-TYPE
    SYNTAX     Integer32 (0..255)
    MAX-ACCESS read-write
    STATUS     current
    DESCRIPTION
            ""
    ::= { lcsSetupWlanMngmtApConfLbsDevLocEntry 9 }

-- {COLUMN} 1.3.6.1.4.1.2356.11.2.37.1.22.2.1.10
lcsSetupWlanMngmtApConfLbsDevLocEntryLongSec OBJECT-TYPE
    SYNTAX     Integer32 (0..2147483647)
    MAX-ACCESS read-write
    STATUS     current
    DESCRIPTION
            ""
    ::= { lcsSetupWlanMngmtApConfLbsDevLocEntry 10 }

-- {COLUMN} 1.3.6.1.4.1.2356.11.2.37.1.22.2.1.11
lcsSetupWlanMngmtApConfLbsDevLocEntryLongHemi OBJECT-TYPE
    SYNTAX     INTEGER {
                  eE (0),
                  eW (1)
            }
    MAX-ACCESS read-write
    STATUS     current
    DESCRIPTION
            ""
    ::= { lcsSetupWlanMngmtApConfLbsDevLocEntry 11 }

-- {COLUMN} 1.3.6.1.4.1.2356.11.2.37.1.22.2.1.12
lcsSetupWlanMngmtApConfLbsDevLocEntryDescription OBJECT-TYPE
    SYNTAX     DisplayString (SIZE(0..31))
    MAX-ACCESS read-write
    STATUS     current
    DESCRIPTION
            "-- empty --"
    ::= { lcsSetupWlanMngmtApConfLbsDevLocEntry 12 }

-- {COLUMN} 1.3.6.1.4.1.2356.11.2.37.1.22.2.1.13
lcsSetupWlanMngmtApConfLbsDevLocEntryLatDecDeg OBJECT-TYPE
    SYNTAX     DisplayString (SIZE(0..12))
    MAX-ACCESS read-write
    STATUS     current
    DESCRIPTION
            ""
    ::= { lcsSetupWlanMngmtApConfLbsDevLocEntry 13 }

-- {COLUMN} 1.3.6.1.4.1.2356.11.2.37.1.22.2.1.14
lcsSetupWlanMngmtApConfLbsDevLocEntryLongDecDeg OBJECT-TYPE
    SYNTAX     DisplayString (SIZE(0..12))
    MAX-ACCESS read-write
    STATUS     current
    DESCRIPTION
            ""
    ::= { lcsSetupWlanMngmtApConfLbsDevLocEntry 14 }

-- {TABLE} 1.3.6.1.4.1.2356.11.2.37.1.23
lcsSetupWlanMngmtApConfWirelessEpaperProfileTable OBJECT-TYPE
    SYNTAX     SEQUENCE OF LcsSetupWlanMngmtApConfWirelessEpaperProfileEntry
    MAX-ACCESS not-accessible
    STATUS     current
    DESCRIPTION
            "-- empty --"
    ::= { lcsSetupWlanMngmtApConf 23 }

-- {ROW} 1.3.6.1.4.1.2356.11.2.37.1.23.1
lcsSetupWlanMngmtApConfWirelessEpaperProfileEntry OBJECT-TYPE
    SYNTAX     LcsSetupWlanMngmtApConfWirelessEpaperProfileEntry
    MAX-ACCESS not-accessible
    STATUS     current
    DESCRIPTION
            ""
    INDEX {
            lcsSetupWlanMngmtApConfWirelessEpaperProfileEntryName
          }
    ::= { lcsSetupWlanMngmtApConfWirelessEpaperProfileTable 1 }

LcsSetupWlanMngmtApConfWirelessEpaperProfileEntry ::= SEQUENCE {
            lcsSetupWlanMngmtApConfWirelessEpaperProfileEntryName DisplayString,
            lcsSetupWlanMngmtApConfWirelessEpaperProfileEntryOperating INTEGER,
            lcsSetupWlanMngmtApConfWirelessEpaperProfileEntryPort Integer32
    }

-- {COLUMN} 1.3.6.1.4.1.2356.11.2.37.1.23.1.1
lcsSetupWlanMngmtApConfWirelessEpaperProfileEntryName OBJECT-TYPE
    SYNTAX     DisplayString (SIZE(0..31))
    MAX-ACCESS read-write
    STATUS     current
    DESCRIPTION
            "-- empty --"
    ::= { lcsSetupWlanMngmtApConfWirelessEpaperProfileEntry 1 }

-- {COLUMN} 1.3.6.1.4.1.2356.11.2.37.1.23.1.2
lcsSetupWlanMngmtApConfWirelessEpaperProfileEntryOperating OBJECT-TYPE
    SYNTAX     INTEGER {
                  eNo (0),
                  eYes (1)
            }
    MAX-ACCESS read-write
    STATUS     current
    DESCRIPTION
            "-- empty --"
    ::= { lcsSetupWlanMngmtApConfWirelessEpaperProfileEntry 2 }

-- {COLUMN} 1.3.6.1.4.1.2356.11.2.37.1.23.1.3
lcsSetupWlanMngmtApConfWirelessEpaperProfileEntryPort OBJECT-TYPE
    SYNTAX     Integer32 (0..65535)
    MAX-ACCESS read-write
    STATUS     current
    DESCRIPTION
            "-- empty --"
    ::= { lcsSetupWlanMngmtApConfWirelessEpaperProfileEntry 3 }

-- {TABLE} 1.3.6.1.4.1.2356.11.2.37.1.24
lcsSetupWlanMngmtApConfIbeaconProfileTable OBJECT-TYPE
    SYNTAX     SEQUENCE OF LcsSetupWlanMngmtApConfIbeaconProfileEntry
    MAX-ACCESS not-accessible
    STATUS     current
    DESCRIPTION
            "-- empty --"
    ::= { lcsSetupWlanMngmtApConf 24 }

-- {ROW} 1.3.6.1.4.1.2356.11.2.37.1.24.1
lcsSetupWlanMngmtApConfIbeaconProfileEntry OBJECT-TYPE
    SYNTAX     LcsSetupWlanMngmtApConfIbeaconProfileEntry
    MAX-ACCESS not-accessible
    STATUS     current
    DESCRIPTION
            ""
    INDEX {
            lcsSetupWlanMngmtApConfIbeaconProfileEntryName
          }
    ::= { lcsSetupWlanMngmtApConfIbeaconProfileTable 1 }

LcsSetupWlanMngmtApConfIbeaconProfileEntry ::= SEQUENCE {
            lcsSetupWlanMngmtApConfIbeaconProfileEntryName DisplayString,
            lcsSetupWlanMngmtApConfIbeaconProfileEntryOperating INTEGER,
            lcsSetupWlanMngmtApConfIbeaconProfileEntryMajor Integer32,
            lcsSetupWlanMngmtApConfIbeaconProfileEntryUuid DisplayString
    }

-- {COLUMN} 1.3.6.1.4.1.2356.11.2.37.1.24.1.1
lcsSetupWlanMngmtApConfIbeaconProfileEntryName OBJECT-TYPE
    SYNTAX     DisplayString (SIZE(0..31))
    MAX-ACCESS read-write
    STATUS     current
    DESCRIPTION
            "-- empty --"
    ::= { lcsSetupWlanMngmtApConfIbeaconProfileEntry 1 }

-- {COLUMN} 1.3.6.1.4.1.2356.11.2.37.1.24.1.2
lcsSetupWlanMngmtApConfIbeaconProfileEntryOperating OBJECT-TYPE
    SYNTAX     INTEGER {
                  eNo (0),
                  eYes (1)
            }
    MAX-ACCESS read-write
    STATUS     current
    DESCRIPTION
            "-- empty --"
    ::= { lcsSetupWlanMngmtApConfIbeaconProfileEntry 2 }

-- {COLUMN} 1.3.6.1.4.1.2356.11.2.37.1.24.1.3
lcsSetupWlanMngmtApConfIbeaconProfileEntryMajor OBJECT-TYPE
    SYNTAX     Integer32 (0..65535)
    MAX-ACCESS read-write
    STATUS     current
    DESCRIPTION
            "-- empty --"
    ::= { lcsSetupWlanMngmtApConfIbeaconProfileEntry 3 }

-- {COLUMN} 1.3.6.1.4.1.2356.11.2.37.1.24.1.4
lcsSetupWlanMngmtApConfIbeaconProfileEntryUuid OBJECT-TYPE
    SYNTAX     DisplayString (SIZE(0..36))
    MAX-ACCESS read-write
    STATUS     current
    DESCRIPTION
            "-- empty --"
    ::= { lcsSetupWlanMngmtApConfIbeaconProfileEntry 4 }

-- {NODE} 1.3.6.1.4.1.2356.11.2.37.1.25
lcsSetupWlanMngmtApConfLepsU OBJECT IDENTIFIER ::= { lcsSetupWlanMngmtApConf 25 }

-- {TABLE} 1.3.6.1.4.1.2356.11.2.37.1.25.1
lcsSetupWlanMngmtApConfLepsUProfilesTable OBJECT-TYPE
    SYNTAX     SEQUENCE OF LcsSetupWlanMngmtApConfLepsUProfilesEntry
    MAX-ACCESS not-accessible
    STATUS     current
    DESCRIPTION
            "-- empty --"
    ::= { lcsSetupWlanMngmtApConfLepsU 1 }

-- {ROW} 1.3.6.1.4.1.2356.11.2.37.1.25.1.1
lcsSetupWlanMngmtApConfLepsUProfilesEntry OBJECT-TYPE
    SYNTAX     LcsSetupWlanMngmtApConfLepsUProfilesEntry
    MAX-ACCESS not-accessible
    STATUS     current
    DESCRIPTION
            ""
    INDEX {
            lcsSetupWlanMngmtApConfLepsUProfilesEntryName
          }
    ::= { lcsSetupWlanMngmtApConfLepsUProfilesTable 1 }

LcsSetupWlanMngmtApConfLepsUProfilesEntry ::= SEQUENCE {
            lcsSetupWlanMngmtApConfLepsUProfilesEntryName DisplayString,
            lcsSetupWlanMngmtApConfLepsUProfilesEntryNetworkprofile DisplayString,
            lcsSetupWlanMngmtApConfLepsUProfilesEntryPerClientTxLimit Integer32,
            lcsSetupWlanMngmtApConfLepsUProfilesEntryPerClientRxLimit Integer32,
            lcsSetupWlanMngmtApConfLepsUProfilesEntryVlanIdnew Integer32
    }

-- {COLUMN} 1.3.6.1.4.1.2356.11.2.37.1.25.1.1.1
lcsSetupWlanMngmtApConfLepsUProfilesEntryName OBJECT-TYPE
    SYNTAX     DisplayString (SIZE(0..32))
    MAX-ACCESS read-write
    STATUS     current
    DESCRIPTION
            "-- empty --"
    ::= { lcsSetupWlanMngmtApConfLepsUProfilesEntry 1 }

-- {COLUMN} 1.3.6.1.4.1.2356.11.2.37.1.25.1.1.2
lcsSetupWlanMngmtApConfLepsUProfilesEntryNetworkprofile OBJECT-TYPE
    SYNTAX     DisplayString (SIZE(0..31))
    MAX-ACCESS read-write
    STATUS     current
    DESCRIPTION
            "-- empty --"
    ::= { lcsSetupWlanMngmtApConfLepsUProfilesEntry 2 }

-- {COLUMN} 1.3.6.1.4.1.2356.11.2.37.1.25.1.1.3
lcsSetupWlanMngmtApConfLepsUProfilesEntryPerClientTxLimit OBJECT-TYPE
    SYNTAX     Integer32 (0..2147483647)
    MAX-ACCESS read-write
    STATUS     current
    DESCRIPTION
            "-- empty --"
    ::= { lcsSetupWlanMngmtApConfLepsUProfilesEntry 3 }

-- {COLUMN} 1.3.6.1.4.1.2356.11.2.37.1.25.1.1.4
lcsSetupWlanMngmtApConfLepsUProfilesEntryPerClientRxLimit OBJECT-TYPE
    SYNTAX     Integer32 (0..2147483647)
    MAX-ACCESS read-write
    STATUS     current
    DESCRIPTION
            "-- empty --"
    ::= { lcsSetupWlanMngmtApConfLepsUProfilesEntry 4 }

-- {COLUMN} 1.3.6.1.4.1.2356.11.2.37.1.25.1.1.5
lcsSetupWlanMngmtApConfLepsUProfilesEntryVlanIdnew OBJECT-TYPE
    SYNTAX     Integer32 (0..65535)
    MAX-ACCESS read-write
    STATUS     current
    DESCRIPTION
            ""
    ::= { lcsSetupWlanMngmtApConfLepsUProfilesEntry 5 }

-- {TABLE} 1.3.6.1.4.1.2356.11.2.37.1.25.2
lcsSetupWlanMngmtApConfLepsUUsersTable OBJECT-TYPE
    SYNTAX     SEQUENCE OF LcsSetupWlanMngmtApConfLepsUUsersEntry
    MAX-ACCESS not-accessible
    STATUS     current
    DESCRIPTION
            "-- empty --"
    ::= { lcsSetupWlanMngmtApConfLepsU 2 }

-- {ROW} 1.3.6.1.4.1.2356.11.2.37.1.25.2.1
lcsSetupWlanMngmtApConfLepsUUsersEntry OBJECT-TYPE
    SYNTAX     LcsSetupWlanMngmtApConfLepsUUsersEntry
    MAX-ACCESS not-accessible
    STATUS     current
    DESCRIPTION
            ""
    INDEX {
            lcsSetupWlanMngmtApConfLepsUUsersEntryName
          }
    ::= { lcsSetupWlanMngmtApConfLepsUUsersTable 1 }

LcsSetupWlanMngmtApConfLepsUUsersEntry ::= SEQUENCE {
            lcsSetupWlanMngmtApConfLepsUUsersEntryName DisplayString,
            lcsSetupWlanMngmtApConfLepsUUsersEntryProfile DisplayString,
            lcsSetupWlanMngmtApConfLepsUUsersEntryWpaPassphrase DisplayString,
            lcsSetupWlanMngmtApConfLepsUUsersEntryPerClientTxLimit Integer32,
            lcsSetupWlanMngmtApConfLepsUUsersEntryPerClientRxLimit Integer32,
            lcsSetupWlanMngmtApConfLepsUUsersEntryVlanIdnew Integer32
    }

-- {COLUMN} 1.3.6.1.4.1.2356.11.2.37.1.25.2.1.1
lcsSetupWlanMngmtApConfLepsUUsersEntryName OBJECT-TYPE
    SYNTAX     DisplayString (SIZE(0..32))
    MAX-ACCESS read-write
    STATUS     current
    DESCRIPTION
            "-- empty --"
    ::= { lcsSetupWlanMngmtApConfLepsUUsersEntry 1 }

-- {COLUMN} 1.3.6.1.4.1.2356.11.2.37.1.25.2.1.2
lcsSetupWlanMngmtApConfLepsUUsersEntryProfile OBJECT-TYPE
    SYNTAX     DisplayString (SIZE(0..32))
    MAX-ACCESS read-write
    STATUS     current
    DESCRIPTION
            "-- empty --"
    ::= { lcsSetupWlanMngmtApConfLepsUUsersEntry 2 }

-- {COLUMN} 1.3.6.1.4.1.2356.11.2.37.1.25.2.1.3
lcsSetupWlanMngmtApConfLepsUUsersEntryWpaPassphrase OBJECT-TYPE
    SYNTAX     DisplayString (SIZE(0..63))
    MAX-ACCESS read-write
    STATUS     current
    DESCRIPTION
            "-- empty --"
    ::= { lcsSetupWlanMngmtApConfLepsUUsersEntry 3 }

-- {COLUMN} 1.3.6.1.4.1.2356.11.2.37.1.25.2.1.4
lcsSetupWlanMngmtApConfLepsUUsersEntryPerClientTxLimit OBJECT-TYPE
    SYNTAX     Integer32 (0..2147483647)
    MAX-ACCESS read-write
    STATUS     current
    DESCRIPTION
            "-- empty --"
    ::= { lcsSetupWlanMngmtApConfLepsUUsersEntry 4 }

-- {COLUMN} 1.3.6.1.4.1.2356.11.2.37.1.25.2.1.5
lcsSetupWlanMngmtApConfLepsUUsersEntryPerClientRxLimit OBJECT-TYPE
    SYNTAX     Integer32 (0..2147483647)
    MAX-ACCESS read-write
    STATUS     current
    DESCRIPTION
            "-- empty --"
    ::= { lcsSetupWlanMngmtApConfLepsUUsersEntry 5 }

-- {COLUMN} 1.3.6.1.4.1.2356.11.2.37.1.25.2.1.6
lcsSetupWlanMngmtApConfLepsUUsersEntryVlanIdnew OBJECT-TYPE
    SYNTAX     Integer32 (0..65535)
    MAX-ACCESS read-write
    STATUS     current
    DESCRIPTION
            ""
    ::= { lcsSetupWlanMngmtApConfLepsUUsersEntry 6 }

-- {TABLE} 1.3.6.1.4.1.2356.11.2.37.1.26
lcsSetupWlanMngmtApConfTimeframeTable OBJECT-TYPE
    SYNTAX     SEQUENCE OF LcsSetupWlanMngmtApConfTimeframeEntry
    MAX-ACCESS not-accessible
    STATUS     current
    DESCRIPTION
            "-- empty --"
    ::= { lcsSetupWlanMngmtApConf 26 }

-- {ROW} 1.3.6.1.4.1.2356.11.2.37.1.26.1
lcsSetupWlanMngmtApConfTimeframeEntry OBJECT-TYPE
    SYNTAX     LcsSetupWlanMngmtApConfTimeframeEntry
    MAX-ACCESS not-accessible
    STATUS     current
    DESCRIPTION
            ""
    INDEX {
            lcsSetupWlanMngmtApConfTimeframeEntryName,
            lcsSetupWlanMngmtApConfTimeframeEntryStart,
            lcsSetupWlanMngmtApConfTimeframeEntryStop,
            lcsSetupWlanMngmtApConfTimeframeEntryWeekdays
          }
    ::= { lcsSetupWlanMngmtApConfTimeframeTable 1 }

LcsSetupWlanMngmtApConfTimeframeEntry ::= SEQUENCE {
            lcsSetupWlanMngmtApConfTimeframeEntryName DisplayString,
            lcsSetupWlanMngmtApConfTimeframeEntryStart DisplayString,
            lcsSetupWlanMngmtApConfTimeframeEntryStop DisplayString,
            lcsSetupWlanMngmtApConfTimeframeEntryWeekdays BITS
    }

-- {COLUMN} 1.3.6.1.4.1.2356.11.2.37.1.26.1.1
lcsSetupWlanMngmtApConfTimeframeEntryName OBJECT-TYPE
    SYNTAX     DisplayString (SIZE(0..31))
    MAX-ACCESS read-write
    STATUS     current
    DESCRIPTION
            "-- empty --"
    ::= { lcsSetupWlanMngmtApConfTimeframeEntry 1 }

-- {COLUMN} 1.3.6.1.4.1.2356.11.2.37.1.26.1.2
lcsSetupWlanMngmtApConfTimeframeEntryStart OBJECT-TYPE
    SYNTAX     DisplayString (SIZE(0..5))
    MAX-ACCESS read-write
    STATUS     current
    DESCRIPTION
            "-- empty --"
    ::= { lcsSetupWlanMngmtApConfTimeframeEntry 2 }

-- {COLUMN} 1.3.6.1.4.1.2356.11.2.37.1.26.1.3
lcsSetupWlanMngmtApConfTimeframeEntryStop OBJECT-TYPE
    SYNTAX     DisplayString (SIZE(0..5))
    MAX-ACCESS read-write
    STATUS     current
    DESCRIPTION
            "-- empty --"
    ::= { lcsSetupWlanMngmtApConfTimeframeEntry 3 }

-- {COLUMN} 1.3.6.1.4.1.2356.11.2.37.1.26.1.4
lcsSetupWlanMngmtApConfTimeframeEntryWeekdays OBJECT-TYPE
    SYNTAX     BITS {
                  eHoliday (0),
                  eSaturday (1),
                  eFriday (2),
                  eThursday (3),
                  eWednesday (4),
                  eTuesday (5),
                  eMonday (6),
                  eSunday (7)
            }
    MAX-ACCESS read-write
    STATUS     current
    DESCRIPTION
            "-- empty --"
    ::= { lcsSetupWlanMngmtApConfTimeframeEntry 4 }

-- {TABLE} 1.3.6.1.4.1.2356.11.2.37.1.27
lcsSetupWlanMngmtApConfHolidaysTable OBJECT-TYPE
    SYNTAX     SEQUENCE OF LcsSetupWlanMngmtApConfHolidaysEntry
    MAX-ACCESS not-accessible
    STATUS     current
    DESCRIPTION
            "-- empty --"
    ::= { lcsSetupWlanMngmtApConf 27 }

-- {ROW} 1.3.6.1.4.1.2356.11.2.37.1.27.1
lcsSetupWlanMngmtApConfHolidaysEntry OBJECT-TYPE
    SYNTAX     LcsSetupWlanMngmtApConfHolidaysEntry
    MAX-ACCESS not-accessible
    STATUS     current
    DESCRIPTION
            ""
    INDEX {
            lcsSetupWlanMngmtApConfHolidaysEntryIndex
          }
    ::= { lcsSetupWlanMngmtApConfHolidaysTable 1 }

LcsSetupWlanMngmtApConfHolidaysEntry ::= SEQUENCE {
            lcsSetupWlanMngmtApConfHolidaysEntryIndex Integer32,
            lcsSetupWlanMngmtApConfHolidaysEntryDate DisplayString
    }

-- {COLUMN} 1.3.6.1.4.1.2356.11.2.37.1.27.1.1
lcsSetupWlanMngmtApConfHolidaysEntryIndex OBJECT-TYPE
    SYNTAX     Integer32 (0..65535)
    MAX-ACCESS read-write
    STATUS     current
    DESCRIPTION
            "-- empty --"
    ::= { lcsSetupWlanMngmtApConfHolidaysEntry 1 }

-- {COLUMN} 1.3.6.1.4.1.2356.11.2.37.1.27.1.2
lcsSetupWlanMngmtApConfHolidaysEntryDate OBJECT-TYPE
    SYNTAX     DisplayString (SIZE(0..13))
    MAX-ACCESS read-write
    STATUS     current
    DESCRIPTION
            "-- empty --"
    ::= { lcsSetupWlanMngmtApConfHolidaysEntry 2 }

-- {TABLE} 1.3.6.1.4.1.2356.11.2.37.1.248
lcsSetupWlanMngmtApConfWIdsTable OBJECT-TYPE
    SYNTAX     SEQUENCE OF LcsSetupWlanMngmtApConfWIdsEntry
    MAX-ACCESS not-accessible
    STATUS     current
    DESCRIPTION
            ""
    ::= { lcsSetupWlanMngmtApConf 248 }

-- {ROW} 1.3.6.1.4.1.2356.11.2.37.1.248.1
lcsSetupWlanMngmtApConfWIdsEntry OBJECT-TYPE
    SYNTAX     LcsSetupWlanMngmtApConfWIdsEntry
    MAX-ACCESS not-accessible
    STATUS     current
    DESCRIPTION
            ""
    INDEX {
            lcsSetupWlanMngmtApConfWIdsEntryName
          }
    ::= { lcsSetupWlanMngmtApConfWIdsTable 1 }

LcsSetupWlanMngmtApConfWIdsEntry ::= SEQUENCE {
            lcsSetupWlanMngmtApConfWIdsEntryName DisplayString,
            lcsSetupWlanMngmtApConfWIdsEntryOperating INTEGER,
            lcsSetupWlanMngmtApConfWIdsEntryEapolstartcounterlimit Integer32,
            lcsSetupWlanMngmtApConfWIdsEntryEapolstartcounterinterval Integer32,
            lcsSetupWlanMngmtApConfWIdsEntryProbebroadcounterlimit Integer32,
            lcsSetupWlanMngmtApConfWIdsEntryProbebroadcounterinterval Integer32,
            lcsSetupWlanMngmtApConfWIdsEntryDeauthenticatebroadcounterlimit Integer32,
            lcsSetupWlanMngmtApConfWIdsEntryDeauthBroadCtrInt Integer32,
            lcsSetupWlanMngmtApConfWIdsEntryDeauthenticatecounterlimit Integer32,
            lcsSetupWlanMngmtApConfWIdsEntryDeauthenticatecounterinterval Integer32,
            lcsSetupWlanMngmtApConfWIdsEntryAssociatereqcounterlimit Integer32,
            lcsSetupWlanMngmtApConfWIdsEntryAssociatereqcounterinterval Integer32,
            lcsSetupWlanMngmtApConfWIdsEntryReassociatereqcounterlimit Integer32,
            lcsSetupWlanMngmtApConfWIdsEntryReassociatereqcounterinterval Integer32,
            lcsSetupWlanMngmtApConfWIdsEntryAuthenticatecounterlimit Integer32,
            lcsSetupWlanMngmtApConfWIdsEntryAuthenticatecounterinterval Integer32,
            lcsSetupWlanMngmtApConfWIdsEntryDisassociatecounterlimit Integer32,
            lcsSetupWlanMngmtApConfWIdsEntryDisassociatecounterinterval Integer32,
            lcsSetupWlanMngmtApConfWIdsEntryIdsOperational INTEGER,
            lcsSetupWlanMngmtApConfWIdsEntrySyslogOperational INTEGER,
            lcsSetupWlanMngmtApConfWIdsEntrySnmptrapsOperational INTEGER,
            lcsSetupWlanMngmtApConfWIdsEntryEMail INTEGER,
            lcsSetupWlanMngmtApConfWIdsEntryEMailReceiver DisplayString,
            lcsSetupWlanMngmtApConfWIdsEntryEMailAggregateInterval Integer32,
            lcsSetupWlanMngmtApConfWIdsEntryBlockackOutOfWindowCounter Integer32,
            lcsSetupWlanMngmtApConfWIdsEntryBlockackOutOfWindowCounterTime Integer32,
            lcsSetupWlanMngmtApConfWIdsEntryBARxAfterDelBACtr Integer32,
            lcsSetupWlanMngmtApConfWIdsEntryBARxAfterDelBAInt Integer32,
            lcsSetupWlanMngmtApConfWIdsEntryNullDataDosCounter Integer32,
            lcsSetupWlanMngmtApConfWIdsEntryNullDataDosCounterTime Integer32,
            lcsSetupWlanMngmtApConfWIdsEntryNullDataPSBufferOverflowCounter Integer32,
            lcsSetupWlanMngmtApConfWIdsEntryNullDataPSOverflowCtr Integer32,
            lcsSetupWlanMngmtApConfWIdsEntryPSPollTIMIntervalDiff Integer32,
            lcsSetupWlanMngmtApConfWIdsEntryPSPollTIMIntervalDiffCounter Integer32,
            lcsSetupWlanMngmtApConfWIdsEntryPSPollTIMIntervalDiffCounterTime Integer32,
            lcsSetupWlanMngmtApConfWIdsEntrySMPSMulStreamFrameCounter Integer32,
            lcsSetupWlanMngmtApConfWIdsEntrySMPSMulStreamFrameCounterTime Integer32,
            lcsSetupWlanMngmtApConfWIdsEntryDisassociatebroadcounterlimit Integer32,
            lcsSetupWlanMngmtApConfWIdsEntryDisassociatebroadcounterinterval Integer32,
            lcsSetupWlanMngmtApConfWIdsEntryEapolsuccesscounterlimit Integer32,
            lcsSetupWlanMngmtApConfWIdsEntryEapolsuccesscounterinterval Integer32,
            lcsSetupWlanMngmtApConfWIdsEntryEapolfailurecounterlimit Integer32,
            lcsSetupWlanMngmtApConfWIdsEntryEapolfailurecounterinterval Integer32,
            lcsSetupWlanMngmtApConfWIdsEntryPromiscuousMode INTEGER
    }

-- {COLUMN} 1.3.6.1.4.1.2356.11.2.37.1.248.1.1
lcsSetupWlanMngmtApConfWIdsEntryName OBJECT-TYPE
    SYNTAX     DisplayString (SIZE(0..31))
    MAX-ACCESS read-write
    STATUS     current
    DESCRIPTION
            "-- empty --"
    ::= { lcsSetupWlanMngmtApConfWIdsEntry 1 }

-- {COLUMN} 1.3.6.1.4.1.2356.11.2.37.1.248.1.2
lcsSetupWlanMngmtApConfWIdsEntryOperating OBJECT-TYPE
    SYNTAX     INTEGER {
                  eNo (0),
                  eYes (1)
            }
    MAX-ACCESS read-write
    STATUS     current
    DESCRIPTION
            "-- empty --"
    ::= { lcsSetupWlanMngmtApConfWIdsEntry 2 }

-- {COLUMN} 1.3.6.1.4.1.2356.11.2.37.1.248.1.3
lcsSetupWlanMngmtApConfWIdsEntryEapolstartcounterlimit OBJECT-TYPE
    SYNTAX     Integer32 (0..2147483647)
    MAX-ACCESS read-write
    STATUS     current
    DESCRIPTION
            "-- empty --"
    ::= { lcsSetupWlanMngmtApConfWIdsEntry 3 }

-- {COLUMN} 1.3.6.1.4.1.2356.11.2.37.1.248.1.4
lcsSetupWlanMngmtApConfWIdsEntryEapolstartcounterinterval OBJECT-TYPE
    SYNTAX     Integer32 (0..2147483647)
    MAX-ACCESS read-write
    STATUS     current
    DESCRIPTION
            "-- empty --"
    ::= { lcsSetupWlanMngmtApConfWIdsEntry 4 }

-- {COLUMN} 1.3.6.1.4.1.2356.11.2.37.1.248.1.5
lcsSetupWlanMngmtApConfWIdsEntryProbebroadcounterlimit OBJECT-TYPE
    SYNTAX     Integer32 (0..2147483647)
    MAX-ACCESS read-write
    STATUS     current
    DESCRIPTION
            "-- empty --"
    ::= { lcsSetupWlanMngmtApConfWIdsEntry 5 }

-- {COLUMN} 1.3.6.1.4.1.2356.11.2.37.1.248.1.6
lcsSetupWlanMngmtApConfWIdsEntryProbebroadcounterinterval OBJECT-TYPE
    SYNTAX     Integer32 (0..2147483647)
    MAX-ACCESS read-write
    STATUS     current
    DESCRIPTION
            "-- empty --"
    ::= { lcsSetupWlanMngmtApConfWIdsEntry 6 }

-- {COLUMN} 1.3.6.1.4.1.2356.11.2.37.1.248.1.7
lcsSetupWlanMngmtApConfWIdsEntryDeauthenticatebroadcounterlimit OBJECT-TYPE
    SYNTAX     Integer32 (0..2147483647)
    MAX-ACCESS read-write
    STATUS     current
    DESCRIPTION
            "-- empty --"
    ::= { lcsSetupWlanMngmtApConfWIdsEntry 7 }

-- {COLUMN} 1.3.6.1.4.1.2356.11.2.37.1.248.1.8
lcsSetupWlanMngmtApConfWIdsEntryDeauthBroadCtrInt OBJECT-TYPE
    SYNTAX     Integer32 (0..2147483647)
    MAX-ACCESS read-write
    STATUS     current
    DESCRIPTION
            ""
    ::= { lcsSetupWlanMngmtApConfWIdsEntry 8 }

-- {COLUMN} 1.3.6.1.4.1.2356.11.2.37.1.248.1.9
lcsSetupWlanMngmtApConfWIdsEntryDeauthenticatecounterlimit OBJECT-TYPE
    SYNTAX     Integer32 (0..2147483647)
    MAX-ACCESS read-write
    STATUS     current
    DESCRIPTION
            "-- empty --"
    ::= { lcsSetupWlanMngmtApConfWIdsEntry 9 }

-- {COLUMN} 1.3.6.1.4.1.2356.11.2.37.1.248.1.10
lcsSetupWlanMngmtApConfWIdsEntryDeauthenticatecounterinterval OBJECT-TYPE
    SYNTAX     Integer32 (0..2147483647)
    MAX-ACCESS read-write
    STATUS     current
    DESCRIPTION
            "-- empty --"
    ::= { lcsSetupWlanMngmtApConfWIdsEntry 10 }

-- {COLUMN} 1.3.6.1.4.1.2356.11.2.37.1.248.1.11
lcsSetupWlanMngmtApConfWIdsEntryAssociatereqcounterlimit OBJECT-TYPE
    SYNTAX     Integer32 (0..2147483647)
    MAX-ACCESS read-write
    STATUS     current
    DESCRIPTION
            "-- empty --"
    ::= { lcsSetupWlanMngmtApConfWIdsEntry 11 }

-- {COLUMN} 1.3.6.1.4.1.2356.11.2.37.1.248.1.12
lcsSetupWlanMngmtApConfWIdsEntryAssociatereqcounterinterval OBJECT-TYPE
    SYNTAX     Integer32 (0..2147483647)
    MAX-ACCESS read-write
    STATUS     current
    DESCRIPTION
            "-- empty --"
    ::= { lcsSetupWlanMngmtApConfWIdsEntry 12 }

-- {COLUMN} 1.3.6.1.4.1.2356.11.2.37.1.248.1.13
lcsSetupWlanMngmtApConfWIdsEntryReassociatereqcounterlimit OBJECT-TYPE
    SYNTAX     Integer32 (0..2147483647)
    MAX-ACCESS read-write
    STATUS     current
    DESCRIPTION
            "-- empty --"
    ::= { lcsSetupWlanMngmtApConfWIdsEntry 13 }

-- {COLUMN} 1.3.6.1.4.1.2356.11.2.37.1.248.1.14
lcsSetupWlanMngmtApConfWIdsEntryReassociatereqcounterinterval OBJECT-TYPE
    SYNTAX     Integer32 (0..2147483647)
    MAX-ACCESS read-write
    STATUS     current
    DESCRIPTION
            "-- empty --"
    ::= { lcsSetupWlanMngmtApConfWIdsEntry 14 }

-- {COLUMN} 1.3.6.1.4.1.2356.11.2.37.1.248.1.15
lcsSetupWlanMngmtApConfWIdsEntryAuthenticatecounterlimit OBJECT-TYPE
    SYNTAX     Integer32 (0..2147483647)
    MAX-ACCESS read-write
    STATUS     current
    DESCRIPTION
            "-- empty --"
    ::= { lcsSetupWlanMngmtApConfWIdsEntry 15 }

-- {COLUMN} 1.3.6.1.4.1.2356.11.2.37.1.248.1.16
lcsSetupWlanMngmtApConfWIdsEntryAuthenticatecounterinterval OBJECT-TYPE
    SYNTAX     Integer32 (0..2147483647)
    MAX-ACCESS read-write
    STATUS     current
    DESCRIPTION
            "-- empty --"
    ::= { lcsSetupWlanMngmtApConfWIdsEntry 16 }

-- {COLUMN} 1.3.6.1.4.1.2356.11.2.37.1.248.1.17
lcsSetupWlanMngmtApConfWIdsEntryDisassociatecounterlimit OBJECT-TYPE
    SYNTAX     Integer32 (0..2147483647)
    MAX-ACCESS read-write
    STATUS     current
    DESCRIPTION
            "-- empty --"
    ::= { lcsSetupWlanMngmtApConfWIdsEntry 17 }

-- {COLUMN} 1.3.6.1.4.1.2356.11.2.37.1.248.1.18
lcsSetupWlanMngmtApConfWIdsEntryDisassociatecounterinterval OBJECT-TYPE
    SYNTAX     Integer32 (0..2147483647)
    MAX-ACCESS read-write
    STATUS     current
    DESCRIPTION
            "-- empty --"
    ::= { lcsSetupWlanMngmtApConfWIdsEntry 18 }

-- {COLUMN} 1.3.6.1.4.1.2356.11.2.37.1.248.1.19
lcsSetupWlanMngmtApConfWIdsEntryIdsOperational OBJECT-TYPE
    SYNTAX     INTEGER {
                  eNo (0),
                  eYes (1)
            }
    MAX-ACCESS read-write
    STATUS     current
    DESCRIPTION
            "-- empty --"
    ::= { lcsSetupWlanMngmtApConfWIdsEntry 19 }

-- {COLUMN} 1.3.6.1.4.1.2356.11.2.37.1.248.1.20
lcsSetupWlanMngmtApConfWIdsEntrySyslogOperational OBJECT-TYPE
    SYNTAX     INTEGER {
                  eNo (0),
                  eYes (1)
            }
    MAX-ACCESS read-write
    STATUS     current
    DESCRIPTION
            "-- empty --"
    ::= { lcsSetupWlanMngmtApConfWIdsEntry 20 }

-- {COLUMN} 1.3.6.1.4.1.2356.11.2.37.1.248.1.21
lcsSetupWlanMngmtApConfWIdsEntrySnmptrapsOperational OBJECT-TYPE
    SYNTAX     INTEGER {
                  eNo (0),
                  eYes (1)
            }
    MAX-ACCESS read-write
    STATUS     current
    DESCRIPTION
            "-- empty --"
    ::= { lcsSetupWlanMngmtApConfWIdsEntry 21 }

-- {COLUMN} 1.3.6.1.4.1.2356.11.2.37.1.248.1.22
lcsSetupWlanMngmtApConfWIdsEntryEMail OBJECT-TYPE
    SYNTAX     INTEGER {
                  eNo (0),
                  eYes (1)
            }
    MAX-ACCESS read-write
    STATUS     current
    DESCRIPTION
            "-- empty --"
    ::= { lcsSetupWlanMngmtApConfWIdsEntry 22 }

-- {COLUMN} 1.3.6.1.4.1.2356.11.2.37.1.248.1.23
lcsSetupWlanMngmtApConfWIdsEntryEMailReceiver OBJECT-TYPE
    SYNTAX     DisplayString (SIZE(0..64))
    MAX-ACCESS read-write
    STATUS     current
    DESCRIPTION
            "-- empty --"
    ::= { lcsSetupWlanMngmtApConfWIdsEntry 23 }

-- {COLUMN} 1.3.6.1.4.1.2356.11.2.37.1.248.1.24
lcsSetupWlanMngmtApConfWIdsEntryEMailAggregateInterval OBJECT-TYPE
    SYNTAX     Integer32 (0..2147483647)
    MAX-ACCESS read-write
    STATUS     current
    DESCRIPTION
            "-- empty --"
    ::= { lcsSetupWlanMngmtApConfWIdsEntry 24 }

-- {COLUMN} 1.3.6.1.4.1.2356.11.2.37.1.248.1.26
lcsSetupWlanMngmtApConfWIdsEntryBlockackOutOfWindowCounter OBJECT-TYPE
    SYNTAX     Integer32 (0..2147483647)
    MAX-ACCESS read-write
    STATUS     current
    DESCRIPTION
            "-- empty --"
    ::= { lcsSetupWlanMngmtApConfWIdsEntry 26 }

-- {COLUMN} 1.3.6.1.4.1.2356.11.2.37.1.248.1.27
lcsSetupWlanMngmtApConfWIdsEntryBlockackOutOfWindowCounterTime OBJECT-TYPE
    SYNTAX     Integer32 (0..2147483647)
    MAX-ACCESS read-write
    STATUS     current
    DESCRIPTION
            "-- empty --"
    ::= { lcsSetupWlanMngmtApConfWIdsEntry 27 }

-- {COLUMN} 1.3.6.1.4.1.2356.11.2.37.1.248.1.28
lcsSetupWlanMngmtApConfWIdsEntryBARxAfterDelBACtr OBJECT-TYPE
    SYNTAX     Integer32 (0..2147483647)
    MAX-ACCESS read-write
    STATUS     current
    DESCRIPTION
            ""
    ::= { lcsSetupWlanMngmtApConfWIdsEntry 28 }

-- {COLUMN} 1.3.6.1.4.1.2356.11.2.37.1.248.1.29
lcsSetupWlanMngmtApConfWIdsEntryBARxAfterDelBAInt OBJECT-TYPE
    SYNTAX     Integer32 (0..2147483647)
    MAX-ACCESS read-write
    STATUS     current
    DESCRIPTION
            ""
    ::= { lcsSetupWlanMngmtApConfWIdsEntry 29 }

-- {COLUMN} 1.3.6.1.4.1.2356.11.2.37.1.248.1.31
lcsSetupWlanMngmtApConfWIdsEntryNullDataDosCounter OBJECT-TYPE
    SYNTAX     Integer32 (0..2147483647)
    MAX-ACCESS read-write
    STATUS     current
    DESCRIPTION
            "-- empty --"
    ::= { lcsSetupWlanMngmtApConfWIdsEntry 31 }

-- {COLUMN} 1.3.6.1.4.1.2356.11.2.37.1.248.1.32
lcsSetupWlanMngmtApConfWIdsEntryNullDataDosCounterTime OBJECT-TYPE
    SYNTAX     Integer32 (0..2147483647)
    MAX-ACCESS read-write
    STATUS     current
    DESCRIPTION
            "-- empty --"
    ::= { lcsSetupWlanMngmtApConfWIdsEntry 32 }

-- {COLUMN} 1.3.6.1.4.1.2356.11.2.37.1.248.1.34
lcsSetupWlanMngmtApConfWIdsEntryNullDataPSBufferOverflowCounter OBJECT-TYPE
    SYNTAX     Integer32 (0..2147483647)
    MAX-ACCESS read-write
    STATUS     current
    DESCRIPTION
            "-- empty --"
    ::= { lcsSetupWlanMngmtApConfWIdsEntry 34 }

-- {COLUMN} 1.3.6.1.4.1.2356.11.2.37.1.248.1.35
lcsSetupWlanMngmtApConfWIdsEntryNullDataPSOverflowCtr OBJECT-TYPE
    SYNTAX     Integer32 (0..2147483647)
    MAX-ACCESS read-write
    STATUS     current
    DESCRIPTION
            ""
    ::= { lcsSetupWlanMngmtApConfWIdsEntry 35 }

-- {COLUMN} 1.3.6.1.4.1.2356.11.2.37.1.248.1.37
lcsSetupWlanMngmtApConfWIdsEntryPSPollTIMIntervalDiff OBJECT-TYPE
    SYNTAX     Integer32 (0..2147483647)
    MAX-ACCESS read-write
    STATUS     current
    DESCRIPTION
            "-- empty --"
    ::= { lcsSetupWlanMngmtApConfWIdsEntry 37 }

-- {COLUMN} 1.3.6.1.4.1.2356.11.2.37.1.248.1.38
lcsSetupWlanMngmtApConfWIdsEntryPSPollTIMIntervalDiffCounter OBJECT-TYPE
    SYNTAX     Integer32 (0..2147483647)
    MAX-ACCESS read-write
    STATUS     current
    DESCRIPTION
            "-- empty --"
    ::= { lcsSetupWlanMngmtApConfWIdsEntry 38 }

-- {COLUMN} 1.3.6.1.4.1.2356.11.2.37.1.248.1.39
lcsSetupWlanMngmtApConfWIdsEntryPSPollTIMIntervalDiffCounterTime OBJECT-TYPE
    SYNTAX     Integer32 (0..2147483647)
    MAX-ACCESS read-write
    STATUS     current
    DESCRIPTION
            "-- empty --"
    ::= { lcsSetupWlanMngmtApConfWIdsEntry 39 }

-- {COLUMN} 1.3.6.1.4.1.2356.11.2.37.1.248.1.41
lcsSetupWlanMngmtApConfWIdsEntrySMPSMulStreamFrameCounter OBJECT-TYPE
    SYNTAX     Integer32 (0..2147483647)
    MAX-ACCESS read-write
    STATUS     current
    DESCRIPTION
            "-- empty --"
    ::= { lcsSetupWlanMngmtApConfWIdsEntry 41 }

-- {COLUMN} 1.3.6.1.4.1.2356.11.2.37.1.248.1.42
lcsSetupWlanMngmtApConfWIdsEntrySMPSMulStreamFrameCounterTime OBJECT-TYPE
    SYNTAX     Integer32 (0..2147483647)
    MAX-ACCESS read-write
    STATUS     current
    DESCRIPTION
            "-- empty --"
    ::= { lcsSetupWlanMngmtApConfWIdsEntry 42 }

-- {COLUMN} 1.3.6.1.4.1.2356.11.2.37.1.248.1.45
lcsSetupWlanMngmtApConfWIdsEntryDisassociatebroadcounterlimit OBJECT-TYPE
    SYNTAX     Integer32 (0..2147483647)
    MAX-ACCESS read-write
    STATUS     current
    DESCRIPTION
            "-- empty --"
    ::= { lcsSetupWlanMngmtApConfWIdsEntry 45 }

-- {COLUMN} 1.3.6.1.4.1.2356.11.2.37.1.248.1.46
lcsSetupWlanMngmtApConfWIdsEntryDisassociatebroadcounterinterval OBJECT-TYPE
    SYNTAX     Integer32 (0..2147483647)
    MAX-ACCESS read-write
    STATUS     current
    DESCRIPTION
            "-- empty --"
    ::= { lcsSetupWlanMngmtApConfWIdsEntry 46 }

-- {COLUMN} 1.3.6.1.4.1.2356.11.2.37.1.248.1.47
lcsSetupWlanMngmtApConfWIdsEntryEapolsuccesscounterlimit OBJECT-TYPE
    SYNTAX     Integer32 (0..2147483647)
    MAX-ACCESS read-write
    STATUS     current
    DESCRIPTION
            "-- empty --"
    ::= { lcsSetupWlanMngmtApConfWIdsEntry 47 }

-- {COLUMN} 1.3.6.1.4.1.2356.11.2.37.1.248.1.48
lcsSetupWlanMngmtApConfWIdsEntryEapolsuccesscounterinterval OBJECT-TYPE
    SYNTAX     Integer32 (0..2147483647)
    MAX-ACCESS read-write
    STATUS     current
    DESCRIPTION
            "-- empty --"
    ::= { lcsSetupWlanMngmtApConfWIdsEntry 48 }

-- {COLUMN} 1.3.6.1.4.1.2356.11.2.37.1.248.1.49
lcsSetupWlanMngmtApConfWIdsEntryEapolfailurecounterlimit OBJECT-TYPE
    SYNTAX     Integer32 (0..2147483647)
    MAX-ACCESS read-write
    STATUS     current
    DESCRIPTION
            "-- empty --"
    ::= { lcsSetupWlanMngmtApConfWIdsEntry 49 }

-- {COLUMN} 1.3.6.1.4.1.2356.11.2.37.1.248.1.50
lcsSetupWlanMngmtApConfWIdsEntryEapolfailurecounterinterval OBJECT-TYPE
    SYNTAX     Integer32 (0..2147483647)
    MAX-ACCESS read-write
    STATUS     current
    DESCRIPTION
            "-- empty --"
    ::= { lcsSetupWlanMngmtApConfWIdsEntry 50 }

-- {COLUMN} 1.3.6.1.4.1.2356.11.2.37.1.248.1.51
lcsSetupWlanMngmtApConfWIdsEntryPromiscuousMode OBJECT-TYPE
    SYNTAX     INTEGER {
                  eNo (0),
                  eYes (1)
            }
    MAX-ACCESS read-write
    STATUS     current
    DESCRIPTION
            "-- empty --"
    ::= { lcsSetupWlanMngmtApConfWIdsEntry 51 }

-- {NODE} 1.3.6.1.4.1.2356.11.2.37.1.249
lcsSetupWlanMngmtApConfWIds OBJECT IDENTIFIER ::= { lcsSetupWlanMngmtApConf 249 }

-- {TABLE} 1.3.6.1.4.1.2356.11.2.37.1.249.1
lcsSetupWlanMngmtApConfWIdsWIdsTable OBJECT-TYPE
    SYNTAX     SEQUENCE OF LcsSetupWlanMngmtApConfWIdsWIdsEntry
    MAX-ACCESS not-accessible
    STATUS     current
    DESCRIPTION
            ""
    ::= { lcsSetupWlanMngmtApConfWIds 1 }

-- {ROW} 1.3.6.1.4.1.2356.11.2.37.1.249.1.1
lcsSetupWlanMngmtApConfWIdsWIdsEntry OBJECT-TYPE
    SYNTAX     LcsSetupWlanMngmtApConfWIdsWIdsEntry
    MAX-ACCESS not-accessible
    STATUS     current
    DESCRIPTION
            ""
    INDEX {
            lcsSetupWlanMngmtApConfWIdsWIdsEntryName
          }
    ::= { lcsSetupWlanMngmtApConfWIdsWIdsTable 1 }

LcsSetupWlanMngmtApConfWIdsWIdsEntry ::= SEQUENCE {
            lcsSetupWlanMngmtApConfWIdsWIdsEntryName DisplayString,
            lcsSetupWlanMngmtApConfWIdsWIdsEntryOperating INTEGER,
            lcsSetupWlanMngmtApConfWIdsWIdsEntryEapolstartcounterlimit Integer32,
            lcsSetupWlanMngmtApConfWIdsWIdsEntryEapolstartcounterinterval Integer32,
            lcsSetupWlanMngmtApConfWIdsWIdsEntryProbebroadcounterlimit Integer32,
            lcsSetupWlanMngmtApConfWIdsWIdsEntryProbebroadcounterinterval Integer32,
            lcsSetupWlanMngmtApConfWIdsWIdsEntryDeauthBroadCtrLimit Integer32,
            lcsSetupWlanMngmtApConfWIdsWIdsEntryDeauthBroadCtrInt Integer32,
            lcsSetupWlanMngmtApConfWIdsWIdsEntryDeauthCounterLimit Integer32,
            lcsSetupWlanMngmtApConfWIdsWIdsEntryDeauthCounterInterval Integer32,
            lcsSetupWlanMngmtApConfWIdsWIdsEntryAssociatereqcounterlimit Integer32,
            lcsSetupWlanMngmtApConfWIdsWIdsEntryAssociatereqcounterinterval Integer32,
            lcsSetupWlanMngmtApConfWIdsWIdsEntryReAssocReqCounterLimit Integer32,
            lcsSetupWlanMngmtApConfWIdsWIdsEntryReAssocReqCounterInterval Integer32,
            lcsSetupWlanMngmtApConfWIdsWIdsEntryAuthenticatecounterlimit Integer32,
            lcsSetupWlanMngmtApConfWIdsWIdsEntryAuthenticatecounterinterval Integer32,
            lcsSetupWlanMngmtApConfWIdsWIdsEntryDisassociatecounterlimit Integer32,
            lcsSetupWlanMngmtApConfWIdsWIdsEntryDisassociatecounterinterval Integer32,
            lcsSetupWlanMngmtApConfWIdsWIdsEntryIdsOperational INTEGER,
            lcsSetupWlanMngmtApConfWIdsWIdsEntrySyslogOperational INTEGER,
            lcsSetupWlanMngmtApConfWIdsWIdsEntrySnmptrapsOperational INTEGER,
            lcsSetupWlanMngmtApConfWIdsWIdsEntryEMail INTEGER,
            lcsSetupWlanMngmtApConfWIdsWIdsEntryEMailReceiver DisplayString,
            lcsSetupWlanMngmtApConfWIdsWIdsEntryEMailAggregateInterval Integer32,
            lcsSetupWlanMngmtApConfWIdsWIdsEntryBAOutOfWindowCtr Integer32,
            lcsSetupWlanMngmtApConfWIdsWIdsEntryBAOutOfWindowCtrTime Integer32,
            lcsSetupWlanMngmtApConfWIdsWIdsEntryBARxAfterDelBACtr Integer32,
            lcsSetupWlanMngmtApConfWIdsWIdsEntryBARxAfterDelBAInt Integer32,
            lcsSetupWlanMngmtApConfWIdsWIdsEntryNullDataDosCounter Integer32,
            lcsSetupWlanMngmtApConfWIdsWIdsEntryNullDataDosCounterTime Integer32,
            lcsSetupWlanMngmtApConfWIdsWIdsEntryNullDataPSBufOvrflwCtr Integer32,
            lcsSetupWlanMngmtApConfWIdsWIdsEntryNullDataPSOverflowCtr Integer32,
            lcsSetupWlanMngmtApConfWIdsWIdsEntryPSPollTIMIntervalDiff Integer32,
            lcsSetupWlanMngmtApConfWIdsWIdsEntryPSPollTIMIntervalDiffCounter Integer32,
            lcsSetupWlanMngmtApConfWIdsWIdsEntryPSPollTIMIntDiffCtrTime Integer32,
            lcsSetupWlanMngmtApConfWIdsWIdsEntrySMPSMulStreamFrameCounter Integer32,
            lcsSetupWlanMngmtApConfWIdsWIdsEntrySMPSMulStrFrameCtrTime Integer32,
            lcsSetupWlanMngmtApConfWIdsWIdsEntryDisAssocBroadCtrLim Integer32,
            lcsSetupWlanMngmtApConfWIdsWIdsEntryDisAssocBroadCtrInt Integer32,
            lcsSetupWlanMngmtApConfWIdsWIdsEntryEapolsuccesscounterlimit Integer32,
            lcsSetupWlanMngmtApConfWIdsWIdsEntryEapolsuccesscounterinterval Integer32,
            lcsSetupWlanMngmtApConfWIdsWIdsEntryEapolfailurecounterlimit Integer32,
            lcsSetupWlanMngmtApConfWIdsWIdsEntryEapolfailurecounterinterval Integer32,
            lcsSetupWlanMngmtApConfWIdsWIdsEntryPromiscuousMode INTEGER
    }

-- {COLUMN} 1.3.6.1.4.1.2356.11.2.37.1.249.1.1.1
lcsSetupWlanMngmtApConfWIdsWIdsEntryName OBJECT-TYPE
    SYNTAX     DisplayString (SIZE(0..31))
    MAX-ACCESS read-write
    STATUS     current
    DESCRIPTION
            "-- empty --"
    ::= { lcsSetupWlanMngmtApConfWIdsWIdsEntry 1 }

-- {COLUMN} 1.3.6.1.4.1.2356.11.2.37.1.249.1.1.2
lcsSetupWlanMngmtApConfWIdsWIdsEntryOperating OBJECT-TYPE
    SYNTAX     INTEGER {
                  eNo (0),
                  eYes (1)
            }
    MAX-ACCESS read-write
    STATUS     current
    DESCRIPTION
            "-- empty --"
    ::= { lcsSetupWlanMngmtApConfWIdsWIdsEntry 2 }

-- {COLUMN} 1.3.6.1.4.1.2356.11.2.37.1.249.1.1.3
lcsSetupWlanMngmtApConfWIdsWIdsEntryEapolstartcounterlimit OBJECT-TYPE
    SYNTAX     Integer32 (0..2147483647)
    MAX-ACCESS read-write
    STATUS     current
    DESCRIPTION
            "-- empty --"
    ::= { lcsSetupWlanMngmtApConfWIdsWIdsEntry 3 }

-- {COLUMN} 1.3.6.1.4.1.2356.11.2.37.1.249.1.1.4
lcsSetupWlanMngmtApConfWIdsWIdsEntryEapolstartcounterinterval OBJECT-TYPE
    SYNTAX     Integer32 (0..2147483647)
    MAX-ACCESS read-write
    STATUS     current
    DESCRIPTION
            "-- empty --"
    ::= { lcsSetupWlanMngmtApConfWIdsWIdsEntry 4 }

-- {COLUMN} 1.3.6.1.4.1.2356.11.2.37.1.249.1.1.5
lcsSetupWlanMngmtApConfWIdsWIdsEntryProbebroadcounterlimit OBJECT-TYPE
    SYNTAX     Integer32 (0..2147483647)
    MAX-ACCESS read-write
    STATUS     current
    DESCRIPTION
            "-- empty --"
    ::= { lcsSetupWlanMngmtApConfWIdsWIdsEntry 5 }

-- {COLUMN} 1.3.6.1.4.1.2356.11.2.37.1.249.1.1.6
lcsSetupWlanMngmtApConfWIdsWIdsEntryProbebroadcounterinterval OBJECT-TYPE
    SYNTAX     Integer32 (0..2147483647)
    MAX-ACCESS read-write
    STATUS     current
    DESCRIPTION
            "-- empty --"
    ::= { lcsSetupWlanMngmtApConfWIdsWIdsEntry 6 }

-- {COLUMN} 1.3.6.1.4.1.2356.11.2.37.1.249.1.1.7
lcsSetupWlanMngmtApConfWIdsWIdsEntryDeauthBroadCtrLimit OBJECT-TYPE
    SYNTAX     Integer32 (0..2147483647)
    MAX-ACCESS read-write
    STATUS     current
    DESCRIPTION
            ""
    ::= { lcsSetupWlanMngmtApConfWIdsWIdsEntry 7 }

-- {COLUMN} 1.3.6.1.4.1.2356.11.2.37.1.249.1.1.8
lcsSetupWlanMngmtApConfWIdsWIdsEntryDeauthBroadCtrInt OBJECT-TYPE
    SYNTAX     Integer32 (0..2147483647)
    MAX-ACCESS read-write
    STATUS     current
    DESCRIPTION
            ""
    ::= { lcsSetupWlanMngmtApConfWIdsWIdsEntry 8 }

-- {COLUMN} 1.3.6.1.4.1.2356.11.2.37.1.249.1.1.9
lcsSetupWlanMngmtApConfWIdsWIdsEntryDeauthCounterLimit OBJECT-TYPE
    SYNTAX     Integer32 (0..2147483647)
    MAX-ACCESS read-write
    STATUS     current
    DESCRIPTION
            ""
    ::= { lcsSetupWlanMngmtApConfWIdsWIdsEntry 9 }

-- {COLUMN} 1.3.6.1.4.1.2356.11.2.37.1.249.1.1.10
lcsSetupWlanMngmtApConfWIdsWIdsEntryDeauthCounterInterval OBJECT-TYPE
    SYNTAX     Integer32 (0..2147483647)
    MAX-ACCESS read-write
    STATUS     current
    DESCRIPTION
            ""
    ::= { lcsSetupWlanMngmtApConfWIdsWIdsEntry 10 }

-- {COLUMN} 1.3.6.1.4.1.2356.11.2.37.1.249.1.1.11
lcsSetupWlanMngmtApConfWIdsWIdsEntryAssociatereqcounterlimit OBJECT-TYPE
    SYNTAX     Integer32 (0..2147483647)
    MAX-ACCESS read-write
    STATUS     current
    DESCRIPTION
            "-- empty --"
    ::= { lcsSetupWlanMngmtApConfWIdsWIdsEntry 11 }

-- {COLUMN} 1.3.6.1.4.1.2356.11.2.37.1.249.1.1.12
lcsSetupWlanMngmtApConfWIdsWIdsEntryAssociatereqcounterinterval OBJECT-TYPE
    SYNTAX     Integer32 (0..2147483647)
    MAX-ACCESS read-write
    STATUS     current
    DESCRIPTION
            "-- empty --"
    ::= { lcsSetupWlanMngmtApConfWIdsWIdsEntry 12 }

-- {COLUMN} 1.3.6.1.4.1.2356.11.2.37.1.249.1.1.13
lcsSetupWlanMngmtApConfWIdsWIdsEntryReAssocReqCounterLimit OBJECT-TYPE
    SYNTAX     Integer32 (0..2147483647)
    MAX-ACCESS read-write
    STATUS     current
    DESCRIPTION
            ""
    ::= { lcsSetupWlanMngmtApConfWIdsWIdsEntry 13 }

-- {COLUMN} 1.3.6.1.4.1.2356.11.2.37.1.249.1.1.14
lcsSetupWlanMngmtApConfWIdsWIdsEntryReAssocReqCounterInterval OBJECT-TYPE
    SYNTAX     Integer32 (0..2147483647)
    MAX-ACCESS read-write
    STATUS     current
    DESCRIPTION
            ""
    ::= { lcsSetupWlanMngmtApConfWIdsWIdsEntry 14 }

-- {COLUMN} 1.3.6.1.4.1.2356.11.2.37.1.249.1.1.15
lcsSetupWlanMngmtApConfWIdsWIdsEntryAuthenticatecounterlimit OBJECT-TYPE
    SYNTAX     Integer32 (0..2147483647)
    MAX-ACCESS read-write
    STATUS     current
    DESCRIPTION
            "-- empty --"
    ::= { lcsSetupWlanMngmtApConfWIdsWIdsEntry 15 }

-- {COLUMN} 1.3.6.1.4.1.2356.11.2.37.1.249.1.1.16
lcsSetupWlanMngmtApConfWIdsWIdsEntryAuthenticatecounterinterval OBJECT-TYPE
    SYNTAX     Integer32 (0..2147483647)
    MAX-ACCESS read-write
    STATUS     current
    DESCRIPTION
            "-- empty --"
    ::= { lcsSetupWlanMngmtApConfWIdsWIdsEntry 16 }

-- {COLUMN} 1.3.6.1.4.1.2356.11.2.37.1.249.1.1.17
lcsSetupWlanMngmtApConfWIdsWIdsEntryDisassociatecounterlimit OBJECT-TYPE
    SYNTAX     Integer32 (0..2147483647)
    MAX-ACCESS read-write
    STATUS     current
    DESCRIPTION
            "-- empty --"
    ::= { lcsSetupWlanMngmtApConfWIdsWIdsEntry 17 }

-- {COLUMN} 1.3.6.1.4.1.2356.11.2.37.1.249.1.1.18
lcsSetupWlanMngmtApConfWIdsWIdsEntryDisassociatecounterinterval OBJECT-TYPE
    SYNTAX     Integer32 (0..2147483647)
    MAX-ACCESS read-write
    STATUS     current
    DESCRIPTION
            "-- empty --"
    ::= { lcsSetupWlanMngmtApConfWIdsWIdsEntry 18 }

-- {COLUMN} 1.3.6.1.4.1.2356.11.2.37.1.249.1.1.19
lcsSetupWlanMngmtApConfWIdsWIdsEntryIdsOperational OBJECT-TYPE
    SYNTAX     INTEGER {
                  eNo (0),
                  eYes (1)
            }
    MAX-ACCESS read-write
    STATUS     current
    DESCRIPTION
            "-- empty --"
    ::= { lcsSetupWlanMngmtApConfWIdsWIdsEntry 19 }

-- {COLUMN} 1.3.6.1.4.1.2356.11.2.37.1.249.1.1.20
lcsSetupWlanMngmtApConfWIdsWIdsEntrySyslogOperational OBJECT-TYPE
    SYNTAX     INTEGER {
                  eNo (0),
                  eYes (1)
            }
    MAX-ACCESS read-write
    STATUS     current
    DESCRIPTION
            "-- empty --"
    ::= { lcsSetupWlanMngmtApConfWIdsWIdsEntry 20 }

-- {COLUMN} 1.3.6.1.4.1.2356.11.2.37.1.249.1.1.21
lcsSetupWlanMngmtApConfWIdsWIdsEntrySnmptrapsOperational OBJECT-TYPE
    SYNTAX     INTEGER {
                  eNo (0),
                  eYes (1)
            }
    MAX-ACCESS read-write
    STATUS     current
    DESCRIPTION
            "-- empty --"
    ::= { lcsSetupWlanMngmtApConfWIdsWIdsEntry 21 }

-- {COLUMN} 1.3.6.1.4.1.2356.11.2.37.1.249.1.1.22
lcsSetupWlanMngmtApConfWIdsWIdsEntryEMail OBJECT-TYPE
    SYNTAX     INTEGER {
                  eNo (0),
                  eYes (1)
            }
    MAX-ACCESS read-write
    STATUS     current
    DESCRIPTION
            "-- empty --"
    ::= { lcsSetupWlanMngmtApConfWIdsWIdsEntry 22 }

-- {COLUMN} 1.3.6.1.4.1.2356.11.2.37.1.249.1.1.23
lcsSetupWlanMngmtApConfWIdsWIdsEntryEMailReceiver OBJECT-TYPE
    SYNTAX     DisplayString (SIZE(0..64))
    MAX-ACCESS read-write
    STATUS     current
    DESCRIPTION
            "-- empty --"
    ::= { lcsSetupWlanMngmtApConfWIdsWIdsEntry 23 }

-- {COLUMN} 1.3.6.1.4.1.2356.11.2.37.1.249.1.1.24
lcsSetupWlanMngmtApConfWIdsWIdsEntryEMailAggregateInterval OBJECT-TYPE
    SYNTAX     Integer32 (0..2147483647)
    MAX-ACCESS read-write
    STATUS     current
    DESCRIPTION
            "-- empty --"
    ::= { lcsSetupWlanMngmtApConfWIdsWIdsEntry 24 }

-- {COLUMN} 1.3.6.1.4.1.2356.11.2.37.1.249.1.1.26
lcsSetupWlanMngmtApConfWIdsWIdsEntryBAOutOfWindowCtr OBJECT-TYPE
    SYNTAX     Integer32 (0..2147483647)
    MAX-ACCESS read-write
    STATUS     current
    DESCRIPTION
            ""
    ::= { lcsSetupWlanMngmtApConfWIdsWIdsEntry 26 }

-- {COLUMN} 1.3.6.1.4.1.2356.11.2.37.1.249.1.1.27
lcsSetupWlanMngmtApConfWIdsWIdsEntryBAOutOfWindowCtrTime OBJECT-TYPE
    SYNTAX     Integer32 (0..2147483647)
    MAX-ACCESS read-write
    STATUS     current
    DESCRIPTION
            ""
    ::= { lcsSetupWlanMngmtApConfWIdsWIdsEntry 27 }

-- {COLUMN} 1.3.6.1.4.1.2356.11.2.37.1.249.1.1.28
lcsSetupWlanMngmtApConfWIdsWIdsEntryBARxAfterDelBACtr OBJECT-TYPE
    SYNTAX     Integer32 (0..2147483647)
    MAX-ACCESS read-write
    STATUS     current
    DESCRIPTION
            ""
    ::= { lcsSetupWlanMngmtApConfWIdsWIdsEntry 28 }

-- {COLUMN} 1.3.6.1.4.1.2356.11.2.37.1.249.1.1.29
lcsSetupWlanMngmtApConfWIdsWIdsEntryBARxAfterDelBAInt OBJECT-TYPE
    SYNTAX     Integer32 (0..2147483647)
    MAX-ACCESS read-write
    STATUS     current
    DESCRIPTION
            ""
    ::= { lcsSetupWlanMngmtApConfWIdsWIdsEntry 29 }

-- {COLUMN} 1.3.6.1.4.1.2356.11.2.37.1.249.1.1.31
lcsSetupWlanMngmtApConfWIdsWIdsEntryNullDataDosCounter OBJECT-TYPE
    SYNTAX     Integer32 (0..2147483647)
    MAX-ACCESS read-write
    STATUS     current
    DESCRIPTION
            "-- empty --"
    ::= { lcsSetupWlanMngmtApConfWIdsWIdsEntry 31 }

-- {COLUMN} 1.3.6.1.4.1.2356.11.2.37.1.249.1.1.32
lcsSetupWlanMngmtApConfWIdsWIdsEntryNullDataDosCounterTime OBJECT-TYPE
    SYNTAX     Integer32 (0..2147483647)
    MAX-ACCESS read-write
    STATUS     current
    DESCRIPTION
            "-- empty --"
    ::= { lcsSetupWlanMngmtApConfWIdsWIdsEntry 32 }

-- {COLUMN} 1.3.6.1.4.1.2356.11.2.37.1.249.1.1.34
lcsSetupWlanMngmtApConfWIdsWIdsEntryNullDataPSBufOvrflwCtr OBJECT-TYPE
    SYNTAX     Integer32 (0..2147483647)
    MAX-ACCESS read-write
    STATUS     current
    DESCRIPTION
            ""
    ::= { lcsSetupWlanMngmtApConfWIdsWIdsEntry 34 }

-- {COLUMN} 1.3.6.1.4.1.2356.11.2.37.1.249.1.1.35
lcsSetupWlanMngmtApConfWIdsWIdsEntryNullDataPSOverflowCtr OBJECT-TYPE
    SYNTAX     Integer32 (0..2147483647)
    MAX-ACCESS read-write
    STATUS     current
    DESCRIPTION
            ""
    ::= { lcsSetupWlanMngmtApConfWIdsWIdsEntry 35 }

-- {COLUMN} 1.3.6.1.4.1.2356.11.2.37.1.249.1.1.37
lcsSetupWlanMngmtApConfWIdsWIdsEntryPSPollTIMIntervalDiff OBJECT-TYPE
    SYNTAX     Integer32 (0..2147483647)
    MAX-ACCESS read-write
    STATUS     current
    DESCRIPTION
            "-- empty --"
    ::= { lcsSetupWlanMngmtApConfWIdsWIdsEntry 37 }

-- {COLUMN} 1.3.6.1.4.1.2356.11.2.37.1.249.1.1.38
lcsSetupWlanMngmtApConfWIdsWIdsEntryPSPollTIMIntervalDiffCounter OBJECT-TYPE
    SYNTAX     Integer32 (0..2147483647)
    MAX-ACCESS read-write
    STATUS     current
    DESCRIPTION
            "-- empty --"
    ::= { lcsSetupWlanMngmtApConfWIdsWIdsEntry 38 }

-- {COLUMN} 1.3.6.1.4.1.2356.11.2.37.1.249.1.1.39
lcsSetupWlanMngmtApConfWIdsWIdsEntryPSPollTIMIntDiffCtrTime OBJECT-TYPE
    SYNTAX     Integer32 (0..2147483647)
    MAX-ACCESS read-write
    STATUS     current
    DESCRIPTION
            ""
    ::= { lcsSetupWlanMngmtApConfWIdsWIdsEntry 39 }

-- {COLUMN} 1.3.6.1.4.1.2356.11.2.37.1.249.1.1.41
lcsSetupWlanMngmtApConfWIdsWIdsEntrySMPSMulStreamFrameCounter OBJECT-TYPE
    SYNTAX     Integer32 (0..2147483647)
    MAX-ACCESS read-write
    STATUS     current
    DESCRIPTION
            "-- empty --"
    ::= { lcsSetupWlanMngmtApConfWIdsWIdsEntry 41 }

-- {COLUMN} 1.3.6.1.4.1.2356.11.2.37.1.249.1.1.42
lcsSetupWlanMngmtApConfWIdsWIdsEntrySMPSMulStrFrameCtrTime OBJECT-TYPE
    SYNTAX     Integer32 (0..2147483647)
    MAX-ACCESS read-write
    STATUS     current
    DESCRIPTION
            ""
    ::= { lcsSetupWlanMngmtApConfWIdsWIdsEntry 42 }

-- {COLUMN} 1.3.6.1.4.1.2356.11.2.37.1.249.1.1.45
lcsSetupWlanMngmtApConfWIdsWIdsEntryDisAssocBroadCtrLim OBJECT-TYPE
    SYNTAX     Integer32 (0..2147483647)
    MAX-ACCESS read-write
    STATUS     current
    DESCRIPTION
            ""
    ::= { lcsSetupWlanMngmtApConfWIdsWIdsEntry 45 }

-- {COLUMN} 1.3.6.1.4.1.2356.11.2.37.1.249.1.1.46
lcsSetupWlanMngmtApConfWIdsWIdsEntryDisAssocBroadCtrInt OBJECT-TYPE
    SYNTAX     Integer32 (0..2147483647)
    MAX-ACCESS read-write
    STATUS     current
    DESCRIPTION
            ""
    ::= { lcsSetupWlanMngmtApConfWIdsWIdsEntry 46 }

-- {COLUMN} 1.3.6.1.4.1.2356.11.2.37.1.249.1.1.47
lcsSetupWlanMngmtApConfWIdsWIdsEntryEapolsuccesscounterlimit OBJECT-TYPE
    SYNTAX     Integer32 (0..2147483647)
    MAX-ACCESS read-write
    STATUS     current
    DESCRIPTION
            "-- empty --"
    ::= { lcsSetupWlanMngmtApConfWIdsWIdsEntry 47 }

-- {COLUMN} 1.3.6.1.4.1.2356.11.2.37.1.249.1.1.48
lcsSetupWlanMngmtApConfWIdsWIdsEntryEapolsuccesscounterinterval OBJECT-TYPE
    SYNTAX     Integer32 (0..2147483647)
    MAX-ACCESS read-write
    STATUS     current
    DESCRIPTION
            "-- empty --"
    ::= { lcsSetupWlanMngmtApConfWIdsWIdsEntry 48 }

-- {COLUMN} 1.3.6.1.4.1.2356.11.2.37.1.249.1.1.49
lcsSetupWlanMngmtApConfWIdsWIdsEntryEapolfailurecounterlimit OBJECT-TYPE
    SYNTAX     Integer32 (0..2147483647)
    MAX-ACCESS read-write
    STATUS     current
    DESCRIPTION
            "-- empty --"
    ::= { lcsSetupWlanMngmtApConfWIdsWIdsEntry 49 }

-- {COLUMN} 1.3.6.1.4.1.2356.11.2.37.1.249.1.1.50
lcsSetupWlanMngmtApConfWIdsWIdsEntryEapolfailurecounterinterval OBJECT-TYPE
    SYNTAX     Integer32 (0..2147483647)
    MAX-ACCESS read-write
    STATUS     current
    DESCRIPTION
            "-- empty --"
    ::= { lcsSetupWlanMngmtApConfWIdsWIdsEntry 50 }

-- {COLUMN} 1.3.6.1.4.1.2356.11.2.37.1.249.1.1.51
lcsSetupWlanMngmtApConfWIdsWIdsEntryPromiscuousMode OBJECT-TYPE
    SYNTAX     INTEGER {
                  eNo (0),
                  eYes (1)
            }
    MAX-ACCESS read-write
    STATUS     current
    DESCRIPTION
            "-- empty --"
    ::= { lcsSetupWlanMngmtApConfWIdsWIdsEntry 51 }

-- {TABLE} 1.3.6.1.4.1.2356.11.2.37.1.249.2
lcsSetupWlanMngmtApConfWIdsWhiteListTableTable OBJECT-TYPE
    SYNTAX     SEQUENCE OF LcsSetupWlanMngmtApConfWIdsWhiteListTableEntry
    MAX-ACCESS not-accessible
    STATUS     current
    DESCRIPTION
            "-- empty --"
    ::= { lcsSetupWlanMngmtApConfWIds 2 }

-- {ROW} 1.3.6.1.4.1.2356.11.2.37.1.249.2.1
lcsSetupWlanMngmtApConfWIdsWhiteListTableEntry OBJECT-TYPE
    SYNTAX     LcsSetupWlanMngmtApConfWIdsWhiteListTableEntry
    MAX-ACCESS not-accessible
    STATUS     current
    DESCRIPTION
            ""
    INDEX {
            lcsSetupWlanMngmtApConfWIdsWhiteListTableEntryWhiteListId,
            lcsSetupWlanMngmtApConfWIdsWhiteListTableEntryStationMac
          }
    ::= { lcsSetupWlanMngmtApConfWIdsWhiteListTableTable 1 }

LcsSetupWlanMngmtApConfWIdsWhiteListTableEntry ::= SEQUENCE {
            lcsSetupWlanMngmtApConfWIdsWhiteListTableEntryWhiteListId Integer32,
            lcsSetupWlanMngmtApConfWIdsWhiteListTableEntryStationMac MacAddress
    }

-- {COLUMN} 1.3.6.1.4.1.2356.11.2.37.1.249.2.1.1
lcsSetupWlanMngmtApConfWIdsWhiteListTableEntryWhiteListId OBJECT-TYPE
    SYNTAX     Integer32 (0..255)
    MAX-ACCESS read-write
    STATUS     current
    DESCRIPTION
            "-- empty --"
    ::= { lcsSetupWlanMngmtApConfWIdsWhiteListTableEntry 1 }

-- {COLUMN} 1.3.6.1.4.1.2356.11.2.37.1.249.2.1.2
lcsSetupWlanMngmtApConfWIdsWhiteListTableEntryStationMac OBJECT-TYPE
    SYNTAX     MacAddress
    MAX-ACCESS read-write
    STATUS     current
    DESCRIPTION
            "-- empty --"
    ::= { lcsSetupWlanMngmtApConfWIdsWhiteListTableEntry 2 }

-- {SCALAR} 1.3.6.1.4.1.2356.11.2.37.5
lcsSetupWlanMngmtCapwapPort OBJECT-TYPE
    SYNTAX     Integer32 (0..65535)
    MAX-ACCESS read-write
    STATUS     current
    DESCRIPTION
            ""
    ::= { lcsSetupWlanMngmt 5 }

-- {SCALAR} 1.3.6.1.4.1.2356.11.2.37.6
lcsSetupWlanMngmtAutoacceptAp OBJECT-TYPE
    SYNTAX     INTEGER {
                  eNo (0),
                  eYes (1)
            }
    MAX-ACCESS read-write
    STATUS     current
    DESCRIPTION
            ""
    ::= { lcsSetupWlanMngmt 6 }

-- {SCALAR} 1.3.6.1.4.1.2356.11.2.37.7
lcsSetupWlanMngmtAcceptAp OBJECT-TYPE
    SYNTAX     DisplayString
    MAX-ACCESS read-write
    STATUS     current
    DESCRIPTION
            ""
    ::= { lcsSetupWlanMngmt 7 }

-- {SCALAR} 1.3.6.1.4.1.2356.11.2.37.8
lcsSetupWlanMngmtProvideDefaultConfiguration OBJECT-TYPE
    SYNTAX     INTEGER {
                  eNo (0),
                  eYes (1)
            }
    MAX-ACCESS read-write
    STATUS     current
    DESCRIPTION
            ""
    ::= { lcsSetupWlanMngmt 8 }

-- {SCALAR} 1.3.6.1.4.1.2356.11.2.37.9
lcsSetupWlanMngmtDisconnectAp OBJECT-TYPE
    SYNTAX     DisplayString
    MAX-ACCESS read-write
    STATUS     current
    DESCRIPTION
            ""
    ::= { lcsSetupWlanMngmt 9 }

-- {NODE} 1.3.6.1.4.1.2356.11.2.37.10
lcsSetupWlanMngmtNotification OBJECT IDENTIFIER ::= { lcsSetupWlanMngmt 10 }

-- {SCALAR} 1.3.6.1.4.1.2356.11.2.37.10.1
lcsSetupWlanMngmtNotificationEMail OBJECT-TYPE
    SYNTAX     INTEGER {
                  eNo (0),
                  eYes (1)
            }
    MAX-ACCESS read-write
    STATUS     current
    DESCRIPTION
            ""
    ::= { lcsSetupWlanMngmtNotification 1 }

-- {SCALAR} 1.3.6.1.4.1.2356.11.2.37.10.2
lcsSetupWlanMngmtNotificationSyslog OBJECT-TYPE
    SYNTAX     INTEGER {
                  eNo (0),
                  eYes (1)
            }
    MAX-ACCESS read-write
    STATUS     current
    DESCRIPTION
            ""
    ::= { lcsSetupWlanMngmtNotification 2 }

-- {SCALAR} 1.3.6.1.4.1.2356.11.2.37.10.3
lcsSetupWlanMngmtNotificationEMailReceiver OBJECT-TYPE
    SYNTAX     DisplayString (SIZE(0..63))
    MAX-ACCESS read-write
    STATUS     current
    DESCRIPTION
            ""
    ::= { lcsSetupWlanMngmtNotification 3 }

-- {TABLE} 1.3.6.1.4.1.2356.11.2.37.10.4
lcsSetupWlanMngmtNotificationAdvancedTable OBJECT-TYPE
    SYNTAX     SEQUENCE OF LcsSetupWlanMngmtNotificationAdvancedEntry
    MAX-ACCESS not-accessible
    STATUS     current
    DESCRIPTION
            ""
    ::= { lcsSetupWlanMngmtNotification 4 }

-- {ROW} 1.3.6.1.4.1.2356.11.2.37.10.4.1
lcsSetupWlanMngmtNotificationAdvancedEntry OBJECT-TYPE
    SYNTAX     LcsSetupWlanMngmtNotificationAdvancedEntry
    MAX-ACCESS not-accessible
    STATUS     current
    DESCRIPTION
            ""
    INDEX {
            lcsSetupWlanMngmtNotificationAdvancedEntryName
          }
    ::= { lcsSetupWlanMngmtNotificationAdvancedTable 1 }

LcsSetupWlanMngmtNotificationAdvancedEntry ::= SEQUENCE {
            lcsSetupWlanMngmtNotificationAdvancedEntryName INTEGER,
            lcsSetupWlanMngmtNotificationAdvancedEntryActiveRadios INTEGER,
            lcsSetupWlanMngmtNotificationAdvancedEntryMissingAp INTEGER,
            lcsSetupWlanMngmtNotificationAdvancedEntryNewAp INTEGER
    }

-- {COLUMN} 1.3.6.1.4.1.2356.11.2.37.10.4.1.1
lcsSetupWlanMngmtNotificationAdvancedEntryName OBJECT-TYPE
    SYNTAX     INTEGER {
                  eEMail (1),
                  eSyslog (2)
            }
    MAX-ACCESS read-only
    STATUS     current
    DESCRIPTION
            ""
    ::= { lcsSetupWlanMngmtNotificationAdvancedEntry 1 }

-- {COLUMN} 1.3.6.1.4.1.2356.11.2.37.10.4.1.2
lcsSetupWlanMngmtNotificationAdvancedEntryActiveRadios OBJECT-TYPE
    SYNTAX     INTEGER {
                  eNo (0),
                  eYes (1)
            }
    MAX-ACCESS read-write
    STATUS     current
    DESCRIPTION
            ""
    ::= { lcsSetupWlanMngmtNotificationAdvancedEntry 2 }

-- {COLUMN} 1.3.6.1.4.1.2356.11.2.37.10.4.1.3
lcsSetupWlanMngmtNotificationAdvancedEntryMissingAp OBJECT-TYPE
    SYNTAX     INTEGER {
                  eNo (0),
                  eYes (1)
            }
    MAX-ACCESS read-write
    STATUS     current
    DESCRIPTION
            ""
    ::= { lcsSetupWlanMngmtNotificationAdvancedEntry 3 }

-- {COLUMN} 1.3.6.1.4.1.2356.11.2.37.10.4.1.4
lcsSetupWlanMngmtNotificationAdvancedEntryNewAp OBJECT-TYPE
    SYNTAX     INTEGER {
                  eNo (0),
                  eYes (1)
            }
    MAX-ACCESS read-write
    STATUS     current
    DESCRIPTION
            ""
    ::= { lcsSetupWlanMngmtNotificationAdvancedEntry 4 }

-- {SCALAR} 1.3.6.1.4.1.2356.11.2.37.10.5
lcsSetupWlanMngmtNotificationSendSnmpTrapForStationTableEvent OBJECT-TYPE
    SYNTAX     INTEGER {
                  eAddRemoveEntry (0),
                  eAllEvents (1)
            }
    MAX-ACCESS read-write
    STATUS     current
    DESCRIPTION
            ""
    ::= { lcsSetupWlanMngmtNotification 5 }

-- {TABLE} 1.3.6.1.4.1.2356.11.2.37.17
lcsSetupWlanMngmtRadiusServerTable OBJECT-TYPE
    SYNTAX     SEQUENCE OF LcsSetupWlanMngmtRadiusServerEntry
    MAX-ACCESS not-accessible
    STATUS     current
    DESCRIPTION
            ""
    ::= { lcsSetupWlanMngmt 17 }

-- {ROW} 1.3.6.1.4.1.2356.11.2.37.17.1
lcsSetupWlanMngmtRadiusServerEntry OBJECT-TYPE
    SYNTAX     LcsSetupWlanMngmtRadiusServerEntry
    MAX-ACCESS not-accessible
    STATUS     current
    DESCRIPTION
            ""
    INDEX {
            lcsSetupWlanMngmtRadiusServerEntryType
          }
    ::= { lcsSetupWlanMngmtRadiusServerTable 1 }

LcsSetupWlanMngmtRadiusServerEntry ::= SEQUENCE {
            lcsSetupWlanMngmtRadiusServerEntryType INTEGER,
            lcsSetupWlanMngmtRadiusServerEntryIpAddress IpAddress,
            lcsSetupWlanMngmtRadiusServerEntryPort Integer32,
            lcsSetupWlanMngmtRadiusServerEntrySecret DisplayString
    }

-- {COLUMN} 1.3.6.1.4.1.2356.11.2.37.17.1.1
lcsSetupWlanMngmtRadiusServerEntryType OBJECT-TYPE
    SYNTAX     INTEGER {
                  eAccount (1),
                  eAccess (2),
                  eBackupAccount (3),
                  eBackupAccess (4)
            }
    MAX-ACCESS read-only
    STATUS     current
    DESCRIPTION
            ""
    ::= { lcsSetupWlanMngmtRadiusServerEntry 1 }

-- {COLUMN} 1.3.6.1.4.1.2356.11.2.37.17.1.2
lcsSetupWlanMngmtRadiusServerEntryIpAddress OBJECT-TYPE
    SYNTAX     IpAddress
    MAX-ACCESS read-write
    STATUS     current
    DESCRIPTION
            ""
    ::= { lcsSetupWlanMngmtRadiusServerEntry 2 }

-- {COLUMN} 1.3.6.1.4.1.2356.11.2.37.17.1.3
lcsSetupWlanMngmtRadiusServerEntryPort OBJECT-TYPE
    SYNTAX     Integer32 (0..65535)
    MAX-ACCESS read-write
    STATUS     current
    DESCRIPTION
            ""
    ::= { lcsSetupWlanMngmtRadiusServerEntry 3 }

-- {COLUMN} 1.3.6.1.4.1.2356.11.2.37.17.1.4
lcsSetupWlanMngmtRadiusServerEntrySecret OBJECT-TYPE
    SYNTAX     DisplayString (SIZE(0..64))
    MAX-ACCESS read-write
    STATUS     current
    DESCRIPTION
            ""
    ::= { lcsSetupWlanMngmtRadiusServerEntry 4 }

-- {SCALAR} 1.3.6.1.4.1.2356.11.2.37.19
lcsSetupWlanMngmtStartAutomaticRadioFieldOptimization OBJECT-TYPE
    SYNTAX     DisplayString
    MAX-ACCESS read-write
    STATUS     current
    DESCRIPTION
            ""
    ::= { lcsSetupWlanMngmt 19 }

-- {TABLE} 1.3.6.1.4.1.2356.11.2.37.20
lcsSetupWlanMngmtAccessListTable OBJECT-TYPE
    SYNTAX     SEQUENCE OF LcsSetupWlanMngmtAccessListEntry
    MAX-ACCESS not-accessible
    STATUS     current
    DESCRIPTION
            ""
    ::= { lcsSetupWlanMngmt 20 }

-- {ROW} 1.3.6.1.4.1.2356.11.2.37.20.1
lcsSetupWlanMngmtAccessListEntry OBJECT-TYPE
    SYNTAX     LcsSetupWlanMngmtAccessListEntry
    MAX-ACCESS not-accessible
    STATUS     current
    DESCRIPTION
            ""
    INDEX {
            lcsSetupWlanMngmtAccessListEntryMacAddress
          }
    ::= { lcsSetupWlanMngmtAccessListTable 1 }

LcsSetupWlanMngmtAccessListEntry ::= SEQUENCE {
            lcsSetupWlanMngmtAccessListEntryMacAddress MacAddress,
            lcsSetupWlanMngmtAccessListEntryName DisplayString,
            lcsSetupWlanMngmtAccessListEntryComment DisplayString,
            lcsSetupWlanMngmtAccessListEntryWpaPassphrase DisplayString,
            lcsSetupWlanMngmtAccessListEntryTxLimit Integer32,
            lcsSetupWlanMngmtAccessListEntryRxLimit Integer32,
            lcsSetupWlanMngmtAccessListEntryVlanId Integer32
    }

-- {COLUMN} 1.3.6.1.4.1.2356.11.2.37.20.1.1
lcsSetupWlanMngmtAccessListEntryMacAddress OBJECT-TYPE
    SYNTAX     MacAddress
    MAX-ACCESS read-write
    STATUS     current
    DESCRIPTION
            ""
    ::= { lcsSetupWlanMngmtAccessListEntry 1 }

-- {COLUMN} 1.3.6.1.4.1.2356.11.2.37.20.1.2
lcsSetupWlanMngmtAccessListEntryName OBJECT-TYPE
    SYNTAX     DisplayString (SIZE(0..32))
    MAX-ACCESS read-write
    STATUS     current
    DESCRIPTION
            ""
    ::= { lcsSetupWlanMngmtAccessListEntry 2 }

-- {COLUMN} 1.3.6.1.4.1.2356.11.2.37.20.1.3
lcsSetupWlanMngmtAccessListEntryComment OBJECT-TYPE
    SYNTAX     DisplayString (SIZE(0..30))
    MAX-ACCESS read-write
    STATUS     current
    DESCRIPTION
            ""
    ::= { lcsSetupWlanMngmtAccessListEntry 3 }

-- {COLUMN} 1.3.6.1.4.1.2356.11.2.37.20.1.4
lcsSetupWlanMngmtAccessListEntryWpaPassphrase OBJECT-TYPE
    SYNTAX     DisplayString (SIZE(0..63))
    MAX-ACCESS read-write
    STATUS     current
    DESCRIPTION
            ""
    ::= { lcsSetupWlanMngmtAccessListEntry 4 }

-- {COLUMN} 1.3.6.1.4.1.2356.11.2.37.20.1.5
lcsSetupWlanMngmtAccessListEntryTxLimit OBJECT-TYPE
    SYNTAX     Integer32 (0..2147483647)
    MAX-ACCESS read-write
    STATUS     current
    DESCRIPTION
            ""
    ::= { lcsSetupWlanMngmtAccessListEntry 5 }

-- {COLUMN} 1.3.6.1.4.1.2356.11.2.37.20.1.6
lcsSetupWlanMngmtAccessListEntryRxLimit OBJECT-TYPE
    SYNTAX     Integer32 (0..2147483647)
    MAX-ACCESS read-write
    STATUS     current
    DESCRIPTION
            ""
    ::= { lcsSetupWlanMngmtAccessListEntry 6 }

-- {COLUMN} 1.3.6.1.4.1.2356.11.2.37.20.1.7
lcsSetupWlanMngmtAccessListEntryVlanId OBJECT-TYPE
    SYNTAX     Integer32 (0..65535)
    MAX-ACCESS read-write
    STATUS     current
    DESCRIPTION
            ""
    ::= { lcsSetupWlanMngmtAccessListEntry 7 }

-- {TABLE} 1.3.6.1.4.1.2356.11.2.37.21
lcsSetupWlanMngmtAccessRulesTable OBJECT-TYPE
    SYNTAX     SEQUENCE OF LcsSetupWlanMngmtAccessRulesEntry
    MAX-ACCESS not-accessible
    STATUS     current
    DESCRIPTION
            "-- empty --"
    ::= { lcsSetupWlanMngmt 21 }

-- {ROW} 1.3.6.1.4.1.2356.11.2.37.21.1
lcsSetupWlanMngmtAccessRulesEntry OBJECT-TYPE
    SYNTAX     LcsSetupWlanMngmtAccessRulesEntry
    MAX-ACCESS not-accessible
    STATUS     current
    DESCRIPTION
            ""
    INDEX {
            lcsSetupWlanMngmtAccessRulesEntryMacAddressPattern,
            lcsSetupWlanMngmtAccessRulesEntrySsidPattern
          }
    ::= { lcsSetupWlanMngmtAccessRulesTable 1 }

LcsSetupWlanMngmtAccessRulesEntry ::= SEQUENCE {
            lcsSetupWlanMngmtAccessRulesEntryMacAddressPattern DisplayString,
            lcsSetupWlanMngmtAccessRulesEntryName DisplayString,
            lcsSetupWlanMngmtAccessRulesEntryComment DisplayString,
            lcsSetupWlanMngmtAccessRulesEntryWpaPassphrase DisplayString,
            lcsSetupWlanMngmtAccessRulesEntryTxLimit Integer32,
            lcsSetupWlanMngmtAccessRulesEntryRxLimit Integer32,
            lcsSetupWlanMngmtAccessRulesEntryVlanId Integer32,
            lcsSetupWlanMngmtAccessRulesEntrySsidPattern DisplayString
    }

-- {COLUMN} 1.3.6.1.4.1.2356.11.2.37.21.1.1
lcsSetupWlanMngmtAccessRulesEntryMacAddressPattern OBJECT-TYPE
    SYNTAX     DisplayString (SIZE(0..20))
    MAX-ACCESS read-write
    STATUS     current
    DESCRIPTION
            "-- empty --"
    ::= { lcsSetupWlanMngmtAccessRulesEntry 1 }

-- {COLUMN} 1.3.6.1.4.1.2356.11.2.37.21.1.2
lcsSetupWlanMngmtAccessRulesEntryName OBJECT-TYPE
    SYNTAX     DisplayString (SIZE(0..32))
    MAX-ACCESS read-write
    STATUS     current
    DESCRIPTION
            "-- empty --"
    ::= { lcsSetupWlanMngmtAccessRulesEntry 2 }

-- {COLUMN} 1.3.6.1.4.1.2356.11.2.37.21.1.3
lcsSetupWlanMngmtAccessRulesEntryComment OBJECT-TYPE
    SYNTAX     DisplayString (SIZE(0..30))
    MAX-ACCESS read-write
    STATUS     current
    DESCRIPTION
            "-- empty --"
    ::= { lcsSetupWlanMngmtAccessRulesEntry 3 }

-- {COLUMN} 1.3.6.1.4.1.2356.11.2.37.21.1.4
lcsSetupWlanMngmtAccessRulesEntryWpaPassphrase OBJECT-TYPE
    SYNTAX     DisplayString (SIZE(0..63))
    MAX-ACCESS read-write
    STATUS     current
    DESCRIPTION
            "-- empty --"
    ::= { lcsSetupWlanMngmtAccessRulesEntry 4 }

-- {COLUMN} 1.3.6.1.4.1.2356.11.2.37.21.1.5
lcsSetupWlanMngmtAccessRulesEntryTxLimit OBJECT-TYPE
    SYNTAX     Integer32 (0..2147483647)
    MAX-ACCESS read-write
    STATUS     current
    DESCRIPTION
            "-- empty --"
    ::= { lcsSetupWlanMngmtAccessRulesEntry 5 }

-- {COLUMN} 1.3.6.1.4.1.2356.11.2.37.21.1.6
lcsSetupWlanMngmtAccessRulesEntryRxLimit OBJECT-TYPE
    SYNTAX     Integer32 (0..2147483647)
    MAX-ACCESS read-write
    STATUS     current
    DESCRIPTION
            "-- empty --"
    ::= { lcsSetupWlanMngmtAccessRulesEntry 6 }

-- {COLUMN} 1.3.6.1.4.1.2356.11.2.37.21.1.7
lcsSetupWlanMngmtAccessRulesEntryVlanId OBJECT-TYPE
    SYNTAX     Integer32 (0..65535)
    MAX-ACCESS read-write
    STATUS     current
    DESCRIPTION
            "-- empty --"
    ::= { lcsSetupWlanMngmtAccessRulesEntry 7 }

-- {COLUMN} 1.3.6.1.4.1.2356.11.2.37.21.1.8
lcsSetupWlanMngmtAccessRulesEntrySsidPattern OBJECT-TYPE
    SYNTAX     DisplayString (SIZE(0..40))
    MAX-ACCESS read-write
    STATUS     current
    DESCRIPTION
            "-- empty --"
    ::= { lcsSetupWlanMngmtAccessRulesEntry 8 }

-- {NODE} 1.3.6.1.4.1.2356.11.2.37.27
lcsSetupWlanMngmtCentralFwMngmt OBJECT IDENTIFIER ::= { lcsSetupWlanMngmt 27 }

-- {SCALAR} 1.3.6.1.4.1.2356.11.2.37.27.11
lcsSetupWlanMngmtCentralFwMngmtFirmwareRepositoryUrl OBJECT-TYPE
    SYNTAX     DisplayString (SIZE(0..251))
    MAX-ACCESS read-write
    STATUS     current
    DESCRIPTION
            ""
    ::= { lcsSetupWlanMngmtCentralFwMngmt 11 }

-- {SCALAR} 1.3.6.1.4.1.2356.11.2.37.27.12
lcsSetupWlanMngmtCentralFwMngmtScriptRepositoryUrl OBJECT-TYPE
    SYNTAX     DisplayString (SIZE(0..251))
    MAX-ACCESS read-write
    STATUS     current
    DESCRIPTION
            ""
    ::= { lcsSetupWlanMngmtCentralFwMngmt 12 }

-- {SCALAR} 1.3.6.1.4.1.2356.11.2.37.27.13
lcsSetupWlanMngmtCentralFwMngmtUpdFwScriptInfo OBJECT-TYPE
    SYNTAX     DisplayString
    MAX-ACCESS read-write
    STATUS     current
    DESCRIPTION
            "update firmware and script information"
    ::= { lcsSetupWlanMngmtCentralFwMngmt 13 }

-- {SCALAR} 1.3.6.1.4.1.2356.11.2.37.27.14
lcsSetupWlanMngmtCentralFwMngmtMaximumNumberOfLoadedFirmwares OBJECT-TYPE
    SYNTAX     Integer32 (0..255)
    MAX-ACCESS read-write
    STATUS     current
    DESCRIPTION
            ""
    ::= { lcsSetupWlanMngmtCentralFwMngmt 14 }

-- {TABLE} 1.3.6.1.4.1.2356.11.2.37.27.15
lcsSetupWlanMngmtCentralFwMngmtFwVersMngmtTable OBJECT-TYPE
    SYNTAX     SEQUENCE OF LcsSetupWlanMngmtCentralFwMngmtFwVersMngmtEntry
    MAX-ACCESS not-accessible
    STATUS     current
    DESCRIPTION
            "firmware version management"
    ::= { lcsSetupWlanMngmtCentralFwMngmt 15 }

-- {ROW} 1.3.6.1.4.1.2356.11.2.37.27.15.1
lcsSetupWlanMngmtCentralFwMngmtFwVersMngmtEntry OBJECT-TYPE
    SYNTAX     LcsSetupWlanMngmtCentralFwMngmtFwVersMngmtEntry
    MAX-ACCESS not-accessible
    STATUS     current
    DESCRIPTION
            ""
    INDEX {
            lcsSetupWlanMngmtCentralFwMngmtFwVersMngmtEntryDevice,
            lcsSetupWlanMngmtCentralFwMngmtFwVersMngmtEntryMacAddress
          }
    ::= { lcsSetupWlanMngmtCentralFwMngmtFwVersMngmtTable 1 }

LcsSetupWlanMngmtCentralFwMngmtFwVersMngmtEntry ::= SEQUENCE {
            lcsSetupWlanMngmtCentralFwMngmtFwVersMngmtEntryDevice INTEGER,
            lcsSetupWlanMngmtCentralFwMngmtFwVersMngmtEntryMacAddress DisplayString,
            lcsSetupWlanMngmtCentralFwMngmtFwVersMngmtEntryVersion DisplayString,
            lcsSetupWlanMngmtCentralFwMngmtFwVersMngmtEntryDate DisplayString
    }

-- {COLUMN} 1.3.6.1.4.1.2356.11.2.37.27.15.1.2
lcsSetupWlanMngmtCentralFwMngmtFwVersMngmtEntryDevice OBJECT-TYPE
    SYNTAX     INTEGER {
                  eAllDevices (1),
                  eLancom1821WirelessAdslAnnA (2),
                  eLancom1821WirelessAdslAnnB (3),
                  eLANCOM1821plusWirelessADSLAnnA (5),
                  eLANCOM1821plusWirelessADSLAnnB (6),
                  eLancom1823VoipAnnexA (10),
                  eLancom1823VoipAnnexB (11),
                  eLancomIap54Wireless (12),
                  eLancomL54agWireless (13),
                  eLancom3850Umts (14),
                  eLancom3550Wireless (15),
                  eLancomOap54Wireless (16),
                  eLancomXap402 (19),
                  eLancomL54DualWireless (20),
                  eLancom1811WirelessDsl (21),
                  eLancomL310agnWireless (22),
                  eLancomL54gWireless (23),
                  eLancomXap402Fcc (24),
                  eLancomL305agnWireless (25),
                  eLancom3050Wireless (26),
                  eLancomOap310agnWireless (27),
                  eLancomOap541Wireless (28),
                  eLancom1811nWireless (29),
                  eLancomL315agnDualWireless (30),
                  eBAT54Rail (31),
                  eBAT54RailPlus (32),
                  eBAT300Rail (33),
                  eBAT300F (34),
                  eBAT300FX2 (35),
                  eBAT54F (36),
                  eBAT54FPlus (37),
                  eBAT54FX2 (38),
                  eBAT54FX2Plus (39),
                  eBAT54FSinglePlus (40),
                  eBAT54FX2SinglePlus (41),
                  eLancomL320agnWireless (42),
                  eLancomL321agnWireless (43),
                  eLancomL322agnDualWireless (44),
                  eBAT54RailSinglePlus (45),
                  eLancomOap321 (46),
                  eLancomIap321 (47),
                  eLancom1780ew3g (48),
                  eLancomIap3213g (49),
                  eLancomOap3213g (50),
                  eBatR (51),
                  eBatF (52),
                  eLancom1781ew (53),
                  eLancom1781aw (54),
                  eLancomOap382 (55),
                  eLancomL450agnWireless (56),
                  eLancomL451agnWireless (57),
                  eLancomL452agnDualWireless (58),
                  eLancomL460agnDualWireless (59),
                  eLancomOap322 (60),
                  eLancom1780ew4g (61),
                  eLancomIap322 (62),
                  eLancomL1302acnDualWireless (63),
                  eLancomL1310acnDualWireless (64),
                  eLancomL151gnWireless (65),
                  eLancomL320agnWirelessR2 (66),
                  eLancomL321agnWirelessR2 (67),
                  eLancomL322agnDualWirelessR2 (68),
                  eLancomL322eWireless (69),
                  eLancomL151eWireless (70),
                  eLancom1781ewPlus (72),
                  eLancomL822acnDualWireless (73),
                  eLancomOap821 (75),
                  eLancomOap822 (76),
                  eLancomL330agnDualWireless (77),
                  eLancomOap830 (78),
                  eLancom1781vaw (79),
                  eLancom1783vaw (80),
                  eLancomLn830acnDualWireless (81),
                  eLancomLn830eWireless (82),
                  eLancomIap821 (83),
                  eLancomIap822 (84),
                  eLancom883Voip (85),
                  eLancomLn630acnDualWireless (86),
                  eLancomLn860 (87),
                  eLancomLn862 (88),
                  eLancomLn1700 (89),
                  eLancomLn1702 (90),
                  eLancom1780ew4gPlus (91),
                  eLancom1790vaw (92),
                  eLancom1793vaw (93),
                  eLancomLn1700b (94),
                  eLancomLn1702b (95),
                  eLancomOap1702b (96),
                  eLancomLn830u (97),
                  eLancomOap1700b (98),
                  eLancomLn1700ue (99)
            }
    MAX-ACCESS read-write
    STATUS     current
    DESCRIPTION
            ""
    ::= { lcsSetupWlanMngmtCentralFwMngmtFwVersMngmtEntry 2 }

-- {COLUMN} 1.3.6.1.4.1.2356.11.2.37.27.15.1.3
lcsSetupWlanMngmtCentralFwMngmtFwVersMngmtEntryMacAddress OBJECT-TYPE
    SYNTAX     DisplayString (SIZE(0..12))
    MAX-ACCESS read-write
    STATUS     current
    DESCRIPTION
            ""
    ::= { lcsSetupWlanMngmtCentralFwMngmtFwVersMngmtEntry 3 }

-- {COLUMN} 1.3.6.1.4.1.2356.11.2.37.27.15.1.4
lcsSetupWlanMngmtCentralFwMngmtFwVersMngmtEntryVersion OBJECT-TYPE
    SYNTAX     DisplayString (SIZE(0..5))
    MAX-ACCESS read-write
    STATUS     current
    DESCRIPTION
            ""
    ::= { lcsSetupWlanMngmtCentralFwMngmtFwVersMngmtEntry 4 }

-- {COLUMN} 1.3.6.1.4.1.2356.11.2.37.27.15.1.5
lcsSetupWlanMngmtCentralFwMngmtFwVersMngmtEntryDate OBJECT-TYPE
    SYNTAX     DisplayString (SIZE(0..8))
    MAX-ACCESS read-write
    STATUS     current
    DESCRIPTION
            "-- empty --"
    ::= { lcsSetupWlanMngmtCentralFwMngmtFwVersMngmtEntry 5 }

-- {TABLE} 1.3.6.1.4.1.2356.11.2.37.27.16
lcsSetupWlanMngmtCentralFwMngmtScriptMngmtTable OBJECT-TYPE
    SYNTAX     SEQUENCE OF LcsSetupWlanMngmtCentralFwMngmtScriptMngmtEntry
    MAX-ACCESS not-accessible
    STATUS     current
    DESCRIPTION
            "script management"
    ::= { lcsSetupWlanMngmtCentralFwMngmt 16 }

-- {ROW} 1.3.6.1.4.1.2356.11.2.37.27.16.1
lcsSetupWlanMngmtCentralFwMngmtScriptMngmtEntry OBJECT-TYPE
    SYNTAX     LcsSetupWlanMngmtCentralFwMngmtScriptMngmtEntry
    MAX-ACCESS not-accessible
    STATUS     current
    DESCRIPTION
            ""
    INDEX {
            lcsSetupWlanMngmtCentralFwMngmtScriptMngmtEntryProfile,
            lcsSetupWlanMngmtCentralFwMngmtScriptMngmtEntryFirmwareVersion
          }
    ::= { lcsSetupWlanMngmtCentralFwMngmtScriptMngmtTable 1 }

LcsSetupWlanMngmtCentralFwMngmtScriptMngmtEntry ::= SEQUENCE {
            lcsSetupWlanMngmtCentralFwMngmtScriptMngmtEntryProfile DisplayString,
            lcsSetupWlanMngmtCentralFwMngmtScriptMngmtEntryName DisplayString,
            lcsSetupWlanMngmtCentralFwMngmtScriptMngmtEntryFirmwareVersion DisplayString
    }

-- {COLUMN} 1.3.6.1.4.1.2356.11.2.37.27.16.1.1
lcsSetupWlanMngmtCentralFwMngmtScriptMngmtEntryProfile OBJECT-TYPE
    SYNTAX     DisplayString (SIZE(0..31))
    MAX-ACCESS read-write
    STATUS     current
    DESCRIPTION
            ""
    ::= { lcsSetupWlanMngmtCentralFwMngmtScriptMngmtEntry 1 }

-- {COLUMN} 1.3.6.1.4.1.2356.11.2.37.27.16.1.2
lcsSetupWlanMngmtCentralFwMngmtScriptMngmtEntryName OBJECT-TYPE
    SYNTAX     DisplayString (SIZE(0..63))
    MAX-ACCESS read-write
    STATUS     current
    DESCRIPTION
            ""
    ::= { lcsSetupWlanMngmtCentralFwMngmtScriptMngmtEntry 2 }

-- {COLUMN} 1.3.6.1.4.1.2356.11.2.37.27.16.1.3
lcsSetupWlanMngmtCentralFwMngmtScriptMngmtEntryFirmwareVersion OBJECT-TYPE
    SYNTAX     DisplayString (SIZE(0..5))
    MAX-ACCESS read-write
    STATUS     current
    DESCRIPTION
            "-- empty --"
    ::= { lcsSetupWlanMngmtCentralFwMngmtScriptMngmtEntry 3 }

-- {SCALAR} 1.3.6.1.4.1.2356.11.2.37.27.18
lcsSetupWlanMngmtCentralFwMngmtRebootUpdatedAps OBJECT-TYPE
    SYNTAX     DisplayString
    MAX-ACCESS read-write
    STATUS     current
    DESCRIPTION
            ""
    ::= { lcsSetupWlanMngmtCentralFwMngmt 18 }

-- {SCALAR} 1.3.6.1.4.1.2356.11.2.37.27.25
lcsSetupWlanMngmtCentralFwMngmtFwLoopbkAddr OBJECT-TYPE
    SYNTAX     DisplayString (SIZE(0..16))
    MAX-ACCESS read-write
    STATUS     current
    DESCRIPTION
            "firmware loopback address"
    ::= { lcsSetupWlanMngmtCentralFwMngmt 25 }

-- {SCALAR} 1.3.6.1.4.1.2356.11.2.37.27.26
lcsSetupWlanMngmtCentralFwMngmtScriptLoopbAddr OBJECT-TYPE
    SYNTAX     DisplayString (SIZE(0..16))
    MAX-ACCESS read-write
    STATUS     current
    DESCRIPTION
            "script loopback address"
    ::= { lcsSetupWlanMngmtCentralFwMngmt 26 }

-- {SCALAR} 1.3.6.1.4.1.2356.11.2.37.27.38
lcsSetupWlanMngmtCentralFwMngmtMaxNumberOfConcurrentUpdates OBJECT-TYPE
    SYNTAX     Integer32 (0..255)
    MAX-ACCESS read-write
    STATUS     current
    DESCRIPTION
            "-- empty --"
    ::= { lcsSetupWlanMngmtCentralFwMngmt 38 }

-- {NODE} 1.3.6.1.4.1.2356.11.2.37.27.39
lcsSetupWlanMngmtCentralFwMngmtSslNew OBJECT IDENTIFIER ::= { lcsSetupWlanMngmtCentralFwMngmt 39 }

-- {SCALAR} 1.3.6.1.4.1.2356.11.2.37.27.39.1
lcsSetupWlanMngmtCentralFwMngmtSslNewVersions OBJECT-TYPE
    SYNTAX     BITS {
                  eTlsv12 (28),
                  eTlsv11 (29),
                  eTlsv1 (30),
                  eSslv3 (31)
            }
    MAX-ACCESS read-write
    STATUS     current
    DESCRIPTION
            "-- empty --"
    ::= { lcsSetupWlanMngmtCentralFwMngmtSslNew 1 }

-- {SCALAR} 1.3.6.1.4.1.2356.11.2.37.27.39.2
lcsSetupWlanMngmtCentralFwMngmtSslNewKeyexAlgorithms OBJECT-TYPE
    SYNTAX     BITS {
                  eEcdhe (27),
                  eDhe (29),
                  eRsa (31)
            }
    MAX-ACCESS read-write
    STATUS     current
    DESCRIPTION
            "-- empty --"
    ::= { lcsSetupWlanMngmtCentralFwMngmtSslNew 2 }

-- {SCALAR} 1.3.6.1.4.1.2356.11.2.37.27.39.3
lcsSetupWlanMngmtCentralFwMngmtSslNewCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupWlanMngmtCentralFwMngmtSslNew 3 }

-- {SCALAR} 1.3.6.1.4.1.2356.11.2.37.27.39.4
lcsSetupWlanMngmtCentralFwMngmtSslNewHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupWlanMngmtCentralFwMngmtSslNew 4 }

-- {SCALAR} 1.3.6.1.4.1.2356.11.2.37.27.39.5
lcsSetupWlanMngmtCentralFwMngmtSslNewPreferPfs OBJECT-TYPE
    SYNTAX     BITS {
                  eNo (0),
                  eYes (7)
            }
    MAX-ACCESS read-write
    STATUS     current
    DESCRIPTION
            "-- empty --"
    ::= { lcsSetupWlanMngmtCentralFwMngmtSslNew 5 }

-- {SCALAR} 1.3.6.1.4.1.2356.11.2.37.27.39.6
lcsSetupWlanMngmtCentralFwMngmtSslNewRenegotiations OBJECT-TYPE
    SYNTAX     INTEGER {
                  eForbidden (0),
                  eAllowed (1),
                  eIgnored (2)
            }
    MAX-ACCESS read-write
    STATUS     current
    DESCRIPTION
            "-- empty --"
    ::= { lcsSetupWlanMngmtCentralFwMngmtSslNew 6 }

-- {SCALAR} 1.3.6.1.4.1.2356.11.2.37.27.39.7
lcsSetupWlanMngmtCentralFwMngmtSslNewEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupWlanMngmtCentralFwMngmtSslNew 7 }

-- {SCALAR} 1.3.6.1.4.1.2356.11.2.37.27.39.21
lcsSetupWlanMngmtCentralFwMngmtSslNewSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupWlanMngmtCentralFwMngmtSslNew 21 }

-- {SCALAR} 1.3.6.1.4.1.2356.11.2.37.29
lcsSetupWlanMngmtAllowWanConnections OBJECT-TYPE
    SYNTAX     INTEGER {
                  eNo (0),
                  eVpn (1),
                  eYes (2)
            }
    MAX-ACCESS read-write
    STATUS     current
    DESCRIPTION
            "-- empty --"
    ::= { lcsSetupWlanMngmt 29 }

-- {SCALAR} 1.3.6.1.4.1.2356.11.2.37.30
lcsSetupWlanMngmtSyncWtpPassword OBJECT-TYPE
    SYNTAX     INTEGER {
                  eNo (0),
                  eYes (1)
            }
    MAX-ACCESS read-write
    STATUS     current
    DESCRIPTION
            ""
    ::= { lcsSetupWlanMngmt 30 }

-- {SCALAR} 1.3.6.1.4.1.2356.11.2.37.31
lcsSetupWlanMngmtIntervalForStatusTableCleanup OBJECT-TYPE
    SYNTAX     Integer32 (0..2147483647)
    MAX-ACCESS read-write
    STATUS     current
    DESCRIPTION
            ""
    ::= { lcsSetupWlanMngmt 31 }

-- {SCALAR} 1.3.6.1.4.1.2356.11.2.37.32
lcsSetupWlanMngmtLicenseCount OBJECT-TYPE
    SYNTAX     Integer32 (0..2147483647)
    MAX-ACCESS read-only
    STATUS     current
    DESCRIPTION
            ""
    ::= { lcsSetupWlanMngmt 32 }

-- {SCALAR} 1.3.6.1.4.1.2356.11.2.37.33
lcsSetupWlanMngmtLicenseLimit OBJECT-TYPE
    SYNTAX     Integer32 (0..2147483647)
    MAX-ACCESS read-only
    STATUS     current
    DESCRIPTION
            ""
    ::= { lcsSetupWlanMngmt 33 }

-- {NODE} 1.3.6.1.4.1.2356.11.2.37.34
lcsSetupWlanMngmtWlcTunnels OBJECT IDENTIFIER ::= { lcsSetupWlanMngmt 34 }

-- {SCALAR} 1.3.6.1.4.1.2356.11.2.37.34.2
lcsSetupWlanMngmtWlcTunnelsWlcDataTunnelActive OBJECT-TYPE
    SYNTAX     INTEGER {
                  eNo (0),
                  eYes (1)
            }
    MAX-ACCESS read-write
    STATUS     current
    DESCRIPTION
            ""
    ::= { lcsSetupWlanMngmtWlcTunnels 2 }

-- {TABLE} 1.3.6.1.4.1.2356.11.2.37.34.3
lcsSetupWlanMngmtWlcTunnelsStaticWlcListTable OBJECT-TYPE
    SYNTAX     SEQUENCE OF LcsSetupWlanMngmtWlcTunnelsStaticWlcListEntry
    MAX-ACCESS not-accessible
    STATUS     current
    DESCRIPTION
            ""
    ::= { lcsSetupWlanMngmtWlcTunnels 3 }

-- {ROW} 1.3.6.1.4.1.2356.11.2.37.34.3.1
lcsSetupWlanMngmtWlcTunnelsStaticWlcListEntry OBJECT-TYPE
    SYNTAX     LcsSetupWlanMngmtWlcTunnelsStaticWlcListEntry
    MAX-ACCESS not-accessible
    STATUS     current
    DESCRIPTION
            ""
    INDEX {
            lcsSetupWlanMngmtWlcTunnelsStaticWlcListEntryIpAddress
          }
    ::= { lcsSetupWlanMngmtWlcTunnelsStaticWlcListTable 1 }

LcsSetupWlanMngmtWlcTunnelsStaticWlcListEntry ::= SEQUENCE {
            lcsSetupWlanMngmtWlcTunnelsStaticWlcListEntryIpAddress IpAddress,
            lcsSetupWlanMngmtWlcTunnelsStaticWlcListEntryLoopbackAddr DisplayString,
            lcsSetupWlanMngmtWlcTunnelsStaticWlcListEntryPort Integer32
    }

-- {COLUMN} 1.3.6.1.4.1.2356.11.2.37.34.3.1.1
lcsSetupWlanMngmtWlcTunnelsStaticWlcListEntryIpAddress OBJECT-TYPE
    SYNTAX     IpAddress
    MAX-ACCESS read-write
    STATUS     current
    DESCRIPTION
            ""
    ::= { lcsSetupWlanMngmtWlcTunnelsStaticWlcListEntry 1 }

-- {COLUMN} 1.3.6.1.4.1.2356.11.2.37.34.3.1.2
lcsSetupWlanMngmtWlcTunnelsStaticWlcListEntryLoopbackAddr OBJECT-TYPE
    SYNTAX     DisplayString (SIZE(0..16))
    MAX-ACCESS read-write
    STATUS     current
    DESCRIPTION
            ""
    ::= { lcsSetupWlanMngmtWlcTunnelsStaticWlcListEntry 2 }

-- {COLUMN} 1.3.6.1.4.1.2356.11.2.37.34.3.1.3
lcsSetupWlanMngmtWlcTunnelsStaticWlcListEntryPort OBJECT-TYPE
    SYNTAX     Integer32 (0..65535)
    MAX-ACCESS read-write
    STATUS     current
    DESCRIPTION
            "-- empty --"
    ::= { lcsSetupWlanMngmtWlcTunnelsStaticWlcListEntry 3 }

-- {TABLE} 1.3.6.1.4.1.2356.11.2.37.34.4
lcsSetupWlanMngmtWlcTunnelsWlcDiscoveryTable OBJECT-TYPE
    SYNTAX     SEQUENCE OF LcsSetupWlanMngmtWlcTunnelsWlcDiscoveryEntry
    MAX-ACCESS not-accessible
    STATUS     current
    DESCRIPTION
            ""
    ::= { lcsSetupWlanMngmtWlcTunnels 4 }

-- {ROW} 1.3.6.1.4.1.2356.11.2.37.34.4.1
lcsSetupWlanMngmtWlcTunnelsWlcDiscoveryEntry OBJECT-TYPE
    SYNTAX     LcsSetupWlanMngmtWlcTunnelsWlcDiscoveryEntry
    MAX-ACCESS not-accessible
    STATUS     current
    DESCRIPTION
            ""
    INDEX {
            lcsSetupWlanMngmtWlcTunnelsWlcDiscoveryEntryNetwork
          }
    ::= { lcsSetupWlanMngmtWlcTunnelsWlcDiscoveryTable 1 }

LcsSetupWlanMngmtWlcTunnelsWlcDiscoveryEntry ::= SEQUENCE {
            lcsSetupWlanMngmtWlcTunnelsWlcDiscoveryEntryNetwork DisplayString,
            lcsSetupWlanMngmtWlcTunnelsWlcDiscoveryEntryActive INTEGER,
            lcsSetupWlanMngmtWlcTunnelsWlcDiscoveryEntryPort Integer32
    }

-- {COLUMN} 1.3.6.1.4.1.2356.11.2.37.34.4.1.1
lcsSetupWlanMngmtWlcTunnelsWlcDiscoveryEntryNetwork OBJECT-TYPE
    SYNTAX     DisplayString (SIZE(0..16))
    MAX-ACCESS read-write
    STATUS     current
    DESCRIPTION
            ""
    ::= { lcsSetupWlanMngmtWlcTunnelsWlcDiscoveryEntry 1 }

-- {COLUMN} 1.3.6.1.4.1.2356.11.2.37.34.4.1.2
lcsSetupWlanMngmtWlcTunnelsWlcDiscoveryEntryActive OBJECT-TYPE
    SYNTAX     INTEGER {
                  eNo (0),
                  eYes (1)
            }
    MAX-ACCESS read-write
    STATUS     current
    DESCRIPTION
            ""
    ::= { lcsSetupWlanMngmtWlcTunnelsWlcDiscoveryEntry 2 }

-- {COLUMN} 1.3.6.1.4.1.2356.11.2.37.34.4.1.3
lcsSetupWlanMngmtWlcTunnelsWlcDiscoveryEntryPort OBJECT-TYPE
    SYNTAX     Integer32 (0..65535)
    MAX-ACCESS read-write
    STATUS     current
    DESCRIPTION
            "-- empty --"
    ::= { lcsSetupWlanMngmtWlcTunnelsWlcDiscoveryEntry 3 }

-- {SCALAR} 1.3.6.1.4.1.2356.11.2.37.34.5
lcsSetupWlanMngmtWlcTunnelsTriggerWlcRediscoveryOnWtps OBJECT-TYPE
    SYNTAX     DisplayString
    MAX-ACCESS read-write
    STATUS     current
    DESCRIPTION
            "-- empty --"
    ::= { lcsSetupWlanMngmtWlcTunnels 5 }

-- {SCALAR} 1.3.6.1.4.1.2356.11.2.37.34.6
lcsSetupWlanMngmtWlcTunnelsWlcTunnelActive OBJECT-TYPE
    SYNTAX     INTEGER {
                  eNo (0),
                  eYes (1)
            }
    MAX-ACCESS read-write
    STATUS     current
    DESCRIPTION
            "-- empty --"
    ::= { lcsSetupWlanMngmtWlcTunnels 6 }

-- {SCALAR} 1.3.6.1.4.1.2356.11.2.37.34.7
lcsSetupWlanMngmtWlcTunnelsWtpWlcRediscovery OBJECT-TYPE
    SYNTAX     INTEGER {
                  eNo (0),
                  eYes (1)
            }
    MAX-ACCESS read-write
    STATUS     current
    DESCRIPTION
            "-- empty --"
    ::= { lcsSetupWlanMngmtWlcTunnels 7 }

-- {TABLE} 1.3.6.1.4.1.2356.11.2.37.35
lcsSetupWlanMngmtRadiusServerProfilesTable OBJECT-TYPE
    SYNTAX     SEQUENCE OF LcsSetupWlanMngmtRadiusServerProfilesEntry
    MAX-ACCESS not-accessible
    STATUS     current
    DESCRIPTION
            "-- empty --"
    ::= { lcsSetupWlanMngmt 35 }

-- {ROW} 1.3.6.1.4.1.2356.11.2.37.35.1
lcsSetupWlanMngmtRadiusServerProfilesEntry OBJECT-TYPE
    SYNTAX     LcsSetupWlanMngmtRadiusServerProfilesEntry
    MAX-ACCESS not-accessible
    STATUS     current
    DESCRIPTION
            ""
    INDEX {
            lcsSetupWlanMngmtRadiusServerProfilesEntryName
          }
    ::= { lcsSetupWlanMngmtRadiusServerProfilesTable 1 }

LcsSetupWlanMngmtRadiusServerProfilesEntry ::= SEQUENCE {
            lcsSetupWlanMngmtRadiusServerProfilesEntryName DisplayString,
            lcsSetupWlanMngmtRadiusServerProfilesEntryAccountIp IpAddress,
            lcsSetupWlanMngmtRadiusServerProfilesEntryAccountPort Integer32,
            lcsSetupWlanMngmtRadiusServerProfilesEntryAccountSecret DisplayString,
            lcsSetupWlanMngmtRadiusServerProfilesEntryAccountLoopback DisplayString,
            lcsSetupWlanMngmtRadiusServerProfilesEntryAccountProtocol INTEGER,
            lcsSetupWlanMngmtRadiusServerProfilesEntryAccessIp IpAddress,
            lcsSetupWlanMngmtRadiusServerProfilesEntryAccessPort Integer32,
            lcsSetupWlanMngmtRadiusServerProfilesEntryAccessSecret DisplayString,
            lcsSetupWlanMngmtRadiusServerProfilesEntryAccessLoopback DisplayString,
            lcsSetupWlanMngmtRadiusServerProfilesEntryAccessProtocol INTEGER,
            lcsSetupWlanMngmtRadiusServerProfilesEntryBackup DisplayString
    }

-- {COLUMN} 1.3.6.1.4.1.2356.11.2.37.35.1.1
lcsSetupWlanMngmtRadiusServerProfilesEntryName OBJECT-TYPE
    SYNTAX     DisplayString (SIZE(0..16))
    MAX-ACCESS read-write
    STATUS     current
    DESCRIPTION
            "-- empty --"
    ::= { lcsSetupWlanMngmtRadiusServerProfilesEntry 1 }

-- {COLUMN} 1.3.6.1.4.1.2356.11.2.37.35.1.2
lcsSetupWlanMngmtRadiusServerProfilesEntryAccountIp OBJECT-TYPE
    SYNTAX     IpAddress
    MAX-ACCESS read-write
    STATUS     current
    DESCRIPTION
            "-- empty --"
    ::= { lcsSetupWlanMngmtRadiusServerProfilesEntry 2 }

-- {COLUMN} 1.3.6.1.4.1.2356.11.2.37.35.1.3
lcsSetupWlanMngmtRadiusServerProfilesEntryAccountPort OBJECT-TYPE
    SYNTAX     Integer32 (0..65535)
    MAX-ACCESS read-write
    STATUS     current
    DESCRIPTION
            "-- empty --"
    ::= { lcsSetupWlanMngmtRadiusServerProfilesEntry 3 }

-- {COLUMN} 1.3.6.1.4.1.2356.11.2.37.35.1.4
lcsSetupWlanMngmtRadiusServerProfilesEntryAccountSecret OBJECT-TYPE
    SYNTAX     DisplayString (SIZE(0..64))
    MAX-ACCESS read-write
    STATUS     current
    DESCRIPTION
            "-- empty --"
    ::= { lcsSetupWlanMngmtRadiusServerProfilesEntry 4 }

-- {COLUMN} 1.3.6.1.4.1.2356.11.2.37.35.1.5
lcsSetupWlanMngmtRadiusServerProfilesEntryAccountLoopback OBJECT-TYPE
    SYNTAX     DisplayString (SIZE(0..16))
    MAX-ACCESS read-write
    STATUS     current
    DESCRIPTION
            "-- empty --"
    ::= { lcsSetupWlanMngmtRadiusServerProfilesEntry 5 }

-- {COLUMN} 1.3.6.1.4.1.2356.11.2.37.35.1.6
lcsSetupWlanMngmtRadiusServerProfilesEntryAccountProtocol OBJECT-TYPE
    SYNTAX     INTEGER {
                  eRadius (0),
                  eRadsec (1)
            }
    MAX-ACCESS read-write
    STATUS     current
    DESCRIPTION
            "-- empty --"
    ::= { lcsSetupWlanMngmtRadiusServerProfilesEntry 6 }

-- {COLUMN} 1.3.6.1.4.1.2356.11.2.37.35.1.7
lcsSetupWlanMngmtRadiusServerProfilesEntryAccessIp OBJECT-TYPE
    SYNTAX     IpAddress
    MAX-ACCESS read-write
    STATUS     current
    DESCRIPTION
            "-- empty --"
    ::= { lcsSetupWlanMngmtRadiusServerProfilesEntry 7 }

-- {COLUMN} 1.3.6.1.4.1.2356.11.2.37.35.1.8
lcsSetupWlanMngmtRadiusServerProfilesEntryAccessPort OBJECT-TYPE
    SYNTAX     Integer32 (0..65535)
    MAX-ACCESS read-write
    STATUS     current
    DESCRIPTION
            "-- empty --"
    ::= { lcsSetupWlanMngmtRadiusServerProfilesEntry 8 }

-- {COLUMN} 1.3.6.1.4.1.2356.11.2.37.35.1.9
lcsSetupWlanMngmtRadiusServerProfilesEntryAccessSecret OBJECT-TYPE
    SYNTAX     DisplayString (SIZE(0..64))
    MAX-ACCESS read-write
    STATUS     current
    DESCRIPTION
            "-- empty --"
    ::= { lcsSetupWlanMngmtRadiusServerProfilesEntry 9 }

-- {COLUMN} 1.3.6.1.4.1.2356.11.2.37.35.1.10
lcsSetupWlanMngmtRadiusServerProfilesEntryAccessLoopback OBJECT-TYPE
    SYNTAX     DisplayString (SIZE(0..16))
    MAX-ACCESS read-write
    STATUS     current
    DESCRIPTION
            "-- empty --"
    ::= { lcsSetupWlanMngmtRadiusServerProfilesEntry 10 }

-- {COLUMN} 1.3.6.1.4.1.2356.11.2.37.35.1.11
lcsSetupWlanMngmtRadiusServerProfilesEntryAccessProtocol OBJECT-TYPE
    SYNTAX     INTEGER {
                  eRadius (0),
                  eRadsec (1)
            }
    MAX-ACCESS read-write
    STATUS     current
    DESCRIPTION
            "-- empty --"
    ::= { lcsSetupWlanMngmtRadiusServerProfilesEntry 11 }

-- {COLUMN} 1.3.6.1.4.1.2356.11.2.37.35.1.12
lcsSetupWlanMngmtRadiusServerProfilesEntryBackup OBJECT-TYPE
    SYNTAX     DisplayString (SIZE(0..16))
    MAX-ACCESS read-write
    STATUS     current
    DESCRIPTION
            "-- empty --"
    ::= { lcsSetupWlanMngmtRadiusServerProfilesEntry 12 }

-- {SCALAR} 1.3.6.1.4.1.2356.11.2.37.36
lcsSetupWlanMngmtCapwapOperating OBJECT-TYPE
    SYNTAX     INTEGER {
                  eNo (0),
                  eYes (1)
            }
    MAX-ACCESS read-write
    STATUS     current
    DESCRIPTION
            "-- empty --"
    ::= { lcsSetupWlanMngmt 36 }

-- {SCALAR} 1.3.6.1.4.1.2356.11.2.37.37
lcsSetupWlanMngmtPreference OBJECT-TYPE
    SYNTAX     Integer32 (0..255)
    MAX-ACCESS read-write
    STATUS     current
    DESCRIPTION
            "-- empty --"
    ::= { lcsSetupWlanMngmt 37 }

-- {NODE} 1.3.6.1.4.1.2356.11.2.37.40
lcsSetupWlanMngmtClSte OBJECT IDENTIFIER ::= { lcsSetupWlanMngmt 40 }

-- {SCALAR} 1.3.6.1.4.1.2356.11.2.37.40.11
lcsSetupWlanMngmtClSteTraceMac OBJECT-TYPE
    SYNTAX     MacAddress
    MAX-ACCESS read-write
    STATUS     current
    DESCRIPTION
            "-- empty --"
    ::= { lcsSetupWlanMngmtClSte 11 }

-- {SCALAR} 1.3.6.1.4.1.2356.11.2.37.40.17
lcsSetupWlanMngmtClSteAcquireStatisticalData OBJECT-TYPE
    SYNTAX     INTEGER {
                  eNo (0),
                  eYes (1)
            }
    MAX-ACCESS read-write
    STATUS     current
    DESCRIPTION
            "-- empty --"
    ::= { lcsSetupWlanMngmtClSte 17 }

-- {TABLE} 1.3.6.1.4.1.2356.11.2.37.40.19
lcsSetupWlanMngmtClSteProfilesTable OBJECT-TYPE
    SYNTAX     SEQUENCE OF LcsSetupWlanMngmtClSteProfilesEntry
    MAX-ACCESS not-accessible
    STATUS     current
    DESCRIPTION
            "-- empty --"
    ::= { lcsSetupWlanMngmtClSte 19 }

-- {ROW} 1.3.6.1.4.1.2356.11.2.37.40.19.1
lcsSetupWlanMngmtClSteProfilesEntry OBJECT-TYPE
    SYNTAX     LcsSetupWlanMngmtClSteProfilesEntry
    MAX-ACCESS not-accessible
    STATUS     current
    DESCRIPTION
            ""
    INDEX {
            lcsSetupWlanMngmtClSteProfilesEntryName
          }
    ::= { lcsSetupWlanMngmtClSteProfilesTable 1 }

LcsSetupWlanMngmtClSteProfilesEntry ::= SEQUENCE {
            lcsSetupWlanMngmtClSteProfilesEntryName DisplayString,
            lcsSetupWlanMngmtClSteProfilesEntryToleranceLevel Integer32,
            lcsSetupWlanMngmtClSteProfilesEntrySignalStrengthWeighting Integer32,
            lcsSetupWlanMngmtClSteProfilesEntryAssociatedClientsWeighting Integer32,
            lcsSetupWlanMngmtClSteProfilesEntryFrequencyBandWeighting Integer32,
            lcsSetupWlanMngmtClSteProfilesEntryPreferredBand INTEGER,
            lcsSetupWlanMngmtClSteProfilesEntryDisassociationThreshold Integer32,
            lcsSetupWlanMngmtClSteProfilesEntryTimeToDisassociation Integer32
    }

-- {COLUMN} 1.3.6.1.4.1.2356.11.2.37.40.19.1.1
lcsSetupWlanMngmtClSteProfilesEntryName OBJECT-TYPE
    SYNTAX     DisplayString (SIZE(0..31))
    MAX-ACCESS read-write
    STATUS     current
    DESCRIPTION
            "-- empty --"
    ::= { lcsSetupWlanMngmtClSteProfilesEntry 1 }

-- {COLUMN} 1.3.6.1.4.1.2356.11.2.37.40.19.1.2
lcsSetupWlanMngmtClSteProfilesEntryToleranceLevel OBJECT-TYPE
    SYNTAX     Integer32 (0..255)
    MAX-ACCESS read-write
    STATUS     current
    DESCRIPTION
            "-- empty --"
    ::= { lcsSetupWlanMngmtClSteProfilesEntry 2 }

-- {COLUMN} 1.3.6.1.4.1.2356.11.2.37.40.19.1.4
lcsSetupWlanMngmtClSteProfilesEntrySignalStrengthWeighting OBJECT-TYPE
    SYNTAX     Integer32 (0..2147483647)
    MAX-ACCESS read-write
    STATUS     current
    DESCRIPTION
            "-- empty --"
    ::= { lcsSetupWlanMngmtClSteProfilesEntry 4 }

-- {COLUMN} 1.3.6.1.4.1.2356.11.2.37.40.19.1.5
lcsSetupWlanMngmtClSteProfilesEntryAssociatedClientsWeighting OBJECT-TYPE
    SYNTAX     Integer32 (0..2147483647)
    MAX-ACCESS read-write
    STATUS     current
    DESCRIPTION
            "-- empty --"
    ::= { lcsSetupWlanMngmtClSteProfilesEntry 5 }

-- {COLUMN} 1.3.6.1.4.1.2356.11.2.37.40.19.1.6
lcsSetupWlanMngmtClSteProfilesEntryFrequencyBandWeighting OBJECT-TYPE
    SYNTAX     Integer32 (0..2147483647)
    MAX-ACCESS read-write
    STATUS     current
    DESCRIPTION
            "-- empty --"
    ::= { lcsSetupWlanMngmtClSteProfilesEntry 6 }

-- {COLUMN} 1.3.6.1.4.1.2356.11.2.37.40.19.1.9
lcsSetupWlanMngmtClSteProfilesEntryPreferredBand OBJECT-TYPE
    SYNTAX     INTEGER {
                  e24ghz (1),
                  e5ghz (2)
            }
    MAX-ACCESS read-write
    STATUS     current
    DESCRIPTION
            "-- empty --"
    ::= { lcsSetupWlanMngmtClSteProfilesEntry 9 }

-- {COLUMN} 1.3.6.1.4.1.2356.11.2.37.40.19.1.10
lcsSetupWlanMngmtClSteProfilesEntryDisassociationThreshold OBJECT-TYPE
    SYNTAX     Integer32 (0..255)
    MAX-ACCESS read-write
    STATUS     current
    DESCRIPTION
            "-- empty --"
    ::= { lcsSetupWlanMngmtClSteProfilesEntry 10 }

-- {COLUMN} 1.3.6.1.4.1.2356.11.2.37.40.19.1.11
lcsSetupWlanMngmtClSteProfilesEntryTimeToDisassociation OBJECT-TYPE
    SYNTAX     Integer32 (0..255)
    MAX-ACCESS read-write
    STATUS     current
    DESCRIPTION
            "-- empty --"
    ::= { lcsSetupWlanMngmtClSteProfilesEntry 11 }

-- {SCALAR} 1.3.6.1.4.1.2356.11.2.37.40.20
lcsSetupWlanMngmtClSteClientMacStatisticFilter OBJECT-TYPE
    SYNTAX     DisplayString (SIZE(0..251))
    MAX-ACCESS read-write
    STATUS     current
    DESCRIPTION
            "-- empty --"
    ::= { lcsSetupWlanMngmtClSte 20 }

-- {NODE} 1.3.6.1.4.1.2356.11.2.38
lcsSetupLldp OBJECT IDENTIFIER ::= { lcsSetup 38 }

-- {SCALAR} 1.3.6.1.4.1.2356.11.2.38.1
lcsSetupLldpMessageTxInterval OBJECT-TYPE
    SYNTAX     Integer32 (0..2147483647)
    MAX-ACCESS read-write
    STATUS     current
    DESCRIPTION
            "-- empty --"
    ::= { lcsSetupLldp 1 }

-- {SCALAR} 1.3.6.1.4.1.2356.11.2.38.2
lcsSetupLldpMessageTxHoldMultiplier OBJECT-TYPE
    SYNTAX     Integer32 (0..2147483647)
    MAX-ACCESS read-write
    STATUS     current
    DESCRIPTION
            "-- empty --"
    ::= { lcsSetupLldp 2 }

-- {SCALAR} 1.3.6.1.4.1.2356.11.2.38.3
lcsSetupLldpReinitDelay OBJECT-TYPE
    SYNTAX     Integer32 (0..2147483647)
    MAX-ACCESS read-write
    STATUS     current
    DESCRIPTION
            "-- empty --"
    ::= { lcsSetupLldp 3 }

-- {SCALAR} 1.3.6.1.4.1.2356.11.2.38.4
lcsSetupLldpTxDelay OBJECT-TYPE
    SYNTAX     Integer32 (0..2147483647)
    MAX-ACCESS read-write
    STATUS     current
    DESCRIPTION
            "-- empty --"
    ::= { lcsSetupLldp 4 }

-- {SCALAR} 1.3.6.1.4.1.2356.11.2.38.5
lcsSetupLldpNotificationInterval OBJECT-TYPE
    SYNTAX     Integer32 (0..2147483647)
    MAX-ACCESS read-write
    STATUS     current
    DESCRIPTION
            "-- empty --"
    ::= { lcsSetupLldp 5 }

-- {TABLE} 1.3.6.1.4.1.2356.11.2.38.6
lcsSetupLldpPortsTable OBJECT-TYPE
    SYNTAX     SEQUENCE OF LcsSetupLldpPortsEntry
    MAX-ACCESS not-accessible
    STATUS     current
    DESCRIPTION
            "-- empty --"
    ::= { lcsSetupLldp 6 }

-- {ROW} 1.3.6.1.4.1.2356.11.2.38.6.1
lcsSetupLldpPortsEntry OBJECT-TYPE
    SYNTAX     LcsSetupLldpPortsEntry
    MAX-ACCESS not-accessible
    STATUS     current
    DESCRIPTION
            ""
    INDEX {
            lcsSetupLldpPortsEntryName
          }
    ::= { lcsSetupLldpPortsTable 1 }

LcsSetupLldpPortsEntry ::= SEQUENCE {
            lcsSetupLldpPortsEntryName DisplayString,
            lcsSetupLldpPortsEntryAdminStatus INTEGER,
            lcsSetupLldpPortsEntryNotifications INTEGER,
            lcsSetupLldpPortsEntryTlvs BITS,
            lcsSetupLldpPortsEntryTlvs8023 BITS,
            lcsSetupLldpPortsEntryMaxNeighbours Integer32,
            lcsSetupLldpPortsEntryUpdateSource INTEGER,
            lcsSetupLldpPortsEntryTlvsLcs BITS
    }

-- {COLUMN} 1.3.6.1.4.1.2356.11.2.38.6.1.1
lcsSetupLldpPortsEntryName OBJECT-TYPE
    SYNTAX     DisplayString (SIZE(0..18))
    MAX-ACCESS read-only
    STATUS     current
    DESCRIPTION
            "-- empty --"
    ::= { lcsSetupLldpPortsEntry 1 }

-- {COLUMN} 1.3.6.1.4.1.2356.11.2.38.6.1.2
lcsSetupLldpPortsEntryAdminStatus OBJECT-TYPE
    SYNTAX     INTEGER {
                  eDisabled (0),
                  eTxOnly (1),
                  eRxOnly (2),
                  eRxTx (3)
            }
    MAX-ACCESS read-write
    STATUS     current
    DESCRIPTION
            "-- empty --"
    ::= { lcsSetupLldpPortsEntry 2 }

-- {COLUMN} 1.3.6.1.4.1.2356.11.2.38.6.1.3
lcsSetupLldpPortsEntryNotifications OBJECT-TYPE
    SYNTAX     INTEGER {
                  eNo (0),
                  eYes (1)
            }
    MAX-ACCESS read-write
    STATUS     current
    DESCRIPTION
            "-- empty --"
    ::= { lcsSetupLldpPortsEntry 3 }

-- {COLUMN} 1.3.6.1.4.1.2356.11.2.38.6.1.4
lcsSetupLldpPortsEntryTlvs OBJECT-TYPE
    SYNTAX     BITS {
                  ePortDescription (0),
                  eSysName (1),
                  eSysDescriptor (2),
                  eSysCaps (3),
                  eNone (7)
            }
    MAX-ACCESS read-write
    STATUS     current
    DESCRIPTION
            "-- empty --"
    ::= { lcsSetupLldpPortsEntry 4 }

-- {COLUMN} 1.3.6.1.4.1.2356.11.2.38.6.1.6
lcsSetupLldpPortsEntryTlvs8023 OBJECT-TYPE
    SYNTAX     BITS {
                  ePhyConfigStatus (0),
                  ePowerViaMdi (1),
                  eLinkAggregation (2),
                  eMaxFrameSize (3),
                  eNone (7)
            }
    MAX-ACCESS read-write
    STATUS     current
    DESCRIPTION
            "-- empty --"
    ::= { lcsSetupLldpPortsEntry 6 }

-- {COLUMN} 1.3.6.1.4.1.2356.11.2.38.6.1.7
lcsSetupLldpPortsEntryMaxNeighbours OBJECT-TYPE
    SYNTAX     Integer32 (0..65535)
    MAX-ACCESS read-write
    STATUS     current
    DESCRIPTION
            "-- empty --"
    ::= { lcsSetupLldpPortsEntry 7 }

-- {COLUMN} 1.3.6.1.4.1.2356.11.2.38.6.1.8
lcsSetupLldpPortsEntryUpdateSource OBJECT-TYPE
    SYNTAX     INTEGER {
                  eLldpOnly (0),
                  eOtherOnly (1),
                  eBoth (2),
                  eAuto (3)
            }
    MAX-ACCESS read-write
    STATUS     current
    DESCRIPTION
            "-- empty --"
    ::= { lcsSetupLldpPortsEntry 8 }

-- {COLUMN} 1.3.6.1.4.1.2356.11.2.38.6.1.9
lcsSetupLldpPortsEntryTlvsLcs OBJECT-TYPE
    SYNTAX     BITS {
                  eSsid (0),
                  eRadioChannel (1),
                  ePhyType (2),
                  eNone (7)
            }
    MAX-ACCESS read-write
    STATUS     current
    DESCRIPTION
            "-- empty --"
    ::= { lcsSetupLldpPortsEntry 9 }

-- {TABLE} 1.3.6.1.4.1.2356.11.2.38.7
lcsSetupLldpManagementAddressesTable OBJECT-TYPE
    SYNTAX     SEQUENCE OF LcsSetupLldpManagementAddressesEntry
    MAX-ACCESS not-accessible
    STATUS     current
    DESCRIPTION
            "-- empty --"
    ::= { lcsSetupLldp 7 }

-- {ROW} 1.3.6.1.4.1.2356.11.2.38.7.1
lcsSetupLldpManagementAddressesEntry OBJECT-TYPE
    SYNTAX     LcsSetupLldpManagementAddressesEntry
    MAX-ACCESS not-accessible
    STATUS     current
    DESCRIPTION
            ""
    INDEX {
            lcsSetupLldpManagementAddressesEntryNetworkName
          }
    ::= { lcsSetupLldpManagementAddressesTable 1 }

LcsSetupLldpManagementAddressesEntry ::= SEQUENCE {
            lcsSetupLldpManagementAddressesEntryNetworkName DisplayString,
            lcsSetupLldpManagementAddressesEntryPortList DisplayString
    }

-- {COLUMN} 1.3.6.1.4.1.2356.11.2.38.7.1.1
lcsSetupLldpManagementAddressesEntryNetworkName OBJECT-TYPE
    SYNTAX     DisplayString (SIZE(0..16))
    MAX-ACCESS read-write
    STATUS     current
    DESCRIPTION
            "-- empty --"
    ::= { lcsSetupLldpManagementAddressesEntry 1 }

-- {COLUMN} 1.3.6.1.4.1.2356.11.2.38.7.1.2
lcsSetupLldpManagementAddressesEntryPortList OBJECT-TYPE
    SYNTAX     DisplayString (SIZE(0..251))
    MAX-ACCESS read-write
    STATUS     current
    DESCRIPTION
            "-- empty --"
    ::= { lcsSetupLldpManagementAddressesEntry 2 }

-- {TABLE} 1.3.6.1.4.1.2356.11.2.38.8
lcsSetupLldpProtocolsTable OBJECT-TYPE
    SYNTAX     SEQUENCE OF LcsSetupLldpProtocolsEntry
    MAX-ACCESS not-accessible
    STATUS     current
    DESCRIPTION
            "-- empty --"
    ::= { lcsSetupLldp 8 }

-- {ROW} 1.3.6.1.4.1.2356.11.2.38.8.1
lcsSetupLldpProtocolsEntry OBJECT-TYPE
    SYNTAX     LcsSetupLldpProtocolsEntry
    MAX-ACCESS not-accessible
    STATUS     current
    DESCRIPTION
            ""
    INDEX {
            lcsSetupLldpProtocolsEntryProtocol
          }
    ::= { lcsSetupLldpProtocolsTable 1 }

LcsSetupLldpProtocolsEntry ::= SEQUENCE {
            lcsSetupLldpProtocolsEntryProtocol INTEGER,
            lcsSetupLldpProtocolsEntryPortList DisplayString
    }

-- {COLUMN} 1.3.6.1.4.1.2356.11.2.38.8.1.1
lcsSetupLldpProtocolsEntryProtocol OBJECT-TYPE
    SYNTAX     INTEGER {
                  eSpanningTree (1),
                  eRapidSpanningTree (2)
            }
    MAX-ACCESS read-only
    STATUS     current
    DESCRIPTION
            "-- empty --"
    ::= { lcsSetupLldpProtocolsEntry 1 }

-- {COLUMN} 1.3.6.1.4.1.2356.11.2.38.8.1.2
lcsSetupLldpProtocolsEntryPortList OBJECT-TYPE
    SYNTAX     DisplayString (SIZE(0..251))
    MAX-ACCESS read-write
    STATUS     current
    DESCRIPTION
            "-- empty --"
    ::= { lcsSetupLldpProtocolsEntry 2 }

-- {SCALAR} 1.3.6.1.4.1.2356.11.2.38.10
lcsSetupLldpOperating OBJECT-TYPE
    SYNTAX     INTEGER {
                  eNo (0),
                  eYes (1)
            }
    MAX-ACCESS read-write
    STATUS     current
    DESCRIPTION
            "-- empty --"
    ::= { lcsSetupLldp 10 }

-- {NODE} 1.3.6.1.4.1.2356.11.2.39
lcsSetupCerts OBJECT IDENTIFIER ::= { lcsSetup 39 }

-- {NODE} 1.3.6.1.4.1.2356.11.2.39.1
lcsSetupCertsScepClnt OBJECT IDENTIFIER ::= { lcsSetupCerts 1 }

-- {SCALAR} 1.3.6.1.4.1.2356.11.2.39.1.1
lcsSetupCertsScepClntScepOperating OBJECT-TYPE
    SYNTAX     INTEGER {
                  eNo (0),
                  eYes (1)
            }
    MAX-ACCESS read-write
    STATUS     current
    DESCRIPTION
            ""
    ::= { lcsSetupCertsScepClnt 1 }

-- {SCALAR} 1.3.6.1.4.1.2356.11.2.39.1.2
lcsSetupCertsScepClntDeviceCertificateUpdateBefore OBJECT-TYPE
    SYNTAX     Integer32 (0..2147483647)
    MAX-ACCESS read-write
    STATUS     current
    DESCRIPTION
            ""
    ::= { lcsSetupCertsScepClnt 2 }

-- {SCALAR} 1.3.6.1.4.1.2356.11.2.39.1.3
lcsSetupCertsScepClntCaCertificateUpdateBefore OBJECT-TYPE
    SYNTAX     Integer32 (0..2147483647)
    MAX-ACCESS read-write
    STATUS     current
    DESCRIPTION
            ""
    ::= { lcsSetupCertsScepClnt 3 }

-- {TABLE} 1.3.6.1.4.1.2356.11.2.39.1.7
lcsSetupCertsScepClntCertsTable OBJECT-TYPE
    SYNTAX     SEQUENCE OF LcsSetupCertsScepClntCertsEntry
    MAX-ACCESS not-accessible
    STATUS     current
    DESCRIPTION
            ""
    ::= { lcsSetupCertsScepClnt 7 }

-- {ROW} 1.3.6.1.4.1.2356.11.2.39.1.7.1
lcsSetupCertsScepClntCertsEntry OBJECT-TYPE
    SYNTAX     LcsSetupCertsScepClntCertsEntry
    MAX-ACCESS not-accessible
    STATUS     current
    DESCRIPTION
            ""
    INDEX {
            lcsSetupCertsScepClntCertsEntryName
          }
    ::= { lcsSetupCertsScepClntCertsTable 1 }

LcsSetupCertsScepClntCertsEntry ::= SEQUENCE {
            lcsSetupCertsScepClntCertsEntryName DisplayString,
            lcsSetupCertsScepClntCertsEntryCadn DisplayString,
            lcsSetupCertsScepClntCertsEntrySubject DisplayString,
            lcsSetupCertsScepClntCertsEntryChallengepwd DisplayString,
            lcsSetupCertsScepClntCertsEntrySubjectaltname DisplayString,
            lcsSetupCertsScepClntCertsEntryKeyusage DisplayString,
            lcsSetupCertsScepClntCertsEntryDevCertKeyl Integer32,
            lcsSetupCertsScepClntCertsEntryApplication INTEGER,
            lcsSetupCertsScepClntCertsEntryExtendedKeyusage DisplayString
    }

-- {COLUMN} 1.3.6.1.4.1.2356.11.2.39.1.7.1.1
lcsSetupCertsScepClntCertsEntryName OBJECT-TYPE
    SYNTAX     DisplayString (SIZE(0..16))
    MAX-ACCESS read-write
    STATUS     current
    DESCRIPTION
            ""
    ::= { lcsSetupCertsScepClntCertsEntry 1 }

-- {COLUMN} 1.3.6.1.4.1.2356.11.2.39.1.7.1.2
lcsSetupCertsScepClntCertsEntryCadn OBJECT-TYPE
    SYNTAX     DisplayString (SIZE(0..251))
    MAX-ACCESS read-write
    STATUS     current
    DESCRIPTION
            ""
    ::= { lcsSetupCertsScepClntCertsEntry 2 }

-- {COLUMN} 1.3.6.1.4.1.2356.11.2.39.1.7.1.3
lcsSetupCertsScepClntCertsEntrySubject OBJECT-TYPE
    SYNTAX     DisplayString (SIZE(0..251))
    MAX-ACCESS read-write
    STATUS     current
    DESCRIPTION
            ""
    ::= { lcsSetupCertsScepClntCertsEntry 3 }

-- {COLUMN} 1.3.6.1.4.1.2356.11.2.39.1.7.1.4
lcsSetupCertsScepClntCertsEntryChallengepwd OBJECT-TYPE
    SYNTAX     DisplayString (SIZE(0..251))
    MAX-ACCESS read-write
    STATUS     current
    DESCRIPTION
            ""
    ::= { lcsSetupCertsScepClntCertsEntry 4 }

-- {COLUMN} 1.3.6.1.4.1.2356.11.2.39.1.7.1.5
lcsSetupCertsScepClntCertsEntrySubjectaltname OBJECT-TYPE
    SYNTAX     DisplayString (SIZE(0..251))
    MAX-ACCESS read-write
    STATUS     current
    DESCRIPTION
            ""
    ::= { lcsSetupCertsScepClntCertsEntry 5 }

-- {COLUMN} 1.3.6.1.4.1.2356.11.2.39.1.7.1.6
lcsSetupCertsScepClntCertsEntryKeyusage OBJECT-TYPE
    SYNTAX     DisplayString (SIZE(0..251))
    MAX-ACCESS read-write
    STATUS     current
    DESCRIPTION
            ""
    ::= { lcsSetupCertsScepClntCertsEntry 6 }

-- {COLUMN} 1.3.6.1.4.1.2356.11.2.39.1.7.1.7
lcsSetupCertsScepClntCertsEntryDevCertKeyl OBJECT-TYPE
    SYNTAX     Integer32 (0..2147483647)
    MAX-ACCESS read-write
    STATUS     current
    DESCRIPTION
            ""
    ::= { lcsSetupCertsScepClntCertsEntry 7 }

-- {COLUMN} 1.3.6.1.4.1.2356.11.2.39.1.7.1.8
lcsSetupCertsScepClntCertsEntryApplication OBJECT-TYPE
    SYNTAX     INTEGER {
                  eUnconfigured (-1),
                  eVpn1 (0),
                  eWlanController (1),
                  eEapTls (3),
                  eVpn2 (5),
                  eVpn3 (6),
                  eVpn4 (7),
                  eVpn5 (8),
                  eVpn6 (9),
                  eVpn7 (10),
                  eVpn8 (11),
                  eVpn9 (12),
                  eDefault (13),
                  eCa (14),
                  eConfigsync (15),
                  eProvsrv (17),
                  eOcsp (18)
            }
    MAX-ACCESS read-write
    STATUS     current
    DESCRIPTION
            ""
    ::= { lcsSetupCertsScepClntCertsEntry 8 }

-- {COLUMN} 1.3.6.1.4.1.2356.11.2.39.1.7.1.9
lcsSetupCertsScepClntCertsEntryExtendedKeyusage OBJECT-TYPE
    SYNTAX     DisplayString (SIZE(0..251))
    MAX-ACCESS read-write
    STATUS     current
    DESCRIPTION
            ""
    ::= { lcsSetupCertsScepClntCertsEntry 9 }

-- {SCALAR} 1.3.6.1.4.1.2356.11.2.39.1.8
lcsSetupCertsScepClntReinit OBJECT-TYPE
    SYNTAX     DisplayString
    MAX-ACCESS read-write
    STATUS     current
    DESCRIPTION
            ""
    ::= { lcsSetupCertsScepClnt 8 }

-- {SCALAR} 1.3.6.1.4.1.2356.11.2.39.1.9
lcsSetupCertsScepClntUpdate OBJECT-TYPE
    SYNTAX     DisplayString
    MAX-ACCESS read-write
    STATUS     current
    DESCRIPTION
            ""
    ::= { lcsSetupCertsScepClnt 9 }

-- {SCALAR} 1.3.6.1.4.1.2356.11.2.39.1.10
lcsSetupCertsScepClntClearScepFilesystem OBJECT-TYPE
    SYNTAX     DisplayString
    MAX-ACCESS read-write
    STATUS     current
    DESCRIPTION
            ""
    ::= { lcsSetupCertsScepClnt 10 }

-- {SCALAR} 1.3.6.1.4.1.2356.11.2.39.1.11
lcsSetupCertsScepClntRetryAfterErrorInterval OBJECT-TYPE
    SYNTAX     Integer32 (0..2147483647)
    MAX-ACCESS read-write
    STATUS     current
    DESCRIPTION
            ""
    ::= { lcsSetupCertsScepClnt 11 }

-- {SCALAR} 1.3.6.1.4.1.2356.11.2.39.1.12
lcsSetupCertsScepClntCheckPendingRequestsInterval OBJECT-TYPE
    SYNTAX     Integer32 (0..2147483647)
    MAX-ACCESS read-write
    STATUS     current
    DESCRIPTION
            ""
    ::= { lcsSetupCertsScepClnt 12 }

-- {SCALAR} 1.3.6.1.4.1.2356.11.2.39.1.13
lcsSetupCertsScepClntTraceLevel OBJECT-TYPE
    SYNTAX     INTEGER {
                  eOnlyErrors (3),
                  eReduced (6),
                  eAll (7)
            }
    MAX-ACCESS read-write
    STATUS     current
    DESCRIPTION
            ""
    ::= { lcsSetupCertsScepClnt 13 }

-- {TABLE} 1.3.6.1.4.1.2356.11.2.39.1.14
lcsSetupCertsScepClntCasTable OBJECT-TYPE
    SYNTAX     SEQUENCE OF LcsSetupCertsScepClntCasEntry
    MAX-ACCESS not-accessible
    STATUS     current
    DESCRIPTION
            ""
    ::= { lcsSetupCertsScepClnt 14 }

-- {ROW} 1.3.6.1.4.1.2356.11.2.39.1.14.1
lcsSetupCertsScepClntCasEntry OBJECT-TYPE
    SYNTAX     LcsSetupCertsScepClntCasEntry
    MAX-ACCESS not-accessible
    STATUS     current
    DESCRIPTION
            ""
    INDEX {
            lcsSetupCertsScepClntCasEntryName
          }
    ::= { lcsSetupCertsScepClntCasTable 1 }

LcsSetupCertsScepClntCasEntry ::= SEQUENCE {
            lcsSetupCertsScepClntCasEntryName DisplayString,
            lcsSetupCertsScepClntCasEntryUrl DisplayString,
            lcsSetupCertsScepClntCasEntryDn DisplayString,
            lcsSetupCertsScepClntCasEntryEncAlg INTEGER,
            lcsSetupCertsScepClntCasEntryIdentifier DisplayString,
            lcsSetupCertsScepClntCasEntryCaSignatureAlgorithm INTEGER,
            lcsSetupCertsScepClntCasEntryRaAutoapprove INTEGER,
            lcsSetupCertsScepClntCasEntryCaFingerprintAlgorithm INTEGER,
            lcsSetupCertsScepClntCasEntryCaFingerprint DisplayString,
            lcsSetupCertsScepClntCasEntryLoopbackAddr DisplayString
    }

-- {COLUMN} 1.3.6.1.4.1.2356.11.2.39.1.14.1.1
lcsSetupCertsScepClntCasEntryName OBJECT-TYPE
    SYNTAX     DisplayString (SIZE(0..16))
    MAX-ACCESS read-write
    STATUS     current
    DESCRIPTION
            ""
    ::= { lcsSetupCertsScepClntCasEntry 1 }

-- {COLUMN} 1.3.6.1.4.1.2356.11.2.39.1.14.1.2
lcsSetupCertsScepClntCasEntryUrl OBJECT-TYPE
    SYNTAX     DisplayString (SIZE(0..251))
    MAX-ACCESS read-write
    STATUS     current
    DESCRIPTION
            ""
    ::= { lcsSetupCertsScepClntCasEntry 2 }

-- {COLUMN} 1.3.6.1.4.1.2356.11.2.39.1.14.1.3
lcsSetupCertsScepClntCasEntryDn OBJECT-TYPE
    SYNTAX     DisplayString (SIZE(0..251))
    MAX-ACCESS read-write
    STATUS     current
    DESCRIPTION
            ""
    ::= { lcsSetupCertsScepClntCasEntry 3 }

-- {COLUMN} 1.3.6.1.4.1.2356.11.2.39.1.14.1.4
lcsSetupCertsScepClntCasEntryEncAlg OBJECT-TYPE
    SYNTAX     INTEGER {
                  eDes (0),
                  e3des (1),
                  eBlowfish (2),
                  eAes128 (3),
                  eAes192 (4),
                  eAes256 (5)
            }
    MAX-ACCESS read-write
    STATUS     current
    DESCRIPTION
            ""
    ::= { lcsSetupCertsScepClntCasEntry 4 }

-- {COLUMN} 1.3.6.1.4.1.2356.11.2.39.1.14.1.5
lcsSetupCertsScepClntCasEntryIdentifier OBJECT-TYPE
    SYNTAX     DisplayString (SIZE(0..251))
    MAX-ACCESS read-write
    STATUS     current
    DESCRIPTION
            ""
    ::= { lcsSetupCertsScepClntCasEntry 5 }

-- {COLUMN} 1.3.6.1.4.1.2356.11.2.39.1.14.1.6
lcsSetupCertsScepClntCasEntryCaSignatureAlgorithm OBJECT-TYPE
    SYNTAX     INTEGER {
                  eMd5 (0),
                  eSha1 (1),
                  eSha256 (2),
                  eSha384 (3),
                  eSha512 (4)
            }
    MAX-ACCESS read-write
    STATUS     current
    DESCRIPTION
            ""
    ::= { lcsSetupCertsScepClntCasEntry 6 }

-- {COLUMN} 1.3.6.1.4.1.2356.11.2.39.1.14.1.7
lcsSetupCertsScepClntCasEntryRaAutoapprove OBJECT-TYPE
    SYNTAX     INTEGER {
                  eNo (0),
                  eYes (1)
            }
    MAX-ACCESS read-write
    STATUS     current
    DESCRIPTION
            ""
    ::= { lcsSetupCertsScepClntCasEntry 7 }

-- {COLUMN} 1.3.6.1.4.1.2356.11.2.39.1.14.1.8
lcsSetupCertsScepClntCasEntryCaFingerprintAlgorithm OBJECT-TYPE
    SYNTAX     INTEGER {
                  eOff (0),
                  eSha1 (1),
                  eMd5 (2),
                  eSha256 (3),
                  eSha384 (4),
                  eSha512 (5)
            }
    MAX-ACCESS read-write
    STATUS     current
    DESCRIPTION
            ""
    ::= { lcsSetupCertsScepClntCasEntry 8 }

-- {COLUMN} 1.3.6.1.4.1.2356.11.2.39.1.14.1.9
lcsSetupCertsScepClntCasEntryCaFingerprint OBJECT-TYPE
    SYNTAX     DisplayString (SIZE(0..192))
    MAX-ACCESS read-write
    STATUS     current
    DESCRIPTION
            ""
    ::= { lcsSetupCertsScepClntCasEntry 9 }

-- {COLUMN} 1.3.6.1.4.1.2356.11.2.39.1.14.1.11
lcsSetupCertsScepClntCasEntryLoopbackAddr OBJECT-TYPE
    SYNTAX     DisplayString (SIZE(0..16))
    MAX-ACCESS read-write
    STATUS     current
    DESCRIPTION
            ""
    ::= { lcsSetupCertsScepClntCasEntry 11 }

-- {NODE} 1.3.6.1.4.1.2356.11.2.39.1.17
lcsSetupCertsScepClntLogging OBJECT IDENTIFIER ::= { lcsSetupCertsScepClnt 17 }

-- {SCALAR} 1.3.6.1.4.1.2356.11.2.39.1.17.1
lcsSetupCertsScepClntLoggingEMail OBJECT-TYPE
    SYNTAX     INTEGER {
                  eNo (0),
                  eYes (1)
            }
    MAX-ACCESS read-write
    STATUS     current
    DESCRIPTION
            "-- empty --"
    ::= { lcsSetupCertsScepClntLogging 1 }

-- {SCALAR} 1.3.6.1.4.1.2356.11.2.39.1.17.2
lcsSetupCertsScepClntLoggingSyslog OBJECT-TYPE
    SYNTAX     INTEGER {
                  eNo (0),
                  eYes (1)
            }
    MAX-ACCESS read-write
    STATUS     current
    DESCRIPTION
            "-- empty --"
    ::= { lcsSetupCertsScepClntLogging 2 }

-- {SCALAR} 1.3.6.1.4.1.2356.11.2.39.1.17.3
lcsSetupCertsScepClntLoggingEMailReceiver OBJECT-TYPE
    SYNTAX     DisplayString (SIZE(0..254))
    MAX-ACCESS read-write
    STATUS     current
    DESCRIPTION
            "-- empty --"
    ::= { lcsSetupCertsScepClntLogging 3 }

-- {SCALAR} 1.3.6.1.4.1.2356.11.2.39.1.17.4
lcsSetupCertsScepClntLoggingExpirationReminderBefore OBJECT-TYPE
    SYNTAX     Integer32 (0..65535)
    MAX-ACCESS read-write
    STATUS     current
    DESCRIPTION
            "-- empty --"
    ::= { lcsSetupCertsScepClntLogging 4 }

-- {NODE} 1.3.6.1.4.1.2356.11.2.39.1.18
lcsSetupCertsScepClntSslNew OBJECT IDENTIFIER ::= { lcsSetupCertsScepClnt 18 }

-- {SCALAR} 1.3.6.1.4.1.2356.11.2.39.1.18.1
lcsSetupCertsScepClntSslNewVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupCertsScepClntSslNew 1 }

-- {SCALAR} 1.3.6.1.4.1.2356.11.2.39.1.18.2
lcsSetupCertsScepClntSslNewKeyexAlgorithms OBJECT-TYPE
    SYNTAX     BITS {
                  eEcdhe (27),
                  eDhe (29),
                  eRsa (31)
            }
    MAX-ACCESS read-write
    STATUS     current
    DESCRIPTION
            "-- empty --"
    ::= { lcsSetupCertsScepClntSslNew 2 }

-- {SCALAR} 1.3.6.1.4.1.2356.11.2.39.1.18.3
lcsSetupCertsScepClntSslNewCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupCertsScepClntSslNew 3 }

-- {SCALAR} 1.3.6.1.4.1.2356.11.2.39.1.18.4
lcsSetupCertsScepClntSslNewHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupCertsScepClntSslNew 4 }

-- {SCALAR} 1.3.6.1.4.1.2356.11.2.39.1.18.5
lcsSetupCertsScepClntSslNewPreferPfs OBJECT-TYPE
    SYNTAX     BITS {
                  eNo (0),
                  eYes (7)
            }
    MAX-ACCESS read-write
    STATUS     current
    DESCRIPTION
            "-- empty --"
    ::= { lcsSetupCertsScepClntSslNew 5 }

-- {SCALAR} 1.3.6.1.4.1.2356.11.2.39.1.18.6
lcsSetupCertsScepClntSslNewRenegotiations OBJECT-TYPE
    SYNTAX     INTEGER {
                  eForbidden (0),
                  eAllowed (1),
                  eIgnored (2)
            }
    MAX-ACCESS read-write
    STATUS     current
    DESCRIPTION
            "-- empty --"
    ::= { lcsSetupCertsScepClntSslNew 6 }

-- {SCALAR} 1.3.6.1.4.1.2356.11.2.39.1.18.7
lcsSetupCertsScepClntSslNewEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupCertsScepClntSslNew 7 }

-- {SCALAR} 1.3.6.1.4.1.2356.11.2.39.1.18.21
lcsSetupCertsScepClntSslNewSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupCertsScepClntSslNew 21 }

-- {NODE} 1.3.6.1.4.1.2356.11.2.39.2
lcsSetupCertsScepCa OBJECT IDENTIFIER ::= { lcsSetupCerts 2 }

-- {SCALAR} 1.3.6.1.4.1.2356.11.2.39.2.1
lcsSetupCertsScepCaOperating OBJECT-TYPE
    SYNTAX     INTEGER {
                  eNo (0),
                  eYes (1)
            }
    MAX-ACCESS read-write
    STATUS     current
    DESCRIPTION
            ""
    ::= { lcsSetupCertsScepCa 1 }

-- {NODE} 1.3.6.1.4.1.2356.11.2.39.2.2
lcsSetupCertsScepCaCaCerts OBJECT IDENTIFIER ::= { lcsSetupCertsScepCa 2 }

-- {SCALAR} 1.3.6.1.4.1.2356.11.2.39.2.2.1
lcsSetupCertsScepCaCaCertsCaDistingName OBJECT-TYPE
    SYNTAX     DisplayString (SIZE(0..251))
    MAX-ACCESS read-write
    STATUS     current
    DESCRIPTION
            "CA distinguished name"
    ::= { lcsSetupCertsScepCaCaCerts 1 }

-- {SCALAR} 1.3.6.1.4.1.2356.11.2.39.2.2.3
lcsSetupCertsScepCaCaCertsAlternativeName OBJECT-TYPE
    SYNTAX     DisplayString (SIZE(0..251))
    MAX-ACCESS read-write
    STATUS     current
    DESCRIPTION
            ""
    ::= { lcsSetupCertsScepCaCaCerts 3 }

-- {SCALAR} 1.3.6.1.4.1.2356.11.2.39.2.2.4
lcsSetupCertsScepCaCaCertsRsaKeyLength OBJECT-TYPE
    SYNTAX     INTEGER {
                  e1024 (1024),
                  e2048 (2048),
                  e3072 (3072),
                  e4096 (4096),
                  e8192 (8192)
            }
    MAX-ACCESS read-write
    STATUS     current
    DESCRIPTION
            ""
    ::= { lcsSetupCertsScepCaCaCerts 4 }

-- {SCALAR} 1.3.6.1.4.1.2356.11.2.39.2.2.5
lcsSetupCertsScepCaCaCertsValidityPeriod OBJECT-TYPE
    SYNTAX     Integer32 (0..65535)
    MAX-ACCESS read-write
    STATUS     current
    DESCRIPTION
            ""
    ::= { lcsSetupCertsScepCaCaCerts 5 }

-- {SCALAR} 1.3.6.1.4.1.2356.11.2.39.2.2.6
lcsSetupCertsScepCaCaCertsUpdateCaCertificatesBeforeExpiration OBJECT-TYPE
    SYNTAX     Integer32 (0..65535)
    MAX-ACCESS read-write
    STATUS     current
    DESCRIPTION
            ""
    ::= { lcsSetupCertsScepCaCaCerts 6 }

-- {SCALAR} 1.3.6.1.4.1.2356.11.2.39.2.2.8
lcsSetupCertsScepCaCaCertsRaDistinguishedName OBJECT-TYPE
    SYNTAX     DisplayString (SIZE(0..251))
    MAX-ACCESS read-write
    STATUS     current
    DESCRIPTION
            ""
    ::= { lcsSetupCertsScepCaCaCerts 8 }

-- {SCALAR} 1.3.6.1.4.1.2356.11.2.39.2.2.9
lcsSetupCertsScepCaCaCertsCreateNewCaCertificates OBJECT-TYPE
    SYNTAX     DisplayString
    MAX-ACCESS read-write
    STATUS     current
    DESCRIPTION
            ""
    ::= { lcsSetupCertsScepCaCaCerts 9 }

-- {SCALAR} 1.3.6.1.4.1.2356.11.2.39.2.2.10
lcsSetupCertsScepCaCaCertsCreatePkcs12BackupFiles OBJECT-TYPE
    SYNTAX     DisplayString
    MAX-ACCESS read-write
    STATUS     current
    DESCRIPTION
            ""
    ::= { lcsSetupCertsScepCaCaCerts 10 }

-- {SCALAR} 1.3.6.1.4.1.2356.11.2.39.2.2.11
lcsSetupCertsScepCaCaCertsRestoreCertificatesFromBackup OBJECT-TYPE
    SYNTAX     DisplayString
    MAX-ACCESS read-write
    STATUS     current
    DESCRIPTION
            ""
    ::= { lcsSetupCertsScepCaCaCerts 11 }

-- {SCALAR} 1.3.6.1.4.1.2356.11.2.39.2.3
lcsSetupCertsScepCaEncryptionAlgorithm OBJECT-TYPE
    SYNTAX     INTEGER {
                  eDes (0),
                  e3des (1),
                  eBlowfish (2),
                  eAes128 (3),
                  eAes192 (4),
                  eAes256 (5)
            }
    MAX-ACCESS read-write
    STATUS     current
    DESCRIPTION
            ""
    ::= { lcsSetupCertsScepCa 3 }

-- {SCALAR} 1.3.6.1.4.1.2356.11.2.39.2.4
lcsSetupCertsScepCaRaAutoapprove OBJECT-TYPE
    SYNTAX     INTEGER {
                  eNo (0),
                  eYes (1)
            }
    MAX-ACCESS read-write
    STATUS     current
    DESCRIPTION
            ""
    ::= { lcsSetupCertsScepCa 4 }

-- {NODE} 1.3.6.1.4.1.2356.11.2.39.2.5
lcsSetupCertsScepCaClientCerts OBJECT IDENTIFIER ::= { lcsSetupCertsScepCa 5 }

-- {SCALAR} 1.3.6.1.4.1.2356.11.2.39.2.5.1
lcsSetupCertsScepCaClientCertsValidityPeriod OBJECT-TYPE
    SYNTAX     Integer32 (0..65535)
    MAX-ACCESS read-write
    STATUS     current
    DESCRIPTION
            ""
    ::= { lcsSetupCertsScepCaClientCerts 1 }

-- {TABLE} 1.3.6.1.4.1.2356.11.2.39.2.5.3
lcsSetupCertsScepCaClientCertsChallPasswdsTable OBJECT-TYPE
    SYNTAX     SEQUENCE OF LcsSetupCertsScepCaClientCertsChallPasswdsEntry
    MAX-ACCESS not-accessible
    STATUS     current
    DESCRIPTION
            "challange passwords"
    ::= { lcsSetupCertsScepCaClientCerts 3 }

-- {ROW} 1.3.6.1.4.1.2356.11.2.39.2.5.3.1
lcsSetupCertsScepCaClientCertsChallPasswdsEntry OBJECT-TYPE
    SYNTAX     LcsSetupCertsScepCaClientCertsChallPasswdsEntry
    MAX-ACCESS not-accessible
    STATUS     current
    DESCRIPTION
            ""
    INDEX {
            lcsSetupCertsScepCaClientCertsChallPasswdsEntryIndex
          }
    ::= { lcsSetupCertsScepCaClientCertsChallPasswdsTable 1 }

LcsSetupCertsScepCaClientCertsChallPasswdsEntry ::= SEQUENCE {
            lcsSetupCertsScepCaClientCertsChallPasswdsEntryIndex Integer32,
            lcsSetupCertsScepCaClientCertsChallPasswdsEntrySubjDistngName DisplayString,
            lcsSetupCertsScepCaClientCertsChallPasswdsEntryMacAddress DisplayString,
            lcsSetupCertsScepCaClientCertsChallPasswdsEntryChallenge DisplayString,
            lcsSetupCertsScepCaClientCertsChallPasswdsEntryValidity INTEGER
    }

-- {COLUMN} 1.3.6.1.4.1.2356.11.2.39.2.5.3.1.1
lcsSetupCertsScepCaClientCertsChallPasswdsEntryIndex OBJECT-TYPE
    SYNTAX     Integer32 (0..2147483647)
    MAX-ACCESS read-write
    STATUS     current
    DESCRIPTION
            ""
    ::= { lcsSetupCertsScepCaClientCertsChallPasswdsEntry 1 }

-- {COLUMN} 1.3.6.1.4.1.2356.11.2.39.2.5.3.1.2
lcsSetupCertsScepCaClientCertsChallPasswdsEntrySubjDistngName OBJECT-TYPE
    SYNTAX     DisplayString (SIZE(0..251))
    MAX-ACCESS read-write
    STATUS     current
    DESCRIPTION
            "subject distinguished name"
    ::= { lcsSetupCertsScepCaClientCertsChallPasswdsEntry 2 }

-- {COLUMN} 1.3.6.1.4.1.2356.11.2.39.2.5.3.1.3
lcsSetupCertsScepCaClientCertsChallPasswdsEntryMacAddress OBJECT-TYPE
    SYNTAX     DisplayString (SIZE(0..12))
    MAX-ACCESS read-write
    STATUS     current
    DESCRIPTION
            ""
    ::= { lcsSetupCertsScepCaClientCertsChallPasswdsEntry 3 }

-- {COLUMN} 1.3.6.1.4.1.2356.11.2.39.2.5.3.1.4
lcsSetupCertsScepCaClientCertsChallPasswdsEntryChallenge OBJECT-TYPE
    SYNTAX     DisplayString (SIZE(0..16))
    MAX-ACCESS read-write
    STATUS     current
    DESCRIPTION
            ""
    ::= { lcsSetupCertsScepCaClientCertsChallPasswdsEntry 4 }

-- {COLUMN} 1.3.6.1.4.1.2356.11.2.39.2.5.3.1.5
lcsSetupCertsScepCaClientCertsChallPasswdsEntryValidity OBJECT-TYPE
    SYNTAX     INTEGER {
                  ePermanently (0),
                  eOneTime (1)
            }
    MAX-ACCESS read-write
    STATUS     current
    DESCRIPTION
            ""
    ::= { lcsSetupCertsScepCaClientCertsChallPasswdsEntry 5 }

-- {SCALAR} 1.3.6.1.4.1.2356.11.2.39.2.5.4
lcsSetupCertsScepCaClientCertsGeneralChallengePassword OBJECT-TYPE
    SYNTAX     DisplayString (SIZE(0..16))
    MAX-ACCESS read-write
    STATUS     current
    DESCRIPTION
            ""
    ::= { lcsSetupCertsScepCaClientCerts 4 }

-- {SCALAR} 1.3.6.1.4.1.2356.11.2.39.2.6
lcsSetupCertsScepCaSignatureAlgorithm OBJECT-TYPE
    SYNTAX     INTEGER {
                  eMd5 (0),
                  eSha1 (1),
                  eSha256 (2),
                  eSha384 (3),
                  eSha512 (4)
            }
    MAX-ACCESS read-write
    STATUS     current
    DESCRIPTION
            ""
    ::= { lcsSetupCertsScepCa 6 }

-- {SCALAR} 1.3.6.1.4.1.2356.11.2.39.2.7
lcsSetupCertsScepCaFingerprintAlgorithm OBJECT-TYPE
    SYNTAX     INTEGER {
                  eMd5 (0),
                  eSha1 (1),
                  eSha256 (2),
                  eSha384 (3),
                  eSha512 (4)
            }
    MAX-ACCESS read-write
    STATUS     current
    DESCRIPTION
            ""
    ::= { lcsSetupCertsScepCa 7 }

-- {NODE} 1.3.6.1.4.1.2356.11.2.39.2.8
lcsSetupCertsScepCaCertRevLists OBJECT IDENTIFIER ::= { lcsSetupCertsScepCa 8 }

-- {SCALAR} 1.3.6.1.4.1.2356.11.2.39.2.8.1
lcsSetupCertsScepCaCertRevListsCrlUpdateInterval OBJECT-TYPE
    SYNTAX     Integer32 (0..2147483647)
    MAX-ACCESS read-write
    STATUS     current
    DESCRIPTION
            ""
    ::= { lcsSetupCertsScepCaCertRevLists 1 }

-- {SCALAR} 1.3.6.1.4.1.2356.11.2.39.2.8.2
lcsSetupCertsScepCaCertRevListsCrlDistributionPointHostname OBJECT-TYPE
    SYNTAX     DisplayString (SIZE(0..63))
    MAX-ACCESS read-write
    STATUS     current
    DESCRIPTION
            ""
    ::= { lcsSetupCertsScepCaCertRevLists 2 }

-- {SCALAR} 1.3.6.1.4.1.2356.11.2.39.2.8.3
lcsSetupCertsScepCaCertRevListsCreateNewCrl OBJECT-TYPE
    SYNTAX     DisplayString
    MAX-ACCESS read-write
    STATUS     current
    DESCRIPTION
            ""
    ::= { lcsSetupCertsScepCaCertRevLists 3 }

-- {TABLE} 1.3.6.1.4.1.2356.11.2.39.2.8.4
lcsSetupCertsScepCaCertRevListsAltDistPtsTable OBJECT-TYPE
    SYNTAX     SEQUENCE OF LcsSetupCertsScepCaCertRevListsAltDistPtsEntry
    MAX-ACCESS not-accessible
    STATUS     current
    DESCRIPTION
            ""
    ::= { lcsSetupCertsScepCaCertRevLists 4 }

-- {ROW} 1.3.6.1.4.1.2356.11.2.39.2.8.4.1
lcsSetupCertsScepCaCertRevListsAltDistPtsEntry OBJECT-TYPE
    SYNTAX     LcsSetupCertsScepCaCertRevListsAltDistPtsEntry
    MAX-ACCESS not-accessible
    STATUS     current
    DESCRIPTION
            ""
    INDEX {
            lcsSetupCertsScepCaCertRevListsAltDistPtsEntryHostname
          }
    ::= { lcsSetupCertsScepCaCertRevListsAltDistPtsTable 1 }

LcsSetupCertsScepCaCertRevListsAltDistPtsEntry ::= SEQUENCE {
            lcsSetupCertsScepCaCertRevListsAltDistPtsEntryHostname DisplayString
    }

-- {COLUMN} 1.3.6.1.4.1.2356.11.2.39.2.8.4.1.1
lcsSetupCertsScepCaCertRevListsAltDistPtsEntryHostname OBJECT-TYPE
    SYNTAX     DisplayString (SIZE(0..63))
    MAX-ACCESS read-write
    STATUS     current
    DESCRIPTION
            "-- empty --"
    ::= { lcsSetupCertsScepCaCertRevListsAltDistPtsEntry 1 }

-- {SCALAR} 1.3.6.1.4.1.2356.11.2.39.2.8.5
lcsSetupCertsScepCaCertRevListsProtocol OBJECT-TYPE
    SYNTAX     INTEGER {
                  eHttp (0),
                  eHttps (1)
            }
    MAX-ACCESS read-write
    STATUS     current
    DESCRIPTION
            "-- empty --"
    ::= { lcsSetupCertsScepCaCertRevLists 5 }

-- {SCALAR} 1.3.6.1.4.1.2356.11.2.39.2.9
lcsSetupCertsScepCaReinitialize OBJECT-TYPE
    SYNTAX     DisplayString
    MAX-ACCESS read-write
    STATUS     current
    DESCRIPTION
            ""
    ::= { lcsSetupCertsScepCa 9 }

-- {NODE} 1.3.6.1.4.1.2356.11.2.39.2.10
lcsSetupCertsScepCaLogging OBJECT IDENTIFIER ::= { lcsSetupCertsScepCa 10 }

-- {SCALAR} 1.3.6.1.4.1.2356.11.2.39.2.10.1
lcsSetupCertsScepCaLoggingEMail OBJECT-TYPE
    SYNTAX     INTEGER {
                  eNo (0),
                  eYes (1)
            }
    MAX-ACCESS read-write
    STATUS     current
    DESCRIPTION
            ""
    ::= { lcsSetupCertsScepCaLogging 1 }

-- {SCALAR} 1.3.6.1.4.1.2356.11.2.39.2.10.2
lcsSetupCertsScepCaLoggingSyslog OBJECT-TYPE
    SYNTAX     INTEGER {
                  eNo (0),
                  eYes (1)
            }
    MAX-ACCESS read-write
    STATUS     current
    DESCRIPTION
            ""
    ::= { lcsSetupCertsScepCaLogging 2 }

-- {SCALAR} 1.3.6.1.4.1.2356.11.2.39.2.10.3
lcsSetupCertsScepCaLoggingEMailReceiver OBJECT-TYPE
    SYNTAX     DisplayString (SIZE(0..63))
    MAX-ACCESS read-write
    STATUS     current
    DESCRIPTION
            ""
    ::= { lcsSetupCertsScepCaLogging 3 }

-- {SCALAR} 1.3.6.1.4.1.2356.11.2.39.2.10.4
lcsSetupCertsScepCaLoggingSendBackupReminder OBJECT-TYPE
    SYNTAX     INTEGER {
                  eNo (0),
                  eYes (1)
            }
    MAX-ACCESS read-write
    STATUS     current
    DESCRIPTION
            ""
    ::= { lcsSetupCertsScepCaLogging 4 }

-- {SCALAR} 1.3.6.1.4.1.2356.11.2.39.2.11
lcsSetupCertsScepCaRootCa OBJECT-TYPE
    SYNTAX     INTEGER {
                  eNo (0),
                  eYes (1)
            }
    MAX-ACCESS read-write
    STATUS     current
    DESCRIPTION
            "-- empty --"
    ::= { lcsSetupCertsScepCa 11 }

-- {SCALAR} 1.3.6.1.4.1.2356.11.2.39.2.12
lcsSetupCertsScepCaCaPathLength OBJECT-TYPE
    SYNTAX     Integer32 (0..65535)
    MAX-ACCESS read-write
    STATUS     current
    DESCRIPTION
            "-- empty --"
    ::= { lcsSetupCertsScepCa 12 }

-- {NODE} 1.3.6.1.4.1.2356.11.2.39.2.13
lcsSetupCertsScepCaSubCa OBJECT IDENTIFIER ::= { lcsSetupCertsScepCa 13 }

-- {SCALAR} 1.3.6.1.4.1.2356.11.2.39.2.13.1
lcsSetupCertsScepCaSubCaAutoGeneratedRequest OBJECT-TYPE
    SYNTAX     INTEGER {
                  eNo (0),
                  eYes (1)
            }
    MAX-ACCESS read-write
    STATUS     current
    DESCRIPTION
            "-- empty --"
    ::= { lcsSetupCertsScepCaSubCa 1 }

-- {SCALAR} 1.3.6.1.4.1.2356.11.2.39.2.13.2
lcsSetupCertsScepCaSubCaCadn OBJECT-TYPE
    SYNTAX     DisplayString (SIZE(0..100))
    MAX-ACCESS read-write
    STATUS     current
    DESCRIPTION
            "-- empty --"
    ::= { lcsSetupCertsScepCaSubCa 2 }

-- {SCALAR} 1.3.6.1.4.1.2356.11.2.39.2.13.3
lcsSetupCertsScepCaSubCaChallengePwd OBJECT-TYPE
    SYNTAX     DisplayString (SIZE(0..16))
    MAX-ACCESS read-write
    STATUS     current
    DESCRIPTION
            "-- empty --"
    ::= { lcsSetupCertsScepCaSubCa 3 }

-- {SCALAR} 1.3.6.1.4.1.2356.11.2.39.2.13.4
lcsSetupCertsScepCaSubCaExtKeyUsage OBJECT-TYPE
    SYNTAX     DisplayString (SIZE(0..100))
    MAX-ACCESS read-write
    STATUS     current
    DESCRIPTION
            "-- empty --"
    ::= { lcsSetupCertsScepCaSubCa 4 }

-- {SCALAR} 1.3.6.1.4.1.2356.11.2.39.2.13.5
lcsSetupCertsScepCaSubCaCertKeyUsage OBJECT-TYPE
    SYNTAX     DisplayString (SIZE(0..100))
    MAX-ACCESS read-write
    STATUS     current
    DESCRIPTION
            "-- empty --"
    ::= { lcsSetupCertsScepCaSubCa 5 }

-- {SCALAR} 1.3.6.1.4.1.2356.11.2.39.2.13.8
lcsSetupCertsScepCaSubCaCaUrlAddress OBJECT-TYPE
    SYNTAX     DisplayString (SIZE(0..251))
    MAX-ACCESS read-write
    STATUS     current
    DESCRIPTION
            "-- empty --"
    ::= { lcsSetupCertsScepCaSubCa 8 }

-- {SCALAR} 1.3.6.1.4.1.2356.11.2.39.2.13.9
lcsSetupCertsScepCaSubCaRestart OBJECT-TYPE
    SYNTAX     DisplayString
    MAX-ACCESS read-write
    STATUS     current
    DESCRIPTION
            "-- empty --"
    ::= { lcsSetupCertsScepCaSubCa 9 }

-- {NODE} 1.3.6.1.4.1.2356.11.2.39.2.14
lcsSetupCertsScepCaWebIfc OBJECT IDENTIFIER ::= { lcsSetupCertsScepCa 14 }

-- {TABLE} 1.3.6.1.4.1.2356.11.2.39.2.14.1
lcsSetupCertsScepCaWebIfcProfilesTable OBJECT-TYPE
    SYNTAX     SEQUENCE OF LcsSetupCertsScepCaWebIfcProfilesEntry
    MAX-ACCESS not-accessible
    STATUS     current
    DESCRIPTION
            "-- empty --"
    ::= { lcsSetupCertsScepCaWebIfc 1 }

-- {ROW} 1.3.6.1.4.1.2356.11.2.39.2.14.1.1
lcsSetupCertsScepCaWebIfcProfilesEntry OBJECT-TYPE
    SYNTAX     LcsSetupCertsScepCaWebIfcProfilesEntry
    MAX-ACCESS not-accessible
    STATUS     current
    DESCRIPTION
            ""
    INDEX {
            lcsSetupCertsScepCaWebIfcProfilesEntryProfileName,
            lcsSetupCertsScepCaWebIfcProfilesEntryTemplate
          }
    ::= { lcsSetupCertsScepCaWebIfcProfilesTable 1 }

LcsSetupCertsScepCaWebIfcProfilesEntry ::= SEQUENCE {
            lcsSetupCertsScepCaWebIfcProfilesEntryProfileName DisplayString,
            lcsSetupCertsScepCaWebIfcProfilesEntryKeyUsage DisplayString,
            lcsSetupCertsScepCaWebIfcProfilesEntryExtendedKeyUsage DisplayString,
            lcsSetupCertsScepCaWebIfcProfilesEntryRsaKeyLength INTEGER,
            lcsSetupCertsScepCaWebIfcProfilesEntryValidityPeriod Integer32,
            lcsSetupCertsScepCaWebIfcProfilesEntryCa INTEGER,
            lcsSetupCertsScepCaWebIfcProfilesEntryPassword DisplayString,
            lcsSetupCertsScepCaWebIfcProfilesEntryCountryName DisplayString,
            lcsSetupCertsScepCaWebIfcProfilesEntryLocalityName DisplayString,
            lcsSetupCertsScepCaWebIfcProfilesEntryOrganizationName DisplayString,
            lcsSetupCertsScepCaWebIfcProfilesEntryOrganizationUnitName DisplayString,
            lcsSetupCertsScepCaWebIfcProfilesEntryStateOrProvince DisplayString,
            lcsSetupCertsScepCaWebIfcProfilesEntryEMail DisplayString,
            lcsSetupCertsScepCaWebIfcProfilesEntrySurname DisplayString,
            lcsSetupCertsScepCaWebIfcProfilesEntrySerialNumber DisplayString,
            lcsSetupCertsScepCaWebIfcProfilesEntryPostalCode DisplayString,
            lcsSetupCertsScepCaWebIfcProfilesEntryTemplate DisplayString,
            lcsSetupCertsScepCaWebIfcProfilesEntrySubjectAlternativeName DisplayString,
            lcsSetupCertsScepCaWebIfcProfilesEntryOcspAia DisplayString
    }

-- {COLUMN} 1.3.6.1.4.1.2356.11.2.39.2.14.1.1.1
lcsSetupCertsScepCaWebIfcProfilesEntryProfileName OBJECT-TYPE
    SYNTAX     DisplayString (SIZE(0..32))
    MAX-ACCESS read-write
    STATUS     current
    DESCRIPTION
            "-- empty --"
    ::= { lcsSetupCertsScepCaWebIfcProfilesEntry 1 }

-- {COLUMN} 1.3.6.1.4.1.2356.11.2.39.2.14.1.1.2
lcsSetupCertsScepCaWebIfcProfilesEntryKeyUsage OBJECT-TYPE
    SYNTAX     DisplayString (SIZE(0..251))
    MAX-ACCESS read-write
    STATUS     current
    DESCRIPTION
            "-- empty --"
    ::= { lcsSetupCertsScepCaWebIfcProfilesEntry 2 }

-- {COLUMN} 1.3.6.1.4.1.2356.11.2.39.2.14.1.1.3
lcsSetupCertsScepCaWebIfcProfilesEntryExtendedKeyUsage OBJECT-TYPE
    SYNTAX     DisplayString (SIZE(0..251))
    MAX-ACCESS read-write
    STATUS     current
    DESCRIPTION
            "-- empty --"
    ::= { lcsSetupCertsScepCaWebIfcProfilesEntry 3 }

-- {COLUMN} 1.3.6.1.4.1.2356.11.2.39.2.14.1.1.4
lcsSetupCertsScepCaWebIfcProfilesEntryRsaKeyLength OBJECT-TYPE
    SYNTAX     INTEGER {
                  e1024 (1024),
                  e2048 (2048),
                  e3072 (3072),
                  e4096 (4096),
                  e8192 (8192)
            }
    MAX-ACCESS read-write
    STATUS     current
    DESCRIPTION
            "-- empty --"
    ::= { lcsSetupCertsScepCaWebIfcProfilesEntry 4 }

-- {COLUMN} 1.3.6.1.4.1.2356.11.2.39.2.14.1.1.5
lcsSetupCertsScepCaWebIfcProfilesEntryValidityPeriod OBJECT-TYPE
    SYNTAX     Integer32 (0..2147483647)
    MAX-ACCESS read-write
    STATUS     current
    DESCRIPTION
            "-- empty --"
    ::= { lcsSetupCertsScepCaWebIfcProfilesEntry 5 }

-- {COLUMN} 1.3.6.1.4.1.2356.11.2.39.2.14.1.1.6
lcsSetupCertsScepCaWebIfcProfilesEntryCa OBJECT-TYPE
    SYNTAX     INTEGER {
                  eNo (0),
                  eYes (1)
            }
    MAX-ACCESS read-write
    STATUS     current
    DESCRIPTION
            "-- empty --"
    ::= { lcsSetupCertsScepCaWebIfcProfilesEntry 6 }

-- {COLUMN} 1.3.6.1.4.1.2356.11.2.39.2.14.1.1.7
lcsSetupCertsScepCaWebIfcProfilesEntryPassword OBJECT-TYPE
    SYNTAX     DisplayString (SIZE(0..32))
    MAX-ACCESS read-write
    STATUS     current
    DESCRIPTION
            "-- empty --"
    ::= { lcsSetupCertsScepCaWebIfcProfilesEntry 7 }

-- {COLUMN} 1.3.6.1.4.1.2356.11.2.39.2.14.1.1.8
lcsSetupCertsScepCaWebIfcProfilesEntryCountryName OBJECT-TYPE
    SYNTAX     DisplayString (SIZE(0..2))
    MAX-ACCESS read-write
    STATUS     current
    DESCRIPTION
            "-- empty --"
    ::= { lcsSetupCertsScepCaWebIfcProfilesEntry 8 }

-- {COLUMN} 1.3.6.1.4.1.2356.11.2.39.2.14.1.1.9
lcsSetupCertsScepCaWebIfcProfilesEntryLocalityName OBJECT-TYPE
    SYNTAX     DisplayString (SIZE(0..32))
    MAX-ACCESS read-write
    STATUS     current
    DESCRIPTION
            "-- empty --"
    ::= { lcsSetupCertsScepCaWebIfcProfilesEntry 9 }

-- {COLUMN} 1.3.6.1.4.1.2356.11.2.39.2.14.1.1.10
lcsSetupCertsScepCaWebIfcProfilesEntryOrganizationName OBJECT-TYPE
    SYNTAX     DisplayString (SIZE(0..32))
    MAX-ACCESS read-write
    STATUS     current
    DESCRIPTION
            "-- empty --"
    ::= { lcsSetupCertsScepCaWebIfcProfilesEntry 10 }

-- {COLUMN} 1.3.6.1.4.1.2356.11.2.39.2.14.1.1.11
lcsSetupCertsScepCaWebIfcProfilesEntryOrganizationUnitName OBJECT-TYPE
    SYNTAX     DisplayString (SIZE(0..32))
    MAX-ACCESS read-write
    STATUS     current
    DESCRIPTION
            "-- empty --"
    ::= { lcsSetupCertsScepCaWebIfcProfilesEntry 11 }

-- {COLUMN} 1.3.6.1.4.1.2356.11.2.39.2.14.1.1.12
lcsSetupCertsScepCaWebIfcProfilesEntryStateOrProvince OBJECT-TYPE
    SYNTAX     DisplayString (SIZE(0..32))
    MAX-ACCESS read-write
    STATUS     current
    DESCRIPTION
            "-- empty --"
    ::= { lcsSetupCertsScepCaWebIfcProfilesEntry 12 }

-- {COLUMN} 1.3.6.1.4.1.2356.11.2.39.2.14.1.1.13
lcsSetupCertsScepCaWebIfcProfilesEntryEMail OBJECT-TYPE
    SYNTAX     DisplayString (SIZE(0..64))
    MAX-ACCESS read-write
    STATUS     current
    DESCRIPTION
            "-- empty --"
    ::= { lcsSetupCertsScepCaWebIfcProfilesEntry 13 }

-- {COLUMN} 1.3.6.1.4.1.2356.11.2.39.2.14.1.1.14
lcsSetupCertsScepCaWebIfcProfilesEntrySurname OBJECT-TYPE
    SYNTAX     DisplayString (SIZE(0..32))
    MAX-ACCESS read-write
    STATUS     current
    DESCRIPTION
            "-- empty --"
    ::= { lcsSetupCertsScepCaWebIfcProfilesEntry 14 }

-- {COLUMN} 1.3.6.1.4.1.2356.11.2.39.2.14.1.1.15
lcsSetupCertsScepCaWebIfcProfilesEntrySerialNumber OBJECT-TYPE
    SYNTAX     DisplayString (SIZE(0..32))
    MAX-ACCESS read-write
    STATUS     current
    DESCRIPTION
            "-- empty --"
    ::= { lcsSetupCertsScepCaWebIfcProfilesEntry 15 }

-- {COLUMN} 1.3.6.1.4.1.2356.11.2.39.2.14.1.1.16
lcsSetupCertsScepCaWebIfcProfilesEntryPostalCode OBJECT-TYPE
    SYNTAX     DisplayString (SIZE(0..25))
    MAX-ACCESS read-write
    STATUS     current
    DESCRIPTION
            "-- empty --"
    ::= { lcsSetupCertsScepCaWebIfcProfilesEntry 16 }

-- {COLUMN} 1.3.6.1.4.1.2356.11.2.39.2.14.1.1.17
lcsSetupCertsScepCaWebIfcProfilesEntryTemplate OBJECT-TYPE
    SYNTAX     DisplayString (SIZE(0..31))
    MAX-ACCESS read-write
    STATUS     current
    DESCRIPTION
            "-- empty --"
    ::= { lcsSetupCertsScepCaWebIfcProfilesEntry 17 }

-- {COLUMN} 1.3.6.1.4.1.2356.11.2.39.2.14.1.1.18
lcsSetupCertsScepCaWebIfcProfilesEntrySubjectAlternativeName OBJECT-TYPE
    SYNTAX     DisplayString (SIZE(0..254))
    MAX-ACCESS read-write
    STATUS     current
    DESCRIPTION
            "-- empty --"
    ::= { lcsSetupCertsScepCaWebIfcProfilesEntry 18 }

-- {COLUMN} 1.3.6.1.4.1.2356.11.2.39.2.14.1.1.19
lcsSetupCertsScepCaWebIfcProfilesEntryOcspAia OBJECT-TYPE
    SYNTAX     DisplayString (SIZE(0..254))
    MAX-ACCESS read-write
    STATUS     current
    DESCRIPTION
            "-- empty --"
    ::= { lcsSetupCertsScepCaWebIfcProfilesEntry 19 }

-- {TABLE} 1.3.6.1.4.1.2356.11.2.39.2.14.2
lcsSetupCertsScepCaWebIfcTemplateTable OBJECT-TYPE
    SYNTAX     SEQUENCE OF LcsSetupCertsScepCaWebIfcTemplateEntry
    MAX-ACCESS not-accessible
    STATUS     current
    DESCRIPTION
            "-- empty --"
    ::= { lcsSetupCertsScepCaWebIfc 2 }

-- {ROW} 1.3.6.1.4.1.2356.11.2.39.2.14.2.1
lcsSetupCertsScepCaWebIfcTemplateEntry OBJECT-TYPE
    SYNTAX     LcsSetupCertsScepCaWebIfcTemplateEntry
    MAX-ACCESS not-accessible
    STATUS     current
    DESCRIPTION
            ""
    INDEX {
            lcsSetupCertsScepCaWebIfcTemplateEntryName
          }
    ::= { lcsSetupCertsScepCaWebIfcTemplateTable 1 }

LcsSetupCertsScepCaWebIfcTemplateEntry ::= SEQUENCE {
            lcsSetupCertsScepCaWebIfcTemplateEntryName DisplayString,
            lcsSetupCertsScepCaWebIfcTemplateEntryKeyUsage INTEGER,
            lcsSetupCertsScepCaWebIfcTemplateEntryExtendedKeyUsage INTEGER,
            lcsSetupCertsScepCaWebIfcTemplateEntryRsaKeyLength INTEGER,
            lcsSetupCertsScepCaWebIfcTemplateEntryValidityPeriod INTEGER,
            lcsSetupCertsScepCaWebIfcTemplateEntryCa INTEGER,
            lcsSetupCertsScepCaWebIfcTemplateEntryPassword Integer32,
            lcsSetupCertsScepCaWebIfcTemplateEntryCountryName INTEGER,
            lcsSetupCertsScepCaWebIfcTemplateEntryLocalityName INTEGER,
            lcsSetupCertsScepCaWebIfcTemplateEntryOrganizationName INTEGER,
            lcsSetupCertsScepCaWebIfcTemplateEntryOrganizationUnitName INTEGER,
            lcsSetupCertsScepCaWebIfcTemplateEntryStateOrProvince INTEGER,
            lcsSetupCertsScepCaWebIfcTemplateEntryEMail INTEGER,
            lcsSetupCertsScepCaWebIfcTemplateEntrySurname INTEGER,
            lcsSetupCertsScepCaWebIfcTemplateEntrySerialNumber INTEGER,
            lcsSetupCertsScepCaWebIfcTemplateEntryPostalCode INTEGER,
            lcsSetupCertsScepCaWebIfcTemplateEntrySubjectAlternativeName INTEGER,
            lcsSetupCertsScepCaWebIfcTemplateEntryOcspAia INTEGER
    }

-- {COLUMN} 1.3.6.1.4.1.2356.11.2.39.2.14.2.1.1
lcsSetupCertsScepCaWebIfcTemplateEntryName OBJECT-TYPE
    SYNTAX     DisplayString (SIZE(0..31))
    MAX-ACCESS read-write
    STATUS     current
    DESCRIPTION
            "-- empty --"
    ::= { lcsSetupCertsScepCaWebIfcTemplateEntry 1 }

-- {COLUMN} 1.3.6.1.4.1.2356.11.2.39.2.14.2.1.2
lcsSetupCertsScepCaWebIfcTemplateEntryKeyUsage OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 2 }

-- {COLUMN} 1.3.6.1.4.1.2356.11.2.39.2.14.2.1.3
lcsSetupCertsScepCaWebIfcTemplateEntryExtendedKeyUsage OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 3 }

-- {COLUMN} 1.3.6.1.4.1.2356.11.2.39.2.14.2.1.4
lcsSetupCertsScepCaWebIfcTemplateEntryRsaKeyLength OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 4 }

-- {COLUMN} 1.3.6.1.4.1.2356.11.2.39.2.14.2.1.5
lcsSetupCertsScepCaWebIfcTemplateEntryValidityPeriod OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 5 }

-- {COLUMN} 1.3.6.1.4.1.2356.11.2.39.2.14.2.1.6
lcsSetupCertsScepCaWebIfcTemplateEntryCa OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 6 }

-- {COLUMN} 1.3.6.1.4.1.2356.11.2.39.2.14.2.1.7
lcsSetupCertsScepCaWebIfcTemplateEntryPassword OBJECT-TYPE
    SYNTAX     Integer32 (0..255)
    MAX-ACCESS read-only
    STATUS     current
    DESCRIPTION
            "-- empty --"
    ::= { lcsSetupCertsScepCaWebIfcTemplateEntry 7 }

-- {COLUMN} 1.3.6.1.4.1.2356.11.2.39.2.14.2.1.8
lcsSetupCertsScepCaWebIfcTemplateEntryCountryName OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 8 }

-- {COLUMN} 1.3.6.1.4.1.2356.11.2.39.2.14.2.1.9
lcsSetupCertsScepCaWebIfcTemplateEntryLocalityName OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 9 }

-- {COLUMN} 1.3.6.1.4.1.2356.11.2.39.2.14.2.1.10
lcsSetupCertsScepCaWebIfcTemplateEntryOrganizationName OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 10 }

-- {COLUMN} 1.3.6.1.4.1.2356.11.2.39.2.14.2.1.11
lcsSetupCertsScepCaWebIfcTemplateEntryOrganizationUnitName OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 11 }

-- {COLUMN} 1.3.6.1.4.1.2356.11.2.39.2.14.2.1.12
lcsSetupCertsScepCaWebIfcTemplateEntryStateOrProvince OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 12 }

-- {COLUMN} 1.3.6.1.4.1.2356.11.2.39.2.14.2.1.13
lcsSetupCertsScepCaWebIfcTemplateEntryEMail OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 13 }

-- {COLUMN} 1.3.6.1.4.1.2356.11.2.39.2.14.2.1.14
lcsSetupCertsScepCaWebIfcTemplateEntrySurname OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 14 }

-- {COLUMN} 1.3.6.1.4.1.2356.11.2.39.2.14.2.1.15
lcsSetupCertsScepCaWebIfcTemplateEntrySerialNumber OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 15 }

-- {COLUMN} 1.3.6.1.4.1.2356.11.2.39.2.14.2.1.16
lcsSetupCertsScepCaWebIfcTemplateEntryPostalCode OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 16 }

-- {COLUMN} 1.3.6.1.4.1.2356.11.2.39.2.14.2.1.17
lcsSetupCertsScepCaWebIfcTemplateEntrySubjectAlternativeName OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 17 }

-- {COLUMN} 1.3.6.1.4.1.2356.11.2.39.2.14.2.1.18
lcsSetupCertsScepCaWebIfcTemplateEntryOcspAia OBJECT-TYPE
    SYNTAX     INTEGER {
                  eNo (0),
                  eYes (1),
                  eMandatory (2),
                  eFixed (3)
            }
    MAX-ACCESS read-write
    STATUS     current
    DESCRIPTION
            "-- empty --"
    ::= { lcsSetupCertsScepCaWebIfcTemplateEntry 18 }

-- {SCALAR} 1.3.6.1.4.1.2356.11.2.39.2.15
lcsSetupCertsScepCaRsaPaddingMethod OBJECT-TYPE
    SYNTAX     INTEGER {
                  ePkcs1 (0),
                  ePss (1)
            }
    MAX-ACCESS read-write
    STATUS     current
    DESCRIPTION
            "-- empty --"
    ::= { lcsSetupCertsScepCa 15 }

-- {NODE} 1.3.6.1.4.1.2356.11.2.39.3
lcsSetupCertsCrls OBJECT IDENTIFIER ::= { lcsSetupCerts 3 }

-- {SCALAR} 1.3.6.1.4.1.2356.11.2.39.3.1
lcsSetupCertsCrlsCrlOperating OBJECT-TYPE
    SYNTAX     INTEGER {
                  eNo (0),
                  eYes (1)
            }
    MAX-ACCESS read-write
    STATUS     current
    DESCRIPTION
            ""
    ::= { lcsSetupCertsCrls 1 }

-- {SCALAR} 1.3.6.1.4.1.2356.11.2.39.3.4
lcsSetupCertsCrlsUpdateBefore OBJECT-TYPE
    SYNTAX     Integer32 (0..2147483647)
    MAX-ACCESS read-write
    STATUS     current
    DESCRIPTION
            ""
    ::= { lcsSetupCertsCrls 4 }

-- {SCALAR} 1.3.6.1.4.1.2356.11.2.39.3.5
lcsSetupCertsCrlsPrefetchPeriod OBJECT-TYPE
    SYNTAX     Integer32 (0..2147483647)
    MAX-ACCESS read-write
    STATUS     current
    DESCRIPTION
            ""
    ::= { lcsSetupCertsCrls 5 }

-- {SCALAR} 1.3.6.1.4.1.2356.11.2.39.3.6
lcsSetupCertsCrlsValidityExceedance OBJECT-TYPE
    SYNTAX     Integer32 (0..2147483647)
    MAX-ACCESS read-write
    STATUS     current
    DESCRIPTION
            ""
    ::= { lcsSetupCertsCrls 6 }

-- {SCALAR} 1.3.6.1.4.1.2356.11.2.39.3.7
lcsSetupCertsCrlsRefreshCrlNow OBJECT-TYPE
    SYNTAX     DisplayString
    MAX-ACCESS read-write
    STATUS     current
    DESCRIPTION
            ""
    ::= { lcsSetupCertsCrls 7 }

-- {TABLE} 1.3.6.1.4.1.2356.11.2.39.3.8
lcsSetupCertsCrlsAlternativeUrlTableTable OBJECT-TYPE
    SYNTAX     SEQUENCE OF LcsSetupCertsCrlsAlternativeUrlTableEntry
    MAX-ACCESS not-accessible
    STATUS     current
    DESCRIPTION
            ""
    ::= { lcsSetupCertsCrls 8 }

-- {ROW} 1.3.6.1.4.1.2356.11.2.39.3.8.1
lcsSetupCertsCrlsAlternativeUrlTableEntry OBJECT-TYPE
    SYNTAX     LcsSetupCertsCrlsAlternativeUrlTableEntry
    MAX-ACCESS not-accessible
    STATUS     current
    DESCRIPTION
            ""
    INDEX {
            lcsSetupCertsCrlsAlternativeUrlTableEntryAlternativeUrl
          }
    ::= { lcsSetupCertsCrlsAlternativeUrlTableTable 1 }

LcsSetupCertsCrlsAlternativeUrlTableEntry ::= SEQUENCE {
            lcsSetupCertsCrlsAlternativeUrlTableEntryAlternativeUrl DisplayString
    }

-- {COLUMN} 1.3.6.1.4.1.2356.11.2.39.3.8.1.1
lcsSetupCertsCrlsAlternativeUrlTableEntryAlternativeUrl OBJECT-TYPE
    SYNTAX     DisplayString (SIZE(0..251))
    MAX-ACCESS read-write
    STATUS     current
    DESCRIPTION
            ""
    ::= { lcsSetupCertsCrlsAlternativeUrlTableEntry 1 }

-- {SCALAR} 1.3.6.1.4.1.2356.11.2.39.3.9
lcsSetupCertsCrlsLoopbackAddress OBJECT-TYPE
    SYNTAX     DisplayString (SIZE(0..16))
    MAX-ACCESS read-write
    STATUS     current
    DESCRIPTION
            ""
    ::= { lcsSetupCertsCrls 9 }

-- {NODE} 1.3.6.1.4.1.2356.11.2.39.6
lcsSetupCertsOcspClient OBJECT IDENTIFIER ::= { lcsSetupCerts 6 }

-- {TABLE} 1.3.6.1.4.1.2356.11.2.39.6.1
lcsSetupCertsOcspClientCaProfileTableTable OBJECT-TYPE
    SYNTAX     SEQUENCE OF LcsSetupCertsOcspClientCaProfileTableEntry
    MAX-ACCESS not-accessible
    STATUS     current
    DESCRIPTION
            ""
    ::= { lcsSetupCertsOcspClient 1 }

-- {ROW} 1.3.6.1.4.1.2356.11.2.39.6.1.1
lcsSetupCertsOcspClientCaProfileTableEntry OBJECT-TYPE
    SYNTAX     LcsSetupCertsOcspClientCaProfileTableEntry
    MAX-ACCESS not-accessible
    STATUS     current
    DESCRIPTION
            ""
    INDEX {
            lcsSetupCertsOcspClientCaProfileTableEntryProfileName
          }
    ::= { lcsSetupCertsOcspClientCaProfileTableTable 1 }

LcsSetupCertsOcspClientCaProfileTableEntry ::= SEQUENCE {
            lcsSetupCertsOcspClientCaProfileTableEntryProfileName DisplayString,
            lcsSetupCertsOcspClientCaProfileTableEntryCaDistinguishedName DisplayString,
            lcsSetupCertsOcspClientCaProfileTableEntryPreferAia INTEGER,
            lcsSetupCertsOcspClientCaProfileTableEntryResponderProfileName DisplayString,
            lcsSetupCertsOcspClientCaProfileTableEntrySourceInterface DisplayString,
            lcsSetupCertsOcspClientCaProfileTableEntryCertEvaluationMode INTEGER,
            lcsSetupCertsOcspClientCaProfileTableEntrySyslogEvents INTEGER
    }

-- {COLUMN} 1.3.6.1.4.1.2356.11.2.39.6.1.1.1
lcsSetupCertsOcspClientCaProfileTableEntryProfileName OBJECT-TYPE
    SYNTAX     DisplayString (SIZE(0..32))
    MAX-ACCESS read-write
    STATUS     current
    DESCRIPTION
            ""
    ::= { lcsSetupCertsOcspClientCaProfileTableEntry 1 }

-- {COLUMN} 1.3.6.1.4.1.2356.11.2.39.6.1.1.2
lcsSetupCertsOcspClientCaProfileTableEntryCaDistinguishedName OBJECT-TYPE
    SYNTAX     DisplayString (SIZE(0..251))
    MAX-ACCESS read-write
    STATUS     current
    DESCRIPTION
            ""
    ::= { lcsSetupCertsOcspClientCaProfileTableEntry 2 }

-- {COLUMN} 1.3.6.1.4.1.2356.11.2.39.6.1.1.3
lcsSetupCertsOcspClientCaProfileTableEntryPreferAia OBJECT-TYPE
    SYNTAX     INTEGER {
                  eNo (0),
                  eYes (1)
            }
    MAX-ACCESS read-write
    STATUS     current
    DESCRIPTION
            ""
    ::= { lcsSetupCertsOcspClientCaProfileTableEntry 3 }

-- {COLUMN} 1.3.6.1.4.1.2356.11.2.39.6.1.1.4
lcsSetupCertsOcspClientCaProfileTableEntryResponderProfileName OBJECT-TYPE
    SYNTAX     DisplayString (SIZE(0..32))
    MAX-ACCESS read-write
    STATUS     current
    DESCRIPTION
            ""
    ::= { lcsSetupCertsOcspClientCaProfileTableEntry 4 }

-- {COLUMN} 1.3.6.1.4.1.2356.11.2.39.6.1.1.5
lcsSetupCertsOcspClientCaProfileTableEntrySourceInterface OBJECT-TYPE
    SYNTAX     DisplayString (SIZE(0..16))
    MAX-ACCESS read-write
    STATUS     current
    DESCRIPTION
            ""
    ::= { lcsSetupCertsOcspClientCaProfileTableEntry 5 }

-- {COLUMN} 1.3.6.1.4.1.2356.11.2.39.6.1.1.6
lcsSetupCertsOcspClientCaProfileTableEntryCertEvaluationMode OBJECT-TYPE
    SYNTAX     INTEGER {
                  eStrict (0),
                  eLoose (1)
            }
    MAX-ACCESS read-write
    STATUS     current
    DESCRIPTION
            ""
    ::= { lcsSetupCertsOcspClientCaProfileTableEntry 6 }

-- {COLUMN} 1.3.6.1.4.1.2356.11.2.39.6.1.1.7
lcsSetupCertsOcspClientCaProfileTableEntrySyslogEvents OBJECT-TYPE
    SYNTAX     INTEGER {
                  eNo (0),
                  eYes (1)
            }
    MAX-ACCESS read-write
    STATUS     current
    DESCRIPTION
            ""
    ::= { lcsSetupCertsOcspClientCaProfileTableEntry 7 }

-- {TABLE} 1.3.6.1.4.1.2356.11.2.39.6.2
lcsSetupCertsOcspClientResponderProfileTableTable OBJECT-TYPE
    SYNTAX     SEQUENCE OF LcsSetupCertsOcspClientResponderProfileTableEntry
    MAX-ACCESS not-accessible
    STATUS     current
    DESCRIPTION
            ""
    ::= { lcsSetupCertsOcspClient 2 }

-- {ROW} 1.3.6.1.4.1.2356.11.2.39.6.2.1
lcsSetupCertsOcspClientResponderProfileTableEntry OBJECT-TYPE
    SYNTAX     LcsSetupCertsOcspClientResponderProfileTableEntry
    MAX-ACCESS not-accessible
    STATUS     current
    DESCRIPTION
            ""
    INDEX {
            lcsSetupCertsOcspClientResponderProfileTableEntryProfileName
          }
    ::= { lcsSetupCertsOcspClientResponderProfileTableTable 1 }

LcsSetupCertsOcspClientResponderProfileTableEntry ::= SEQUENCE {
            lcsSetupCertsOcspClientResponderProfileTableEntryProfileName DisplayString,
            lcsSetupCertsOcspClientResponderProfileTableEntryUrl DisplayString
    }

-- {COLUMN} 1.3.6.1.4.1.2356.11.2.39.6.2.1.1
lcsSetupCertsOcspClientResponderProfileTableEntryProfileName OBJECT-TYPE
    SYNTAX     DisplayString (SIZE(0..32))
    MAX-ACCESS read-write
    STATUS     current
    DESCRIPTION
            ""
    ::= { lcsSetupCertsOcspClientResponderProfileTableEntry 1 }

-- {COLUMN} 1.3.6.1.4.1.2356.11.2.39.6.2.1.2
lcsSetupCertsOcspClientResponderProfileTableEntryUrl OBJECT-TYPE
    SYNTAX     DisplayString (SIZE(0..251))
    MAX-ACCESS read-write
    STATUS     current
    DESCRIPTION
            ""
    ::= { lcsSetupCertsOcspClientResponderProfileTableEntry 2 }

-- {NODE} 1.3.6.1.4.1.2356.11.2.39.7
lcsSetupCertsOcspServer OBJECT IDENTIFIER ::= { lcsSetupCerts 7 }

-- {SCALAR} 1.3.6.1.4.1.2356.11.2.39.7.1
lcsSetupCertsOcspServerOperating OBJECT-TYPE
    SYNTAX     INTEGER {
                  eNo (0),
                  eYes (1)
            }
    MAX-ACCESS read-write
    STATUS     current
    DESCRIPTION
            "-- empty --"
    ::= { lcsSetupCertsOcspServer 1 }

-- {SCALAR} 1.3.6.1.4.1.2356.11.2.39.7.2
lcsSetupCertsOcspServerPort OBJECT-TYPE
    SYNTAX     Integer32 (0..65535)
    MAX-ACCESS read-write
    STATUS     current
    DESCRIPTION
            "-- empty --"
    ::= { lcsSetupCertsOcspServer 2 }

-- {SCALAR} 1.3.6.1.4.1.2356.11.2.39.7.3
lcsSetupCertsOcspServerCertificateSubject OBJECT-TYPE
    SYNTAX     DisplayString (SIZE(0..251))
    MAX-ACCESS read-write
    STATUS     current
    DESCRIPTION
            "-- empty --"
    ::= { lcsSetupCertsOcspServer 3 }

-- {SCALAR} 1.3.6.1.4.1.2356.11.2.39.7.4
lcsSetupCertsOcspServerWanAccess OBJECT-TYPE
    SYNTAX     INTEGER {
                  eNo (0),
                  eYes (1),
                  eOverVpn (2)
            }
    MAX-ACCESS read-write
    STATUS     current
    DESCRIPTION
            "-- empty --"
    ::= { lcsSetupCertsOcspServer 4 }

-- {SCALAR} 1.3.6.1.4.1.2356.11.2.39.7.5
lcsSetupCertsOcspServerSignatureAlgo OBJECT-TYPE
    SYNTAX     INTEGER {
                  eSha1 (1),
                  eSha256 (2),
                  eSha384 (3),
                  eSha512 (4)
            }
    MAX-ACCESS read-write
    STATUS     current
    DESCRIPTION
            "-- empty --"
    ::= { lcsSetupCertsOcspServer 5 }

-- {NODE} 1.3.6.1.4.1.2356.11.2.40
lcsSetupGps OBJECT IDENTIFIER ::= { lcsSetup 40 }

-- {SCALAR} 1.3.6.1.4.1.2356.11.2.40.1
lcsSetupGpsOperating OBJECT-TYPE
    SYNTAX     INTEGER {
                  eNo (0),
                  eYes (1)
            }
    MAX-ACCESS read-write
    STATUS     current
    DESCRIPTION
            ""
    ::= { lcsSetupGps 1 }

-- {NODE} 1.3.6.1.4.1.2356.11.2.41
lcsSetupUtm OBJECT IDENTIFIER ::= { lcsSetup 41 }

-- {NODE} 1.3.6.1.4.1.2356.11.2.41.2
lcsSetupUtmCf OBJECT IDENTIFIER ::= { lcsSetupUtm 2 }

-- {SCALAR} 1.3.6.1.4.1.2356.11.2.41.2.1
lcsSetupUtmCfOperating OBJECT-TYPE
    SYNTAX     INTEGER {
                  eNo (0),
                  eYes (1)
            }
    MAX-ACCESS read-write
    STATUS     current
    DESCRIPTION
            ""
    ::= { lcsSetupUtmCf 1 }

-- {NODE} 1.3.6.1.4.1.2356.11.2.41.2.2
lcsSetupUtmCfGlobalSettings OBJECT IDENTIFIER ::= { lcsSetupUtmCf 2 }

-- {SCALAR} 1.3.6.1.4.1.2356.11.2.41.2.2.1
lcsSetupUtmCfGlobalSettingsAdminEmail OBJECT-TYPE
    SYNTAX     DisplayString (SIZE(0..63))
    MAX-ACCESS read-write
    STATUS     current
    DESCRIPTION
            ""
    ::= { lcsSetupUtmCfGlobalSettings 1 }

-- {SCALAR} 1.3.6.1.4.1.2356.11.2.41.2.2.5
lcsSetupUtmCfGlobalSettingsActionOnError OBJECT-TYPE
    SYNTAX     INTEGER {
                  eBlock (0),
                  ePass (1)
            }
    MAX-ACCESS read-write
    STATUS     current
    DESCRIPTION
            ""
    ::= { lcsSetupUtmCfGlobalSettings 5 }

-- {SCALAR} 1.3.6.1.4.1.2356.11.2.41.2.2.6
lcsSetupUtmCfGlobalSettingsActionOnLicenseExceedance OBJECT-TYPE
    SYNTAX     INTEGER {
                  eBlock (0),
                  ePass (1)
            }
    MAX-ACCESS read-write
    STATUS     current
    DESCRIPTION
            ""
    ::= { lcsSetupUtmCfGlobalSettings 6 }

-- {SCALAR} 1.3.6.1.4.1.2356.11.2.41.2.2.7
lcsSetupUtmCfGlobalSettingsActionOnLicenseExpiration OBJECT-TYPE
    SYNTAX     INTEGER {
                  eBlock (0),
                  ePass (1)
            }
    MAX-ACCESS read-write
    STATUS     current
    DESCRIPTION
            ""
    ::= { lcsSetupUtmCfGlobalSettings 7 }

-- {TABLE} 1.3.6.1.4.1.2356.11.2.41.2.2.9
lcsSetupUtmCfGlobalSettingsNotificationTable OBJECT-TYPE
    SYNTAX     SEQUENCE OF LcsSetupUtmCfGlobalSettingsNotificationEntry
    MAX-ACCESS not-accessible
    STATUS     current
    DESCRIPTION
            ""
    ::= { lcsSetupUtmCfGlobalSettings 9 }

-- {ROW} 1.3.6.1.4.1.2356.11.2.41.2.2.9.1
lcsSetupUtmCfGlobalSettingsNotificationEntry OBJECT-TYPE
    SYNTAX     LcsSetupUtmCfGlobalSettingsNotificationEntry
    MAX-ACCESS not-accessible
    STATUS     current
    DESCRIPTION
            ""
    INDEX {
            lcsSetupUtmCfGlobalSettingsNotificationEntryCause
          }
    ::= { lcsSetupUtmCfGlobalSettingsNotificationTable 1 }

LcsSetupUtmCfGlobalSettingsNotificationEntry ::= SEQUENCE {
            lcsSetupUtmCfGlobalSettingsNotificationEntryCause INTEGER,
            lcsSetupUtmCfGlobalSettingsNotificationEntryEMail INTEGER,
            lcsSetupUtmCfGlobalSettingsNotificationEntrySnmp INTEGER,
            lcsSetupUtmCfGlobalSettingsNotificationEntrySyslog INTEGER
    }

-- {COLUMN} 1.3.6.1.4.1.2356.11.2.41.2.2.9.1.1
lcsSetupUtmCfGlobalSettingsNotificationEntryCause OBJECT-TYPE
    SYNTAX     INTEGER {
                  eSpamMail (1),
                  ePhishingMail (2),
                  eUpdate (3),
                  eInfected (4),
                  eBlockedUrl (5),
                  eError (6),
                  eLicenseExpired (7),
                  eLicenseExceeded (8),
                  eOverride (9),
                  eProxyLimit (10)
            }
    MAX-ACCESS read-only
    STATUS     current
    DESCRIPTION
            ""
    ::= { lcsSetupUtmCfGlobalSettingsNotificationEntry 1 }

-- {COLUMN} 1.3.6.1.4.1.2356.11.2.41.2.2.9.1.2
lcsSetupUtmCfGlobalSettingsNotificationEntryEMail OBJECT-TYPE
    SYNTAX     INTEGER {
                  eNo (0),
                  eDaily (1),
                  eImmediately (2)
            }
    MAX-ACCESS read-write
    STATUS     current
    DESCRIPTION
            ""
    ::= { lcsSetupUtmCfGlobalSettingsNotificationEntry 2 }

-- {COLUMN} 1.3.6.1.4.1.2356.11.2.41.2.2.9.1.3
lcsSetupUtmCfGlobalSettingsNotificationEntrySnmp OBJECT-TYPE
    SYNTAX     INTEGER {
                  eNo (0),
                  eYes (1)
            }
    MAX-ACCESS read-write
    STATUS     current
    DESCRIPTION
            ""
    ::= { lcsSetupUtmCfGlobalSettingsNotificationEntry 3 }

-- {COLUMN} 1.3.6.1.4.1.2356.11.2.41.2.2.9.1.4
lcsSetupUtmCfGlobalSettingsNotificationEntrySyslog OBJECT-TYPE
    SYNTAX     INTEGER {
                  eNo (0),
                  eYes (1)
            }
    MAX-ACCESS read-write
    STATUS     current
    DESCRIPTION
            ""
    ::= { lcsSetupUtmCfGlobalSettingsNotificationEntry 4 }

-- {TABLE} 1.3.6.1.4.1.2356.11.2.41.2.2.10
lcsSetupUtmCfGlobalSettingsBlockTextTable OBJECT-TYPE
    SYNTAX     SEQUENCE OF LcsSetupUtmCfGlobalSettingsBlockTextEntry
    MAX-ACCESS not-accessible
    STATUS     current
    DESCRIPTION
            ""
    ::= { lcsSetupUtmCfGlobalSettings 10 }

-- {ROW} 1.3.6.1.4.1.2356.11.2.41.2.2.10.1
lcsSetupUtmCfGlobalSettingsBlockTextEntry OBJECT-TYPE
    SYNTAX     LcsSetupUtmCfGlobalSettingsBlockTextEntry
    MAX-ACCESS not-accessible
    STATUS     current
    DESCRIPTION
            ""
    INDEX {
            lcsSetupUtmCfGlobalSettingsBlockTextEntryLanguage
          }
    ::= { lcsSetupUtmCfGlobalSettingsBlockTextTable 1 }

LcsSetupUtmCfGlobalSettingsBlockTextEntry ::= SEQUENCE {
            lcsSetupUtmCfGlobalSettingsBlockTextEntryLanguage DisplayString,
            lcsSetupUtmCfGlobalSettingsBlockTextEntryText DisplayString
    }

-- {COLUMN} 1.3.6.1.4.1.2356.11.2.41.2.2.10.1.1
lcsSetupUtmCfGlobalSettingsBlockTextEntryLanguage OBJECT-TYPE
    SYNTAX     DisplayString (SIZE(0..10))
    MAX-ACCESS read-write
    STATUS     current
    DESCRIPTION
            ""
    ::= { lcsSetupUtmCfGlobalSettingsBlockTextEntry 1 }

-- {COLUMN} 1.3.6.1.4.1.2356.11.2.41.2.2.10.1.2
lcsSetupUtmCfGlobalSettingsBlockTextEntryText OBJECT-TYPE
    SYNTAX     DisplayString (SIZE(0..254))
    MAX-ACCESS read-write
    STATUS     current
    DESCRIPTION
            ""
    ::= { lcsSetupUtmCfGlobalSettingsBlockTextEntry 2 }

-- {SCALAR} 1.3.6.1.4.1.2356.11.2.41.2.2.11
lcsSetupUtmCfGlobalSettingsUrlToShowOnBlocking OBJECT-TYPE
    SYNTAX     DisplayString (SIZE(0..254))
    MAX-ACCESS read-write
    STATUS     current
    DESCRIPTION
            ""
    ::= { lcsSetupUtmCfGlobalSettings 11 }

-- {SCALAR} 1.3.6.1.4.1.2356.11.2.41.2.2.12
lcsSetupUtmCfGlobalSettingsLoopbackToUseOnBlocking OBJECT-TYPE
    SYNTAX     DisplayString (SIZE(0..16))
    MAX-ACCESS read-write
    STATUS     current
    DESCRIPTION
            ""
    ::= { lcsSetupUtmCfGlobalSettings 12 }

-- {SCALAR} 1.3.6.1.4.1.2356.11.2.41.2.2.13
lcsSetupUtmCfGlobalSettingsOverrideActive OBJECT-TYPE
    SYNTAX     INTEGER {
                  eNo (0),
                  eYes (1)
            }
    MAX-ACCESS read-write
    STATUS     current
    DESCRIPTION
            ""
    ::= { lcsSetupUtmCfGlobalSettings 13 }

-- {SCALAR} 1.3.6.1.4.1.2356.11.2.41.2.2.14
lcsSetupUtmCfGlobalSettingsOverrideDuration OBJECT-TYPE
    SYNTAX     Integer32 (0..65535)
    MAX-ACCESS read-write
    STATUS     current
    DESCRIPTION
            ""
    ::= { lcsSetupUtmCfGlobalSettings 14 }

-- {SCALAR} 1.3.6.1.4.1.2356.11.2.41.2.2.15
lcsSetupUtmCfGlobalSettingsOverrideType OBJECT-TYPE
    SYNTAX     INTEGER {
                  eCategory (0),
                  eDomain (1),
                  eCategoryAndDomain (2)
            }
    MAX-ACCESS read-write
    STATUS     current
    DESCRIPTION
            ""
    ::= { lcsSetupUtmCfGlobalSettings 15 }

-- {SCALAR} 1.3.6.1.4.1.2356.11.2.41.2.2.17
lcsSetupUtmCfGlobalSettingsSaveToFlashrom OBJECT-TYPE
    SYNTAX     INTEGER {
                  eNo (0),
                  eYes (1)
            }
    MAX-ACCESS read-write
    STATUS     current
    DESCRIPTION
            ""
    ::= { lcsSetupUtmCfGlobalSettings 17 }

-- {TABLE} 1.3.6.1.4.1.2356.11.2.41.2.2.19
lcsSetupUtmCfGlobalSettingsErrorTextTable OBJECT-TYPE
    SYNTAX     SEQUENCE OF LcsSetupUtmCfGlobalSettingsErrorTextEntry
    MAX-ACCESS not-accessible
    STATUS     current
    DESCRIPTION
            ""
    ::= { lcsSetupUtmCfGlobalSettings 19 }

-- {ROW} 1.3.6.1.4.1.2356.11.2.41.2.2.19.1
lcsSetupUtmCfGlobalSettingsErrorTextEntry OBJECT-TYPE
    SYNTAX     LcsSetupUtmCfGlobalSettingsErrorTextEntry
    MAX-ACCESS not-accessible
    STATUS     current
    DESCRIPTION
            ""
    INDEX {
            lcsSetupUtmCfGlobalSettingsErrorTextEntryLanguage
          }
    ::= { lcsSetupUtmCfGlobalSettingsErrorTextTable 1 }

LcsSetupUtmCfGlobalSettingsErrorTextEntry ::= SEQUENCE {
            lcsSetupUtmCfGlobalSettingsErrorTextEntryLanguage DisplayString,
            lcsSetupUtmCfGlobalSettingsErrorTextEntryText DisplayString
    }

-- {COLUMN} 1.3.6.1.4.1.2356.11.2.41.2.2.19.1.1
lcsSetupUtmCfGlobalSettingsErrorTextEntryLanguage OBJECT-TYPE
    SYNTAX     DisplayString (SIZE(0..10))
    MAX-ACCESS read-write
    STATUS     current
    DESCRIPTION
            ""
    ::= { lcsSetupUtmCfGlobalSettingsErrorTextEntry 1 }

-- {COLUMN} 1.3.6.1.4.1.2356.11.2.41.2.2.19.1.2
lcsSetupUtmCfGlobalSettingsErrorTextEntryText OBJECT-TYPE
    SYNTAX     DisplayString (SIZE(0..254))
    MAX-ACCESS read-write
    STATUS     current
    DESCRIPTION
            ""
    ::= { lcsSetupUtmCfGlobalSettingsErrorTextEntry 2 }

-- {TABLE} 1.3.6.1.4.1.2356.11.2.41.2.2.20
lcsSetupUtmCfGlobalSettingsOverrideTextTable OBJECT-TYPE
    SYNTAX     SEQUENCE OF LcsSetupUtmCfGlobalSettingsOverrideTextEntry
    MAX-ACCESS not-accessible
    STATUS     current
    DESCRIPTION
            ""
    ::= { lcsSetupUtmCfGlobalSettings 20 }

-- {ROW} 1.3.6.1.4.1.2356.11.2.41.2.2.20.1
lcsSetupUtmCfGlobalSettingsOverrideTextEntry OBJECT-TYPE
    SYNTAX     LcsSetupUtmCfGlobalSettingsOverrideTextEntry
    MAX-ACCESS not-accessible
    STATUS     current
    DESCRIPTION
            ""
    INDEX {
            lcsSetupUtmCfGlobalSettingsOverrideTextEntryLanguage
          }
    ::= { lcsSetupUtmCfGlobalSettingsOverrideTextTable 1 }

LcsSetupUtmCfGlobalSettingsOverrideTextEntry ::= SEQUENCE {
            lcsSetupUtmCfGlobalSettingsOverrideTextEntryLanguage DisplayString,
            lcsSetupUtmCfGlobalSettingsOverrideTextEntryText DisplayString
    }

-- {COLUMN} 1.3.6.1.4.1.2356.11.2.41.2.2.20.1.1
lcsSetupUtmCfGlobalSettingsOverrideTextEntryLanguage OBJECT-TYPE
    SYNTAX     DisplayString (SIZE(0..10))
    MAX-ACCESS read-write
    STATUS     current
    DESCRIPTION
            ""
    ::= { lcsSetupUtmCfGlobalSettingsOverrideTextEntry 1 }

-- {COLUMN} 1.3.6.1.4.1.2356.11.2.41.2.2.20.1.2
lcsSetupUtmCfGlobalSettingsOverrideTextEntryText OBJECT-TYPE
    SYNTAX     DisplayString (SIZE(0..254))
    MAX-ACCESS read-write
    STATUS     current
    DESCRIPTION
            ""
    ::= { lcsSetupUtmCfGlobalSettingsOverrideTextEntry 2 }

-- {SCALAR} 1.3.6.1.4.1.2356.11.2.41.2.2.21
lcsSetupUtmCfGlobalSettingsUrlToShowOnOverride OBJECT-TYPE
    SYNTAX     DisplayString (SIZE(0..254))
    MAX-ACCESS read-only
    STATUS     current
    DESCRIPTION
            ""
    ::= { lcsSetupUtmCfGlobalSettings 21 }

-- {SCALAR} 1.3.6.1.4.1.2356.11.2.41.2.2.22
lcsSetupUtmCfGlobalSettingsLoopbackToUseOnOverride OBJECT-TYPE
    SYNTAX     DisplayString (SIZE(0..16))
    MAX-ACCESS read-only
    STATUS     current
    DESCRIPTION
            ""
    ::= { lcsSetupUtmCfGlobalSettings 22 }

-- {NODE} 1.3.6.1.4.1.2356.11.2.41.2.2.23
lcsSetupUtmCfGlobalSettingsSnapshot OBJECT IDENTIFIER ::= { lcsSetupUtmCfGlobalSettings 23 }

-- {SCALAR} 1.3.6.1.4.1.2356.11.2.41.2.2.23.1
lcsSetupUtmCfGlobalSettingsSnapshotActive OBJECT-TYPE
    SYNTAX     INTEGER {
                  eNo (0),
                  eYes (1)
            }
    MAX-ACCESS read-write
    STATUS     current
    DESCRIPTION
            ""
    ::= { lcsSetupUtmCfGlobalSettingsSnapshot 1 }

-- {SCALAR} 1.3.6.1.4.1.2356.11.2.41.2.2.23.2
lcsSetupUtmCfGlobalSettingsSnapshotType OBJECT-TYPE
    SYNTAX     INTEGER {
                  eMonthly (0),
                  eWeekly (1),
                  eDaily (2)
            }
    MAX-ACCESS read-write
    STATUS     current
    DESCRIPTION
            ""
    ::= { lcsSetupUtmCfGlobalSettingsSnapshot 2 }

-- {SCALAR} 1.3.6.1.4.1.2356.11.2.41.2.2.23.3
lcsSetupUtmCfGlobalSettingsSnapshotTime OBJECT-TYPE
    SYNTAX     DisplayString (SIZE(0..5))
    MAX-ACCESS read-write
    STATUS     current
    DESCRIPTION
            ""
    ::= { lcsSetupUtmCfGlobalSettingsSnapshot 3 }

-- {SCALAR} 1.3.6.1.4.1.2356.11.2.41.2.2.23.4
lcsSetupUtmCfGlobalSettingsSnapshotDay OBJECT-TYPE
    SYNTAX     Integer32 (0..255)
    MAX-ACCESS read-write
    STATUS     current
    DESCRIPTION
            ""
    ::= { lcsSetupUtmCfGlobalSettingsSnapshot 4 }

-- {SCALAR} 1.3.6.1.4.1.2356.11.2.41.2.2.23.5
lcsSetupUtmCfGlobalSettingsSnapshotWeekday OBJECT-TYPE
    SYNTAX     INTEGER {
                  eSunday (0),
                  eMonday (1),
                  eTuesday (2),
                  eWednesday (3),
                  eThursday (4),
                  eFriday (5),
                  eSaturday (6)
            }
    MAX-ACCESS read-write
    STATUS     current
    DESCRIPTION
            ""
    ::= { lcsSetupUtmCfGlobalSettingsSnapshot 5 }

-- {SCALAR} 1.3.6.1.4.1.2356.11.2.41.2.2.24
lcsSetupUtmCfGlobalSettingsProxyConnectionsLimit OBJECT-TYPE
    SYNTAX     Integer32 (0..2147483647)
    MAX-ACCESS read-write
    STATUS     current
    DESCRIPTION
            ""
    ::= { lcsSetupUtmCfGlobalSettings 24 }

-- {SCALAR} 1.3.6.1.4.1.2356.11.2.41.2.2.25
lcsSetupUtmCfGlobalSettingsProcessingTimeoutInMs OBJECT-TYPE
    SYNTAX     Integer32 (0..2147483647)
    MAX-ACCESS read-write
    STATUS     current
    DESCRIPTION
            ""
    ::= { lcsSetupUtmCfGlobalSettings 25 }

-- {SCALAR} 1.3.6.1.4.1.2356.11.2.41.2.2.26
lcsSetupUtmCfGlobalSettingsUrlToShowOnError OBJECT-TYPE
    SYNTAX     DisplayString (SIZE(0..254))
    MAX-ACCESS read-write
    STATUS     current
    DESCRIPTION
            ""
    ::= { lcsSetupUtmCfGlobalSettings 26 }

-- {SCALAR} 1.3.6.1.4.1.2356.11.2.41.2.2.27
lcsSetupUtmCfGlobalSettingsLoopbackToUseOnError OBJECT-TYPE
    SYNTAX     DisplayString (SIZE(0..16))
    MAX-ACCESS read-write
    STATUS     current
    DESCRIPTION
            ""
    ::= { lcsSetupUtmCfGlobalSettings 27 }

-- {SCALAR} 1.3.6.1.4.1.2356.11.2.41.2.2.28
lcsSetupUtmCfGlobalSettingsLoopbackToRatingServer OBJECT-TYPE
    SYNTAX     DisplayString (SIZE(0..16))
    MAX-ACCESS read-write
    STATUS     current
    DESCRIPTION
            "-- empty --"
    ::= { lcsSetupUtmCfGlobalSettings 28 }

-- {SCALAR} 1.3.6.1.4.1.2356.11.2.41.2.2.29
lcsSetupUtmCfGlobalSettingsWildcard OBJECT-TYPE
    SYNTAX     INTEGER {
                  eNo (0),
                  eYes (1)
            }
    MAX-ACCESS read-write
    STATUS     current
    DESCRIPTION
            "-- empty --"
    ::= { lcsSetupUtmCfGlobalSettings 29 }

-- {SCALAR} 1.3.6.1.4.1.2356.11.2.41.2.2.30
lcsSetupUtmCfGlobalSettingsUnknown443Traffic OBJECT-TYPE
    SYNTAX     INTEGER {
                  eDeny (0),
                  eAllow (1)
            }
    MAX-ACCESS read-write
    STATUS     current
    DESCRIPTION
            "-- empty --"
    ::= { lcsSetupUtmCfGlobalSettings 30 }

-- {NODE} 1.3.6.1.4.1.2356.11.2.41.2.3
lcsSetupUtmCfProf OBJECT IDENTIFIER ::= { lcsSetupUtmCf 3 }

-- {TABLE} 1.3.6.1.4.1.2356.11.2.41.2.3.1
lcsSetupUtmCfProfProfTable OBJECT-TYPE
    SYNTAX     SEQUENCE OF LcsSetupUtmCfProfProfEntry
    MAX-ACCESS not-accessible
    STATUS     current
    DESCRIPTION
            "Profiles"
    ::= { lcsSetupUtmCfProf 1 }

-- {ROW} 1.3.6.1.4.1.2356.11.2.41.2.3.1.1
lcsSetupUtmCfProfProfEntry OBJECT-TYPE
    SYNTAX     LcsSetupUtmCfProfProfEntry
    MAX-ACCESS not-accessible
    STATUS     current
    DESCRIPTION
            ""
    INDEX {
            lcsSetupUtmCfProfProfEntryName,
            lcsSetupUtmCfProfProfEntryTimeframe
          }
    ::= { lcsSetupUtmCfProfProfTable 1 }

LcsSetupUtmCfProfProfEntry ::= SEQUENCE {
            lcsSetupUtmCfProfProfEntryName DisplayString,
            lcsSetupUtmCfProfProfEntryTimeframe DisplayString,
            lcsSetupUtmCfProfProfEntryWhitelist DisplayString,
            lcsSetupUtmCfProfProfEntryBlacklist DisplayString,
            lcsSetupUtmCfProfProfEntryCatProf DisplayString
    }

-- {COLUMN} 1.3.6.1.4.1.2356.11.2.41.2.3.1.1.1
lcsSetupUtmCfProfProfEntryName OBJECT-TYPE
    SYNTAX     DisplayString (SIZE(0..31))
    MAX-ACCESS read-write
    STATUS     current
    DESCRIPTION
            ""
    ::= { lcsSetupUtmCfProfProfEntry 1 }

-- {COLUMN} 1.3.6.1.4.1.2356.11.2.41.2.3.1.1.2
lcsSetupUtmCfProfProfEntryTimeframe OBJECT-TYPE
    SYNTAX     DisplayString (SIZE(0..31))
    MAX-ACCESS read-write
    STATUS     current
    DESCRIPTION
            ""
    ::= { lcsSetupUtmCfProfProfEntry 2 }

-- {COLUMN} 1.3.6.1.4.1.2356.11.2.41.2.3.1.1.3
lcsSetupUtmCfProfProfEntryWhitelist OBJECT-TYPE
    SYNTAX     DisplayString (SIZE(0..31))
    MAX-ACCESS read-write
    STATUS     current
    DESCRIPTION
            ""
    ::= { lcsSetupUtmCfProfProfEntry 3 }

-- {COLUMN} 1.3.6.1.4.1.2356.11.2.41.2.3.1.1.4
lcsSetupUtmCfProfProfEntryBlacklist OBJECT-TYPE
    SYNTAX     DisplayString (SIZE(0..31))
    MAX-ACCESS read-write
    STATUS     current
    DESCRIPTION
            ""
    ::= { lcsSetupUtmCfProfProfEntry 4 }

-- {COLUMN} 1.3.6.1.4.1.2356.11.2.41.2.3.1.1.5
lcsSetupUtmCfProfProfEntryCatProf OBJECT-TYPE
    SYNTAX     DisplayString (SIZE(0..31))
    MAX-ACCESS read-write
    STATUS     current
    DESCRIPTION
            "Category-Profile"
    ::= { lcsSetupUtmCfProfProfEntry 5 }

-- {TABLE} 1.3.6.1.4.1.2356.11.2.41.2.3.2
lcsSetupUtmCfProfWhitelistsTable OBJECT-TYPE
    SYNTAX     SEQUENCE OF LcsSetupUtmCfProfWhitelistsEntry
    MAX-ACCESS not-accessible
    STATUS     current
    DESCRIPTION
            ""
    ::= { lcsSetupUtmCfProf 2 }

-- {ROW} 1.3.6.1.4.1.2356.11.2.41.2.3.2.1
lcsSetupUtmCfProfWhitelistsEntry OBJECT-TYPE
    SYNTAX     LcsSetupUtmCfProfWhitelistsEntry
    MAX-ACCESS not-accessible
    STATUS     current
    DESCRIPTION
            ""
    INDEX {
            lcsSetupUtmCfProfWhitelistsEntryName
          }
    ::= { lcsSetupUtmCfProfWhitelistsTable 1 }

LcsSetupUtmCfProfWhitelistsEntry ::= SEQUENCE {
            lcsSetupUtmCfProfWhitelistsEntryName DisplayString,
            lcsSetupUtmCfProfWhitelistsEntryWhitelist DisplayString
    }

-- {COLUMN} 1.3.6.1.4.1.2356.11.2.41.2.3.2.1.1
lcsSetupUtmCfProfWhitelistsEntryName OBJECT-TYPE
    SYNTAX     DisplayString (SIZE(0..31))
    MAX-ACCESS read-write
    STATUS     current
    DESCRIPTION
            ""
    ::= { lcsSetupUtmCfProfWhitelistsEntry 1 }

-- {COLUMN} 1.3.6.1.4.1.2356.11.2.41.2.3.2.1.2
lcsSetupUtmCfProfWhitelistsEntryWhitelist OBJECT-TYPE
    SYNTAX     DisplayString (SIZE(0..251))
    MAX-ACCESS read-write
    STATUS     current
    DESCRIPTION
            ""
    ::= { lcsSetupUtmCfProfWhitelistsEntry 2 }

-- {TABLE} 1.3.6.1.4.1.2356.11.2.41.2.3.3
lcsSetupUtmCfProfBlacklistsTable OBJECT-TYPE
    SYNTAX     SEQUENCE OF LcsSetupUtmCfProfBlacklistsEntry
    MAX-ACCESS not-accessible
    STATUS     current
    DESCRIPTION
            ""
    ::= { lcsSetupUtmCfProf 3 }

-- {ROW} 1.3.6.1.4.1.2356.11.2.41.2.3.3.1
lcsSetupUtmCfProfBlacklistsEntry OBJECT-TYPE
    SYNTAX     LcsSetupUtmCfProfBlacklistsEntry
    MAX-ACCESS not-accessible
    STATUS     current
    DESCRIPTION
            ""
    INDEX {
            lcsSetupUtmCfProfBlacklistsEntryName
          }
    ::= { lcsSetupUtmCfProfBlacklistsTable 1 }

LcsSetupUtmCfProfBlacklistsEntry ::= SEQUENCE {
            lcsSetupUtmCfProfBlacklistsEntryName DisplayString,
            lcsSetupUtmCfProfBlacklistsEntryBlacklist DisplayString
    }

-- {COLUMN} 1.3.6.1.4.1.2356.11.2.41.2.3.3.1.1
lcsSetupUtmCfProfBlacklistsEntryName OBJECT-TYPE
    SYNTAX     DisplayString (SIZE(0..31))
    MAX-ACCESS read-write
    STATUS     current
    DESCRIPTION
            ""
    ::= { lcsSetupUtmCfProfBlacklistsEntry 1 }

-- {COLUMN} 1.3.6.1.4.1.2356.11.2.41.2.3.3.1.2
lcsSetupUtmCfProfBlacklistsEntryBlacklist OBJECT-TYPE
    SYNTAX     DisplayString (SIZE(0..251))
    MAX-ACCESS read-write
    STATUS     current
    DESCRIPTION
            ""
    ::= { lcsSetupUtmCfProfBlacklistsEntry 2 }

-- {TABLE} 1.3.6.1.4.1.2356.11.2.41.2.3.4
lcsSetupUtmCfProfCatProfTable OBJECT-TYPE
    SYNTAX     SEQUENCE OF LcsSetupUtmCfProfCatProfEntry
    MAX-ACCESS not-accessible
    STATUS     current
    DESCRIPTION
            "Category-Profiles"
    ::= { lcsSetupUtmCfProf 4 }

-- {ROW} 1.3.6.1.4.1.2356.11.2.41.2.3.4.1
lcsSetupUtmCfProfCatProfEntry OBJECT-TYPE
    SYNTAX     LcsSetupUtmCfProfCatProfEntry
    MAX-ACCESS not-accessible
    STATUS     current
    DESCRIPTION
            ""
    INDEX {
            lcsSetupUtmCfProfCatProfEntryName
          }
    ::= { lcsSetupUtmCfProfCatProfTable 1 }

LcsSetupUtmCfProfCatProfEntry ::= SEQUENCE {
            lcsSetupUtmCfProfCatProfEntryName DisplayString,
            lcsSetupUtmCfProfCatProfEntryUnknown INTEGER,
            lcsSetupUtmCfProfCatProfEntryPornographyEroticSex INTEGER,
            lcsSetupUtmCfProfCatProfEntryEroticSex INTEGER,
            lcsSetupUtmCfProfCatProfEntrySwimwearLingerie INTEGER,
            lcsSetupUtmCfProfCatProfEntryShopping INTEGER,
            lcsSetupUtmCfProfCatProfEntryAuctionsClassifiedAds INTEGER,
            lcsSetupUtmCfProfCatProfEntryGovNonProv INTEGER,
            lcsSetupUtmCfProfCatProfEntryNonGovernmentalOrganizations INTEGER,
            lcsSetupUtmCfProfCatProfEntryCitiesRegionsCountries INTEGER,
            lcsSetupUtmCfProfCatProfEntryEducation INTEGER,
            lcsSetupUtmCfProfCatProfEntryPoliticalParties INTEGER,
            lcsSetupUtmCfProfCatProfEntryReligionSpirituality INTEGER,
            lcsSetupUtmCfProfCatProfEntrySects INTEGER,
            lcsSetupUtmCfProfCatProfEntryIllegalActivities INTEGER,
            lcsSetupUtmCfProfCatProfEntryComputerCrimeWarezHacking INTEGER,
            lcsSetupUtmCfProfCatProfEntryPolHateDiscr INTEGER,
            lcsSetupUtmCfProfCatProfEntryWarezSoftwarePrivacy INTEGER,
            lcsSetupUtmCfProfCatProfEntryViolenceExtreme INTEGER,
            lcsSetupUtmCfProfCatProfEntryGamblingLottery INTEGER,
            lcsSetupUtmCfProfCatProfEntryComputerGames INTEGER,
            lcsSetupUtmCfProfCatProfEntryToys INTEGER,
            lcsSetupUtmCfProfCatProfEntryCinTvSocial INTEGER,
            lcsSetupUtmCfProfCatProfEntryRecrFacThemPark INTEGER,
            lcsSetupUtmCfProfCatProfEntryArtsMuseumsTheaters INTEGER,
            lcsSetupUtmCfProfCatProfEntryMusicRadioBroadcast INTEGER,
            lcsSetupUtmCfProfCatProfEntryLiteratureBooks INTEGER,
            lcsSetupUtmCfProfCatProfEntryHumorCartoons INTEGER,
            lcsSetupUtmCfProfCatProfEntryNewsMagazines INTEGER,
            lcsSetupUtmCfProfCatProfEntryWebmailUnifiedMessaging INTEGER,
            lcsSetupUtmCfProfCatProfEntryChat INTEGER,
            lcsSetupUtmCfProfCatProfEntryBlogsBulletinBoards INTEGER,
            lcsSetupUtmCfProfCatProfEntryMobileTelephony INTEGER,
            lcsSetupUtmCfProfCatProfEntryDigitalPostcards INTEGER,
            lcsSetupUtmCfProfCatProfEntrySearchWebPortal INTEGER,
            lcsSetupUtmCfProfCatProfEntrySoftwareHardware INTEGER,
            lcsSetupUtmCfProfCatProfEntryCommunicationServices INTEGER,
            lcsSetupUtmCfProfCatProfEntryItSecurityItInformation INTEGER,
            lcsSetupUtmCfProfCatProfEntryWebSiteTranslation INTEGER,
            lcsSetupUtmCfProfCatProfEntryAnonymousProxies INTEGER,
            lcsSetupUtmCfProfCatProfEntryIllegalDrugs INTEGER,
            lcsSetupUtmCfProfCatProfEntryAlcoholTobacco INTEGER,
            lcsSetupUtmCfProfCatProfEntryTobacco INTEGER,
            lcsSetupUtmCfProfCatProfEntrySelfHelpAddiction INTEGER,
            lcsSetupUtmCfProfCatProfEntryDatingNetworks INTEGER,
            lcsSetupUtmCfProfCatProfEntryRestEnter INTEGER,
            lcsSetupUtmCfProfCatProfEntryTravel INTEGER,
            lcsSetupUtmCfProfCatProfEntryFashionCosmeticsJewelry INTEGER,
            lcsSetupUtmCfProfCatProfEntrySports INTEGER,
            lcsSetupUtmCfProfCatProfEntryArchConstFurn INTEGER,
            lcsSetupUtmCfProfCatProfEntryEnvironmentClimatePets INTEGER,
            lcsSetupUtmCfProfCatProfEntryPersonalWebSites INTEGER,
            lcsSetupUtmCfProfCatProfEntryJobSearch INTEGER,
            lcsSetupUtmCfProfCatProfEntryFinanceInvestment INTEGER,
            lcsSetupUtmCfProfCatProfEntryFinServInsurance INTEGER,
            lcsSetupUtmCfProfCatProfEntryBanking INTEGER,
            lcsSetupUtmCfProfCatProfEntryVehicles INTEGER,
            lcsSetupUtmCfProfCatProfEntryWeaponsMilitary INTEGER,
            lcsSetupUtmCfProfCatProfEntryMedicineHealthSelfHelp INTEGER,
            lcsSetupUtmCfProfCatProfEntryAbortion INTEGER,
            lcsSetupUtmCfProfCatProfEntrySpamUrls INTEGER,
            lcsSetupUtmCfProfCatProfEntryMalware INTEGER,
            lcsSetupUtmCfProfCatProfEntryPhishingUrls INTEGER,
            lcsSetupUtmCfProfCatProfEntryInstantMessaging INTEGER,
            lcsSetupUtmCfProfCatProfEntryGeneralBusiness INTEGER,
            lcsSetupUtmCfProfCatProfEntryBannerAdvertisements INTEGER,
            lcsSetupUtmCfProfCatProfEntrySocialNetworking INTEGER,
            lcsSetupUtmCfProfCatProfEntryBusinessNetworking INTEGER,
            lcsSetupUtmCfProfCatProfEntrySocialMedia INTEGER,
            lcsSetupUtmCfProfCatProfEntryWebStorage INTEGER,
            lcsSetupUtmCfProfCatProfEntryCommandControlServer INTEGER,
            lcsSetupUtmCfProfCatProfEntryBotnetCommandAndControlServer INTEGER,
            lcsSetupUtmCfProfCatProfEntryCloud INTEGER,
            lcsSetupUtmCfProfCatProfEntryInfrastructureAsAService INTEGER,
            lcsSetupUtmCfProfCatProfEntryPlatformAsAService INTEGER,
            lcsSetupUtmCfProfCatProfEntrySoftwareAsAService INTEGER
    }

-- {COLUMN} 1.3.6.1.4.1.2356.11.2.41.2.3.4.1.1
lcsSetupUtmCfProfCatProfEntryName OBJECT-TYPE
    SYNTAX     DisplayString (SIZE(0..31))
    MAX-ACCESS read-write
    STATUS     current
    DESCRIPTION
            ""
    ::= { lcsSetupUtmCfProfCatProfEntry 1 }

-- {COLUMN} 1.3.6.1.4.1.2356.11.2.41.2.3.4.1.100
lcsSetupUtmCfProfCatProfEntryUnknown OBJECT-TYPE
    SYNTAX     INTEGER {
                  eAllowed (0),
                  eForbidden (1),
                  eOverride (2)
            }
    MAX-ACCESS read-write
    STATUS     current
    DESCRIPTION
            ""
    ::= { lcsSetupUtmCfProfCatProfEntry 100 }

-- {COLUMN} 1.3.6.1.4.1.2356.11.2.41.2.3.4.1.101
lcsSetupUtmCfProfCatProfEntryPornographyEroticSex OBJECT-TYPE
    SYNTAX     INTEGER {
                  eAllowed (0),
                  eForbidden (1),
                  eOverride (2)
            }
    MAX-ACCESS read-write
    STATUS     current
    DESCRIPTION
            ""
    ::= { lcsSetupUtmCfProfCatProfEntry 101 }

-- {COLUMN} 1.3.6.1.4.1.2356.11.2.41.2.3.4.1.102
lcsSetupUtmCfProfCatProfEntryEroticSex OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 102 }

-- {COLUMN} 1.3.6.1.4.1.2356.11.2.41.2.3.4.1.103
lcsSetupUtmCfProfCatProfEntrySwimwearLingerie OBJECT-TYPE
    SYNTAX     INTEGER {
                  eAllowed (0),
                  eForbidden (1),
                  eOverride (2)
            }
    MAX-ACCESS read-write
    STATUS     current
    DESCRIPTION
            ""
    ::= { lcsSetupUtmCfProfCatProfEntry 103 }

-- {COLUMN} 1.3.6.1.4.1.2356.11.2.41.2.3.4.1.104
lcsSetupUtmCfProfCatProfEntryShopping OBJECT-TYPE
    SYNTAX     INTEGER {
                  eAllowed (0),
                  eForbidden (1),
                  eOverride (2)
            }
    MAX-ACCESS read-write
    STATUS     current
    DESCRIPTION
            ""
    ::= { lcsSetupUtmCfProfCatProfEntry 104 }

-- {COLUMN} 1.3.6.1.4.1.2356.11.2.41.2.3.4.1.105
lcsSetupUtmCfProfCatProfEntryAuctionsClassifiedAds OBJECT-TYPE
    SYNTAX     INTEGER {
                  eAllowed (0),
                  eForbidden (1),
                  eOverride (2)
            }
    MAX-ACCESS read-write
    STATUS     current
    DESCRIPTION
            ""
    ::= { lcsSetupUtmCfProfCatProfEntry 105 }

-- {COLUMN} 1.3.6.1.4.1.2356.11.2.41.2.3.4.1.106
lcsSetupUtmCfProfCatProfEntryGovNonProv OBJECT-TYPE
    SYNTAX     INTEGER {
                  eAllowed (0),
                  eForbidden (1),
                  eOverride (2)
            }
    MAX-ACCESS read-write
    STATUS     current
    DESCRIPTION
            "Governmental / Non-Profit Organizations"
    ::= { lcsSetupUtmCfProfCatProfEntry 106 }

-- {COLUMN} 1.3.6.1.4.1.2356.11.2.41.2.3.4.1.107
lcsSetupUtmCfProfCatProfEntryNonGovernmentalOrganizations OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 107 }

-- {COLUMN} 1.3.6.1.4.1.2356.11.2.41.2.3.4.1.108
lcsSetupUtmCfProfCatProfEntryCitiesRegionsCountries OBJECT-TYPE
    SYNTAX     INTEGER {
                  eAllowed (0),
                  eForbidden (1),
                  eOverride (2)
            }
    MAX-ACCESS read-write
    STATUS     current
    DESCRIPTION
            ""
    ::= { lcsSetupUtmCfProfCatProfEntry 108 }

-- {COLUMN} 1.3.6.1.4.1.2356.11.2.41.2.3.4.1.109
lcsSetupUtmCfProfCatProfEntryEducation OBJECT-TYPE
    SYNTAX     INTEGER {
                  eAllowed (0),
                  eForbidden (1),
                  eOverride (2)
            }
    MAX-ACCESS read-write
    STATUS     current
    DESCRIPTION
            ""
    ::= { lcsSetupUtmCfProfCatProfEntry 109 }

-- {COLUMN} 1.3.6.1.4.1.2356.11.2.41.2.3.4.1.110
lcsSetupUtmCfProfCatProfEntryPoliticalParties OBJECT-TYPE
    SYNTAX     INTEGER {
                  eAllowed (0),
                  eForbidden (1),
                  eOverride (2)
            }
    MAX-ACCESS read-write
    STATUS     current
    DESCRIPTION
            ""
    ::= { lcsSetupUtmCfProfCatProfEntry 110 }

-- {COLUMN} 1.3.6.1.4.1.2356.11.2.41.2.3.4.1.111
lcsSetupUtmCfProfCatProfEntryReligionSpirituality OBJECT-TYPE
    SYNTAX     INTEGER {
                  eAllowed (0),
                  eForbidden (1),
                  eOverride (2)
            }
    MAX-ACCESS read-write
    STATUS     current
    DESCRIPTION
            ""
    ::= { lcsSetupUtmCfProfCatProfEntry 111 }

-- {COLUMN} 1.3.6.1.4.1.2356.11.2.41.2.3.4.1.112
lcsSetupUtmCfProfCatProfEntrySects OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 112 }

-- {COLUMN} 1.3.6.1.4.1.2356.11.2.41.2.3.4.1.113
lcsSetupUtmCfProfCatProfEntryIllegalActivities OBJECT-TYPE
    SYNTAX     INTEGER {
                  eAllowed (0),
                  eForbidden (1),
                  eOverride (2)
            }
    MAX-ACCESS read-write
    STATUS     current
    DESCRIPTION
            ""
    ::= { lcsSetupUtmCfProfCatProfEntry 113 }

-- {COLUMN} 1.3.6.1.4.1.2356.11.2.41.2.3.4.1.114
lcsSetupUtmCfProfCatProfEntryComputerCrimeWarezHacking OBJECT-TYPE
    SYNTAX     INTEGER {
                  eAllowed (0),
                  eForbidden (1),
                  eOverride (2)
            }
    MAX-ACCESS read-write
    STATUS     current
    DESCRIPTION
            ""
    ::= { lcsSetupUtmCfProfCatProfEntry 114 }

-- {COLUMN} 1.3.6.1.4.1.2356.11.2.41.2.3.4.1.115
lcsSetupUtmCfProfCatProfEntryPolHateDiscr OBJECT-TYPE
    SYNTAX     INTEGER {
                  eAllowed (0),
                  eForbidden (1),
                  eOverride (2)
            }
    MAX-ACCESS read-write
    STATUS     current
    DESCRIPTION
            "Political Extreme / Hate / Discrimination"
    ::= { lcsSetupUtmCfProfCatProfEntry 115 }

-- {COLUMN} 1.3.6.1.4.1.2356.11.2.41.2.3.4.1.116
lcsSetupUtmCfProfCatProfEntryWarezSoftwarePrivacy OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 116 }

-- {COLUMN} 1.3.6.1.4.1.2356.11.2.41.2.3.4.1.117
lcsSetupUtmCfProfCatProfEntryViolenceExtreme OBJECT-TYPE
    SYNTAX     INTEGER {
                  eAllowed (0),
                  eForbidden (1),
                  eOverride (2)
            }
    MAX-ACCESS read-write
    STATUS     current
    DESCRIPTION
            ""
    ::= { lcsSetupUtmCfProfCatProfEntry 117 }

-- {COLUMN} 1.3.6.1.4.1.2356.11.2.41.2.3.4.1.118
lcsSetupUtmCfProfCatProfEntryGamblingLottery OBJECT-TYPE
    SYNTAX     INTEGER {
                  eAllowed (0),
                  eForbidden (1),
                  eOverride (2)
            }
    MAX-ACCESS read-write
    STATUS     current
    DESCRIPTION
            ""
    ::= { lcsSetupUtmCfProfCatProfEntry 118 }

-- {COLUMN} 1.3.6.1.4.1.2356.11.2.41.2.3.4.1.119
lcsSetupUtmCfProfCatProfEntryComputerGames OBJECT-TYPE
    SYNTAX     INTEGER {
                  eAllowed (0),
                  eForbidden (1),
                  eOverride (2)
            }
    MAX-ACCESS read-write
    STATUS     current
    DESCRIPTION
            ""
    ::= { lcsSetupUtmCfProfCatProfEntry 119 }

-- {COLUMN} 1.3.6.1.4.1.2356.11.2.41.2.3.4.1.120
lcsSetupUtmCfProfCatProfEntryToys OBJECT-TYPE
    SYNTAX     INTEGER {
                  eAllowed (0),
                  eForbidden (1),
                  eOverride (2)
            }
    MAX-ACCESS read-write
    STATUS     current
    DESCRIPTION
            ""
    ::= { lcsSetupUtmCfProfCatProfEntry 120 }

-- {COLUMN} 1.3.6.1.4.1.2356.11.2.41.2.3.4.1.121
lcsSetupUtmCfProfCatProfEntryCinTvSocial OBJECT-TYPE
    SYNTAX     INTEGER {
                  eAllowed (0),
                  eForbidden (1),
                  eOverride (2)
            }
    MAX-ACCESS read-write
    STATUS     current
    DESCRIPTION
            "Cinema / Television / Social Media"
    ::= { lcsSetupUtmCfProfCatProfEntry 121 }

-- {COLUMN} 1.3.6.1.4.1.2356.11.2.41.2.3.4.1.122
lcsSetupUtmCfProfCatProfEntryRecrFacThemPark OBJECT-TYPE
    SYNTAX     INTEGER {
                  eAllowed (0),
                  eForbidden (1),
                  eOverride (2)
            }
    MAX-ACCESS read-write
    STATUS     current
    DESCRIPTION
            "Recreational Facilities / Theme Parks"
    ::= { lcsSetupUtmCfProfCatProfEntry 122 }

-- {COLUMN} 1.3.6.1.4.1.2356.11.2.41.2.3.4.1.123
lcsSetupUtmCfProfCatProfEntryArtsMuseumsTheaters OBJECT-TYPE
    SYNTAX     INTEGER {
                  eAllowed (0),
                  eForbidden (1),
                  eOverride (2)
            }
    MAX-ACCESS read-write
    STATUS     current
    DESCRIPTION
            ""
    ::= { lcsSetupUtmCfProfCatProfEntry 123 }

-- {COLUMN} 1.3.6.1.4.1.2356.11.2.41.2.3.4.1.124
lcsSetupUtmCfProfCatProfEntryMusicRadioBroadcast OBJECT-TYPE
    SYNTAX     INTEGER {
                  eAllowed (0),
                  eForbidden (1),
                  eOverride (2)
            }
    MAX-ACCESS read-write
    STATUS     current
    DESCRIPTION
            ""
    ::= { lcsSetupUtmCfProfCatProfEntry 124 }

-- {COLUMN} 1.3.6.1.4.1.2356.11.2.41.2.3.4.1.125
lcsSetupUtmCfProfCatProfEntryLiteratureBooks OBJECT-TYPE
    SYNTAX     INTEGER {
                  eAllowed (0),
                  eForbidden (1),
                  eOverride (2)
            }
    MAX-ACCESS read-write
    STATUS     current
    DESCRIPTION
            ""
    ::= { lcsSetupUtmCfProfCatProfEntry 125 }

-- {COLUMN} 1.3.6.1.4.1.2356.11.2.41.2.3.4.1.126
lcsSetupUtmCfProfCatProfEntryHumorCartoons OBJECT-TYPE
    SYNTAX     INTEGER {
                  eAllowed (0),
                  eForbidden (1),
                  eOverride (2)
            }
    MAX-ACCESS read-write
    STATUS     current
    DESCRIPTION
            ""
    ::= { lcsSetupUtmCfProfCatProfEntry 126 }

-- {COLUMN} 1.3.6.1.4.1.2356.11.2.41.2.3.4.1.127
lcsSetupUtmCfProfCatProfEntryNewsMagazines OBJECT-TYPE
    SYNTAX     INTEGER {
                  eAllowed (0),
                  eForbidden (1),
                  eOverride (2)
            }
    MAX-ACCESS read-write
    STATUS     current
    DESCRIPTION
            ""
    ::= { lcsSetupUtmCfProfCatProfEntry 127 }

-- {COLUMN} 1.3.6.1.4.1.2356.11.2.41.2.3.4.1.128
lcsSetupUtmCfProfCatProfEntryWebmailUnifiedMessaging OBJECT-TYPE
    SYNTAX     INTEGER {
                  eAllowed (0),
                  eForbidden (1),
                  eOverride (2)
            }
    MAX-ACCESS read-write
    STATUS     current
    DESCRIPTION
            ""
    ::= { lcsSetupUtmCfProfCatProfEntry 128 }

-- {COLUMN} 1.3.6.1.4.1.2356.11.2.41.2.3.4.1.129
lcsSetupUtmCfProfCatProfEntryChat OBJECT-TYPE
    SYNTAX     INTEGER {
                  eAllowed (0),
                  eForbidden (1),
                  eOverride (2)
            }
    MAX-ACCESS read-write
    STATUS     current
    DESCRIPTION
            ""
    ::= { lcsSetupUtmCfProfCatProfEntry 129 }

-- {COLUMN} 1.3.6.1.4.1.2356.11.2.41.2.3.4.1.130
lcsSetupUtmCfProfCatProfEntryBlogsBulletinBoards OBJECT-TYPE
    SYNTAX     INTEGER {
                  eAllowed (0),
                  eForbidden (1),
                  eOverride (2)
            }
    MAX-ACCESS read-write
    STATUS     current
    DESCRIPTION
            ""
    ::= { lcsSetupUtmCfProfCatProfEntry 130 }

-- {COLUMN} 1.3.6.1.4.1.2356.11.2.41.2.3.4.1.131
lcsSetupUtmCfProfCatProfEntryMobileTelephony OBJECT-TYPE
    SYNTAX     INTEGER {
                  eAllowed (0),
                  eForbidden (1),
                  eOverride (2)
            }
    MAX-ACCESS read-write
    STATUS     current
    DESCRIPTION
            ""
    ::= { lcsSetupUtmCfProfCatProfEntry 131 }

-- {COLUMN} 1.3.6.1.4.1.2356.11.2.41.2.3.4.1.132
lcsSetupUtmCfProfCatProfEntryDigitalPostcards OBJECT-TYPE
    SYNTAX     INTEGER {
                  eAllowed (0),
                  eForbidden (1),
                  eOverride (2)
            }
    MAX-ACCESS read-write
    STATUS     current
    DESCRIPTION
            ""
    ::= { lcsSetupUtmCfProfCatProfEntry 132 }

-- {COLUMN} 1.3.6.1.4.1.2356.11.2.41.2.3.4.1.133
lcsSetupUtmCfProfCatProfEntrySearchWebPortal OBJECT-TYPE
    SYNTAX     INTEGER {
                  eAllowed (0),
                  eForbidden (1),
                  eOverride (2)
            }
    MAX-ACCESS read-write
    STATUS     current
    DESCRIPTION
            "Search Engines / Web Catalogs / Portals"
    ::= { lcsSetupUtmCfProfCatProfEntry 133 }

-- {COLUMN} 1.3.6.1.4.1.2356.11.2.41.2.3.4.1.134
lcsSetupUtmCfProfCatProfEntrySoftwareHardware OBJECT-TYPE
    SYNTAX     INTEGER {
                  eAllowed (0),
                  eForbidden (1),
                  eOverride (2)
            }
    MAX-ACCESS read-write
    STATUS     current
    DESCRIPTION
            ""
    ::= { lcsSetupUtmCfProfCatProfEntry 134 }

-- {COLUMN} 1.3.6.1.4.1.2356.11.2.41.2.3.4.1.135
lcsSetupUtmCfProfCatProfEntryCommunicationServices OBJECT-TYPE
    SYNTAX     INTEGER {
                  eAllowed (0),
                  eForbidden (1),
                  eOverride (2)
            }
    MAX-ACCESS read-write
    STATUS     current
    DESCRIPTION
            ""
    ::= { lcsSetupUtmCfProfCatProfEntry 135 }

-- {COLUMN} 1.3.6.1.4.1.2356.11.2.41.2.3.4.1.136
lcsSetupUtmCfProfCatProfEntryItSecurityItInformation OBJECT-TYPE
    SYNTAX     INTEGER {
                  eAllowed (0),
                  eForbidden (1),
                  eOverride (2)
            }
    MAX-ACCESS read-write
    STATUS     current
    DESCRIPTION
            ""
    ::= { lcsSetupUtmCfProfCatProfEntry 136 }

-- {COLUMN} 1.3.6.1.4.1.2356.11.2.41.2.3.4.1.137
lcsSetupUtmCfProfCatProfEntryWebSiteTranslation OBJECT-TYPE
    SYNTAX     INTEGER {
                  eAllowed (0),
                  eForbidden (1),
                  eOverride (2)
            }
    MAX-ACCESS read-write
    STATUS     current
    DESCRIPTION
            ""
    ::= { lcsSetupUtmCfProfCatProfEntry 137 }

-- {COLUMN} 1.3.6.1.4.1.2356.11.2.41.2.3.4.1.138
lcsSetupUtmCfProfCatProfEntryAnonymousProxies OBJECT-TYPE
    SYNTAX     INTEGER {
                  eAllowed (0),
                  eForbidden (1),
                  eOverride (2)
            }
    MAX-ACCESS read-write
    STATUS     current
    DESCRIPTION
            ""
    ::= { lcsSetupUtmCfProfCatProfEntry 138 }

-- {COLUMN} 1.3.6.1.4.1.2356.11.2.41.2.3.4.1.139
lcsSetupUtmCfProfCatProfEntryIllegalDrugs OBJECT-TYPE
    SYNTAX     INTEGER {
                  eAllowed (0),
                  eForbidden (1),
                  eOverride (2)
            }
    MAX-ACCESS read-write
    STATUS     current
    DESCRIPTION
            ""
    ::= { lcsSetupUtmCfProfCatProfEntry 139 }

-- {COLUMN} 1.3.6.1.4.1.2356.11.2.41.2.3.4.1.140
lcsSetupUtmCfProfCatProfEntryAlcoholTobacco OBJECT-TYPE
    SYNTAX     INTEGER {
                  eAllowed (0),
                  eForbidden (1),
                  eOverride (2)
            }
    MAX-ACCESS read-write
    STATUS     current
    DESCRIPTION
            ""
    ::= { lcsSetupUtmCfProfCatProfEntry 140 }

-- {COLUMN} 1.3.6.1.4.1.2356.11.2.41.2.3.4.1.141
lcsSetupUtmCfProfCatProfEntryTobacco OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 141 }

-- {COLUMN} 1.3.6.1.4.1.2356.11.2.41.2.3.4.1.142
lcsSetupUtmCfProfCatProfEntrySelfHelpAddiction OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 142 }

-- {COLUMN} 1.3.6.1.4.1.2356.11.2.41.2.3.4.1.143
lcsSetupUtmCfProfCatProfEntryDatingNetworks OBJECT-TYPE
    SYNTAX     INTEGER {
                  eAllowed (0),
                  eForbidden (1),
                  eOverride (2)
            }
    MAX-ACCESS read-write
    STATUS     current
    DESCRIPTION
            ""
    ::= { lcsSetupUtmCfProfCatProfEntry 143 }

-- {COLUMN} 1.3.6.1.4.1.2356.11.2.41.2.3.4.1.144
lcsSetupUtmCfProfCatProfEntryRestEnter OBJECT-TYPE
    SYNTAX     INTEGER {
                  eAllowed (0),
                  eForbidden (1),
                  eOverride (2)
            }
    MAX-ACCESS read-write
    STATUS     current
    DESCRIPTION
            "Restaurants / Entertainment Venues"
    ::= { lcsSetupUtmCfProfCatProfEntry 144 }

-- {COLUMN} 1.3.6.1.4.1.2356.11.2.41.2.3.4.1.145
lcsSetupUtmCfProfCatProfEntryTravel OBJECT-TYPE
    SYNTAX     INTEGER {
                  eAllowed (0),
                  eForbidden (1),
                  eOverride (2)
            }
    MAX-ACCESS read-write
    STATUS     current
    DESCRIPTION
            ""
    ::= { lcsSetupUtmCfProfCatProfEntry 145 }

-- {COLUMN} 1.3.6.1.4.1.2356.11.2.41.2.3.4.1.146
lcsSetupUtmCfProfCatProfEntryFashionCosmeticsJewelry OBJECT-TYPE
    SYNTAX     INTEGER {
                  eAllowed (0),
                  eForbidden (1),
                  eOverride (2)
            }
    MAX-ACCESS read-write
    STATUS     current
    DESCRIPTION
            ""
    ::= { lcsSetupUtmCfProfCatProfEntry 146 }

-- {COLUMN} 1.3.6.1.4.1.2356.11.2.41.2.3.4.1.147
lcsSetupUtmCfProfCatProfEntrySports OBJECT-TYPE
    SYNTAX     INTEGER {
                  eAllowed (0),
                  eForbidden (1),
                  eOverride (2)
            }
    MAX-ACCESS read-write
    STATUS     current
    DESCRIPTION
            ""
    ::= { lcsSetupUtmCfProfCatProfEntry 147 }

-- {COLUMN} 1.3.6.1.4.1.2356.11.2.41.2.3.4.1.148
lcsSetupUtmCfProfCatProfEntryArchConstFurn OBJECT-TYPE
    SYNTAX     INTEGER {
                  eAllowed (0),
                  eForbidden (1),
                  eOverride (2)
            }
    MAX-ACCESS read-write
    STATUS     current
    DESCRIPTION
            "Architecture / Construction / Furniture"
    ::= { lcsSetupUtmCfProfCatProfEntry 148 }

-- {COLUMN} 1.3.6.1.4.1.2356.11.2.41.2.3.4.1.149
lcsSetupUtmCfProfCatProfEntryEnvironmentClimatePets OBJECT-TYPE
    SYNTAX     INTEGER {
                  eAllowed (0),
                  eForbidden (1),
                  eOverride (2)
            }
    MAX-ACCESS read-write
    STATUS     current
    DESCRIPTION
            ""
    ::= { lcsSetupUtmCfProfCatProfEntry 149 }

-- {COLUMN} 1.3.6.1.4.1.2356.11.2.41.2.3.4.1.150
lcsSetupUtmCfProfCatProfEntryPersonalWebSites OBJECT-TYPE
    SYNTAX     INTEGER {
                  eAllowed (0),
                  eForbidden (1),
                  eOverride (2)
            }
    MAX-ACCESS read-write
    STATUS     current
    DESCRIPTION
            ""
    ::= { lcsSetupUtmCfProfCatProfEntry 150 }

-- {COLUMN} 1.3.6.1.4.1.2356.11.2.41.2.3.4.1.151
lcsSetupUtmCfProfCatProfEntryJobSearch OBJECT-TYPE
    SYNTAX     INTEGER {
                  eAllowed (0),
                  eForbidden (1),
                  eOverride (2)
            }
    MAX-ACCESS read-write
    STATUS     current
    DESCRIPTION
            ""
    ::= { lcsSetupUtmCfProfCatProfEntry 151 }

-- {COLUMN} 1.3.6.1.4.1.2356.11.2.41.2.3.4.1.152
lcsSetupUtmCfProfCatProfEntryFinanceInvestment OBJECT-TYPE
    SYNTAX     INTEGER {
                  eAllowed (0),
                  eForbidden (1),
                  eOverride (2)
            }
    MAX-ACCESS read-write
    STATUS     current
    DESCRIPTION
            ""
    ::= { lcsSetupUtmCfProfCatProfEntry 152 }

-- {COLUMN} 1.3.6.1.4.1.2356.11.2.41.2.3.4.1.153
lcsSetupUtmCfProfCatProfEntryFinServInsurance OBJECT-TYPE
    SYNTAX     INTEGER {
                  eAllowed (0),
                  eForbidden (1),
                  eOverride (2)
            }
    MAX-ACCESS read-write
    STATUS     current
    DESCRIPTION
            ""
    ::= { lcsSetupUtmCfProfCatProfEntry 153 }

-- {COLUMN} 1.3.6.1.4.1.2356.11.2.41.2.3.4.1.154
lcsSetupUtmCfProfCatProfEntryBanking OBJECT-TYPE
    SYNTAX     INTEGER {
                  eAllowed (0),
                  eForbidden (1),
                  eOverride (2)
            }
    MAX-ACCESS read-write
    STATUS     current
    DESCRIPTION
            ""
    ::= { lcsSetupUtmCfProfCatProfEntry 154 }

-- {COLUMN} 1.3.6.1.4.1.2356.11.2.41.2.3.4.1.155
lcsSetupUtmCfProfCatProfEntryVehicles OBJECT-TYPE
    SYNTAX     INTEGER {
                  eAllowed (0),
                  eForbidden (1),
                  eOverride (2)
            }
    MAX-ACCESS read-write
    STATUS     current
    DESCRIPTION
            ""
    ::= { lcsSetupUtmCfProfCatProfEntry 155 }

-- {COLUMN} 1.3.6.1.4.1.2356.11.2.41.2.3.4.1.156
lcsSetupUtmCfProfCatProfEntryWeaponsMilitary OBJECT-TYPE
    SYNTAX     INTEGER {
                  eAllowed (0),
                  eForbidden (1),
                  eOverride (2)
            }
    MAX-ACCESS read-write
    STATUS     current
    DESCRIPTION
            ""
    ::= { lcsSetupUtmCfProfCatProfEntry 156 }

-- {COLUMN} 1.3.6.1.4.1.2356.11.2.41.2.3.4.1.157
lcsSetupUtmCfProfCatProfEntryMedicineHealthSelfHelp OBJECT-TYPE
    SYNTAX     INTEGER {
                  eAllowed (0),
                  eForbidden (1),
                  eOverride (2)
            }
    MAX-ACCESS read-write
    STATUS     current
    DESCRIPTION
            ""
    ::= { lcsSetupUtmCfProfCatProfEntry 157 }

-- {COLUMN} 1.3.6.1.4.1.2356.11.2.41.2.3.4.1.158
lcsSetupUtmCfProfCatProfEntryAbortion OBJECT-TYPE
    SYNTAX     INTEGER {
                  eAllowed (0),
                  eForbidden (1),
                  eOverride (2)
            }
    MAX-ACCESS read-write
    STATUS     current
    DESCRIPTION
            ""
    ::= { lcsSetupUtmCfProfCatProfEntry 158 }

-- {COLUMN} 1.3.6.1.4.1.2356.11.2.41.2.3.4.1.160
lcsSetupUtmCfProfCatProfEntrySpamUrls OBJECT-TYPE
    SYNTAX     INTEGER {
                  eAllowed (0),
                  eForbidden (1),
                  eOverride (2)
            }
    MAX-ACCESS read-write
    STATUS     current
    DESCRIPTION
            ""
    ::= { lcsSetupUtmCfProfCatProfEntry 160 }

-- {COLUMN} 1.3.6.1.4.1.2356.11.2.41.2.3.4.1.161
lcsSetupUtmCfProfCatProfEntryMalware OBJECT-TYPE
    SYNTAX     INTEGER {
                  eAllowed (0),
                  eForbidden (1),
                  eOverride (2)
            }
    MAX-ACCESS read-write
    STATUS     current
    DESCRIPTION
            ""
    ::= { lcsSetupUtmCfProfCatProfEntry 161 }

-- {COLUMN} 1.3.6.1.4.1.2356.11.2.41.2.3.4.1.162
lcsSetupUtmCfProfCatProfEntryPhishingUrls OBJECT-TYPE
    SYNTAX     INTEGER {
                  eAllowed (0),
                  eForbidden (1),
                  eOverride (2)
            }
    MAX-ACCESS read-write
    STATUS     current
    DESCRIPTION
            ""
    ::= { lcsSetupUtmCfProfCatProfEntry 162 }

-- {COLUMN} 1.3.6.1.4.1.2356.11.2.41.2.3.4.1.163
lcsSetupUtmCfProfCatProfEntryInstantMessaging OBJECT-TYPE
    SYNTAX     INTEGER {
                  eAllowed (0),
                  eForbidden (1),
                  eOverride (2)
            }
    MAX-ACCESS read-write
    STATUS     current
    DESCRIPTION
            ""
    ::= { lcsSetupUtmCfProfCatProfEntry 163 }

-- {COLUMN} 1.3.6.1.4.1.2356.11.2.41.2.3.4.1.167
lcsSetupUtmCfProfCatProfEntryGeneralBusiness OBJECT-TYPE
    SYNTAX     INTEGER {
                  eAllowed (0),
                  eForbidden (1),
                  eOverride (2)
            }
    MAX-ACCESS read-write
    STATUS     current
    DESCRIPTION
            ""
    ::= { lcsSetupUtmCfProfCatProfEntry 167 }

-- {COLUMN} 1.3.6.1.4.1.2356.11.2.41.2.3.4.1.174
lcsSetupUtmCfProfCatProfEntryBannerAdvertisements OBJECT-TYPE
    SYNTAX     INTEGER {
                  eAllowed (0),
                  eForbidden (1),
                  eOverride (2)
            }
    MAX-ACCESS read-write
    STATUS     current
    DESCRIPTION
            ""
    ::= { lcsSetupUtmCfProfCatProfEntry 174 }

-- {COLUMN} 1.3.6.1.4.1.2356.11.2.41.2.3.4.1.177
lcsSetupUtmCfProfCatProfEntrySocialNetworking OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 177 }

-- {COLUMN} 1.3.6.1.4.1.2356.11.2.41.2.3.4.1.178
lcsSetupUtmCfProfCatProfEntryBusinessNetworking OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 178 }

-- {COLUMN} 1.3.6.1.4.1.2356.11.2.41.2.3.4.1.179
lcsSetupUtmCfProfCatProfEntrySocialMedia OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 179 }

-- {COLUMN} 1.3.6.1.4.1.2356.11.2.41.2.3.4.1.180
lcsSetupUtmCfProfCatProfEntryWebStorage OBJECT-TYPE
    SYNTAX     INTEGER {
                  eAllowed (0),
                  eForbidden (1),
                  eOverride (2)
            }
    MAX-ACCESS read-write
    STATUS     current
    DESCRIPTION
            ""
    ::= { lcsSetupUtmCfProfCatProfEntry 180 }

-- {COLUMN} 1.3.6.1.4.1.2356.11.2.41.2.3.4.1.181
lcsSetupUtmCfProfCatProfEntryCommandControlServer OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 181 }

-- {COLUMN} 1.3.6.1.4.1.2356.11.2.41.2.3.4.1.182
lcsSetupUtmCfProfCatProfEntryBotnetCommandAndControlServer OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 182 }

-- {COLUMN} 1.3.6.1.4.1.2356.11.2.41.2.3.4.1.183
lcsSetupUtmCfProfCatProfEntryCloud OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 183 }

-- {COLUMN} 1.3.6.1.4.1.2356.11.2.41.2.3.4.1.184
lcsSetupUtmCfProfCatProfEntryInfrastructureAsAService OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 184 }

-- {COLUMN} 1.3.6.1.4.1.2356.11.2.41.2.3.4.1.185
lcsSetupUtmCfProfCatProfEntryPlatformAsAService OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 185 }

-- {COLUMN} 1.3.6.1.4.1.2356.11.2.41.2.3.4.1.186
lcsSetupUtmCfProfCatProfEntrySoftwareAsAService OBJECT-TYPE
    SYNTAX     INTEGER {
                  eAllowed (0),
                  eForbidden (1),
                  eOverride (2)
            }
    MAX-ACCESS read-write
    STATUS     current
    DESCRIPTION
            "-- empty --"
    ::= { lcsSetupUtmCfProfCatProfEntry 186 }

-- {NODE} 1.3.6.1.4.1.2356.11.2.42
lcsSetupXdsl OBJECT IDENTIFIER ::= { lcsSetup 42 }

-- {SCALAR} 1.3.6.1.4.1.2356.11.2.42.1
lcsSetupXdslVendorId OBJECT-TYPE
    SYNTAX     INTEGER {
                  eDefaultId (0),
                  eAlternateId (1)
            }
    MAX-ACCESS read-write
    STATUS     current
    DESCRIPTION
            "-- empty --"
    ::= { lcsSetupXdsl 1 }

-- {SCALAR} 1.3.6.1.4.1.2356.11.2.42.2
lcsSetupXdslSyncLimitsTxRate OBJECT-TYPE
    SYNTAX     INTEGER {
                  eNo (0),
                  eYes (1)
            }
    MAX-ACCESS read-write
    STATUS     current
    DESCRIPTION
            "-- empty --"
    ::= { lcsSetupXdsl 2 }

-- {TABLE} 1.3.6.1.4.1.2356.11.2.42.3
lcsSetupXdslWanBridgeTable OBJECT-TYPE
    SYNTAX     SEQUENCE OF LcsSetupXdslWanBridgeEntry
    MAX-ACCESS not-accessible
    STATUS     current
    DESCRIPTION
            "-- empty --"
    ::= { lcsSetupXdsl 3 }

-- {ROW} 1.3.6.1.4.1.2356.11.2.42.3.1
lcsSetupXdslWanBridgeEntry OBJECT-TYPE
    SYNTAX     LcsSetupXdslWanBridgeEntry
    MAX-ACCESS not-accessible
    STATUS     current
    DESCRIPTION
            ""
    INDEX {
            lcsSetupXdslWanBridgeEntryInterface
          }
    ::= { lcsSetupXdslWanBridgeTable 1 }

LcsSetupXdslWanBridgeEntry ::= SEQUENCE {
            lcsSetupXdslWanBridgeEntryInterface INTEGER,
            lcsSetupXdslWanBridgeEntryMode INTEGER,
            lcsSetupXdslWanBridgeEntryAtmVpi Integer32,
            lcsSetupXdslWanBridgeEntryAtmVci Integer32,
            lcsSetupXdslWanBridgeEntryAtmMuxmode INTEGER
    }

-- {COLUMN} 1.3.6.1.4.1.2356.11.2.42.3.1.1
lcsSetupXdslWanBridgeEntryInterface OBJECT-TYPE
    SYNTAX     INTEGER {
                  eXdsl1 (1),
                  eXdsl2 (2)
            }
    MAX-ACCESS read-only
    STATUS     current
    DESCRIPTION
            "-- empty --"
    ::= { lcsSetupXdslWanBridgeEntry 1 }

-- {COLUMN} 1.3.6.1.4.1.2356.11.2.42.3.1.2
lcsSetupXdslWanBridgeEntryMode OBJECT-TYPE
    SYNTAX     INTEGER {
                  eRouter (0),
                  eBridge (1)
            }
    MAX-ACCESS read-write
    STATUS     current
    DESCRIPTION
            "-- empty --"
    ::= { lcsSetupXdslWanBridgeEntry 2 }

-- {COLUMN} 1.3.6.1.4.1.2356.11.2.42.3.1.3
lcsSetupXdslWanBridgeEntryAtmVpi OBJECT-TYPE
    SYNTAX     Integer32 (0..255)
    MAX-ACCESS read-write
    STATUS     current
    DESCRIPTION
            "-- empty --"
    ::= { lcsSetupXdslWanBridgeEntry 3 }

-- {COLUMN} 1.3.6.1.4.1.2356.11.2.42.3.1.4
lcsSetupXdslWanBridgeEntryAtmVci OBJECT-TYPE
    SYNTAX     Integer32 (0..65535)
    MAX-ACCESS read-write
    STATUS     current
    DESCRIPTION
            "-- empty --"
    ::= { lcsSetupXdslWanBridgeEntry 4 }

-- {COLUMN} 1.3.6.1.4.1.2356.11.2.42.3.1.5
lcsSetupXdslWanBridgeEntryAtmMuxmode OBJECT-TYPE
    SYNTAX     INTEGER {
                  eVcMux (0),
                  eLlcMux (1)
            }
    MAX-ACCESS read-write
    STATUS     current
    DESCRIPTION
            "-- empty --"
    ::= { lcsSetupXdslWanBridgeEntry 5 }

-- {NODE} 1.3.6.1.4.1.2356.11.2.44
lcsSetupCwmp OBJECT IDENTIFIER ::= { lcsSetup 44 }

-- {NODE} 1.3.6.1.4.1.2356.11.2.44.1
lcsSetupCwmpNtpServer OBJECT IDENTIFIER ::= { lcsSetupCwmp 1 }

-- {SCALAR} 1.3.6.1.4.1.2356.11.2.44.1.1
lcsSetupCwmpNtpServerNtpServer1 OBJECT-TYPE
    SYNTAX     DisplayString (SIZE(0..63))
    MAX-ACCESS read-only
    STATUS     current
    DESCRIPTION
            "-- empty --"
    ::= { lcsSetupCwmpNtpServer 1 }

-- {SCALAR} 1.3.6.1.4.1.2356.11.2.44.1.2
lcsSetupCwmpNtpServerNtpServer2 OBJECT-TYPE
    SYNTAX     DisplayString (SIZE(0..63))
    MAX-ACCESS read-only
    STATUS     current
    DESCRIPTION
            "-- empty --"
    ::= { lcsSetupCwmpNtpServer 2 }

-- {SCALAR} 1.3.6.1.4.1.2356.11.2.44.1.3
lcsSetupCwmpNtpServerNtpServer3 OBJECT-TYPE
    SYNTAX     DisplayString (SIZE(0..63))
    MAX-ACCESS read-only
    STATUS     current
    DESCRIPTION
            "-- empty --"
    ::= { lcsSetupCwmpNtpServer 3 }

-- {SCALAR} 1.3.6.1.4.1.2356.11.2.44.1.4
lcsSetupCwmpNtpServerNtpServer4 OBJECT-TYPE
    SYNTAX     DisplayString (SIZE(0..63))
    MAX-ACCESS read-only
    STATUS     current
    DESCRIPTION
            "-- empty --"
    ::= { lcsSetupCwmpNtpServer 4 }

-- {SCALAR} 1.3.6.1.4.1.2356.11.2.44.1.5
lcsSetupCwmpNtpServerNtpServer5 OBJECT-TYPE
    SYNTAX     DisplayString (SIZE(0..63))
    MAX-ACCESS read-only
    STATUS     current
    DESCRIPTION
            "-- empty --"
    ::= { lcsSetupCwmpNtpServer 5 }

-- {SCALAR} 1.3.6.1.4.1.2356.11.2.44.2
lcsSetupCwmpOperating OBJECT-TYPE
    SYNTAX     INTEGER {
                  eNo (0),
                  eYes (1)
            }
    MAX-ACCESS read-write
    STATUS     current
    DESCRIPTION
            "-- empty --"
    ::= { lcsSetupCwmp 2 }

-- {SCALAR} 1.3.6.1.4.1.2356.11.2.44.3
lcsSetupCwmpAllowFileDownload OBJECT-TYPE
    SYNTAX     INTEGER {
                  eNo (0),
                  eYes (1)
            }
    MAX-ACCESS read-write
    STATUS     current
    DESCRIPTION
            "-- empty --"
    ::= { lcsSetupCwmp 3 }

-- {SCALAR} 1.3.6.1.4.1.2356.11.2.44.4
lcsSetupCwmpInformRetryLimit OBJECT-TYPE
    SYNTAX     Integer32 (0..2147483647)
    MAX-ACCESS read-write
    STATUS     current
    DESCRIPTION
            "-- empty --"
    ::= { lcsSetupCwmp 4 }

-- {SCALAR} 1.3.6.1.4.1.2356.11.2.44.5
lcsSetupCwmpLoopbackAddress OBJECT-TYPE
    SYNTAX     DisplayString (SIZE(0..16))
    MAX-ACCESS read-write
    STATUS     current
    DESCRIPTION
            "-- empty --"
    ::= { lcsSetupCwmp 5 }

-- {SCALAR} 1.3.6.1.4.1.2356.11.2.44.6
lcsSetupCwmpAcsUrl OBJECT-TYPE
    SYNTAX     DisplayString (SIZE(0..256))
    MAX-ACCESS read-write
    STATUS     current
    DESCRIPTION
            "-- empty --"
    ::= { lcsSetupCwmp 6 }

-- {SCALAR} 1.3.6.1.4.1.2356.11.2.44.7
lcsSetupCwmpAcsUsername OBJECT-TYPE
    SYNTAX     DisplayString (SIZE(0..256))
    MAX-ACCESS read-write
    STATUS     current
    DESCRIPTION
            "-- empty --"
    ::= { lcsSetupCwmp 7 }

-- {SCALAR} 1.3.6.1.4.1.2356.11.2.44.8
lcsSetupCwmpAcsPassword OBJECT-TYPE
    SYNTAX     DisplayString (SIZE(0..256))
    MAX-ACCESS read-write
    STATUS     current
    DESCRIPTION
            "-- empty --"
    ::= { lcsSetupCwmp 8 }

-- {SCALAR} 1.3.6.1.4.1.2356.11.2.44.9
lcsSetupCwmpPeriodicInformEnable OBJECT-TYPE
    SYNTAX     INTEGER {
                  eNo (0),
                  eYes (1)
            }
    MAX-ACCESS read-write
    STATUS     current
    DESCRIPTION
            "-- empty --"
    ::= { lcsSetupCwmp 9 }

-- {SCALAR} 1.3.6.1.4.1.2356.11.2.44.10
lcsSetupCwmpPeriodicInformInterval OBJECT-TYPE
    SYNTAX     Integer32 (0..2147483647)
    MAX-ACCESS read-write
    STATUS     current
    DESCRIPTION
            "-- empty --"
    ::= { lcsSetupCwmp 10 }

-- {SCALAR} 1.3.6.1.4.1.2356.11.2.44.11
lcsSetupCwmpPeriodicInformTime OBJECT-TYPE
    SYNTAX     DisplayString (SIZE(0..63))
    MAX-ACCESS read-write
    STATUS     current
    DESCRIPTION
            "-- empty --"
    ::= { lcsSetupCwmp 11 }

-- {SCALAR} 1.3.6.1.4.1.2356.11.2.44.12
lcsSetupCwmpConnectionRequestUsername OBJECT-TYPE
    SYNTAX     DisplayString (SIZE(0..256))
    MAX-ACCESS read-write
    STATUS     current
    DESCRIPTION
            "-- empty --"
    ::= { lcsSetupCwmp 12 }

-- {SCALAR} 1.3.6.1.4.1.2356.11.2.44.13
lcsSetupCwmpUpgradesManaged OBJECT-TYPE
    SYNTAX     INTEGER {
                  eNo (0),
                  eYes (1)
            }
    MAX-ACCESS read-write
    STATUS     current
    DESCRIPTION
            "-- empty --"
    ::= { lcsSetupCwmp 13 }

-- {SCALAR} 1.3.6.1.4.1.2356.11.2.44.14
lcsSetupCwmpAllowUserChange OBJECT-TYPE
    SYNTAX     INTEGER {
                  eNo (0),
                  eYes (1)
            }
    MAX-ACCESS read-write
    STATUS     current
    DESCRIPTION
            "-- empty --"
    ::= { lcsSetupCwmp 14 }

-- {SCALAR} 1.3.6.1.4.1.2356.11.2.44.15
lcsSetupCwmpProvisioningCode OBJECT-TYPE
    SYNTAX     DisplayString (SIZE(0..63))
    MAX-ACCESS read-only
    STATUS     current
    DESCRIPTION
            "-- empty --"
    ::= { lcsSetupCwmp 15 }

-- {SCALAR} 1.3.6.1.4.1.2356.11.2.44.16
lcsSetupCwmpParameterKey OBJECT-TYPE
    SYNTAX     DisplayString (SIZE(0..63))
    MAX-ACCESS read-only
    STATUS     current
    DESCRIPTION
            "-- empty --"
    ::= { lcsSetupCwmp 16 }

-- {SCALAR} 1.3.6.1.4.1.2356.11.2.44.17
lcsSetupCwmpCommandKey OBJECT-TYPE
    SYNTAX     DisplayString (SIZE(0..31))
    MAX-ACCESS read-only
    STATUS     current
    DESCRIPTION
            "-- empty --"
    ::= { lcsSetupCwmp 17 }

-- {SCALAR} 1.3.6.1.4.1.2356.11.2.44.18
lcsSetupCwmpDataModel OBJECT-TYPE
    SYNTAX     INTEGER {
                  eTr098 (0),
                  eTr181 (1)
            }
    MAX-ACCESS read-write
    STATUS     current
    DESCRIPTION
            "-- empty --"
    ::= { lcsSetupCwmp 18 }

-- {SCALAR} 1.3.6.1.4.1.2356.11.2.44.19
lcsSetupCwmpLocalPort OBJECT-TYPE
    SYNTAX     Integer32 (0..65535)
    MAX-ACCESS read-write
    STATUS     current
    DESCRIPTION
            "-- empty --"
    ::= { lcsSetupCwmp 19 }

-- {SCALAR} 1.3.6.1.4.1.2356.11.2.44.20
lcsSetupCwmpConnectionRequestPassword OBJECT-TYPE
    SYNTAX     DisplayString (SIZE(0..256))
    MAX-ACCESS read-write
    STATUS     current
    DESCRIPTION
            "-- empty --"
    ::= { lcsSetupCwmp 20 }

-- {SCALAR} 1.3.6.1.4.1.2356.11.2.44.23
lcsSetupCwmpConfigurationManaged OBJECT-TYPE
    SYNTAX     INTEGER {
                  eNo (0),
                  eYes (1)
            }
    MAX-ACCESS read-write
    STATUS     current
    DESCRIPTION
            "-- empty --"
    ::= { lcsSetupCwmp 23 }

-- {NODE} 1.3.6.1.4.1.2356.11.2.44.26
lcsSetupCwmpSslNew OBJECT IDENTIFIER ::= { lcsSetupCwmp 26 }

-- {SCALAR} 1.3.6.1.4.1.2356.11.2.44.26.1
lcsSetupCwmpSslNewVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupCwmpSslNew 1 }

-- {SCALAR} 1.3.6.1.4.1.2356.11.2.44.26.2
lcsSetupCwmpSslNewKeyexAlgorithms OBJECT-TYPE
    SYNTAX     BITS {
                  eEcdhe (27),
                  eDhe (29),
                  eRsa (31)
            }
    MAX-ACCESS read-write
    STATUS     current
    DESCRIPTION
            "-- empty --"
    ::= { lcsSetupCwmpSslNew 2 }

-- {SCALAR} 1.3.6.1.4.1.2356.11.2.44.26.3
lcsSetupCwmpSslNewCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupCwmpSslNew 3 }

-- {SCALAR} 1.3.6.1.4.1.2356.11.2.44.26.4
lcsSetupCwmpSslNewHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupCwmpSslNew 4 }

-- {SCALAR} 1.3.6.1.4.1.2356.11.2.44.26.5
lcsSetupCwmpSslNewPreferPfs OBJECT-TYPE
    SYNTAX     BITS {
                  eNo (0),
                  eYes (7)
            }
    MAX-ACCESS read-write
    STATUS     current
    DESCRIPTION
            "-- empty --"
    ::= { lcsSetupCwmpSslNew 5 }

-- {SCALAR} 1.3.6.1.4.1.2356.11.2.44.26.6
lcsSetupCwmpSslNewRenegotiations OBJECT-TYPE
    SYNTAX     INTEGER {
                  eForbidden (0),
                  eAllowed (1),
                  eIgnored (2)
            }
    MAX-ACCESS read-write
    STATUS     current
    DESCRIPTION
            "-- empty --"
    ::= { lcsSetupCwmpSslNew 6 }

-- {SCALAR} 1.3.6.1.4.1.2356.11.2.44.26.7
lcsSetupCwmpSslNewEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupCwmpSslNew 7 }

-- {SCALAR} 1.3.6.1.4.1.2356.11.2.44.26.21
lcsSetupCwmpSslNewSigHashAlgs OBJECT-TYPE
    SYNTAX     BITS {
                  eSha512Ecdsa (20),
                  eSha384Ecdsa (21),
                  eSha256Ecdsa (22),
                  eSha224Ecdsa (23),
                  eSha1Ecdsa (24),
                  eSha512Rsa (26),
                  eSha384Rsa (27),
                  eSha256Rsa (28),
                  eSha224Rsa (29),
                  eSha1Rsa (30)
            }
    MAX-ACCESS read-write
    STATUS     current
    DESCRIPTION
            "list of allowed signature/hash algorithms"
    ::= { lcsSetupCwmpSslNew 21 }

-- {NODE} 1.3.6.1.4.1.2356.11.2.45
lcsSetupSlaMonitor OBJECT IDENTIFIER ::= { lcsSetup 45 }

-- {TABLE} 1.3.6.1.4.1.2356.11.2.45.1
lcsSetupSlaMonitorIcmpTable OBJECT-TYPE
    SYNTAX     SEQUENCE OF LcsSetupSlaMonitorIcmpEntry
    MAX-ACCESS not-accessible
    STATUS     current
    DESCRIPTION
            "-- empty --"
    ::= { lcsSetupSlaMonitor 1 }

-- {ROW} 1.3.6.1.4.1.2356.11.2.45.1.1
lcsSetupSlaMonitorIcmpEntry OBJECT-TYPE
    SYNTAX     LcsSetupSlaMonitorIcmpEntry
    MAX-ACCESS not-accessible
    STATUS     current
    DESCRIPTION
            ""
    INDEX {
            lcsSetupSlaMonitorIcmpEntryName
          }
    ::= { lcsSetupSlaMonitorIcmpTable 1 }

LcsSetupSlaMonitorIcmpEntry ::= SEQUENCE {
            lcsSetupSlaMonitorIcmpEntryName DisplayString,
            lcsSetupSlaMonitorIcmpEntryActive INTEGER,
            lcsSetupSlaMonitorIcmpEntryDestination DisplayString,
            lcsSetupSlaMonitorIcmpEntryRtgTag Integer32,
            lcsSetupSlaMonitorIcmpEntryLoopbackAddress DisplayString,
            lcsSetupSlaMonitorIcmpEntryInterval Integer32,
            lcsSetupSlaMonitorIcmpEntryStartOffset Integer32,
            lcsSetupSlaMonitorIcmpEntryCount Integer32,
            lcsSetupSlaMonitorIcmpEntryPacketDelay Integer32,
            lcsSetupSlaMonitorIcmpEntryPacketSize Integer32,
            lcsSetupSlaMonitorIcmpEntryWarnLvlRttMax Integer32,
            lcsSetupSlaMonitorIcmpEntryCritLvlRttMax Integer32,
            lcsSetupSlaMonitorIcmpEntryWarnLvlRttAvg Integer32,
            lcsSetupSlaMonitorIcmpEntryCritLvlRttAvg Integer32,
            lcsSetupSlaMonitorIcmpEntryWarnLvlPktLossPercent Integer32,
            lcsSetupSlaMonitorIcmpEntryCritLvlPktLossPercent Integer32,
            lcsSetupSlaMonitorIcmpEntryIpVersion INTEGER,
            lcsSetupSlaMonitorIcmpEntryComment DisplayString,
            lcsSetupSlaMonitorIcmpEntryWarnLvlJitter Integer32,
            lcsSetupSlaMonitorIcmpEntryCritLvlJitter Integer32,
            lcsSetupSlaMonitorIcmpEntryDscp INTEGER
    }

-- {COLUMN} 1.3.6.1.4.1.2356.11.2.45.1.1.1
lcsSetupSlaMonitorIcmpEntryName OBJECT-TYPE
    SYNTAX     DisplayString (SIZE(0..16))
    MAX-ACCESS read-write
    STATUS     current
    DESCRIPTION
            "-- empty --"
    ::= { lcsSetupSlaMonitorIcmpEntry 1 }

-- {COLUMN} 1.3.6.1.4.1.2356.11.2.45.1.1.2
lcsSetupSlaMonitorIcmpEntryActive OBJECT-TYPE
    SYNTAX     INTEGER {
                  eNo (0),
                  eYes (1)
            }
    MAX-ACCESS read-write
    STATUS     current
    DESCRIPTION
            "-- empty --"
    ::= { lcsSetupSlaMonitorIcmpEntry 2 }

-- {COLUMN} 1.3.6.1.4.1.2356.11.2.45.1.1.3
lcsSetupSlaMonitorIcmpEntryDestination OBJECT-TYPE
    SYNTAX     DisplayString (SIZE(0..40))
    MAX-ACCESS read-write
    STATUS     current
    DESCRIPTION
            "-- empty --"
    ::= { lcsSetupSlaMonitorIcmpEntry 3 }

-- {COLUMN} 1.3.6.1.4.1.2356.11.2.45.1.1.4
lcsSetupSlaMonitorIcmpEntryRtgTag OBJECT-TYPE
    SYNTAX     Integer32 (0..2147483647)
    MAX-ACCESS read-write
    STATUS     current
    DESCRIPTION
            "-- empty --"
    ::= { lcsSetupSlaMonitorIcmpEntry 4 }

-- {COLUMN} 1.3.6.1.4.1.2356.11.2.45.1.1.5
lcsSetupSlaMonitorIcmpEntryLoopbackAddress OBJECT-TYPE
    SYNTAX     DisplayString (SIZE(0..56))
    MAX-ACCESS read-write
    STATUS     current
    DESCRIPTION
            "-- empty --"
    ::= { lcsSetupSlaMonitorIcmpEntry 5 }

-- {COLUMN} 1.3.6.1.4.1.2356.11.2.45.1.1.6
lcsSetupSlaMonitorIcmpEntryInterval OBJECT-TYPE
    SYNTAX     Integer32 (0..2147483647)
    MAX-ACCESS read-write
    STATUS     current
    DESCRIPTION
            "-- empty --"
    ::= { lcsSetupSlaMonitorIcmpEntry 6 }

-- {COLUMN} 1.3.6.1.4.1.2356.11.2.45.1.1.7
lcsSetupSlaMonitorIcmpEntryStartOffset OBJECT-TYPE
    SYNTAX     Integer32 (0..2147483647)
    MAX-ACCESS read-write
    STATUS     current
    DESCRIPTION
            "-- empty --"
    ::= { lcsSetupSlaMonitorIcmpEntry 7 }

-- {COLUMN} 1.3.6.1.4.1.2356.11.2.45.1.1.8
lcsSetupSlaMonitorIcmpEntryCount OBJECT-TYPE
    SYNTAX     Integer32 (0..2147483647)
    MAX-ACCESS read-write
    STATUS     current
    DESCRIPTION
            "-- empty --"
    ::= { lcsSetupSlaMonitorIcmpEntry 8 }

-- {COLUMN} 1.3.6.1.4.1.2356.11.2.45.1.1.9
lcsSetupSlaMonitorIcmpEntryPacketDelay OBJECT-TYPE
    SYNTAX     Integer32 (0..2147483647)
    MAX-ACCESS read-write
    STATUS     current
    DESCRIPTION
            "-- empty --"
    ::= { lcsSetupSlaMonitorIcmpEntry 9 }

-- {COLUMN} 1.3.6.1.4.1.2356.11.2.45.1.1.10
lcsSetupSlaMonitorIcmpEntryPacketSize OBJECT-TYPE
    SYNTAX     Integer32 (0..2147483647)
    MAX-ACCESS read-write
    STATUS     current
    DESCRIPTION
            "-- empty --"
    ::= { lcsSetupSlaMonitorIcmpEntry 10 }

-- {COLUMN} 1.3.6.1.4.1.2356.11.2.45.1.1.11
lcsSetupSlaMonitorIcmpEntryWarnLvlRttMax OBJECT-TYPE
    SYNTAX     Integer32 (0..2147483647)
    MAX-ACCESS read-write
    STATUS     current
    DESCRIPTION
            "-- empty --"
    ::= { lcsSetupSlaMonitorIcmpEntry 11 }

-- {COLUMN} 1.3.6.1.4.1.2356.11.2.45.1.1.12
lcsSetupSlaMonitorIcmpEntryCritLvlRttMax OBJECT-TYPE
    SYNTAX     Integer32 (0..2147483647)
    MAX-ACCESS read-write
    STATUS     current
    DESCRIPTION
            "-- empty --"
    ::= { lcsSetupSlaMonitorIcmpEntry 12 }

-- {COLUMN} 1.3.6.1.4.1.2356.11.2.45.1.1.13
lcsSetupSlaMonitorIcmpEntryWarnLvlRttAvg OBJECT-TYPE
    SYNTAX     Integer32 (0..2147483647)
    MAX-ACCESS read-write
    STATUS     current
    DESCRIPTION
            "-- empty --"
    ::= { lcsSetupSlaMonitorIcmpEntry 13 }

-- {COLUMN} 1.3.6.1.4.1.2356.11.2.45.1.1.14
lcsSetupSlaMonitorIcmpEntryCritLvlRttAvg OBJECT-TYPE
    SYNTAX     Integer32 (0..2147483647)
    MAX-ACCESS read-write
    STATUS     current
    DESCRIPTION
            "-- empty --"
    ::= { lcsSetupSlaMonitorIcmpEntry 14 }

-- {COLUMN} 1.3.6.1.4.1.2356.11.2.45.1.1.15
lcsSetupSlaMonitorIcmpEntryWarnLvlPktLossPercent OBJECT-TYPE
    SYNTAX     Integer32 (0..2147483647)
    MAX-ACCESS read-write
    STATUS     current
    DESCRIPTION
            "-- empty --"
    ::= { lcsSetupSlaMonitorIcmpEntry 15 }

-- {COLUMN} 1.3.6.1.4.1.2356.11.2.45.1.1.16
lcsSetupSlaMonitorIcmpEntryCritLvlPktLossPercent OBJECT-TYPE
    SYNTAX     Integer32 (0..2147483647)
    MAX-ACCESS read-write
    STATUS     current
    DESCRIPTION
            "-- empty --"
    ::= { lcsSetupSlaMonitorIcmpEntry 16 }

-- {COLUMN} 1.3.6.1.4.1.2356.11.2.45.1.1.17
lcsSetupSlaMonitorIcmpEntryIpVersion OBJECT-TYPE
    SYNTAX     INTEGER {
                  eAuto (0),
                  eIpv4 (1),
                  eIpv6 (2)
            }
    MAX-ACCESS read-write
    STATUS     current
    DESCRIPTION
            "-- empty --"
    ::= { lcsSetupSlaMonitorIcmpEntry 17 }

-- {COLUMN} 1.3.6.1.4.1.2356.11.2.45.1.1.19
lcsSetupSlaMonitorIcmpEntryComment OBJECT-TYPE
    SYNTAX     DisplayString (SIZE(0..63))
    MAX-ACCESS read-write
    STATUS     current
    DESCRIPTION
            "-- empty --"
    ::= { lcsSetupSlaMonitorIcmpEntry 19 }

-- {COLUMN} 1.3.6.1.4.1.2356.11.2.45.1.1.20
lcsSetupSlaMonitorIcmpEntryWarnLvlJitter OBJECT-TYPE
    SYNTAX     Integer32 (0..2147483647)
    MAX-ACCESS read-write
    STATUS     current
    DESCRIPTION
            "-- empty --"
    ::= { lcsSetupSlaMonitorIcmpEntry 20 }

-- {COLUMN} 1.3.6.1.4.1.2356.11.2.45.1.1.21
lcsSetupSlaMonitorIcmpEntryCritLvlJitter OBJECT-TYPE
    SYNTAX     Integer32 (0..2147483647)
    MAX-ACCESS read-write
    STATUS     current
    DESCRIPTION
            "-- empty --"
    ::= { lcsSetupSlaMonitorIcmpEntry 21 }

-- {COLUMN} 1.3.6.1.4.1.2356.11.2.45.1.1.22
lcsSetupSlaMonitorIcmpEntryDscp OBJECT-TYPE
    SYNTAX     INTEGER {
                  eBeCs0 (0),
                  eCs1 (32),
                  eAf11 (40),
                  eAf12 (48),
                  eAf13 (56),
                  eCs2 (64),
                  eAf21 (72),
                  eAf22 (80),
                  eAf23 (88),
                  eCs3 (96),
                  eAf31 (104),
                  eAf32 (112),
                  eAf33 (120),
                  eCs4 (128),
                  eAf41 (136),
                  eAf42 (144),
                  eAf43 (152),
                  eCs5 (160),
                  eEf (184),
                  eCs6 (192),
                  eCs7 (224)
            }
    MAX-ACCESS read-write
    STATUS     current
    DESCRIPTION
            "-- empty --"
    ::= { lcsSetupSlaMonitorIcmpEntry 22 }

-- {SCALAR} 1.3.6.1.4.1.2356.11.2.45.2
lcsSetupSlaMonitorEventCount OBJECT-TYPE
    SYNTAX     Integer32 (0..2147483647)
    MAX-ACCESS read-write
    STATUS     current
    DESCRIPTION
            "-- empty --"
    ::= { lcsSetupSlaMonitor 2 }

-- {SCALAR} 1.3.6.1.4.1.2356.11.2.45.3
lcsSetupSlaMonitorStartupDelay OBJECT-TYPE
    SYNTAX     Integer32 (0..2147483647)
    MAX-ACCESS read-write
    STATUS     current
    DESCRIPTION
            "-- empty --"
    ::= { lcsSetupSlaMonitor 3 }

-- {NODE} 1.3.6.1.4.1.2356.11.2.52
lcsSetupComPorts OBJECT IDENTIFIER ::= { lcsSetup 52 }

-- {TABLE} 1.3.6.1.4.1.2356.11.2.52.1
lcsSetupComPortsDevTable OBJECT-TYPE
    SYNTAX     SEQUENCE OF LcsSetupComPortsDevEntry
    MAX-ACCESS not-accessible
    STATUS     current
    DESCRIPTION
            ""
    ::= { lcsSetupComPorts 1 }

-- {ROW} 1.3.6.1.4.1.2356.11.2.52.1.1
lcsSetupComPortsDevEntry OBJECT-TYPE
    SYNTAX     LcsSetupComPortsDevEntry
    MAX-ACCESS not-accessible
    STATUS     current
    DESCRIPTION
            ""
    INDEX {
            lcsSetupComPortsDevEntryDeviceType
          }
    ::= { lcsSetupComPortsDevTable 1 }

LcsSetupComPortsDevEntry ::= SEQUENCE {
            lcsSetupComPortsDevEntryDeviceType INTEGER,
            lcsSetupComPortsDevEntryServ INTEGER
    }

-- {COLUMN} 1.3.6.1.4.1.2356.11.2.52.1.1.1
lcsSetupComPortsDevEntryDeviceType OBJECT-TYPE
    SYNTAX     INTEGER {
                  eOutband (1),
                  eSierraMinicard8780 (11),
                  eSierraMinicard8781 (12),
                  eOptionIcon (17),
                  eOptionMinicard0201 (19),
                  eHuaweiE612E630E1750 (21),
                  e4gSystemsUxs1 (23),
                  eNovatelMerlinMc950d (26),
                  eSierraAircard875u (30),
                  eHuaweiE172E220E870 (31),
                  eBelkinF5u103 (33),
                  eProlific2303 (34),
                  eFtdi8u232am (35),
                  eGpsNmea (36),
                  eSierraMinicard8790 (38),
                  eSierraCompass885 (39),
                  eQualcomDm (45),
                  eSierraAircard501 (46),
                  eHuaweiK4505 (49),
                  eHuaweiK3765 (51),
                  eSierraDirectIp (53),
                  eHuaweiE182 (54),
                  eSierraMinicard8705 (55),
                  eSierraMinicard8801 (56),
                  eHuaweiE1750 (57),
                  eNokiaCs19 (59),
                  eHuaweiE398 (60),
                  eHuaweiE1550 (61),
                  eSierraMinicard7710 (62),
                  eHuaweiE352 (64),
                  eSierraQmi73xx (66),
                  eSierraQmi74xx (67),
                  eUsbSerialAdapter (72),
                  eSubghzModule (73),
                  eSierraQmi75xx (74),
                  eModuleConsole (76),
                  eFtdi232h (77)
            }
    MAX-ACCESS read-write
    STATUS     current
    DESCRIPTION
            ""
    ::= { lcsSetupComPortsDevEntry 1 }

-- {COLUMN} 1.3.6.1.4.1.2356.11.2.52.1.1.4
lcsSetupComPortsDevEntryServ OBJECT-TYPE
    SYNTAX     INTEGER {
                  eWan (1),
                  eCOMPortServ (2),
                  eUps (8),
                  eEpaper (16)
            }
    MAX-ACCESS read-write
    STATUS     current
    DESCRIPTION
            ""
    ::= { lcsSetupComPortsDevEntry 4 }

-- {NODE} 1.3.6.1.4.1.2356.11.2.52.2
lcsSetupComPortsCOMPortServ OBJECT IDENTIFIER ::= { lcsSetupComPorts 2 }

-- {TABLE} 1.3.6.1.4.1.2356.11.2.52.2.1
lcsSetupComPortsCOMPortServOperTable OBJECT-TYPE
    SYNTAX     SEQUENCE OF LcsSetupComPortsCOMPortServOperEntry
    MAX-ACCESS not-accessible
    STATUS     current
    DESCRIPTION
            ""
    ::= { lcsSetupComPortsCOMPortServ 1 }

-- {ROW} 1.3.6.1.4.1.2356.11.2.52.2.1.1
lcsSetupComPortsCOMPortServOperEntry OBJECT-TYPE
    SYNTAX     LcsSetupComPortsCOMPortServOperEntry
    MAX-ACCESS not-accessible
    STATUS     current
    DESCRIPTION
            ""
    INDEX {
            lcsSetupComPortsCOMPortServOperEntryDeviceType,
            lcsSetupComPortsCOMPortServOperEntryPortNumber
          }
    ::= { lcsSetupComPortsCOMPortServOperTable 1 }

LcsSetupComPortsCOMPortServOperEntry ::= SEQUENCE {
            lcsSetupComPortsCOMPortServOperEntryDeviceType INTEGER,
            lcsSetupComPortsCOMPortServOperEntryPortNumber Integer32,
            lcsSetupComPortsCOMPortServOperEntryOperating INTEGER
    }

-- {COLUMN} 1.3.6.1.4.1.2356.11.2.52.2.1.1.1
lcsSetupComPortsCOMPortServOperEntryDeviceType OBJECT-TYPE
    SYNTAX     INTEGER {
                  eOutband (1),
                  eBelkinF5u103 (33),
                  eProlific2303 (34),
                  eFtdi8u232am (35),
                  eGpsNmea (36),
                  eQualcomDm (45),
                  eUsbSerialAdapter (72),
                  eSubghzModule (73),
                  eModuleConsole (76),
                  eFtdi232h (77)
            }
    MAX-ACCESS read-write
    STATUS     current
    DESCRIPTION
            ""
    ::= { lcsSetupComPortsCOMPortServOperEntry 1 }

-- {COLUMN} 1.3.6.1.4.1.2356.11.2.52.2.1.1.2
lcsSetupComPortsCOMPortServOperEntryPortNumber OBJECT-TYPE
    SYNTAX     Integer32 (0..255)
    MAX-ACCESS read-write
    STATUS     current
    DESCRIPTION
            ""
    ::= { lcsSetupComPortsCOMPortServOperEntry 2 }

-- {COLUMN} 1.3.6.1.4.1.2356.11.2.52.2.1.1.4
lcsSetupComPortsCOMPortServOperEntryOperating OBJECT-TYPE
    SYNTAX     INTEGER {
                  eNo (0),
                  eYes (1)
            }
    MAX-ACCESS read-write
    STATUS     current
    DESCRIPTION
            ""
    ::= { lcsSetupComPortsCOMPortServOperEntry 4 }

-- {TABLE} 1.3.6.1.4.1.2356.11.2.52.2.2
lcsSetupComPortsCOMPortServCOMPortSetTable OBJECT-TYPE
    SYNTAX     SEQUENCE OF LcsSetupComPortsCOMPortServCOMPortSetEntry
    MAX-ACCESS not-accessible
    STATUS     current
    DESCRIPTION
            ""
    ::= { lcsSetupComPortsCOMPortServ 2 }

-- {ROW} 1.3.6.1.4.1.2356.11.2.52.2.2.1
lcsSetupComPortsCOMPortServCOMPortSetEntry OBJECT-TYPE
    SYNTAX     LcsSetupComPortsCOMPortServCOMPortSetEntry
    MAX-ACCESS not-accessible
    STATUS     current
    DESCRIPTION
            ""
    INDEX {
            lcsSetupComPortsCOMPortServCOMPortSetEntryDeviceType,
            lcsSetupComPortsCOMPortServCOMPortSetEntryPortNumber
          }
    ::= { lcsSetupComPortsCOMPortServCOMPortSetTable 1 }

LcsSetupComPortsCOMPortServCOMPortSetEntry ::= SEQUENCE {
            lcsSetupComPortsCOMPortServCOMPortSetEntryDeviceType INTEGER,
            lcsSetupComPortsCOMPortServCOMPortSetEntryPortNumber Integer32,
            lcsSetupComPortsCOMPortServCOMPortSetEntryBitRate INTEGER,
            lcsSetupComPortsCOMPortServCOMPortSetEntryDataBits INTEGER,
            lcsSetupComPortsCOMPortServCOMPortSetEntryParity INTEGER,
            lcsSetupComPortsCOMPortServCOMPortSetEntryStopBits INTEGER,
            lcsSetupComPortsCOMPortServCOMPortSetEntryHandshake INTEGER,
            lcsSetupComPortsCOMPortServCOMPortSetEntryReadyCondition INTEGER,
            lcsSetupComPortsCOMPortServCOMPortSetEntryReadyDataTimeout Integer32
    }

-- {COLUMN} 1.3.6.1.4.1.2356.11.2.52.2.2.1.1
lcsSetupComPortsCOMPortServCOMPortSetEntryDeviceType OBJECT-TYPE
    SYNTAX     INTEGER {
                  eOutband (1),
                  eBelkinF5u103 (33),
                  eProlific2303 (34),
                  eFtdi8u232am (35),
                  eGpsNmea (36),
                  eQualcomDm (45),
                  eUsbSerialAdapter (72),
                  eSubghzModule (73),
                  eModuleConsole (76),
                  eFtdi232h (77)
            }
    MAX-ACCESS read-write
    STATUS     current
    DESCRIPTION
            ""
    ::= { lcsSetupComPortsCOMPortServCOMPortSetEntry 1 }

-- {COLUMN} 1.3.6.1.4.1.2356.11.2.52.2.2.1.2
lcsSetupComPortsCOMPortServCOMPortSetEntryPortNumber OBJECT-TYPE
    SYNTAX     Integer32 (0..255)
    MAX-ACCESS read-write
    STATUS     current
    DESCRIPTION
            ""
    ::= { lcsSetupComPortsCOMPortServCOMPortSetEntry 2 }

-- {COLUMN} 1.3.6.1.4.1.2356.11.2.52.2.2.1.4
lcsSetupComPortsCOMPortServCOMPortSetEntryBitRate OBJECT-TYPE
    SYNTAX     INTEGER {
                  e110 (110),
                  e300 (300),
                  e600 (600),
                  e1200 (1200),
                  e2400 (2400),
                  e4800 (4800),
                  e9600 (9600),
                  e19200 (19200),
                  e38400 (38400),
                  e57600 (57600),
                  e74880 (74880),
                  e76800 (76800),
                  e115200 (115200),
                  e125000 (125000),
                  e230400 (230400),
                  e460800 (460800),
                  e921600 (921600),
                  e1000000 (1000000),
                  e1500000 (1500000),
                  e2000000 (2000000),
                  e3000000 (3000000)
            }
    MAX-ACCESS read-write
    STATUS     current
    DESCRIPTION
            ""
    ::= { lcsSetupComPortsCOMPortServCOMPortSetEntry 4 }

-- {COLUMN} 1.3.6.1.4.1.2356.11.2.52.2.2.1.5
lcsSetupComPortsCOMPortServCOMPortSetEntryDataBits OBJECT-TYPE
    SYNTAX     INTEGER {
                  e7 (7),
                  e8 (8)
            }
    MAX-ACCESS read-write
    STATUS     current
    DESCRIPTION
            ""
    ::= { lcsSetupComPortsCOMPortServCOMPortSetEntry 5 }

-- {COLUMN} 1.3.6.1.4.1.2356.11.2.52.2.2.1.6
lcsSetupComPortsCOMPortServCOMPortSetEntryParity OBJECT-TYPE
    SYNTAX     INTEGER {
                  eNone (1),
                  eOdd (2),
                  eEven (3)
            }
    MAX-ACCESS read-write
    STATUS     current
    DESCRIPTION
            ""
    ::= { lcsSetupComPortsCOMPortServCOMPortSetEntry 6 }

-- {COLUMN} 1.3.6.1.4.1.2356.11.2.52.2.2.1.7
lcsSetupComPortsCOMPortServCOMPortSetEntryStopBits OBJECT-TYPE
    SYNTAX     INTEGER {
                  e1 (1),
                  e2 (2)
            }
    MAX-ACCESS read-write
    STATUS     current
    DESCRIPTION
            ""
    ::= { lcsSetupComPortsCOMPortServCOMPortSetEntry 7 }

-- {COLUMN} 1.3.6.1.4.1.2356.11.2.52.2.2.1.8
lcsSetupComPortsCOMPortServCOMPortSetEntryHandshake OBJECT-TYPE
    SYNTAX     INTEGER {
                  eNone (0),
                  eRtsCts (1)
            }
    MAX-ACCESS read-write
    STATUS     current
    DESCRIPTION
            ""
    ::= { lcsSetupComPortsCOMPortServCOMPortSetEntry 8 }

-- {COLUMN} 1.3.6.1.4.1.2356.11.2.52.2.2.1.9
lcsSetupComPortsCOMPortServCOMPortSetEntryReadyCondition OBJECT-TYPE
    SYNTAX     INTEGER {
                  eDtr (0),
                  eData (1)
            }
    MAX-ACCESS read-write
    STATUS     current
    DESCRIPTION
            ""
    ::= { lcsSetupComPortsCOMPortServCOMPortSetEntry 9 }

-- {COLUMN} 1.3.6.1.4.1.2356.11.2.52.2.2.1.10
lcsSetupComPortsCOMPortServCOMPortSetEntryReadyDataTimeout OBJECT-TYPE
    SYNTAX     Integer32 (0..2147483647)
    MAX-ACCESS read-write
    STATUS     current
    DESCRIPTION
            ""
    ::= { lcsSetupComPortsCOMPortServCOMPortSetEntry 10 }

-- {TABLE} 1.3.6.1.4.1.2356.11.2.52.2.3
lcsSetupComPortsCOMPortServNetwSetTable OBJECT-TYPE
    SYNTAX     SEQUENCE OF LcsSetupComPortsCOMPortServNetwSetEntry
    MAX-ACCESS not-accessible
    STATUS     current
    DESCRIPTION
            ""
    ::= { lcsSetupComPortsCOMPortServ 3 }

-- {ROW} 1.3.6.1.4.1.2356.11.2.52.2.3.1
lcsSetupComPortsCOMPortServNetwSetEntry OBJECT-TYPE
    SYNTAX     LcsSetupComPortsCOMPortServNetwSetEntry
    MAX-ACCESS not-accessible
    STATUS     current
    DESCRIPTION
            ""
    INDEX {
            lcsSetupComPortsCOMPortServNetwSetEntryDeviceType,
            lcsSetupComPortsCOMPortServNetwSetEntryPortNumber
          }
    ::= { lcsSetupComPortsCOMPortServNetwSetTable 1 }

LcsSetupComPortsCOMPortServNetwSetEntry ::= SEQUENCE {
            lcsSetupComPortsCOMPortServNetwSetEntryDeviceType INTEGER,
            lcsSetupComPortsCOMPortServNetwSetEntryPortNumber Integer32,
            lcsSetupComPortsCOMPortServNetwSetEntryTcpMode INTEGER,
            lcsSetupComPortsCOMPortServNetwSetEntryListenPort Integer32,
            lcsSetupComPortsCOMPortServNetwSetEntryConnectHostname DisplayString,
            lcsSetupComPortsCOMPortServNetwSetEntryConnectPort Integer32,
            lcsSetupComPortsCOMPortServNetwSetEntryLoopbackAddr DisplayString,
            lcsSetupComPortsCOMPortServNetwSetEntryRfc2217Extensions INTEGER,
            lcsSetupComPortsCOMPortServNetwSetEntryNewlineConversion INTEGER,
            lcsSetupComPortsCOMPortServNetwSetEntryAssumeBinaryMode INTEGER,
            lcsSetupComPortsCOMPortServNetwSetEntryTcpRetransmitTimeout Integer32,
            lcsSetupComPortsCOMPortServNetwSetEntryTcpRetryCount Integer32,
            lcsSetupComPortsCOMPortServNetwSetEntryTcpKeepalive INTEGER,
            lcsSetupComPortsCOMPortServNetwSetEntryTcpKeepaliveInterval Integer32,
            lcsSetupComPortsCOMPortServNetwSetEntryBinaryMode INTEGER,
            lcsSetupComPortsCOMPortServNetwSetEntryWanAccess INTEGER
    }

-- {COLUMN} 1.3.6.1.4.1.2356.11.2.52.2.3.1.1
lcsSetupComPortsCOMPortServNetwSetEntryDeviceType OBJECT-TYPE
    SYNTAX     INTEGER {
                  eOutband (1),
                  eBelkinF5u103 (33),
                  eProlific2303 (34),
                  eFtdi8u232am (35),
                  eGpsNmea (36),
                  eQualcomDm (45),
                  eUsbSerialAdapter (72),
                  eSubghzModule (73),
                  eModuleConsole (76),
                  eFtdi232h (77)
            }
    MAX-ACCESS read-write
    STATUS     current
    DESCRIPTION
            ""
    ::= { lcsSetupComPortsCOMPortServNetwSetEntry 1 }

-- {COLUMN} 1.3.6.1.4.1.2356.11.2.52.2.3.1.2
lcsSetupComPortsCOMPortServNetwSetEntryPortNumber OBJECT-TYPE
    SYNTAX     Integer32 (0..255)
    MAX-ACCESS read-write
    STATUS     current
    DESCRIPTION
            ""
    ::= { lcsSetupComPortsCOMPortServNetwSetEntry 2 }

-- {COLUMN} 1.3.6.1.4.1.2356.11.2.52.2.3.1.4
lcsSetupComPortsCOMPortServNetwSetEntryTcpMode OBJECT-TYPE
    SYNTAX     INTEGER {
                  eServer (0),
                  eClient (1)
            }
    MAX-ACCESS read-write
    STATUS     current
    DESCRIPTION
            ""
    ::= { lcsSetupComPortsCOMPortServNetwSetEntry 4 }

-- {COLUMN} 1.3.6.1.4.1.2356.11.2.52.2.3.1.5
lcsSetupComPortsCOMPortServNetwSetEntryListenPort OBJECT-TYPE
    SYNTAX     Integer32 (0..65535)
    MAX-ACCESS read-write
    STATUS     current
    DESCRIPTION
            ""
    ::= { lcsSetupComPortsCOMPortServNetwSetEntry 5 }

-- {COLUMN} 1.3.6.1.4.1.2356.11.2.52.2.3.1.6
lcsSetupComPortsCOMPortServNetwSetEntryConnectHostname OBJECT-TYPE
    SYNTAX     DisplayString (SIZE(0..48))
    MAX-ACCESS read-write
    STATUS     current
    DESCRIPTION
            ""
    ::= { lcsSetupComPortsCOMPortServNetwSetEntry 6 }

-- {COLUMN} 1.3.6.1.4.1.2356.11.2.52.2.3.1.7
lcsSetupComPortsCOMPortServNetwSetEntryConnectPort OBJECT-TYPE
    SYNTAX     Integer32 (0..65535)
    MAX-ACCESS read-write
    STATUS     current
    DESCRIPTION
            ""
    ::= { lcsSetupComPortsCOMPortServNetwSetEntry 7 }

-- {COLUMN} 1.3.6.1.4.1.2356.11.2.52.2.3.1.8
lcsSetupComPortsCOMPortServNetwSetEntryLoopbackAddr OBJECT-TYPE
    SYNTAX     DisplayString (SIZE(0..16))
    MAX-ACCESS read-write
    STATUS     current
    DESCRIPTION
            ""
    ::= { lcsSetupComPortsCOMPortServNetwSetEntry 8 }

-- {COLUMN} 1.3.6.1.4.1.2356.11.2.52.2.3.1.9
lcsSetupComPortsCOMPortServNetwSetEntryRfc2217Extensions OBJECT-TYPE
    SYNTAX     INTEGER {
                  eNo (0),
                  eYes (1)
            }
    MAX-ACCESS read-write
    STATUS     current
    DESCRIPTION
            ""
    ::= { lcsSetupComPortsCOMPortServNetwSetEntry 9 }

-- {COLUMN} 1.3.6.1.4.1.2356.11.2.52.2.3.1.10
lcsSetupComPortsCOMPortServNetwSetEntryNewlineConversion OBJECT-TYPE
    SYNTAX     INTEGER {
                  eCrlf (0),
                  eCr (1),
                  eLf (2)
            }
    MAX-ACCESS read-write
    STATUS     current
    DESCRIPTION
            ""
    ::= { lcsSetupComPortsCOMPortServNetwSetEntry 10 }

-- {COLUMN} 1.3.6.1.4.1.2356.11.2.52.2.3.1.11
lcsSetupComPortsCOMPortServNetwSetEntryAssumeBinaryMode OBJECT-TYPE
    SYNTAX     INTEGER {
                  eNo (0),
                  eYes (1)
            }
    MAX-ACCESS read-only
    STATUS     obsolete
    DESCRIPTION
            ""
    ::= { lcsSetupComPortsCOMPortServNetwSetEntry 11 }

-- {COLUMN} 1.3.6.1.4.1.2356.11.2.52.2.3.1.12
lcsSetupComPortsCOMPortServNetwSetEntryTcpRetransmitTimeout OBJECT-TYPE
    SYNTAX     Integer32 (0..255)
    MAX-ACCESS read-write
    STATUS     current
    DESCRIPTION
            ""
    ::= { lcsSetupComPortsCOMPortServNetwSetEntry 12 }

-- {COLUMN} 1.3.6.1.4.1.2356.11.2.52.2.3.1.13
lcsSetupComPortsCOMPortServNetwSetEntryTcpRetryCount OBJECT-TYPE
    SYNTAX     Integer32 (0..255)
    MAX-ACCESS read-write
    STATUS     current
    DESCRIPTION
            ""
    ::= { lcsSetupComPortsCOMPortServNetwSetEntry 13 }

-- {COLUMN} 1.3.6.1.4.1.2356.11.2.52.2.3.1.14
lcsSetupComPortsCOMPortServNetwSetEntryTcpKeepalive OBJECT-TYPE
    SYNTAX     INTEGER {
                  eInactive (0),
                  eActive (1),
                  eProactive (2)
            }
    MAX-ACCESS read-write
    STATUS     current
    DESCRIPTION
            ""
    ::= { lcsSetupComPortsCOMPortServNetwSetEntry 14 }

-- {COLUMN} 1.3.6.1.4.1.2356.11.2.52.2.3.1.15
lcsSetupComPortsCOMPortServNetwSetEntryTcpKeepaliveInterval OBJECT-TYPE
    SYNTAX     Integer32 (0..2147483647)
    MAX-ACCESS read-write
    STATUS     current
    DESCRIPTION
            ""
    ::= { lcsSetupComPortsCOMPortServNetwSetEntry 15 }

-- {COLUMN} 1.3.6.1.4.1.2356.11.2.52.2.3.1.16
lcsSetupComPortsCOMPortServNetwSetEntryBinaryMode OBJECT-TYPE
    SYNTAX     INTEGER {
                  eAuto (0),
                  eYes (1),
                  eNo (2)
            }
    MAX-ACCESS read-write
    STATUS     current
    DESCRIPTION
            ""
    ::= { lcsSetupComPortsCOMPortServNetwSetEntry 16 }

-- {COLUMN} 1.3.6.1.4.1.2356.11.2.52.2.3.1.17
lcsSetupComPortsCOMPortServNetwSetEntryWanAccess OBJECT-TYPE
    SYNTAX     INTEGER {
                  eNo (0),
                  eYes (1),
                  eVpnOnly (2)
            }
    MAX-ACCESS read-write
    STATUS     current
    DESCRIPTION
            "-- empty --"
    ::= { lcsSetupComPortsCOMPortServNetwSetEntry 17 }

-- {NODE} 1.3.6.1.4.1.2356.11.2.52.3
lcsSetupComPortsWan OBJECT IDENTIFIER ::= { lcsSetupComPorts 3 }

-- {TABLE} 1.3.6.1.4.1.2356.11.2.52.3.1
lcsSetupComPortsWanDevTable OBJECT-TYPE
    SYNTAX     SEQUENCE OF LcsSetupComPortsWanDevEntry
    MAX-ACCESS not-accessible
    STATUS     current
    DESCRIPTION
            ""
    ::= { lcsSetupComPortsWan 1 }

-- {ROW} 1.3.6.1.4.1.2356.11.2.52.3.1.1
lcsSetupComPortsWanDevEntry OBJECT-TYPE
    SYNTAX     LcsSetupComPortsWanDevEntry
    MAX-ACCESS not-accessible
    STATUS     current
    DESCRIPTION
            ""
    INDEX {
            lcsSetupComPortsWanDevEntryDeviceType
          }
    ::= { lcsSetupComPortsWanDevTable 1 }

LcsSetupComPortsWanDevEntry ::= SEQUENCE {
            lcsSetupComPortsWanDevEntryDeviceType INTEGER,
            lcsSetupComPortsWanDevEntryOperating INTEGER
    }

-- {COLUMN} 1.3.6.1.4.1.2356.11.2.52.3.1.1.1
lcsSetupComPortsWanDevEntryDeviceType OBJECT-TYPE
    SYNTAX     INTEGER {
                  eOutbandModem (2),
                  eSierraMinicard8780 (11),
                  eSierraMinicard8781 (12),
                  eOptionIcon (17),
                  eOptionMinicard0201 (19),
                  eHuaweiE612E630E1750 (21),
                  e4gSystemsUxs1 (23),
                  eNovatelMerlinMc950d (26),
                  eSierraAircard875u (30),
                  eHuaweiE172E220E870 (31),
                  eBelkinF5u103 (33),
                  eProlific2303 (34),
                  eFtdi8u232am (35),
                  eSierraMinicard8790 (38),
                  eSierraCompass885 (39),
                  eSierraAircard501 (46),
                  eHuaweiK4505 (49),
                  eHuaweiK3765 (51),
                  eSierraDirectIp (53),
                  eHuaweiE182 (54),
                  eSierraMinicard8705 (55),
                  eSierraMinicard8801 (56),
                  eHuaweiE1750 (57),
                  eNokiaCs19 (59),
                  eHuaweiE398 (60),
                  eHuaweiE1550 (61),
                  eSierraMinicard7710 (62),
                  eHuaweiE352 (64),
                  eSierraQmi73xx (66),
                  eSierraQmi74xx (67),
                  eSierraQmi75xx (74),
                  eFtdi232h (77)
            }
    MAX-ACCESS read-write
    STATUS     current
    DESCRIPTION
            ""
    ::= { lcsSetupComPortsWanDevEntry 1 }

-- {COLUMN} 1.3.6.1.4.1.2356.11.2.52.3.1.1.3
lcsSetupComPortsWanDevEntryOperating OBJECT-TYPE
    SYNTAX     INTEGER {
                  eNo (0),
                  eYes (1)
            }
    MAX-ACCESS read-write
    STATUS     current
    DESCRIPTION
            ""
    ::= { lcsSetupComPortsWanDevEntry 3 }

-- {NODE} 1.3.6.1.4.1.2356.11.2.53
lcsSetupTemperatureMonitor OBJECT IDENTIFIER ::= { lcsSetup 53 }

-- {SCALAR} 1.3.6.1.4.1.2356.11.2.53.1
lcsSetupTemperatureMonitorUpperLimitDegrees OBJECT-TYPE
    SYNTAX     Integer32 (-128..127)
    MAX-ACCESS read-write
    STATUS     current
    DESCRIPTION
            ""
    ::= { lcsSetupTemperatureMonitor 1 }

-- {SCALAR} 1.3.6.1.4.1.2356.11.2.53.2
lcsSetupTemperatureMonitorLowerLimitDegrees OBJECT-TYPE
    SYNTAX     Integer32 (-128..127)
    MAX-ACCESS read-write
    STATUS     current
    DESCRIPTION
            ""
    ::= { lcsSetupTemperatureMonitor 2 }

-- {NODE} 1.3.6.1.4.1.2356.11.2.54
lcsSetupTacacsPlus OBJECT IDENTIFIER ::= { lcsSetup 54 }

-- {SCALAR} 1.3.6.1.4.1.2356.11.2.54.1
lcsSetupTacacsPlusAuthentication OBJECT-TYPE
    SYNTAX     INTEGER {
                  eDeactivated (0),
                  eActivated (1)
            }
    MAX-ACCESS read-only
    STATUS     current
    DESCRIPTION
            ""
    ::= { lcsSetupTacacsPlus 1 }

-- {SCALAR} 1.3.6.1.4.1.2356.11.2.54.2
lcsSetupTacacsPlusAuthorisation OBJECT-TYPE
    SYNTAX     INTEGER {
                  eDeactivated (0),
                  eActivated (1)
            }
    MAX-ACCESS read-write
    STATUS     current
    DESCRIPTION
            ""
    ::= { lcsSetupTacacsPlus 2 }

-- {SCALAR} 1.3.6.1.4.1.2356.11.2.54.3
lcsSetupTacacsPlusAccounting OBJECT-TYPE
    SYNTAX     INTEGER {
                  eDeactivated (0),
                  eActivated (1)
            }
    MAX-ACCESS read-write
    STATUS     current
    DESCRIPTION
            ""
    ::= { lcsSetupTacacsPlus 3 }

-- {SCALAR} 1.3.6.1.4.1.2356.11.2.54.6
lcsSetupTacacsPlusSharedSecret OBJECT-TYPE
    SYNTAX     DisplayString (SIZE(0..31))
    MAX-ACCESS read-write
    STATUS     current
    DESCRIPTION
            ""
    ::= { lcsSetupTacacsPlus 6 }

-- {SCALAR} 1.3.6.1.4.1.2356.11.2.54.7
lcsSetupTacacsPlusEncryption OBJECT-TYPE
    SYNTAX     INTEGER {
                  eDeactivated (0),
                  eActivated (1)
            }
    MAX-ACCESS read-write
    STATUS     current
    DESCRIPTION
            ""
    ::= { lcsSetupTacacsPlus 7 }

-- {TABLE} 1.3.6.1.4.1.2356.11.2.54.9
lcsSetupTacacsPlusServerTable OBJECT-TYPE
    SYNTAX     SEQUENCE OF LcsSetupTacacsPlusServerEntry
    MAX-ACCESS not-accessible
    STATUS     current
    DESCRIPTION
            ""
    ::= { lcsSetupTacacsPlus 9 }

-- {ROW} 1.3.6.1.4.1.2356.11.2.54.9.1
lcsSetupTacacsPlusServerEntry OBJECT-TYPE
    SYNTAX     LcsSetupTacacsPlusServerEntry
    MAX-ACCESS not-accessible
    STATUS     current
    DESCRIPTION
            ""
    INDEX {
            lcsSetupTacacsPlusServerEntryServerAddress
          }
    ::= { lcsSetupTacacsPlusServerTable 1 }

LcsSetupTacacsPlusServerEntry ::= SEQUENCE {
            lcsSetupTacacsPlusServerEntryServerAddress DisplayString,
            lcsSetupTacacsPlusServerEntryLoopbackAddress DisplayString,
            lcsSetupTacacsPlusServerEntryCompatibilityMode INTEGER
    }

-- {COLUMN} 1.3.6.1.4.1.2356.11.2.54.9.1.1
lcsSetupTacacsPlusServerEntryServerAddress OBJECT-TYPE
    SYNTAX     DisplayString (SIZE(0..63))
    MAX-ACCESS read-write
    STATUS     current
    DESCRIPTION
            ""
    ::= { lcsSetupTacacsPlusServerEntry 1 }

-- {COLUMN} 1.3.6.1.4.1.2356.11.2.54.9.1.2
lcsSetupTacacsPlusServerEntryLoopbackAddress OBJECT-TYPE
    SYNTAX     DisplayString (SIZE(0..16))
    MAX-ACCESS read-write
    STATUS     current
    DESCRIPTION
            ""
    ::= { lcsSetupTacacsPlusServerEntry 2 }

-- {COLUMN} 1.3.6.1.4.1.2356.11.2.54.9.1.3
lcsSetupTacacsPlusServerEntryCompatibilityMode OBJECT-TYPE
    SYNTAX     INTEGER {
                  eDeactivated (0),
                  eActivated (1)
            }
    MAX-ACCESS read-write
    STATUS     current
    DESCRIPTION
            ""
    ::= { lcsSetupTacacsPlusServerEntry 3 }

-- {SCALAR} 1.3.6.1.4.1.2356.11.2.54.10
lcsSetupTacacsPlusFallbackToLocalUsers OBJECT-TYPE
    SYNTAX     INTEGER {
                  eAllowed (0),
                  eProhibited (1)
            }
    MAX-ACCESS read-write
    STATUS     current
    DESCRIPTION
            ""
    ::= { lcsSetupTacacsPlus 10 }

-- {SCALAR} 1.3.6.1.4.1.2356.11.2.54.11
lcsSetupTacacsPlusSnmpGetRequestsAuthorisation OBJECT-TYPE
    SYNTAX     INTEGER {
                  eOnlyForSetupTree (0),
                  eAll (1),
                  eNone (2)
            }
    MAX-ACCESS read-write
    STATUS     current
    DESCRIPTION
            ""
    ::= { lcsSetupTacacsPlus 11 }

-- {SCALAR} 1.3.6.1.4.1.2356.11.2.54.12
lcsSetupTacacsPlusSnmpGetRequestsAccounting OBJECT-TYPE
    SYNTAX     INTEGER {
                  eOnlyForSetupTree (0),
                  eAll (1),
                  eNone (2)
            }
    MAX-ACCESS read-write
    STATUS     current
    DESCRIPTION
            ""
    ::= { lcsSetupTacacsPlus 12 }

-- {SCALAR} 1.3.6.1.4.1.2356.11.2.54.13
lcsSetupTacacsPlusBypassTacacsForCronScriptsActionTable OBJECT-TYPE
    SYNTAX     INTEGER {
                  eDeactivated (0),
                  eActivated (1)
            }
    MAX-ACCESS read-write
    STATUS     current
    DESCRIPTION
            ""
    ::= { lcsSetupTacacsPlus 13 }

-- {SCALAR} 1.3.6.1.4.1.2356.11.2.54.14
lcsSetupTacacsPlusIncludeValueIntoAuthorisationRequest OBJECT-TYPE
    SYNTAX     INTEGER {
                  eDeactivated (0),
                  eActivated (1)
            }
    MAX-ACCESS read-write
    STATUS     current
    DESCRIPTION
            ""
    ::= { lcsSetupTacacsPlus 14 }

-- {SCALAR} 1.3.6.1.4.1.2356.11.2.54.15
lcsSetupTacacsPlusAuthorisationType OBJECT-TYPE
    SYNTAX     INTEGER {
                  eCommands (0),
                  eShell (1)
            }
    MAX-ACCESS read-write
    STATUS     current
    DESCRIPTION
            "-- empty --"
    ::= { lcsSetupTacacsPlus 15 }

-- {NODE} 1.3.6.1.4.1.2356.11.2.56
lcsSetupUsb OBJECT IDENTIFIER ::= { lcsSetup 56 }

-- {SCALAR} 1.3.6.1.4.1.2356.11.2.56.1
lcsSetupUsbFirmwareAndLoader OBJECT-TYPE
    SYNTAX     INTEGER {
                  eInactive (1),
                  eIfUnconfigured (2),
                  eActive (3)
            }
    MAX-ACCESS read-only
    STATUS     current
    DESCRIPTION
            ""
    ::= { lcsSetupUsb 1 }

-- {SCALAR} 1.3.6.1.4.1.2356.11.2.56.2
lcsSetupUsbConfigAndScript OBJECT-TYPE
    SYNTAX     INTEGER {
                  eInactive (1),
                  eIfUnconfigured (2),
                  eActive (3)
            }
    MAX-ACCESS read-only
    STATUS     current
    DESCRIPTION
            ""
    ::= { lcsSetupUsb 2 }

-- {NODE} 1.3.6.1.4.1.2356.11.2.57
lcsSetupNetioServer OBJECT IDENTIFIER ::= { lcsSetup 57 }

-- {SCALAR} 1.3.6.1.4.1.2356.11.2.57.1
lcsSetupNetioServerTcpOperation OBJECT-TYPE
    SYNTAX     INTEGER {
                  eNo (0),
                  eYes (1)
            }
    MAX-ACCESS read-write
    STATUS     current
    DESCRIPTION
            "-- empty --"
    ::= { lcsSetupNetioServer 1 }

-- {SCALAR} 1.3.6.1.4.1.2356.11.2.57.2
lcsSetupNetioServerUdpOperation OBJECT-TYPE
    SYNTAX     INTEGER {
                  eNo (0),
                  eYes (1)
            }
    MAX-ACCESS read-write
    STATUS     current
    DESCRIPTION
            "-- empty --"
    ::= { lcsSetupNetioServer 2 }

-- {SCALAR} 1.3.6.1.4.1.2356.11.2.57.3
lcsSetupNetioServerSslOperation OBJECT-TYPE
    SYNTAX     INTEGER {
                  eNo (0),
                  eYes (1)
            }
    MAX-ACCESS read-write
    STATUS     current
    DESCRIPTION
            "-- empty --"
    ::= { lcsSetupNetioServer 3 }

-- {SCALAR} 1.3.6.1.4.1.2356.11.2.57.4
lcsSetupNetioServerUpstreamLimitKbps OBJECT-TYPE
    SYNTAX     Integer32 (0..2147483647)
    MAX-ACCESS read-write
    STATUS     current
    DESCRIPTION
            "-- empty --"
    ::= { lcsSetupNetioServer 4 }

-- {SCALAR} 1.3.6.1.4.1.2356.11.2.57.5
lcsSetupNetioServerDownstreamLimitKbps OBJECT-TYPE
    SYNTAX     Integer32 (0..2147483647)
    MAX-ACCESS read-write
    STATUS     current
    DESCRIPTION
            "-- empty --"
    ::= { lcsSetupNetioServer 5 }

-- {NODE} 1.3.6.1.4.1.2356.11.2.57.6
lcsSetupNetioServerSslParameters OBJECT IDENTIFIER ::= { lcsSetupNetioServer 6 }

-- {SCALAR} 1.3.6.1.4.1.2356.11.2.57.6.1
lcsSetupNetioServerSslParametersVersions OBJECT-TYPE
    SYNTAX     BITS {
                  eTlsv12 (28),
                  eTlsv11 (29),
                  eTlsv1 (30),
                  eSslv3 (31)
            }
    MAX-ACCESS read-write
    STATUS     current
    DESCRIPTION
            "-- empty --"
    ::= { lcsSetupNetioServerSslParameters 1 }

-- {SCALAR} 1.3.6.1.4.1.2356.11.2.57.6.2
lcsSetupNetioServerSslParametersKeyexAlgorithms OBJECT-TYPE
    SYNTAX     BITS {
                  eEcdhe (27),
                  eDhe (29),
                  eRsa (31)
            }
    MAX-ACCESS read-write
    STATUS     current
    DESCRIPTION
            "-- empty --"
    ::= { lcsSetupNetioServerSslParameters 2 }

-- {SCALAR} 1.3.6.1.4.1.2356.11.2.57.6.3
lcsSetupNetioServerSslParametersCryptoAlgorithms OBJECT-TYPE
    SYNTAX     BITS {
                  eAesgcm256 (20),
                  eAesgcm128 (21),
                  eAes256 (22),
                  eAes128 (23),
                  e3des (24),
                  eDes (25),
                  eDes40 (26),
                  eRc4128 (27),
                  eRc456 (28),
                  eRc440 (29),
                  eNull (31)
            }
    MAX-ACCESS read-write
    STATUS     current
    DESCRIPTION
            "-- empty --"
    ::= { lcsSetupNetioServerSslParameters 3 }

-- {SCALAR} 1.3.6.1.4.1.2356.11.2.57.6.4
lcsSetupNetioServerSslParametersHashAlgorithms OBJECT-TYPE
    SYNTAX     BITS {
                  eSha384 (26),
                  eSha256 (27),
                  eSha1 (29),
                  eMd5 (30),
                  eNull (31)
            }
    MAX-ACCESS read-write
    STATUS     current
    DESCRIPTION
            "-- empty --"
    ::= { lcsSetupNetioServerSslParameters 4 }

-- {SCALAR} 1.3.6.1.4.1.2356.11.2.57.6.5
lcsSetupNetioServerSslParametersPreferPfs OBJECT-TYPE
    SYNTAX     BITS {
                  eNo (0),
                  eYes (7)
            }
    MAX-ACCESS read-write
    STATUS     current
    DESCRIPTION
            "-- empty --"
    ::= { lcsSetupNetioServerSslParameters 5 }

-- {NODE} 1.3.6.1.4.1.2356.11.2.59
lcsSetupWtpMngmt OBJECT IDENTIFIER ::= { lcsSetup 59 }

-- {TABLE} 1.3.6.1.4.1.2356.11.2.59.1
lcsSetupWtpMngmtStaticWlcConfTable OBJECT-TYPE
    SYNTAX     SEQUENCE OF LcsSetupWtpMngmtStaticWlcConfEntry
    MAX-ACCESS not-accessible
    STATUS     current
    DESCRIPTION
            "static WLC configuartion"
    ::= { lcsSetupWtpMngmt 1 }

-- {ROW} 1.3.6.1.4.1.2356.11.2.59.1.1
lcsSetupWtpMngmtStaticWlcConfEntry OBJECT-TYPE
    SYNTAX     LcsSetupWtpMngmtStaticWlcConfEntry
    MAX-ACCESS not-accessible
    STATUS     current
    DESCRIPTION
            ""
    INDEX {
            lcsSetupWtpMngmtStaticWlcConfEntryIpAddress
          }
    ::= { lcsSetupWtpMngmtStaticWlcConfTable 1 }

LcsSetupWtpMngmtStaticWlcConfEntry ::= SEQUENCE {
            lcsSetupWtpMngmtStaticWlcConfEntryIpAddress DisplayString,
            lcsSetupWtpMngmtStaticWlcConfEntryPort Integer32,
            lcsSetupWtpMngmtStaticWlcConfEntryLoopbackAddr DisplayString
    }

-- {COLUMN} 1.3.6.1.4.1.2356.11.2.59.1.1.1
lcsSetupWtpMngmtStaticWlcConfEntryIpAddress OBJECT-TYPE
    SYNTAX     DisplayString (SIZE(0..63))
    MAX-ACCESS read-write
    STATUS     current
    DESCRIPTION
            ""
    ::= { lcsSetupWtpMngmtStaticWlcConfEntry 1 }

-- {COLUMN} 1.3.6.1.4.1.2356.11.2.59.1.1.2
lcsSetupWtpMngmtStaticWlcConfEntryPort OBJECT-TYPE
    SYNTAX     Integer32 (0..65535)
    MAX-ACCESS read-write
    STATUS     current
    DESCRIPTION
            ""
    ::= { lcsSetupWtpMngmtStaticWlcConfEntry 2 }

-- {COLUMN} 1.3.6.1.4.1.2356.11.2.59.1.1.3
lcsSetupWtpMngmtStaticWlcConfEntryLoopbackAddr OBJECT-TYPE
    SYNTAX     DisplayString (SIZE(0..16))
    MAX-ACCESS read-write
    STATUS     current
    DESCRIPTION
            ""
    ::= { lcsSetupWtpMngmtStaticWlcConfEntry 3 }

-- {NODE} 1.3.6.1.4.1.2356.11.2.59.4
lcsSetupWtpMngmtAutowds OBJECT IDENTIFIER ::= { lcsSetupWtpMngmt 4 }

-- {SCALAR} 1.3.6.1.4.1.2356.11.2.59.4.1
lcsSetupWtpMngmtAutowdsOperation OBJECT-TYPE
    SYNTAX     INTEGER {
                  eNo (0),
                  eYes (1)
            }
    MAX-ACCESS read-write
    STATUS     current
    DESCRIPTION
            "-- empty --"
    ::= { lcsSetupWtpMngmtAutowds 1 }

-- {SCALAR} 1.3.6.1.4.1.2356.11.2.59.4.2
lcsSetupWtpMngmtAutowdsPreconfSsid OBJECT-TYPE
    SYNTAX     DisplayString (SIZE(0..32))
    MAX-ACCESS read-write
    STATUS     current
    DESCRIPTION
            "-- empty --"
    ::= { lcsSetupWtpMngmtAutowds 2 }

-- {SCALAR} 1.3.6.1.4.1.2356.11.2.59.4.3
lcsSetupWtpMngmtAutowdsPreconfKey OBJECT-TYPE
    SYNTAX     DisplayString (SIZE(0..63))
    MAX-ACCESS read-write
    STATUS     current
    DESCRIPTION
            "-- empty --"
    ::= { lcsSetupWtpMngmtAutowds 3 }

-- {SCALAR} 1.3.6.1.4.1.2356.11.2.59.4.4
lcsSetupWtpMngmtAutowdsTimeTillPreconfScan OBJECT-TYPE
    SYNTAX     Integer32 (0..2147483647)
    MAX-ACCESS read-write
    STATUS     current
    DESCRIPTION
            "-- empty --"
    ::= { lcsSetupWtpMngmtAutowds 4 }

-- {SCALAR} 1.3.6.1.4.1.2356.11.2.59.4.5
lcsSetupWtpMngmtAutowdsTimeTillExpressScan OBJECT-TYPE
    SYNTAX     Integer32 (0..2147483647)
    MAX-ACCESS read-write
    STATUS     current
    DESCRIPTION
            "-- empty --"
    ::= { lcsSetupWtpMngmtAutowds 5 }

-- {SCALAR} 1.3.6.1.4.1.2356.11.2.59.5
lcsSetupWtpMngmtCapwapPort OBJECT-TYPE
    SYNTAX     Integer32 (0..65535)
    MAX-ACCESS read-write
    STATUS     current
    DESCRIPTION
            "-- empty --"
    ::= { lcsSetupWtpMngmt 5 }

-- {SCALAR} 1.3.6.1.4.1.2356.11.2.59.6
lcsSetupWtpMngmtLogEvents OBJECT-TYPE
    SYNTAX     BITS {
                  eAutowds (26),
                  eStatechange (27),
                  eError (28),
                  eWarning (29),
                  eInfo (30),
                  eDebug (31)
            }
    MAX-ACCESS read-write
    STATUS     current
    DESCRIPTION
            "-- empty --"
    ::= { lcsSetupWtpMngmt 6 }

-- {SCALAR} 1.3.6.1.4.1.2356.11.2.59.120
lcsSetupWtpMngmtLogEntries OBJECT-TYPE
    SYNTAX     Integer32 (0..2147483647)
    MAX-ACCESS read-write
    STATUS     current
    DESCRIPTION
            ""
    ::= { lcsSetupWtpMngmt 120 }

-- {NODE} 1.3.6.1.4.1.2356.11.2.60
lcsSetupAutold OBJECT IDENTIFIER ::= { lcsSetup 60 }

-- {NODE} 1.3.6.1.4.1.2356.11.2.60.1
lcsSetupAutoldNetwork OBJECT IDENTIFIER ::= { lcsSetupAutold 1 }

-- {NODE} 1.3.6.1.4.1.2356.11.2.60.1.1
lcsSetupAutoldNetworkFirmware OBJECT IDENTIFIER ::= { lcsSetupAutoldNetwork 1 }

-- {SCALAR} 1.3.6.1.4.1.2356.11.2.60.1.1.1
lcsSetupAutoldNetworkFirmwareCondition OBJECT-TYPE
    SYNTAX     INTEGER {
                  eUnconditionally (0),
                  eIfDifferent (1),
                  eIfNewer (2)
            }
    MAX-ACCESS read-write
    STATUS     current
    DESCRIPTION
            ""
    ::= { lcsSetupAutoldNetworkFirmware 1 }

-- {SCALAR} 1.3.6.1.4.1.2356.11.2.60.1.1.2
lcsSetupAutoldNetworkFirmwareUrl OBJECT-TYPE
    SYNTAX     DisplayString (SIZE(0..127))
    MAX-ACCESS read-write
    STATUS     current
    DESCRIPTION
            ""
    ::= { lcsSetupAutoldNetworkFirmware 2 }

-- {SCALAR} 1.3.6.1.4.1.2356.11.2.60.1.1.3
lcsSetupAutoldNetworkFirmwareMinimumVersion OBJECT-TYPE
    SYNTAX     DisplayString (SIZE(0..14))
    MAX-ACCESS read-write
    STATUS     current
    DESCRIPTION
            ""
    ::= { lcsSetupAutoldNetworkFirmware 3 }

-- {SCALAR} 1.3.6.1.4.1.2356.11.2.60.1.1.4
lcsSetupAutoldNetworkFirmwareLoopbackAddress OBJECT-TYPE
    SYNTAX     DisplayString (SIZE(0..16))
    MAX-ACCESS read-write
    STATUS     current
    DESCRIPTION
            "-- empty --"
    ::= { lcsSetupAutoldNetworkFirmware 4 }

-- {NODE} 1.3.6.1.4.1.2356.11.2.60.1.2
lcsSetupAutoldNetworkConfig OBJECT IDENTIFIER ::= { lcsSetupAutoldNetwork 2 }

-- {SCALAR} 1.3.6.1.4.1.2356.11.2.60.1.2.1
lcsSetupAutoldNetworkConfigCondition OBJECT-TYPE
    SYNTAX     INTEGER {
                  eUnconditionally (0),
                  eIfDifferent (1)
            }
    MAX-ACCESS read-write
    STATUS     current
    DESCRIPTION
            ""
    ::= { lcsSetupAutoldNetworkConfig 1 }

-- {SCALAR} 1.3.6.1.4.1.2356.11.2.60.1.2.2
lcsSetupAutoldNetworkConfigUrl OBJECT-TYPE
    SYNTAX     DisplayString (SIZE(0..127))
    MAX-ACCESS read-write
    STATUS     current
    DESCRIPTION
            ""
    ::= { lcsSetupAutoldNetworkConfig 2 }

-- {NODE} 1.3.6.1.4.1.2356.11.2.60.1.3
lcsSetupAutoldNetworkScript OBJECT IDENTIFIER ::= { lcsSetupAutoldNetwork 3 }

-- {SCALAR} 1.3.6.1.4.1.2356.11.2.60.1.3.1
lcsSetupAutoldNetworkScriptCondition OBJECT-TYPE
    SYNTAX     INTEGER {
                  eUnconditionally (0),
                  eIfDifferent (1)
            }
    MAX-ACCESS read-write
    STATUS     current
    DESCRIPTION
            ""
    ::= { lcsSetupAutoldNetworkScript 1 }

-- {SCALAR} 1.3.6.1.4.1.2356.11.2.60.1.3.2
lcsSetupAutoldNetworkScriptUrl OBJECT-TYPE
    SYNTAX     DisplayString (SIZE(0..127))
    MAX-ACCESS read-write
    STATUS     current
    DESCRIPTION
            ""
    ::= { lcsSetupAutoldNetworkScript 2 }

-- {NODE} 1.3.6.1.4.1.2356.11.2.60.1.4
lcsSetupAutoldNetworkTftpClient OBJECT IDENTIFIER ::= { lcsSetupAutoldNetwork 4 }

-- {SCALAR} 1.3.6.1.4.1.2356.11.2.60.1.4.1
lcsSetupAutoldNetworkTftpClientBytesPerHashmark OBJECT-TYPE
    SYNTAX     Integer32 (0..2147483647)
    MAX-ACCESS read-write
    STATUS     current
    DESCRIPTION
            ""
    ::= { lcsSetupAutoldNetworkTftpClient 1 }

-- {NODE} 1.3.6.1.4.1.2356.11.2.60.1.5
lcsSetupAutoldNetworkSslNew OBJECT IDENTIFIER ::= { lcsSetupAutoldNetwork 5 }

-- {SCALAR} 1.3.6.1.4.1.2356.11.2.60.1.5.1
lcsSetupAutoldNetworkSslNewVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupAutoldNetworkSslNew 1 }

-- {SCALAR} 1.3.6.1.4.1.2356.11.2.60.1.5.2
lcsSetupAutoldNetworkSslNewKeyexAlgorithms OBJECT-TYPE
    SYNTAX     BITS {
                  eEcdhe (27),
                  eDhe (29),
                  eRsa (31)
            }
    MAX-ACCESS read-write
    STATUS     current
    DESCRIPTION
            "-- empty --"
    ::= { lcsSetupAutoldNetworkSslNew 2 }

-- {SCALAR} 1.3.6.1.4.1.2356.11.2.60.1.5.3
lcsSetupAutoldNetworkSslNewCryptoAlgorithms OBJECT-TYPE
    SYNTAX     BITS {
                  eChacha20Poly1305 (19),
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { lcsSetupAutoldNetworkSslNew 3 }

-- {SCALAR} 1.3.6.1.4.1.2356.11.2.60.1.5.4
lcsSetupAutoldNetworkSslNewHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupAutoldNetworkSslNew 4 }

-- {SCALAR} 1.3.6.1.4.1.2356.11.2.60.1.5.5
lcsSetupAutoldNetworkSslNewPreferPfs OBJECT-TYPE
    SYNTAX     BITS {
                  eNo (0),
                  eYes (7)
            }
    MAX-ACCESS read-write
    STATUS     current
    DESCRIPTION
            "-- empty --"
    ::= { lcsSetupAutoldNetworkSslNew 5 }

-- {SCALAR} 1.3.6.1.4.1.2356.11.2.60.1.5.6
lcsSetupAutoldNetworkSslNewRenegotiations OBJECT-TYPE
    SYNTAX     INTEGER {
                  eForbidden (0),
                  eAllowed (1),
                  eIgnored (2)
            }
    MAX-ACCESS read-write
    STATUS     current
    DESCRIPTION
            "-- empty --"
    ::= { lcsSetupAutoldNetworkSslNew 6 }

-- {SCALAR} 1.3.6.1.4.1.2356.11.2.60.1.5.7
lcsSetupAutoldNetworkSslNewEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupAutoldNetworkSslNew 7 }

-- {SCALAR} 1.3.6.1.4.1.2356.11.2.60.1.5.21
lcsSetupAutoldNetworkSslNewSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupAutoldNetworkSslNew 21 }

-- {NODE} 1.3.6.1.4.1.2356.11.2.60.3
lcsSetupAutoldLicense OBJECT IDENTIFIER ::= { lcsSetupAutold 3 }

-- {SCALAR} 1.3.6.1.4.1.2356.11.2.60.3.1
lcsSetupAutoldLicenseUrl OBJECT-TYPE
    SYNTAX     DisplayString (SIZE(0..127))
    MAX-ACCESS read-write
    STATUS     current
    DESCRIPTION
            "-- empty --"
    ::= { lcsSetupAutoldLicense 1 }

-- {SCALAR} 1.3.6.1.4.1.2356.11.2.60.3.2
lcsSetupAutoldLicenseLoopbackAddress OBJECT-TYPE
    SYNTAX     DisplayString (SIZE(0..16))
    MAX-ACCESS read-write
    STATUS     current
    DESCRIPTION
            "-- empty --"
    ::= { lcsSetupAutoldLicense 2 }

-- {SCALAR} 1.3.6.1.4.1.2356.11.2.60.3.10
lcsSetupAutoldLicenseCompany OBJECT-TYPE
    SYNTAX     DisplayString (SIZE(0..127))
    MAX-ACCESS read-write
    STATUS     current
    DESCRIPTION
            "-- empty --"
    ::= { lcsSetupAutoldLicense 10 }

-- {SCALAR} 1.3.6.1.4.1.2356.11.2.60.3.11
lcsSetupAutoldLicenseLastName OBJECT-TYPE
    SYNTAX     DisplayString (SIZE(0..31))
    MAX-ACCESS read-write
    STATUS     current
    DESCRIPTION
            "-- empty --"
    ::= { lcsSetupAutoldLicense 11 }

-- {SCALAR} 1.3.6.1.4.1.2356.11.2.60.3.12
lcsSetupAutoldLicenseFirstName OBJECT-TYPE
    SYNTAX     DisplayString (SIZE(0..31))
    MAX-ACCESS read-write
    STATUS     current
    DESCRIPTION
            "-- empty --"
    ::= { lcsSetupAutoldLicense 12 }

-- {SCALAR} 1.3.6.1.4.1.2356.11.2.60.3.13
lcsSetupAutoldLicenseStreetAndNumber OBJECT-TYPE
    SYNTAX     DisplayString (SIZE(0..127))
    MAX-ACCESS read-write
    STATUS     current
    DESCRIPTION
            "-- empty --"
    ::= { lcsSetupAutoldLicense 13 }

-- {SCALAR} 1.3.6.1.4.1.2356.11.2.60.3.14
lcsSetupAutoldLicensePostCode OBJECT-TYPE
    SYNTAX     DisplayString (SIZE(0..10))
    MAX-ACCESS read-write
    STATUS     current
    DESCRIPTION
            "-- empty --"
    ::= { lcsSetupAutoldLicense 14 }

-- {SCALAR} 1.3.6.1.4.1.2356.11.2.60.3.15
lcsSetupAutoldLicenseCity OBJECT-TYPE
    SYNTAX     DisplayString (SIZE(0..63))
    MAX-ACCESS read-write
    STATUS     current
    DESCRIPTION
            "-- empty --"
    ::= { lcsSetupAutoldLicense 15 }

-- {SCALAR} 1.3.6.1.4.1.2356.11.2.60.3.16
lcsSetupAutoldLicenseCountry OBJECT-TYPE
    SYNTAX     DisplayString (SIZE(0..63))
    MAX-ACCESS read-write
    STATUS     current
    DESCRIPTION
            "-- empty --"
    ::= { lcsSetupAutoldLicense 16 }

-- {SCALAR} 1.3.6.1.4.1.2356.11.2.60.3.17
lcsSetupAutoldLicenseEmailAddress OBJECT-TYPE
    SYNTAX     DisplayString (SIZE(0..63))
    MAX-ACCESS read-write
    STATUS     current
    DESCRIPTION
            "-- empty --"
    ::= { lcsSetupAutoldLicense 17 }

-- {NODE} 1.3.6.1.4.1.2356.11.2.60.56
lcsSetupAutoldUsb OBJECT IDENTIFIER ::= { lcsSetupAutold 56 }

-- {SCALAR} 1.3.6.1.4.1.2356.11.2.60.56.1
lcsSetupAutoldUsbFirmwareAndLoader OBJECT-TYPE
    SYNTAX     INTEGER {
                  eInactive (1),
                  eIfUnconfigured (2),
                  eActive (3)
            }
    MAX-ACCESS read-write
    STATUS     current
    DESCRIPTION
            ""
    ::= { lcsSetupAutoldUsb 1 }

-- {SCALAR} 1.3.6.1.4.1.2356.11.2.60.56.2
lcsSetupAutoldUsbConfigAndScript OBJECT-TYPE
    SYNTAX     INTEGER {
                  eInactive (1),
                  eIfUnconfigured (2),
                  eActive (3)
            }
    MAX-ACCESS read-write
    STATUS     current
    DESCRIPTION
            ""
    ::= { lcsSetupAutoldUsb 2 }

-- {NODE} 1.3.6.1.4.1.2356.11.2.63
lcsSetupPacketCapture OBJECT IDENTIFIER ::= { lcsSetup 63 }

-- {SCALAR} 1.3.6.1.4.1.2356.11.2.63.1
lcsSetupPacketCaptureLcoscapOperating OBJECT-TYPE
    SYNTAX     INTEGER {
                  eNo (0),
                  eYes (1)
            }
    MAX-ACCESS read-write
    STATUS     current
    DESCRIPTION
            "-- empty --"
    ::= { lcsSetupPacketCapture 1 }

-- {SCALAR} 1.3.6.1.4.1.2356.11.2.63.2
lcsSetupPacketCaptureLcoscapPort OBJECT-TYPE
    SYNTAX     Integer32 (0..65535)
    MAX-ACCESS read-write
    STATUS     current
    DESCRIPTION
            "-- empty --"
    ::= { lcsSetupPacketCapture 2 }

-- {SCALAR} 1.3.6.1.4.1.2356.11.2.63.3
lcsSetupPacketCaptureLcoscapMaxCaptureLength OBJECT-TYPE
    SYNTAX     Integer32 (0..65535)
    MAX-ACCESS read-write
    STATUS     current
    DESCRIPTION
            "-- empty --"
    ::= { lcsSetupPacketCapture 3 }

-- {SCALAR} 1.3.6.1.4.1.2356.11.2.63.11
lcsSetupPacketCaptureRpcapOperating OBJECT-TYPE
    SYNTAX     INTEGER {
                  eNo (0),
                  eYes (1)
            }
    MAX-ACCESS read-write
    STATUS     current
    DESCRIPTION
            "-- empty --"
    ::= { lcsSetupPacketCapture 11 }

-- {SCALAR} 1.3.6.1.4.1.2356.11.2.63.12
lcsSetupPacketCaptureRpcapPort OBJECT-TYPE
    SYNTAX     Integer32 (0..65535)
    MAX-ACCESS read-write
    STATUS     current
    DESCRIPTION
            "-- empty --"
    ::= { lcsSetupPacketCapture 12 }

-- {SCALAR} 1.3.6.1.4.1.2356.11.2.63.13
lcsSetupPacketCaptureRpcapBlockingTcp OBJECT-TYPE
    SYNTAX     INTEGER {
                  eNo (0),
                  eYes (1)
            }
    MAX-ACCESS read-write
    STATUS     current
    DESCRIPTION
            "-- empty --"
    ::= { lcsSetupPacketCapture 13 }

-- {NODE} 1.3.6.1.4.1.2356.11.2.64
lcsSetupPmsInterface OBJECT IDENTIFIER ::= { lcsSetup 64 }

-- {SCALAR} 1.3.6.1.4.1.2356.11.2.64.1
lcsSetupPmsInterfaceOperating OBJECT-TYPE
    SYNTAX     INTEGER {
                  eNo (0),
                  eYes (1)
            }
    MAX-ACCESS read-write
    STATUS     current
    DESCRIPTION
            "-- empty --"
    ::= { lcsSetupPmsInterface 1 }

-- {SCALAR} 1.3.6.1.4.1.2356.11.2.64.2
lcsSetupPmsInterfacePmsTyp OBJECT-TYPE
    SYNTAX     INTEGER {
                  eTcpIp (0)
            }
    MAX-ACCESS read-write
    STATUS     current
    DESCRIPTION
            "-- empty --"
    ::= { lcsSetupPmsInterface 2 }

-- {SCALAR} 1.3.6.1.4.1.2356.11.2.64.3
lcsSetupPmsInterfacePmsServerIpAddress OBJECT-TYPE
    SYNTAX     DisplayString (SIZE(0..32))
    MAX-ACCESS read-write
    STATUS     current
    DESCRIPTION
            "-- empty --"
    ::= { lcsSetupPmsInterface 3 }

-- {SCALAR} 1.3.6.1.4.1.2356.11.2.64.4
lcsSetupPmsInterfaceLoopbackAddress OBJECT-TYPE
    SYNTAX     DisplayString (SIZE(0..17))
    MAX-ACCESS read-write
    STATUS     current
    DESCRIPTION
            "-- empty --"
    ::= { lcsSetupPmsInterface 4 }

-- {SCALAR} 1.3.6.1.4.1.2356.11.2.64.5
lcsSetupPmsInterfacePmsPort OBJECT-TYPE
    SYNTAX     Integer32 (0..65535)
    MAX-ACCESS read-write
    STATUS     current
    DESCRIPTION
            "-- empty --"
    ::= { lcsSetupPmsInterface 5 }

-- {SCALAR} 1.3.6.1.4.1.2356.11.2.64.6
lcsSetupPmsInterfaceSeparator OBJECT-TYPE
    SYNTAX     DisplayString (SIZE(0..2))
    MAX-ACCESS read-write
    STATUS     current
    DESCRIPTION
            "-- empty --"
    ::= { lcsSetupPmsInterface 6 }

-- {SCALAR} 1.3.6.1.4.1.2356.11.2.64.7
lcsSetupPmsInterfaceCharset OBJECT-TYPE
    SYNTAX     INTEGER {
                  eCp850 (0),
                  eW1252 (1)
            }
    MAX-ACCESS read-write
    STATUS     current
    DESCRIPTION
            "-- empty --"
    ::= { lcsSetupPmsInterface 7 }

-- {SCALAR} 1.3.6.1.4.1.2356.11.2.64.8
lcsSetupPmsInterfaceCurrency OBJECT-TYPE
    SYNTAX     INTEGER {
                  eCent (0),
                  ePenny (1)
            }
    MAX-ACCESS read-write
    STATUS     current
    DESCRIPTION
            "-- empty --"
    ::= { lcsSetupPmsInterface 8 }

-- {TABLE} 1.3.6.1.4.1.2356.11.2.64.9
lcsSetupPmsInterfaceRateTable OBJECT-TYPE
    SYNTAX     SEQUENCE OF LcsSetupPmsInterfaceRateEntry
    MAX-ACCESS not-accessible
    STATUS     current
    DESCRIPTION
            "-- empty --"
    ::= { lcsSetupPmsInterface 9 }

-- {ROW} 1.3.6.1.4.1.2356.11.2.64.9.1
lcsSetupPmsInterfaceRateEntry OBJECT-TYPE
    SYNTAX     LcsSetupPmsInterfaceRateEntry
    MAX-ACCESS not-accessible
    STATUS     current
    DESCRIPTION
            ""
    INDEX {
            lcsSetupPmsInterfaceRateEntryRate,
            lcsSetupPmsInterfaceRateEntryUnit
          }
    ::= { lcsSetupPmsInterfaceRateTable 1 }

LcsSetupPmsInterfaceRateEntry ::= SEQUENCE {
            lcsSetupPmsInterfaceRateEntryRate DisplayString,
            lcsSetupPmsInterfaceRateEntryUnit INTEGER,
            lcsSetupPmsInterfaceRateEntryRateValue DisplayString
    }

-- {COLUMN} 1.3.6.1.4.1.2356.11.2.64.9.1.1
lcsSetupPmsInterfaceRateEntryRate OBJECT-TYPE
    SYNTAX     DisplayString (SIZE(0..20))
    MAX-ACCESS read-write
    STATUS     current
    DESCRIPTION
            "-- empty --"
    ::= { lcsSetupPmsInterfaceRateEntry 1 }

-- {COLUMN} 1.3.6.1.4.1.2356.11.2.64.9.1.2
lcsSetupPmsInterfaceRateEntryUnit OBJECT-TYPE
    SYNTAX     INTEGER {
                  eHourS (0),
                  eDayS (1),
                  eMinuteS (2)
            }
    MAX-ACCESS read-write
    STATUS     current
    DESCRIPTION
            "-- empty --"
    ::= { lcsSetupPmsInterfaceRateEntry 2 }

-- {COLUMN} 1.3.6.1.4.1.2356.11.2.64.9.1.3
lcsSetupPmsInterfaceRateEntryRateValue OBJECT-TYPE
    SYNTAX     DisplayString (SIZE(0..20))
    MAX-ACCESS read-write
    STATUS     current
    DESCRIPTION
            "-- empty --"
    ::= { lcsSetupPmsInterfaceRateEntry 3 }

-- {NODE} 1.3.6.1.4.1.2356.11.2.64.10
lcsSetupPmsInterfaceAccounting OBJECT IDENTIFIER ::= { lcsSetupPmsInterface 10 }

-- {SCALAR} 1.3.6.1.4.1.2356.11.2.64.10.1
lcsSetupPmsInterfaceAccountingSaveToFlashrom OBJECT-TYPE
    SYNTAX     INTEGER {
                  eNo (0),
                  eYes (1)
            }
    MAX-ACCESS read-write
    STATUS     current
    DESCRIPTION
            "-- empty --"
    ::= { lcsSetupPmsInterfaceAccounting 1 }

-- {SCALAR} 1.3.6.1.4.1.2356.11.2.64.10.2
lcsSetupPmsInterfaceAccountingSaveToFlashromPeriod OBJECT-TYPE
    SYNTAX     Integer32 (0..2147483647)
    MAX-ACCESS read-write
    STATUS     current
    DESCRIPTION
            "-- empty --"
    ::= { lcsSetupPmsInterfaceAccounting 2 }

-- {SCALAR} 1.3.6.1.4.1.2356.11.2.64.10.3
lcsSetupPmsInterfaceAccountingCleanupAccountingTablePeriod OBJECT-TYPE
    SYNTAX     Integer32 (0..2147483647)
    MAX-ACCESS read-write
    STATUS     current
    DESCRIPTION
            "-- empty --"
    ::= { lcsSetupPmsInterfaceAccounting 3 }

-- {SCALAR} 1.3.6.1.4.1.2356.11.2.64.10.4
lcsSetupPmsInterfaceAccountingUpdateAccountingTablePeriod OBJECT-TYPE
    SYNTAX     Integer32 (0..2147483647)
    MAX-ACCESS read-write
    STATUS     current
    DESCRIPTION
            "-- empty --"
    ::= { lcsSetupPmsInterfaceAccounting 4 }

-- {NODE} 1.3.6.1.4.1.2356.11.2.64.11
lcsSetupPmsInterfaceLoginForm OBJECT IDENTIFIER ::= { lcsSetupPmsInterface 11 }

-- {SCALAR} 1.3.6.1.4.1.2356.11.2.64.11.1
lcsSetupPmsInterfaceLoginFormPublicspotLoginForm OBJECT-TYPE
    SYNTAX     INTEGER {
                  eNo (0),
                  eYes (1)
            }
    MAX-ACCESS read-write
    STATUS     current
    DESCRIPTION
            "-- empty --"
    ::= { lcsSetupPmsInterfaceLoginForm 1 }

-- {SCALAR} 1.3.6.1.4.1.2356.11.2.64.11.2
lcsSetupPmsInterfaceLoginFormPmsLoginForm OBJECT-TYPE
    SYNTAX     INTEGER {
                  eNone (0),
                  eFree (1),
                  eCharge (2),
                  eFreeVip (3)
            }
    MAX-ACCESS read-write
    STATUS     current
    DESCRIPTION
            "-- empty --"
    ::= { lcsSetupPmsInterfaceLoginForm 2 }

-- {SCALAR} 1.3.6.1.4.1.2356.11.2.64.11.3
lcsSetupPmsInterfaceLoginFormFidelioFreeAdditionalCheck OBJECT-TYPE
    SYNTAX     INTEGER {
                  eNoCheck (0),
                  eReservationNumber (1),
                  eArrivalDate (2),
                  eDepartureDate (3),
                  eFirstName (4),
                  eProfileNumber (5)
            }
    MAX-ACCESS read-write
    STATUS     current
    DESCRIPTION
            "-- empty --"
    ::= { lcsSetupPmsInterfaceLoginForm 3 }

-- {SCALAR} 1.3.6.1.4.1.2356.11.2.64.11.4
lcsSetupPmsInterfaceLoginFormFidelioChargeAdditionalCheck OBJECT-TYPE
    SYNTAX     INTEGER {
                  eNoCheck (0),
                  eReservationNumber (1),
                  eArrivalDate (2),
                  eDepartureDate (3),
                  eFirstName (4),
                  eProfileNumber (5)
            }
    MAX-ACCESS read-write
    STATUS     current
    DESCRIPTION
            "-- empty --"
    ::= { lcsSetupPmsInterfaceLoginForm 4 }

-- {SCALAR} 1.3.6.1.4.1.2356.11.2.64.11.5
lcsSetupPmsInterfaceLoginFormFidelioFreeVipAdditionalCheck OBJECT-TYPE
    SYNTAX     INTEGER {
                  eNoCheck (0),
                  eReservationNumber (1),
                  eArrivalDate (2),
                  eDepartureDate (3),
                  eFirstName (4),
                  eProfileNumber (5)
            }
    MAX-ACCESS read-write
    STATUS     current
    DESCRIPTION
            "-- empty --"
    ::= { lcsSetupPmsInterfaceLoginForm 5 }

-- {TABLE} 1.3.6.1.4.1.2356.11.2.64.11.6
lcsSetupPmsInterfaceLoginFormFreeVipStatusTable OBJECT-TYPE
    SYNTAX     SEQUENCE OF LcsSetupPmsInterfaceLoginFormFreeVipStatusEntry
    MAX-ACCESS not-accessible
    STATUS     current
    DESCRIPTION
            "-- empty --"
    ::= { lcsSetupPmsInterfaceLoginForm 6 }

-- {ROW} 1.3.6.1.4.1.2356.11.2.64.11.6.1
lcsSetupPmsInterfaceLoginFormFreeVipStatusEntry OBJECT-TYPE
    SYNTAX     LcsSetupPmsInterfaceLoginFormFreeVipStatusEntry
    MAX-ACCESS not-accessible
    STATUS     current
    DESCRIPTION
            ""
    INDEX {
            lcsSetupPmsInterfaceLoginFormFreeVipStatusEntryStatus
          }
    ::= { lcsSetupPmsInterfaceLoginFormFreeVipStatusTable 1 }

LcsSetupPmsInterfaceLoginFormFreeVipStatusEntry ::= SEQUENCE {
            lcsSetupPmsInterfaceLoginFormFreeVipStatusEntryStatus DisplayString
    }

-- {COLUMN} 1.3.6.1.4.1.2356.11.2.64.11.6.1.1
lcsSetupPmsInterfaceLoginFormFreeVipStatusEntryStatus OBJECT-TYPE
    SYNTAX     DisplayString (SIZE(0..20))
    MAX-ACCESS read-write
    STATUS     current
    DESCRIPTION
            "-- empty --"
    ::= { lcsSetupPmsInterfaceLoginFormFreeVipStatusEntry 1 }

-- {SCALAR} 1.3.6.1.4.1.2356.11.2.64.11.14
lcsSetupPmsInterfaceLoginFormUserMustAcceptGtc OBJECT-TYPE
    SYNTAX     INTEGER {
                  eNo (0),
                  eYes (1)
            }
    MAX-ACCESS read-write
    STATUS     current
    DESCRIPTION
            "-- empty --"
    ::= { lcsSetupPmsInterfaceLoginForm 14 }

-- {SCALAR} 1.3.6.1.4.1.2356.11.2.64.12
lcsSetupPmsInterfaceGuestNameCaseSensitive OBJECT-TYPE
    SYNTAX     INTEGER {
                  eNo (0),
                  eYes (1)
            }
    MAX-ACCESS read-write
    STATUS     current
    DESCRIPTION
            "-- empty --"
    ::= { lcsSetupPmsInterface 12 }

-- {SCALAR} 1.3.6.1.4.1.2356.11.2.64.13
lcsSetupPmsInterfaceMultiLogin OBJECT-TYPE
    SYNTAX     INTEGER {
                  eNo (0),
                  eYes (1)
            }
    MAX-ACCESS read-write
    STATUS     current
    DESCRIPTION
            "-- empty --"
    ::= { lcsSetupPmsInterface 13 }

-- {TABLE} 1.3.6.1.4.1.2356.11.2.64.15
lcsSetupPmsInterfaceRateNewTable OBJECT-TYPE
    SYNTAX     SEQUENCE OF LcsSetupPmsInterfaceRateNewEntry
    MAX-ACCESS not-accessible
    STATUS     current
    DESCRIPTION
            ""
    ::= { lcsSetupPmsInterface 15 }

-- {ROW} 1.3.6.1.4.1.2356.11.2.64.15.1
lcsSetupPmsInterfaceRateNewEntry OBJECT-TYPE
    SYNTAX     LcsSetupPmsInterfaceRateNewEntry
    MAX-ACCESS not-accessible
    STATUS     current
    DESCRIPTION
            ""
    INDEX {
            lcsSetupPmsInterfaceRateNewEntryName,
            lcsSetupPmsInterfaceRateNewEntryRate,
            lcsSetupPmsInterfaceRateNewEntryUnit
          }
    ::= { lcsSetupPmsInterfaceRateNewTable 1 }

LcsSetupPmsInterfaceRateNewEntry ::= SEQUENCE {
            lcsSetupPmsInterfaceRateNewEntryRate DisplayString,
            lcsSetupPmsInterfaceRateNewEntryUnit INTEGER,
            lcsSetupPmsInterfaceRateNewEntryRateValue DisplayString,
            lcsSetupPmsInterfaceRateNewEntryName DisplayString,
            lcsSetupPmsInterfaceRateNewEntryTxBandwidth Integer32,
            lcsSetupPmsInterfaceRateNewEntryRxBandwidth Integer32
    }

-- {COLUMN} 1.3.6.1.4.1.2356.11.2.64.15.1.1
lcsSetupPmsInterfaceRateNewEntryRate OBJECT-TYPE
    SYNTAX     DisplayString (SIZE(0..20))
    MAX-ACCESS read-write
    STATUS     current
    DESCRIPTION
            "-- empty --"
    ::= { lcsSetupPmsInterfaceRateNewEntry 1 }

-- {COLUMN} 1.3.6.1.4.1.2356.11.2.64.15.1.2
lcsSetupPmsInterfaceRateNewEntryUnit OBJECT-TYPE
    SYNTAX     INTEGER {
                  eHourS (0),
                  eDayS (1),
                  eMinuteS (2)
            }
    MAX-ACCESS read-write
    STATUS     current
    DESCRIPTION
            "-- empty --"
    ::= { lcsSetupPmsInterfaceRateNewEntry 2 }

-- {COLUMN} 1.3.6.1.4.1.2356.11.2.64.15.1.3
lcsSetupPmsInterfaceRateNewEntryRateValue OBJECT-TYPE
    SYNTAX     DisplayString (SIZE(0..20))
    MAX-ACCESS read-write
    STATUS     current
    DESCRIPTION
            "-- empty --"
    ::= { lcsSetupPmsInterfaceRateNewEntry 3 }

-- {COLUMN} 1.3.6.1.4.1.2356.11.2.64.15.1.4
lcsSetupPmsInterfaceRateNewEntryName OBJECT-TYPE
    SYNTAX     DisplayString (SIZE(0..20))
    MAX-ACCESS read-write
    STATUS     current
    DESCRIPTION
            "-- empty --"
    ::= { lcsSetupPmsInterfaceRateNewEntry 4 }

-- {COLUMN} 1.3.6.1.4.1.2356.11.2.64.15.1.5
lcsSetupPmsInterfaceRateNewEntryTxBandwidth OBJECT-TYPE
    SYNTAX     Integer32 (0..2147483647)
    MAX-ACCESS read-write
    STATUS     current
    DESCRIPTION
            "-- empty --"
    ::= { lcsSetupPmsInterfaceRateNewEntry 5 }

-- {COLUMN} 1.3.6.1.4.1.2356.11.2.64.15.1.6
lcsSetupPmsInterfaceRateNewEntryRxBandwidth OBJECT-TYPE
    SYNTAX     Integer32 (0..2147483647)
    MAX-ACCESS read-write
    STATUS     current
    DESCRIPTION
            "-- empty --"
    ::= { lcsSetupPmsInterfaceRateNewEntry 6 }

-- {NODE} 1.3.6.1.4.1.2356.11.2.70
lcsSetupIpv6 OBJECT IDENTIFIER ::= { lcsSetup 70 }

-- {NODE} 1.3.6.1.4.1.2356.11.2.70.1
lcsSetupIpv6Tunnel OBJECT IDENTIFIER ::= { lcsSetupIpv6 1 }

-- {TABLE} 1.3.6.1.4.1.2356.11.2.70.1.1
lcsSetupIpv6Tunnel6in4Table OBJECT-TYPE
    SYNTAX     SEQUENCE OF LcsSetupIpv6Tunnel6in4Entry
    MAX-ACCESS not-accessible
    STATUS     current
    DESCRIPTION
            "-- empty --"
    ::= { lcsSetupIpv6Tunnel 1 }

-- {ROW} 1.3.6.1.4.1.2356.11.2.70.1.1.1
lcsSetupIpv6Tunnel6in4Entry OBJECT-TYPE
    SYNTAX     LcsSetupIpv6Tunnel6in4Entry
    MAX-ACCESS not-accessible
    STATUS     current
    DESCRIPTION
            ""
    INDEX {
            lcsSetupIpv6Tunnel6in4EntryPeerName
          }
    ::= { lcsSetupIpv6Tunnel6in4Table 1 }

LcsSetupIpv6Tunnel6in4Entry ::= SEQUENCE {
            lcsSetupIpv6Tunnel6in4EntryPeerName DisplayString,
            lcsSetupIpv6Tunnel6in4EntryRtgTag Integer32,
            lcsSetupIpv6Tunnel6in4EntryGatewayAddress DisplayString,
            lcsSetupIpv6Tunnel6in4EntryIpv4RtgTag Integer32,
            lcsSetupIpv6Tunnel6in4EntryGatewayIpv6Address DisplayString,
            lcsSetupIpv6Tunnel6in4EntryLocalIpv6Address DisplayString,
            lcsSetupIpv6Tunnel6in4EntryRoutedIpv6Prefix DisplayString,
            lcsSetupIpv6Tunnel6in4EntryFirewall INTEGER
    }

-- {COLUMN} 1.3.6.1.4.1.2356.11.2.70.1.1.1.1
lcsSetupIpv6Tunnel6in4EntryPeerName OBJECT-TYPE
    SYNTAX     DisplayString (SIZE(0..16))
    MAX-ACCESS read-write
    STATUS     current
    DESCRIPTION
            "-- empty --"
    ::= { lcsSetupIpv6Tunnel6in4Entry 1 }

-- {COLUMN} 1.3.6.1.4.1.2356.11.2.70.1.1.1.2
lcsSetupIpv6Tunnel6in4EntryRtgTag OBJECT-TYPE
    SYNTAX     Integer32 (0..65535)
    MAX-ACCESS read-write
    STATUS     current
    DESCRIPTION
            "-- empty --"
    ::= { lcsSetupIpv6Tunnel6in4Entry 2 }

-- {COLUMN} 1.3.6.1.4.1.2356.11.2.70.1.1.1.3
lcsSetupIpv6Tunnel6in4EntryGatewayAddress OBJECT-TYPE
    SYNTAX     DisplayString (SIZE(0..64))
    MAX-ACCESS read-write
    STATUS     current
    DESCRIPTION
            "-- empty --"
    ::= { lcsSetupIpv6Tunnel6in4Entry 3 }

-- {COLUMN} 1.3.6.1.4.1.2356.11.2.70.1.1.1.4
lcsSetupIpv6Tunnel6in4EntryIpv4RtgTag OBJECT-TYPE
    SYNTAX     Integer32 (0..65535)
    MAX-ACCESS read-write
    STATUS     current
    DESCRIPTION
            "-- empty --"
    ::= { lcsSetupIpv6Tunnel6in4Entry 4 }

-- {COLUMN} 1.3.6.1.4.1.2356.11.2.70.1.1.1.5
lcsSetupIpv6Tunnel6in4EntryGatewayIpv6Address OBJECT-TYPE
    SYNTAX     DisplayString (SIZE(0..43))
    MAX-ACCESS read-write
    STATUS     current
    DESCRIPTION
            "-- empty --"
    ::= { lcsSetupIpv6Tunnel6in4Entry 5 }

-- {COLUMN} 1.3.6.1.4.1.2356.11.2.70.1.1.1.6
lcsSetupIpv6Tunnel6in4EntryLocalIpv6Address OBJECT-TYPE
    SYNTAX     DisplayString (SIZE(0..43))
    MAX-ACCESS read-write
    STATUS     current
    DESCRIPTION
            "-- empty --"
    ::= { lcsSetupIpv6Tunnel6in4Entry 6 }

-- {COLUMN} 1.3.6.1.4.1.2356.11.2.70.1.1.1.7
lcsSetupIpv6Tunnel6in4EntryRoutedIpv6Prefix OBJECT-TYPE
    SYNTAX     DisplayString (SIZE(0..43))
    MAX-ACCESS read-write
    STATUS     current
    DESCRIPTION
            "-- empty --"
    ::= { lcsSetupIpv6Tunnel6in4Entry 7 }

-- {COLUMN} 1.3.6.1.4.1.2356.11.2.70.1.1.1.8
lcsSetupIpv6Tunnel6in4EntryFirewall OBJECT-TYPE
    SYNTAX     INTEGER {
                  eYes (0),
                  eNo (1)
            }
    MAX-ACCESS read-write
    STATUS     current
    DESCRIPTION
            "-- empty --"
    ::= { lcsSetupIpv6Tunnel6in4Entry 8 }

-- {TABLE} 1.3.6.1.4.1.2356.11.2.70.1.2
lcsSetupIpv6Tunnel6rdBorderRelayTable OBJECT-TYPE
    SYNTAX     SEQUENCE OF LcsSetupIpv6Tunnel6rdBorderRelayEntry
    MAX-ACCESS not-accessible
    STATUS     current
    DESCRIPTION
            "-- empty --"
    ::= { lcsSetupIpv6Tunnel 2 }

-- {ROW} 1.3.6.1.4.1.2356.11.2.70.1.2.1
lcsSetupIpv6Tunnel6rdBorderRelayEntry OBJECT-TYPE
    SYNTAX     LcsSetupIpv6Tunnel6rdBorderRelayEntry
    MAX-ACCESS not-accessible
    STATUS     current
    DESCRIPTION
            ""
    INDEX {
            lcsSetupIpv6Tunnel6rdBorderRelayEntryPeerName
          }
    ::= { lcsSetupIpv6Tunnel6rdBorderRelayTable 1 }

LcsSetupIpv6Tunnel6rdBorderRelayEntry ::= SEQUENCE {
            lcsSetupIpv6Tunnel6rdBorderRelayEntryPeerName DisplayString,
            lcsSetupIpv6Tunnel6rdBorderRelayEntryRtgTag Integer32,
            lcsSetupIpv6Tunnel6rdBorderRelayEntryIpv4LoopbackAddress DisplayString,
            lcsSetupIpv6Tunnel6rdBorderRelayEntry6rdPrefix DisplayString,
            lcsSetupIpv6Tunnel6rdBorderRelayEntryIpv4MaskLength Integer32,
            lcsSetupIpv6Tunnel6rdBorderRelayEntryDhcpv4Propagate INTEGER,
            lcsSetupIpv6Tunnel6rdBorderRelayEntryFirewall INTEGER
    }

-- {COLUMN} 1.3.6.1.4.1.2356.11.2.70.1.2.1.1
lcsSetupIpv6Tunnel6rdBorderRelayEntryPeerName OBJECT-TYPE
    SYNTAX     DisplayString (SIZE(0..16))
    MAX-ACCESS read-write
    STATUS     current
    DESCRIPTION
            "-- empty --"
    ::= { lcsSetupIpv6Tunnel6rdBorderRelayEntry 1 }

-- {COLUMN} 1.3.6.1.4.1.2356.11.2.70.1.2.1.2
lcsSetupIpv6Tunnel6rdBorderRelayEntryRtgTag OBJECT-TYPE
    SYNTAX     Integer32 (0..65535)
    MAX-ACCESS read-write
    STATUS     current
    DESCRIPTION
            "-- empty --"
    ::= { lcsSetupIpv6Tunnel6rdBorderRelayEntry 2 }

-- {COLUMN} 1.3.6.1.4.1.2356.11.2.70.1.2.1.3
lcsSetupIpv6Tunnel6rdBorderRelayEntryIpv4LoopbackAddress OBJECT-TYPE
    SYNTAX     DisplayString (SIZE(0..21))
    MAX-ACCESS read-write
    STATUS     current
    DESCRIPTION
            "-- empty --"
    ::= { lcsSetupIpv6Tunnel6rdBorderRelayEntry 3 }

-- {COLUMN} 1.3.6.1.4.1.2356.11.2.70.1.2.1.4
lcsSetupIpv6Tunnel6rdBorderRelayEntry6rdPrefix OBJECT-TYPE
    SYNTAX     DisplayString (SIZE(0..24))
    MAX-ACCESS read-write
    STATUS     current
    DESCRIPTION
            "-- empty --"
    ::= { lcsSetupIpv6Tunnel6rdBorderRelayEntry 4 }

-- {COLUMN} 1.3.6.1.4.1.2356.11.2.70.1.2.1.5
lcsSetupIpv6Tunnel6rdBorderRelayEntryIpv4MaskLength OBJECT-TYPE
    SYNTAX     Integer32 (0..65535)
    MAX-ACCESS read-write
    STATUS     current
    DESCRIPTION
            "-- empty --"
    ::= { lcsSetupIpv6Tunnel6rdBorderRelayEntry 5 }

-- {COLUMN} 1.3.6.1.4.1.2356.11.2.70.1.2.1.6
lcsSetupIpv6Tunnel6rdBorderRelayEntryDhcpv4Propagate OBJECT-TYPE
    SYNTAX     INTEGER {
                  eNo (0),
                  eYes (1)
            }
    MAX-ACCESS read-write
    STATUS     current
    DESCRIPTION
            "-- empty --"
    ::= { lcsSetupIpv6Tunnel6rdBorderRelayEntry 6 }

-- {COLUMN} 1.3.6.1.4.1.2356.11.2.70.1.2.1.7
lcsSetupIpv6Tunnel6rdBorderRelayEntryFirewall OBJECT-TYPE
    SYNTAX     INTEGER {
                  eYes (0),
                  eNo (1)
            }
    MAX-ACCESS read-write
    STATUS     current
    DESCRIPTION
            "-- empty --"
    ::= { lcsSetupIpv6Tunnel6rdBorderRelayEntry 7 }

-- {TABLE} 1.3.6.1.4.1.2356.11.2.70.1.3
lcsSetupIpv6Tunnel6rdTable OBJECT-TYPE
    SYNTAX     SEQUENCE OF LcsSetupIpv6Tunnel6rdEntry
    MAX-ACCESS not-accessible
    STATUS     current
    DESCRIPTION
            "-- empty --"
    ::= { lcsSetupIpv6Tunnel 3 }

-- {ROW} 1.3.6.1.4.1.2356.11.2.70.1.3.1
lcsSetupIpv6Tunnel6rdEntry OBJECT-TYPE
    SYNTAX     LcsSetupIpv6Tunnel6rdEntry
    MAX-ACCESS not-accessible
    STATUS     current
    DESCRIPTION
            ""
    INDEX {
            lcsSetupIpv6Tunnel6rdEntryPeerName
          }
    ::= { lcsSetupIpv6Tunnel6rdTable 1 }

LcsSetupIpv6Tunnel6rdEntry ::= SEQUENCE {
            lcsSetupIpv6Tunnel6rdEntryPeerName DisplayString,
            lcsSetupIpv6Tunnel6rdEntryRtgTag Integer32,
            lcsSetupIpv6Tunnel6rdEntryBorderRelayAddress DisplayString,
            lcsSetupIpv6Tunnel6rdEntryIpv4RtgTag Integer32,
            lcsSetupIpv6Tunnel6rdEntry6rdPrefix DisplayString,
            lcsSetupIpv6Tunnel6rdEntryIpv4MaskLength Integer32,
            lcsSetupIpv6Tunnel6rdEntryFirewall INTEGER
    }

-- {COLUMN} 1.3.6.1.4.1.2356.11.2.70.1.3.1.1
lcsSetupIpv6Tunnel6rdEntryPeerName OBJECT-TYPE
    SYNTAX     DisplayString (SIZE(0..16))
    MAX-ACCESS read-write
    STATUS     current
    DESCRIPTION
            "-- empty --"
    ::= { lcsSetupIpv6Tunnel6rdEntry 1 }

-- {COLUMN} 1.3.6.1.4.1.2356.11.2.70.1.3.1.2
lcsSetupIpv6Tunnel6rdEntryRtgTag OBJECT-TYPE
    SYNTAX     Integer32 (0..65535)
    MAX-ACCESS read-write
    STATUS     current
    DESCRIPTION
            "-- empty --"
    ::= { lcsSetupIpv6Tunnel6rdEntry 2 }

-- {COLUMN} 1.3.6.1.4.1.2356.11.2.70.1.3.1.3
lcsSetupIpv6Tunnel6rdEntryBorderRelayAddress OBJECT-TYPE
    SYNTAX     DisplayString (SIZE(0..64))
    MAX-ACCESS read-write
    STATUS     current
    DESCRIPTION
            "-- empty --"
    ::= { lcsSetupIpv6Tunnel6rdEntry 3 }

-- {COLUMN} 1.3.6.1.4.1.2356.11.2.70.1.3.1.4
lcsSetupIpv6Tunnel6rdEntryIpv4RtgTag OBJECT-TYPE
    SYNTAX     Integer32 (0..65535)
    MAX-ACCESS read-write
    STATUS     current
    DESCRIPTION
            "-- empty --"
    ::= { lcsSetupIpv6Tunnel6rdEntry 4 }

-- {COLUMN} 1.3.6.1.4.1.2356.11.2.70.1.3.1.5
lcsSetupIpv6Tunnel6rdEntry6rdPrefix OBJECT-TYPE
    SYNTAX     DisplayString (SIZE(0..24))
    MAX-ACCESS read-write
    STATUS     current
    DESCRIPTION
            "-- empty --"
    ::= { lcsSetupIpv6Tunnel6rdEntry 5 }

-- {COLUMN} 1.3.6.1.4.1.2356.11.2.70.1.3.1.6
lcsSetupIpv6Tunnel6rdEntryIpv4MaskLength OBJECT-TYPE
    SYNTAX     Integer32 (0..65535)
    MAX-ACCESS read-write
    STATUS     current
    DESCRIPTION
            "-- empty --"
    ::= { lcsSetupIpv6Tunnel6rdEntry 6 }

-- {COLUMN} 1.3.6.1.4.1.2356.11.2.70.1.3.1.7
lcsSetupIpv6Tunnel6rdEntryFirewall OBJECT-TYPE
    SYNTAX     INTEGER {
                  eYes (0),
                  eNo (1)
            }
    MAX-ACCESS read-write
    STATUS     current
    DESCRIPTION
            "-- empty --"
    ::= { lcsSetupIpv6Tunnel6rdEntry 7 }

-- {TABLE} 1.3.6.1.4.1.2356.11.2.70.1.4
lcsSetupIpv6Tunnel6to4Table OBJECT-TYPE
    SYNTAX     SEQUENCE OF LcsSetupIpv6Tunnel6to4Entry
    MAX-ACCESS not-accessible
    STATUS     current
    DESCRIPTION
            "-- empty --"
    ::= { lcsSetupIpv6Tunnel 4 }

-- {ROW} 1.3.6.1.4.1.2356.11.2.70.1.4.1
lcsSetupIpv6Tunnel6to4Entry OBJECT-TYPE
    SYNTAX     LcsSetupIpv6Tunnel6to4Entry
    MAX-ACCESS not-accessible
    STATUS     current
    DESCRIPTION
            ""
    INDEX {
            lcsSetupIpv6Tunnel6to4EntryPeerName
          }
    ::= { lcsSetupIpv6Tunnel6to4Table 1 }

LcsSetupIpv6Tunnel6to4Entry ::= SEQUENCE {
            lcsSetupIpv6Tunnel6to4EntryPeerName DisplayString,
            lcsSetupIpv6Tunnel6to4EntryRtgTag Integer32,
            lcsSetupIpv6Tunnel6to4EntryGatewayAddress DisplayString,
            lcsSetupIpv6Tunnel6to4EntryIpv4RtgTag Integer32,
            lcsSetupIpv6Tunnel6to4EntryFirewall INTEGER
    }

-- {COLUMN} 1.3.6.1.4.1.2356.11.2.70.1.4.1.1
lcsSetupIpv6Tunnel6to4EntryPeerName OBJECT-TYPE
    SYNTAX     DisplayString (SIZE(0..16))
    MAX-ACCESS read-write
    STATUS     current
    DESCRIPTION
            "-- empty --"
    ::= { lcsSetupIpv6Tunnel6to4Entry 1 }

-- {COLUMN} 1.3.6.1.4.1.2356.11.2.70.1.4.1.2
lcsSetupIpv6Tunnel6to4EntryRtgTag OBJECT-TYPE
    SYNTAX     Integer32 (0..65535)
    MAX-ACCESS read-write
    STATUS     current
    DESCRIPTION
            "-- empty --"
    ::= { lcsSetupIpv6Tunnel6to4Entry 2 }

-- {COLUMN} 1.3.6.1.4.1.2356.11.2.70.1.4.1.3
lcsSetupIpv6Tunnel6to4EntryGatewayAddress OBJECT-TYPE
    SYNTAX     DisplayString (SIZE(0..64))
    MAX-ACCESS read-write
    STATUS     current
    DESCRIPTION
            "-- empty --"
    ::= { lcsSetupIpv6Tunnel6to4Entry 3 }

-- {COLUMN} 1.3.6.1.4.1.2356.11.2.70.1.4.1.4
lcsSetupIpv6Tunnel6to4EntryIpv4RtgTag OBJECT-TYPE
    SYNTAX     Integer32 (0..65535)
    MAX-ACCESS read-write
    STATUS     current
    DESCRIPTION
            "-- empty --"
    ::= { lcsSetupIpv6Tunnel6to4Entry 4 }

-- {COLUMN} 1.3.6.1.4.1.2356.11.2.70.1.4.1.5
lcsSetupIpv6Tunnel6to4EntryFirewall OBJECT-TYPE
    SYNTAX     INTEGER {
                  eYes (0),
                  eNo (1)
            }
    MAX-ACCESS read-write
    STATUS     current
    DESCRIPTION
            "-- empty --"
    ::= { lcsSetupIpv6Tunnel6to4Entry 5 }

-- {NODE} 1.3.6.1.4.1.2356.11.2.70.2
lcsSetupIpv6RouterAdv OBJECT IDENTIFIER ::= { lcsSetupIpv6 2 }

-- {TABLE} 1.3.6.1.4.1.2356.11.2.70.2.1
lcsSetupIpv6RouterAdvPrefixOptionsTable OBJECT-TYPE
    SYNTAX     SEQUENCE OF LcsSetupIpv6RouterAdvPrefixOptionsEntry
    MAX-ACCESS not-accessible
    STATUS     current
    DESCRIPTION
            "-- empty --"
    ::= { lcsSetupIpv6RouterAdv 1 }

-- {ROW} 1.3.6.1.4.1.2356.11.2.70.2.1.1
lcsSetupIpv6RouterAdvPrefixOptionsEntry OBJECT-TYPE
    SYNTAX     LcsSetupIpv6RouterAdvPrefixOptionsEntry
    MAX-ACCESS not-accessible
    STATUS     current
    DESCRIPTION
            ""
    INDEX {
            lcsSetupIpv6RouterAdvPrefixOptionsEntryInterfaceName,
            lcsSetupIpv6RouterAdvPrefixOptionsEntryPrefix
          }
    ::= { lcsSetupIpv6RouterAdvPrefixOptionsTable 1 }

LcsSetupIpv6RouterAdvPrefixOptionsEntry ::= SEQUENCE {
            lcsSetupIpv6RouterAdvPrefixOptionsEntryInterfaceName DisplayString,
            lcsSetupIpv6RouterAdvPrefixOptionsEntryPrefix DisplayString,
            lcsSetupIpv6RouterAdvPrefixOptionsEntrySubnetId DisplayString,
            lcsSetupIpv6RouterAdvPrefixOptionsEntryAdvOnlink INTEGER,
            lcsSetupIpv6RouterAdvPrefixOptionsEntryAdvAutonomous INTEGER,
            lcsSetupIpv6RouterAdvPrefixOptionsEntryPdSource DisplayString,
            lcsSetupIpv6RouterAdvPrefixOptionsEntryAdvPrefLifetime Integer32,
            lcsSetupIpv6RouterAdvPrefixOptionsEntryAdvValidLifetime Integer32,
            lcsSetupIpv6RouterAdvPrefixOptionsEntryDecrementlifetimes INTEGER
    }

-- {COLUMN} 1.3.6.1.4.1.2356.11.2.70.2.1.1.1
lcsSetupIpv6RouterAdvPrefixOptionsEntryInterfaceName OBJECT-TYPE
    SYNTAX     DisplayString (SIZE(0..16))
    MAX-ACCESS read-write
    STATUS     current
    DESCRIPTION
            "-- empty --"
    ::= { lcsSetupIpv6RouterAdvPrefixOptionsEntry 1 }

-- {COLUMN} 1.3.6.1.4.1.2356.11.2.70.2.1.1.2
lcsSetupIpv6RouterAdvPrefixOptionsEntryPrefix OBJECT-TYPE
    SYNTAX     DisplayString (SIZE(0..43))
    MAX-ACCESS read-write
    STATUS     current
    DESCRIPTION
            "-- empty --"
    ::= { lcsSetupIpv6RouterAdvPrefixOptionsEntry 2 }

-- {COLUMN} 1.3.6.1.4.1.2356.11.2.70.2.1.1.3
lcsSetupIpv6RouterAdvPrefixOptionsEntrySubnetId OBJECT-TYPE
    SYNTAX     DisplayString (SIZE(0..19))
    MAX-ACCESS read-write
    STATUS     current
    DESCRIPTION
            "-- empty --"
    ::= { lcsSetupIpv6RouterAdvPrefixOptionsEntry 3 }

-- {COLUMN} 1.3.6.1.4.1.2356.11.2.70.2.1.1.4
lcsSetupIpv6RouterAdvPrefixOptionsEntryAdvOnlink OBJECT-TYPE
    SYNTAX     INTEGER {
                  eYes (0),
                  eNo (1)
            }
    MAX-ACCESS read-write
    STATUS     current
    DESCRIPTION
            "-- empty --"
    ::= { lcsSetupIpv6RouterAdvPrefixOptionsEntry 4 }

-- {COLUMN} 1.3.6.1.4.1.2356.11.2.70.2.1.1.5
lcsSetupIpv6RouterAdvPrefixOptionsEntryAdvAutonomous OBJECT-TYPE
    SYNTAX     INTEGER {
                  eYes (0),
                  eNo (1)
            }
    MAX-ACCESS read-write
    STATUS     current
    DESCRIPTION
            "-- empty --"
    ::= { lcsSetupIpv6RouterAdvPrefixOptionsEntry 5 }

-- {COLUMN} 1.3.6.1.4.1.2356.11.2.70.2.1.1.6
lcsSetupIpv6RouterAdvPrefixOptionsEntryPdSource OBJECT-TYPE
    SYNTAX     DisplayString (SIZE(0..16))
    MAX-ACCESS read-write
    STATUS     current
    DESCRIPTION
            "-- empty --"
    ::= { lcsSetupIpv6RouterAdvPrefixOptionsEntry 6 }

-- {COLUMN} 1.3.6.1.4.1.2356.11.2.70.2.1.1.7
lcsSetupIpv6RouterAdvPrefixOptionsEntryAdvPrefLifetime OBJECT-TYPE
    SYNTAX     Integer32 (0..2147483647)
    MAX-ACCESS read-write
    STATUS     current
    DESCRIPTION
            "-- empty --"
    ::= { lcsSetupIpv6RouterAdvPrefixOptionsEntry 7 }

-- {COLUMN} 1.3.6.1.4.1.2356.11.2.70.2.1.1.8
lcsSetupIpv6RouterAdvPrefixOptionsEntryAdvValidLifetime OBJECT-TYPE
    SYNTAX     Integer32 (0..2147483647)
    MAX-ACCESS read-write
    STATUS     current
    DESCRIPTION
            "-- empty --"
    ::= { lcsSetupIpv6RouterAdvPrefixOptionsEntry 8 }

-- {COLUMN} 1.3.6.1.4.1.2356.11.2.70.2.1.1.9
lcsSetupIpv6RouterAdvPrefixOptionsEntryDecrementlifetimes OBJECT-TYPE
    SYNTAX     INTEGER {
                  eYes (0),
                  eNo (1)
            }
    MAX-ACCESS read-write
    STATUS     current
    DESCRIPTION
            "-- empty --"
    ::= { lcsSetupIpv6RouterAdvPrefixOptionsEntry 9 }

-- {TABLE} 1.3.6.1.4.1.2356.11.2.70.2.2
lcsSetupIpv6RouterAdvInterfaceOptionsTable OBJECT-TYPE
    SYNTAX     SEQUENCE OF LcsSetupIpv6RouterAdvInterfaceOptionsEntry
    MAX-ACCESS not-accessible
    STATUS     current
    DESCRIPTION
            "-- empty --"
    ::= { lcsSetupIpv6RouterAdv 2 }

-- {ROW} 1.3.6.1.4.1.2356.11.2.70.2.2.1
lcsSetupIpv6RouterAdvInterfaceOptionsEntry OBJECT-TYPE
    SYNTAX     LcsSetupIpv6RouterAdvInterfaceOptionsEntry
    MAX-ACCESS not-accessible
    STATUS     current
    DESCRIPTION
            ""
    INDEX {
            lcsSetupIpv6RouterAdvInterfaceOptionsEntryInterfaceName
          }
    ::= { lcsSetupIpv6RouterAdvInterfaceOptionsTable 1 }

LcsSetupIpv6RouterAdvInterfaceOptionsEntry ::= SEQUENCE {
            lcsSetupIpv6RouterAdvInterfaceOptionsEntryInterfaceName DisplayString,
            lcsSetupIpv6RouterAdvInterfaceOptionsEntrySendAdverts INTEGER,
            lcsSetupIpv6RouterAdvInterfaceOptionsEntryMinRtrInterval Integer32,
            lcsSetupIpv6RouterAdvInterfaceOptionsEntryMaxRtrInterval Integer32,
            lcsSetupIpv6RouterAdvInterfaceOptionsEntryManagedFlag INTEGER,
            lcsSetupIpv6RouterAdvInterfaceOptionsEntryOtherConfigFlag INTEGER,
            lcsSetupIpv6RouterAdvInterfaceOptionsEntryLinkMtu Integer32,
            lcsSetupIpv6RouterAdvInterfaceOptionsEntryReachableTime Integer32,
            lcsSetupIpv6RouterAdvInterfaceOptionsEntryCrtHopLimit Integer32,
            lcsSetupIpv6RouterAdvInterfaceOptionsEntryDefaultLifetime Integer32,
            lcsSetupIpv6RouterAdvInterfaceOptionsEntryDefaultRouterMode INTEGER,
            lcsSetupIpv6RouterAdvInterfaceOptionsEntryRouterPreference INTEGER,
            lcsSetupIpv6RouterAdvInterfaceOptionsEntryRtrTime Integer32
    }

-- {COLUMN} 1.3.6.1.4.1.2356.11.2.70.2.2.1.1
lcsSetupIpv6RouterAdvInterfaceOptionsEntryInterfaceName OBJECT-TYPE
    SYNTAX     DisplayString (SIZE(0..16))
    MAX-ACCESS read-write
    STATUS     current
    DESCRIPTION
            "-- empty --"
    ::= { lcsSetupIpv6RouterAdvInterfaceOptionsEntry 1 }

-- {COLUMN} 1.3.6.1.4.1.2356.11.2.70.2.2.1.2
lcsSetupIpv6RouterAdvInterfaceOptionsEntrySendAdverts OBJECT-TYPE
    SYNTAX     INTEGER {
                  eYes (0),
                  eNo (1)
            }
    MAX-ACCESS read-write
    STATUS     current
    DESCRIPTION
            "-- empty --"
    ::= { lcsSetupIpv6RouterAdvInterfaceOptionsEntry 2 }

-- {COLUMN} 1.3.6.1.4.1.2356.11.2.70.2.2.1.3
lcsSetupIpv6RouterAdvInterfaceOptionsEntryMinRtrInterval OBJECT-TYPE
    SYNTAX     Integer32 (0..2147483647)
    MAX-ACCESS read-write
    STATUS     current
    DESCRIPTION
            "-- empty --"
    ::= { lcsSetupIpv6RouterAdvInterfaceOptionsEntry 3 }

-- {COLUMN} 1.3.6.1.4.1.2356.11.2.70.2.2.1.4
lcsSetupIpv6RouterAdvInterfaceOptionsEntryMaxRtrInterval OBJECT-TYPE
    SYNTAX     Integer32 (0..2147483647)
    MAX-ACCESS read-write
    STATUS     current
    DESCRIPTION
            "-- empty --"
    ::= { lcsSetupIpv6RouterAdvInterfaceOptionsEntry 4 }

-- {COLUMN} 1.3.6.1.4.1.2356.11.2.70.2.2.1.5
lcsSetupIpv6RouterAdvInterfaceOptionsEntryManagedFlag OBJECT-TYPE
    SYNTAX     INTEGER {
                  eYes (0),
                  eNo (1)
            }
    MAX-ACCESS read-write
    STATUS     current
    DESCRIPTION
            "-- empty --"
    ::= { lcsSetupIpv6RouterAdvInterfaceOptionsEntry 5 }

-- {COLUMN} 1.3.6.1.4.1.2356.11.2.70.2.2.1.6
lcsSetupIpv6RouterAdvInterfaceOptionsEntryOtherConfigFlag OBJECT-TYPE
    SYNTAX     INTEGER {
                  eYes (0),
                  eNo (1)
            }
    MAX-ACCESS read-write
    STATUS     current
    DESCRIPTION
            "-- empty --"
    ::= { lcsSetupIpv6RouterAdvInterfaceOptionsEntry 6 }

-- {COLUMN} 1.3.6.1.4.1.2356.11.2.70.2.2.1.7
lcsSetupIpv6RouterAdvInterfaceOptionsEntryLinkMtu OBJECT-TYPE
    SYNTAX     Integer32 (0..2147483647)
    MAX-ACCESS read-write
    STATUS     current
    DESCRIPTION
            "-- empty --"
    ::= { lcsSetupIpv6RouterAdvInterfaceOptionsEntry 7 }

-- {COLUMN} 1.3.6.1.4.1.2356.11.2.70.2.2.1.8
lcsSetupIpv6RouterAdvInterfaceOptionsEntryReachableTime OBJECT-TYPE
    SYNTAX     Integer32 (0..2147483647)
    MAX-ACCESS read-write
    STATUS     current
    DESCRIPTION
            "-- empty --"
    ::= { lcsSetupIpv6RouterAdvInterfaceOptionsEntry 8 }

-- {COLUMN} 1.3.6.1.4.1.2356.11.2.70.2.2.1.10
lcsSetupIpv6RouterAdvInterfaceOptionsEntryCrtHopLimit OBJECT-TYPE
    SYNTAX     Integer32 (0..2147483647)
    MAX-ACCESS read-write
    STATUS     current
    DESCRIPTION
            "-- empty --"
    ::= { lcsSetupIpv6RouterAdvInterfaceOptionsEntry 10 }

-- {COLUMN} 1.3.6.1.4.1.2356.11.2.70.2.2.1.11
lcsSetupIpv6RouterAdvInterfaceOptionsEntryDefaultLifetime OBJECT-TYPE
    SYNTAX     Integer32 (0..2147483647)
    MAX-ACCESS read-write
    STATUS     current
    DESCRIPTION
            "-- empty --"
    ::= { lcsSetupIpv6RouterAdvInterfaceOptionsEntry 11 }

-- {COLUMN} 1.3.6.1.4.1.2356.11.2.70.2.2.1.12
lcsSetupIpv6RouterAdvInterfaceOptionsEntryDefaultRouterMode OBJECT-TYPE
    SYNTAX     INTEGER {
                  eAuto (0),
                  eAlways (1),
                  eNever (2)
            }
    MAX-ACCESS read-write
    STATUS     current
    DESCRIPTION
            "-- empty --"
    ::= { lcsSetupIpv6RouterAdvInterfaceOptionsEntry 12 }

-- {COLUMN} 1.3.6.1.4.1.2356.11.2.70.2.2.1.13
lcsSetupIpv6RouterAdvInterfaceOptionsEntryRouterPreference OBJECT-TYPE
    SYNTAX     INTEGER {
                  eMedium (0),
                  eHigh (1),
                  eLow (2)
            }
    MAX-ACCESS read-write
    STATUS     current
    DESCRIPTION
            "-- empty --"
    ::= { lcsSetupIpv6RouterAdvInterfaceOptionsEntry 13 }

-- {COLUMN} 1.3.6.1.4.1.2356.11.2.70.2.2.1.14
lcsSetupIpv6RouterAdvInterfaceOptionsEntryRtrTime OBJECT-TYPE
    SYNTAX     Integer32 (0..2147483647)
    MAX-ACCESS read-write
    STATUS     current
    DESCRIPTION
            "-- empty --"
    ::= { lcsSetupIpv6RouterAdvInterfaceOptionsEntry 14 }

-- {TABLE} 1.3.6.1.4.1.2356.11.2.70.2.3
lcsSetupIpv6RouterAdvRouteOptionsTable OBJECT-TYPE
    SYNTAX     SEQUENCE OF LcsSetupIpv6RouterAdvRouteOptionsEntry
    MAX-ACCESS not-accessible
    STATUS     current
    DESCRIPTION
            "-- empty --"
    ::= { lcsSetupIpv6RouterAdv 3 }

-- {ROW} 1.3.6.1.4.1.2356.11.2.70.2.3.1
lcsSetupIpv6RouterAdvRouteOptionsEntry OBJECT-TYPE
    SYNTAX     LcsSetupIpv6RouterAdvRouteOptionsEntry
    MAX-ACCESS not-accessible
    STATUS     current
    DESCRIPTION
            ""
    INDEX {
            lcsSetupIpv6RouterAdvRouteOptionsEntryInterfaceName,
            lcsSetupIpv6RouterAdvRouteOptionsEntryPrefix
          }
    ::= { lcsSetupIpv6RouterAdvRouteOptionsTable 1 }

LcsSetupIpv6RouterAdvRouteOptionsEntry ::= SEQUENCE {
            lcsSetupIpv6RouterAdvRouteOptionsEntryInterfaceName DisplayString,
            lcsSetupIpv6RouterAdvRouteOptionsEntryPrefix DisplayString,
            lcsSetupIpv6RouterAdvRouteOptionsEntryRouteLifetime Integer32,
            lcsSetupIpv6RouterAdvRouteOptionsEntryRoutePreference INTEGER
    }

-- {COLUMN} 1.3.6.1.4.1.2356.11.2.70.2.3.1.1
lcsSetupIpv6RouterAdvRouteOptionsEntryInterfaceName OBJECT-TYPE
    SYNTAX     DisplayString (SIZE(0..16))
    MAX-ACCESS read-write
    STATUS     current
    DESCRIPTION
            "-- empty --"
    ::= { lcsSetupIpv6RouterAdvRouteOptionsEntry 1 }

-- {COLUMN} 1.3.6.1.4.1.2356.11.2.70.2.3.1.2
lcsSetupIpv6RouterAdvRouteOptionsEntryPrefix OBJECT-TYPE
    SYNTAX     DisplayString (SIZE(0..43))
    MAX-ACCESS read-write
    STATUS     current
    DESCRIPTION
            "-- empty --"
    ::= { lcsSetupIpv6RouterAdvRouteOptionsEntry 2 }

-- {COLUMN} 1.3.6.1.4.1.2356.11.2.70.2.3.1.3
lcsSetupIpv6RouterAdvRouteOptionsEntryRouteLifetime OBJECT-TYPE
    SYNTAX     Integer32 (0..2147483647)
    MAX-ACCESS read-write
    STATUS     current
    DESCRIPTION
            "-- empty --"
    ::= { lcsSetupIpv6RouterAdvRouteOptionsEntry 3 }

-- {COLUMN} 1.3.6.1.4.1.2356.11.2.70.2.3.1.4
lcsSetupIpv6RouterAdvRouteOptionsEntryRoutePreference OBJECT-TYPE
    SYNTAX     INTEGER {
                  eMedium (0),
                  eHigh (1),
                  eLow (2)
            }
    MAX-ACCESS read-write
    STATUS     current
    DESCRIPTION
            "-- empty --"
    ::= { lcsSetupIpv6RouterAdvRouteOptionsEntry 4 }

-- {TABLE} 1.3.6.1.4.1.2356.11.2.70.2.5
lcsSetupIpv6RouterAdvRdnssOptionsTable OBJECT-TYPE
    SYNTAX     SEQUENCE OF LcsSetupIpv6RouterAdvRdnssOptionsEntry
    MAX-ACCESS not-accessible
    STATUS     current
    DESCRIPTION
            "-- empty --"
    ::= { lcsSetupIpv6RouterAdv 5 }

-- {ROW} 1.3.6.1.4.1.2356.11.2.70.2.5.1
lcsSetupIpv6RouterAdvRdnssOptionsEntry OBJECT-TYPE
    SYNTAX     LcsSetupIpv6RouterAdvRdnssOptionsEntry
    MAX-ACCESS not-accessible
    STATUS     current
    DESCRIPTION
            ""
    INDEX {
            lcsSetupIpv6RouterAdvRdnssOptionsEntryInterfaceName
          }
    ::= { lcsSetupIpv6RouterAdvRdnssOptionsTable 1 }

LcsSetupIpv6RouterAdvRdnssOptionsEntry ::= SEQUENCE {
            lcsSetupIpv6RouterAdvRdnssOptionsEntryInterfaceName DisplayString,
            lcsSetupIpv6RouterAdvRdnssOptionsEntryPrimaryDns DisplayString,
            lcsSetupIpv6RouterAdvRdnssOptionsEntrySecondaryDns DisplayString,
            lcsSetupIpv6RouterAdvRdnssOptionsEntryDnsSearchList BITS,
            lcsSetupIpv6RouterAdvRdnssOptionsEntryLifetime Integer32
    }

-- {COLUMN} 1.3.6.1.4.1.2356.11.2.70.2.5.1.1
lcsSetupIpv6RouterAdvRdnssOptionsEntryInterfaceName OBJECT-TYPE
    SYNTAX     DisplayString (SIZE(0..16))
    MAX-ACCESS read-write
    STATUS     current
    DESCRIPTION
            "-- empty --"
    ::= { lcsSetupIpv6RouterAdvRdnssOptionsEntry 1 }

-- {COLUMN} 1.3.6.1.4.1.2356.11.2.70.2.5.1.2
lcsSetupIpv6RouterAdvRdnssOptionsEntryPrimaryDns OBJECT-TYPE
    SYNTAX     DisplayString (SIZE(0..39))
    MAX-ACCESS read-write
    STATUS     current
    DESCRIPTION
            "-- empty --"
    ::= { lcsSetupIpv6RouterAdvRdnssOptionsEntry 2 }

-- {COLUMN} 1.3.6.1.4.1.2356.11.2.70.2.5.1.3
lcsSetupIpv6RouterAdvRdnssOptionsEntrySecondaryDns OBJECT-TYPE
    SYNTAX     DisplayString (SIZE(0..39))
    MAX-ACCESS read-write
    STATUS     current
    DESCRIPTION
            "-- empty --"
    ::= { lcsSetupIpv6RouterAdvRdnssOptionsEntry 3 }

-- {COLUMN} 1.3.6.1.4.1.2356.11.2.70.2.5.1.4
lcsSetupIpv6RouterAdvRdnssOptionsEntryDnsSearchList OBJECT-TYPE
    SYNTAX     BITS {
                  eNone (0),
                  eWan (6),
                  eInternal (7)
            }
    MAX-ACCESS read-write
    STATUS     current
    DESCRIPTION
            "-- empty --"
    ::= { lcsSetupIpv6RouterAdvRdnssOptionsEntry 4 }

-- {COLUMN} 1.3.6.1.4.1.2356.11.2.70.2.5.1.5
lcsSetupIpv6RouterAdvRdnssOptionsEntryLifetime OBJECT-TYPE
    SYNTAX     Integer32 (0..2147483647)
    MAX-ACCESS read-write
    STATUS     current
    DESCRIPTION
            "-- empty --"
    ::= { lcsSetupIpv6RouterAdvRdnssOptionsEntry 5 }

-- {TABLE} 1.3.6.1.4.1.2356.11.2.70.2.6
lcsSetupIpv6RouterAdvPrefixPoolsTable OBJECT-TYPE
    SYNTAX     SEQUENCE OF LcsSetupIpv6RouterAdvPrefixPoolsEntry
    MAX-ACCESS not-accessible
    STATUS     current
    DESCRIPTION
            "-- empty --"
    ::= { lcsSetupIpv6RouterAdv 6 }

-- {ROW} 1.3.6.1.4.1.2356.11.2.70.2.6.1
lcsSetupIpv6RouterAdvPrefixPoolsEntry OBJECT-TYPE
    SYNTAX     LcsSetupIpv6RouterAdvPrefixPoolsEntry
    MAX-ACCESS not-accessible
    STATUS     current
    DESCRIPTION
            ""
    INDEX {
            lcsSetupIpv6RouterAdvPrefixPoolsEntryInterfaceName
          }
    ::= { lcsSetupIpv6RouterAdvPrefixPoolsTable 1 }

LcsSetupIpv6RouterAdvPrefixPoolsEntry ::= SEQUENCE {
            lcsSetupIpv6RouterAdvPrefixPoolsEntryInterfaceName DisplayString,
            lcsSetupIpv6RouterAdvPrefixPoolsEntryStartPrefixPool DisplayString,
            lcsSetupIpv6RouterAdvPrefixPoolsEntryEndPrefixPool DisplayString,
            lcsSetupIpv6RouterAdvPrefixPoolsEntryPrefixLength Integer32,
            lcsSetupIpv6RouterAdvPrefixPoolsEntryAdvOnlink INTEGER,
            lcsSetupIpv6RouterAdvPrefixPoolsEntryAdvAutonomous INTEGER,
            lcsSetupIpv6RouterAdvPrefixPoolsEntryAdvPrefLifetime Integer32,
            lcsSetupIpv6RouterAdvPrefixPoolsEntryAdvValidLifetime Integer32
    }

-- {COLUMN} 1.3.6.1.4.1.2356.11.2.70.2.6.1.1
lcsSetupIpv6RouterAdvPrefixPoolsEntryInterfaceName OBJECT-TYPE
    SYNTAX     DisplayString (SIZE(0..16))
    MAX-ACCESS read-write
    STATUS     current
    DESCRIPTION
            "-- empty --"
    ::= { lcsSetupIpv6RouterAdvPrefixPoolsEntry 1 }

-- {COLUMN} 1.3.6.1.4.1.2356.11.2.70.2.6.1.2
lcsSetupIpv6RouterAdvPrefixPoolsEntryStartPrefixPool OBJECT-TYPE
    SYNTAX     DisplayString (SIZE(0..43))
    MAX-ACCESS read-write
    STATUS     current
    DESCRIPTION
            "-- empty --"
    ::= { lcsSetupIpv6RouterAdvPrefixPoolsEntry 2 }

-- {COLUMN} 1.3.6.1.4.1.2356.11.2.70.2.6.1.3
lcsSetupIpv6RouterAdvPrefixPoolsEntryEndPrefixPool OBJECT-TYPE
    SYNTAX     DisplayString (SIZE(0..43))
    MAX-ACCESS read-write
    STATUS     current
    DESCRIPTION
            "-- empty --"
    ::= { lcsSetupIpv6RouterAdvPrefixPoolsEntry 3 }

-- {COLUMN} 1.3.6.1.4.1.2356.11.2.70.2.6.1.4
lcsSetupIpv6RouterAdvPrefixPoolsEntryPrefixLength OBJECT-TYPE
    SYNTAX     Integer32 (0..255)
    MAX-ACCESS read-write
    STATUS     current
    DESCRIPTION
            "-- empty --"
    ::= { lcsSetupIpv6RouterAdvPrefixPoolsEntry 4 }

-- {COLUMN} 1.3.6.1.4.1.2356.11.2.70.2.6.1.5
lcsSetupIpv6RouterAdvPrefixPoolsEntryAdvOnlink OBJECT-TYPE
    SYNTAX     INTEGER {
                  eYes (0),
                  eNo (1)
            }
    MAX-ACCESS read-write
    STATUS     current
    DESCRIPTION
            "-- empty --"
    ::= { lcsSetupIpv6RouterAdvPrefixPoolsEntry 5 }

-- {COLUMN} 1.3.6.1.4.1.2356.11.2.70.2.6.1.6
lcsSetupIpv6RouterAdvPrefixPoolsEntryAdvAutonomous OBJECT-TYPE
    SYNTAX     INTEGER {
                  eYes (0),
                  eNo (1)
            }
    MAX-ACCESS read-write
    STATUS     current
    DESCRIPTION
            "-- empty --"
    ::= { lcsSetupIpv6RouterAdvPrefixPoolsEntry 6 }

-- {COLUMN} 1.3.6.1.4.1.2356.11.2.70.2.6.1.7
lcsSetupIpv6RouterAdvPrefixPoolsEntryAdvPrefLifetime OBJECT-TYPE
    SYNTAX     Integer32 (0..2147483647)
    MAX-ACCESS read-write
    STATUS     current
    DESCRIPTION
            "-- empty --"
    ::= { lcsSetupIpv6RouterAdvPrefixPoolsEntry 7 }

-- {COLUMN} 1.3.6.1.4.1.2356.11.2.70.2.6.1.8
lcsSetupIpv6RouterAdvPrefixPoolsEntryAdvValidLifetime OBJECT-TYPE
    SYNTAX     Integer32 (0..2147483647)
    MAX-ACCESS read-write
    STATUS     current
    DESCRIPTION
            "-- empty --"
    ::= { lcsSetupIpv6RouterAdvPrefixPoolsEntry 8 }

-- {SCALAR} 1.3.6.1.4.1.2356.11.2.70.2.7
lcsSetupIpv6RouterAdvDiscontinuation OBJECT-TYPE
    SYNTAX     INTEGER {
                  eNo (0),
                  eYes (1)
            }
    MAX-ACCESS read-write
    STATUS     current
    DESCRIPTION
            "-- empty --"
    ::= { lcsSetupIpv6RouterAdv 7 }

-- {NODE} 1.3.6.1.4.1.2356.11.2.70.3
lcsSetupIpv6Dhcpv6 OBJECT IDENTIFIER ::= { lcsSetupIpv6 3 }

-- {NODE} 1.3.6.1.4.1.2356.11.2.70.3.1
lcsSetupIpv6Dhcpv6Server OBJECT IDENTIFIER ::= { lcsSetupIpv6Dhcpv6 1 }

-- {TABLE} 1.3.6.1.4.1.2356.11.2.70.3.1.2
lcsSetupIpv6Dhcpv6ServerAddressPoolsTable OBJECT-TYPE
    SYNTAX     SEQUENCE OF LcsSetupIpv6Dhcpv6ServerAddressPoolsEntry
    MAX-ACCESS not-accessible
    STATUS     current
    DESCRIPTION
            "-- empty --"
    ::= { lcsSetupIpv6Dhcpv6Server 2 }

-- {ROW} 1.3.6.1.4.1.2356.11.2.70.3.1.2.1
lcsSetupIpv6Dhcpv6ServerAddressPoolsEntry OBJECT-TYPE
    SYNTAX     LcsSetupIpv6Dhcpv6ServerAddressPoolsEntry
    MAX-ACCESS not-accessible
    STATUS     current
    DESCRIPTION
            ""
    INDEX {
            lcsSetupIpv6Dhcpv6ServerAddressPoolsEntryAddressPoolName,
            lcsSetupIpv6Dhcpv6ServerAddressPoolsEntryStartAddressPool,
            lcsSetupIpv6Dhcpv6ServerAddressPoolsEntryPdSource
          }
    ::= { lcsSetupIpv6Dhcpv6ServerAddressPoolsTable 1 }

LcsSetupIpv6Dhcpv6ServerAddressPoolsEntry ::= SEQUENCE {
            lcsSetupIpv6Dhcpv6ServerAddressPoolsEntryAddressPoolName DisplayString,
            lcsSetupIpv6Dhcpv6ServerAddressPoolsEntryStartAddressPool DisplayString,
            lcsSetupIpv6Dhcpv6ServerAddressPoolsEntryEndAddressPool DisplayString,
            lcsSetupIpv6Dhcpv6ServerAddressPoolsEntryPrefLifetime Integer32,
            lcsSetupIpv6Dhcpv6ServerAddressPoolsEntryValidLifetime Integer32,
            lcsSetupIpv6Dhcpv6ServerAddressPoolsEntryPdSource DisplayString
    }

-- {COLUMN} 1.3.6.1.4.1.2356.11.2.70.3.1.2.1.1
lcsSetupIpv6Dhcpv6ServerAddressPoolsEntryAddressPoolName OBJECT-TYPE
    SYNTAX     DisplayString (SIZE(0..31))
    MAX-ACCESS read-write
    STATUS     current
    DESCRIPTION
            "-- empty --"
    ::= { lcsSetupIpv6Dhcpv6ServerAddressPoolsEntry 1 }

-- {COLUMN} 1.3.6.1.4.1.2356.11.2.70.3.1.2.1.2
lcsSetupIpv6Dhcpv6ServerAddressPoolsEntryStartAddressPool OBJECT-TYPE
    SYNTAX     DisplayString (SIZE(0..39))
    MAX-ACCESS read-write
    STATUS     current
    DESCRIPTION
            "-- empty --"
    ::= { lcsSetupIpv6Dhcpv6ServerAddressPoolsEntry 2 }

-- {COLUMN} 1.3.6.1.4.1.2356.11.2.70.3.1.2.1.3
lcsSetupIpv6Dhcpv6ServerAddressPoolsEntryEndAddressPool OBJECT-TYPE
    SYNTAX     DisplayString (SIZE(0..39))
    MAX-ACCESS read-write
    STATUS     current
    DESCRIPTION
            "-- empty --"
    ::= { lcsSetupIpv6Dhcpv6ServerAddressPoolsEntry 3 }

-- {COLUMN} 1.3.6.1.4.1.2356.11.2.70.3.1.2.1.5
lcsSetupIpv6Dhcpv6ServerAddressPoolsEntryPrefLifetime OBJECT-TYPE
    SYNTAX     Integer32 (0..2147483647)
    MAX-ACCESS read-write
    STATUS     current
    DESCRIPTION
            "-- empty --"
    ::= { lcsSetupIpv6Dhcpv6ServerAddressPoolsEntry 5 }

-- {COLUMN} 1.3.6.1.4.1.2356.11.2.70.3.1.2.1.6
lcsSetupIpv6Dhcpv6ServerAddressPoolsEntryValidLifetime OBJECT-TYPE
    SYNTAX     Integer32 (0..2147483647)
    MAX-ACCESS read-write
    STATUS     current
    DESCRIPTION
            "-- empty --"
    ::= { lcsSetupIpv6Dhcpv6ServerAddressPoolsEntry 6 }

-- {COLUMN} 1.3.6.1.4.1.2356.11.2.70.3.1.2.1.7
lcsSetupIpv6Dhcpv6ServerAddressPoolsEntryPdSource OBJECT-TYPE
    SYNTAX     DisplayString (SIZE(0..16))
    MAX-ACCESS read-write
    STATUS     current
    DESCRIPTION
            "-- empty --"
    ::= { lcsSetupIpv6Dhcpv6ServerAddressPoolsEntry 7 }

-- {TABLE} 1.3.6.1.4.1.2356.11.2.70.3.1.3
lcsSetupIpv6Dhcpv6ServerPdPoolsTable OBJECT-TYPE
    SYNTAX     SEQUENCE OF LcsSetupIpv6Dhcpv6ServerPdPoolsEntry
    MAX-ACCESS not-accessible
    STATUS     current
    DESCRIPTION
            "-- empty --"
    ::= { lcsSetupIpv6Dhcpv6Server 3 }

-- {ROW} 1.3.6.1.4.1.2356.11.2.70.3.1.3.1
lcsSetupIpv6Dhcpv6ServerPdPoolsEntry OBJECT-TYPE
    SYNTAX     LcsSetupIpv6Dhcpv6ServerPdPoolsEntry
    MAX-ACCESS not-accessible
    STATUS     current
    DESCRIPTION
            ""
    INDEX {
            lcsSetupIpv6Dhcpv6ServerPdPoolsEntryPdPoolName,
            lcsSetupIpv6Dhcpv6ServerPdPoolsEntryStartPdPool,
            lcsSetupIpv6Dhcpv6ServerPdPoolsEntryPdSource
          }
    ::= { lcsSetupIpv6Dhcpv6ServerPdPoolsTable 1 }

LcsSetupIpv6Dhcpv6ServerPdPoolsEntry ::= SEQUENCE {
            lcsSetupIpv6Dhcpv6ServerPdPoolsEntryPdPoolName DisplayString,
            lcsSetupIpv6Dhcpv6ServerPdPoolsEntryStartPdPool DisplayString,
            lcsSetupIpv6Dhcpv6ServerPdPoolsEntryEndPdPool DisplayString,
            lcsSetupIpv6Dhcpv6ServerPdPoolsEntryPrefixLength Integer32,
            lcsSetupIpv6Dhcpv6ServerPdPoolsEntryPrefLifetime Integer32,
            lcsSetupIpv6Dhcpv6ServerPdPoolsEntryValidLifetime Integer32,
            lcsSetupIpv6Dhcpv6ServerPdPoolsEntryPdSource DisplayString
    }

-- {COLUMN} 1.3.6.1.4.1.2356.11.2.70.3.1.3.1.1
lcsSetupIpv6Dhcpv6ServerPdPoolsEntryPdPoolName OBJECT-TYPE
    SYNTAX     DisplayString (SIZE(0..31))
    MAX-ACCESS read-write
    STATUS     current
    DESCRIPTION
            "-- empty --"
    ::= { lcsSetupIpv6Dhcpv6ServerPdPoolsEntry 1 }

-- {COLUMN} 1.3.6.1.4.1.2356.11.2.70.3.1.3.1.2
lcsSetupIpv6Dhcpv6ServerPdPoolsEntryStartPdPool OBJECT-TYPE
    SYNTAX     DisplayString (SIZE(0..39))
    MAX-ACCESS read-write
    STATUS     current
    DESCRIPTION
            "-- empty --"
    ::= { lcsSetupIpv6Dhcpv6ServerPdPoolsEntry 2 }

-- {COLUMN} 1.3.6.1.4.1.2356.11.2.70.3.1.3.1.3
lcsSetupIpv6Dhcpv6ServerPdPoolsEntryEndPdPool OBJECT-TYPE
    SYNTAX     DisplayString (SIZE(0..39))
    MAX-ACCESS read-write
    STATUS     current
    DESCRIPTION
            "-- empty --"
    ::= { lcsSetupIpv6Dhcpv6ServerPdPoolsEntry 3 }

-- {COLUMN} 1.3.6.1.4.1.2356.11.2.70.3.1.3.1.4
lcsSetupIpv6Dhcpv6ServerPdPoolsEntryPrefixLength OBJECT-TYPE
    SYNTAX     Integer32 (0..255)
    MAX-ACCESS read-write
    STATUS     current
    DESCRIPTION
            "-- empty --"
    ::= { lcsSetupIpv6Dhcpv6ServerPdPoolsEntry 4 }

-- {COLUMN} 1.3.6.1.4.1.2356.11.2.70.3.1.3.1.5
lcsSetupIpv6Dhcpv6ServerPdPoolsEntryPrefLifetime OBJECT-TYPE
    SYNTAX     Integer32 (0..2147483647)
    MAX-ACCESS read-write
    STATUS     current
    DESCRIPTION
            "-- empty --"
    ::= { lcsSetupIpv6Dhcpv6ServerPdPoolsEntry 5 }

-- {COLUMN} 1.3.6.1.4.1.2356.11.2.70.3.1.3.1.6
lcsSetupIpv6Dhcpv6ServerPdPoolsEntryValidLifetime OBJECT-TYPE
    SYNTAX     Integer32 (0..2147483647)
    MAX-ACCESS read-write
    STATUS     current
    DESCRIPTION
            "-- empty --"
    ::= { lcsSetupIpv6Dhcpv6ServerPdPoolsEntry 6 }

-- {COLUMN} 1.3.6.1.4.1.2356.11.2.70.3.1.3.1.7
lcsSetupIpv6Dhcpv6ServerPdPoolsEntryPdSource OBJECT-TYPE
    SYNTAX     DisplayString (SIZE(0..16))
    MAX-ACCESS read-write
    STATUS     current
    DESCRIPTION
            "-- empty --"
    ::= { lcsSetupIpv6Dhcpv6ServerPdPoolsEntry 7 }

-- {TABLE} 1.3.6.1.4.1.2356.11.2.70.3.1.4
lcsSetupIpv6Dhcpv6ServerIfcListTable OBJECT-TYPE
    SYNTAX     SEQUENCE OF LcsSetupIpv6Dhcpv6ServerIfcListEntry
    MAX-ACCESS not-accessible
    STATUS     current
    DESCRIPTION
            ""
    ::= { lcsSetupIpv6Dhcpv6Server 4 }

-- {ROW} 1.3.6.1.4.1.2356.11.2.70.3.1.4.1
lcsSetupIpv6Dhcpv6ServerIfcListEntry OBJECT-TYPE
    SYNTAX     LcsSetupIpv6Dhcpv6ServerIfcListEntry
    MAX-ACCESS not-accessible
    STATUS     current
    DESCRIPTION
            ""
    INDEX {
            lcsSetupIpv6Dhcpv6ServerIfcListEntryInterfaceNameOrRelay
          }
    ::= { lcsSetupIpv6Dhcpv6ServerIfcListTable 1 }

LcsSetupIpv6Dhcpv6ServerIfcListEntry ::= SEQUENCE {
            lcsSetupIpv6Dhcpv6ServerIfcListEntryInterfaceNameOrRelay DisplayString,
            lcsSetupIpv6Dhcpv6ServerIfcListEntryOperating INTEGER,
            lcsSetupIpv6Dhcpv6ServerIfcListEntryPrimaryDns DisplayString,
            lcsSetupIpv6Dhcpv6ServerIfcListEntrySecondaryDns DisplayString,
            lcsSetupIpv6Dhcpv6ServerIfcListEntryAddressPoolName DisplayString,
            lcsSetupIpv6Dhcpv6ServerIfcListEntryPdPoolName DisplayString,
            lcsSetupIpv6Dhcpv6ServerIfcListEntryRapidCommit INTEGER,
            lcsSetupIpv6Dhcpv6ServerIfcListEntryPreference Integer32,
            lcsSetupIpv6Dhcpv6ServerIfcListEntryRenewTime Integer32,
            lcsSetupIpv6Dhcpv6ServerIfcListEntryRebindTime Integer32,
            lcsSetupIpv6Dhcpv6ServerIfcListEntryUnicastAddress DisplayString,
            lcsSetupIpv6Dhcpv6ServerIfcListEntryDnsSearchList BITS,
            lcsSetupIpv6Dhcpv6ServerIfcListEntryReconfigure INTEGER
    }

-- {COLUMN} 1.3.6.1.4.1.2356.11.2.70.3.1.4.1.1
lcsSetupIpv6Dhcpv6ServerIfcListEntryInterfaceNameOrRelay OBJECT-TYPE
    SYNTAX     DisplayString (SIZE(0..39))
    MAX-ACCESS read-write
    STATUS     current
    DESCRIPTION
            "-- empty --"
    ::= { lcsSetupIpv6Dhcpv6ServerIfcListEntry 1 }

-- {COLUMN} 1.3.6.1.4.1.2356.11.2.70.3.1.4.1.2
lcsSetupIpv6Dhcpv6ServerIfcListEntryOperating OBJECT-TYPE
    SYNTAX     INTEGER {
                  eNo (0),
                  eYes (1)
            }
    MAX-ACCESS read-write
    STATUS     current
    DESCRIPTION
            "-- empty --"
    ::= { lcsSetupIpv6Dhcpv6ServerIfcListEntry 2 }

-- {COLUMN} 1.3.6.1.4.1.2356.11.2.70.3.1.4.1.3
lcsSetupIpv6Dhcpv6ServerIfcListEntryPrimaryDns OBJECT-TYPE
    SYNTAX     DisplayString (SIZE(0..39))
    MAX-ACCESS read-write
    STATUS     current
    DESCRIPTION
            "-- empty --"
    ::= { lcsSetupIpv6Dhcpv6ServerIfcListEntry 3 }

-- {COLUMN} 1.3.6.1.4.1.2356.11.2.70.3.1.4.1.4
lcsSetupIpv6Dhcpv6ServerIfcListEntrySecondaryDns OBJECT-TYPE
    SYNTAX     DisplayString (SIZE(0..39))
    MAX-ACCESS read-write
    STATUS     current
    DESCRIPTION
            "-- empty --"
    ::= { lcsSetupIpv6Dhcpv6ServerIfcListEntry 4 }

-- {COLUMN} 1.3.6.1.4.1.2356.11.2.70.3.1.4.1.5
lcsSetupIpv6Dhcpv6ServerIfcListEntryAddressPoolName OBJECT-TYPE
    SYNTAX     DisplayString (SIZE(0..31))
    MAX-ACCESS read-write
    STATUS     current
    DESCRIPTION
            "-- empty --"
    ::= { lcsSetupIpv6Dhcpv6ServerIfcListEntry 5 }

-- {COLUMN} 1.3.6.1.4.1.2356.11.2.70.3.1.4.1.6
lcsSetupIpv6Dhcpv6ServerIfcListEntryPdPoolName OBJECT-TYPE
    SYNTAX     DisplayString (SIZE(0..31))
    MAX-ACCESS read-write
    STATUS     current
    DESCRIPTION
            "-- empty --"
    ::= { lcsSetupIpv6Dhcpv6ServerIfcListEntry 6 }

-- {COLUMN} 1.3.6.1.4.1.2356.11.2.70.3.1.4.1.7
lcsSetupIpv6Dhcpv6ServerIfcListEntryRapidCommit OBJECT-TYPE
    SYNTAX     INTEGER {
                  eNo (0),
                  eYes (1)
            }
    MAX-ACCESS read-write
    STATUS     current
    DESCRIPTION
            "-- empty --"
    ::= { lcsSetupIpv6Dhcpv6ServerIfcListEntry 7 }

-- {COLUMN} 1.3.6.1.4.1.2356.11.2.70.3.1.4.1.8
lcsSetupIpv6Dhcpv6ServerIfcListEntryPreference OBJECT-TYPE
    SYNTAX     Integer32 (0..255)
    MAX-ACCESS read-write
    STATUS     current
    DESCRIPTION
            "-- empty --"
    ::= { lcsSetupIpv6Dhcpv6ServerIfcListEntry 8 }

-- {COLUMN} 1.3.6.1.4.1.2356.11.2.70.3.1.4.1.9
lcsSetupIpv6Dhcpv6ServerIfcListEntryRenewTime OBJECT-TYPE
    SYNTAX     Integer32 (0..2147483647)
    MAX-ACCESS read-write
    STATUS     current
    DESCRIPTION
            "-- empty --"
    ::= { lcsSetupIpv6Dhcpv6ServerIfcListEntry 9 }

-- {COLUMN} 1.3.6.1.4.1.2356.11.2.70.3.1.4.1.10
lcsSetupIpv6Dhcpv6ServerIfcListEntryRebindTime OBJECT-TYPE
    SYNTAX     Integer32 (0..2147483647)
    MAX-ACCESS read-write
    STATUS     current
    DESCRIPTION
            "-- empty --"
    ::= { lcsSetupIpv6Dhcpv6ServerIfcListEntry 10 }

-- {COLUMN} 1.3.6.1.4.1.2356.11.2.70.3.1.4.1.11
lcsSetupIpv6Dhcpv6ServerIfcListEntryUnicastAddress OBJECT-TYPE
    SYNTAX     DisplayString (SIZE(0..39))
    MAX-ACCESS read-write
    STATUS     current
    DESCRIPTION
            "-- empty --"
    ::= { lcsSetupIpv6Dhcpv6ServerIfcListEntry 11 }

-- {COLUMN} 1.3.6.1.4.1.2356.11.2.70.3.1.4.1.12
lcsSetupIpv6Dhcpv6ServerIfcListEntryDnsSearchList OBJECT-TYPE
    SYNTAX     BITS {
                  eNone (0),
                  eWan (6),
                  eInternal (7)
            }
    MAX-ACCESS read-write
    STATUS     current
    DESCRIPTION
            "-- empty --"
    ::= { lcsSetupIpv6Dhcpv6ServerIfcListEntry 12 }

-- {COLUMN} 1.3.6.1.4.1.2356.11.2.70.3.1.4.1.13
lcsSetupIpv6Dhcpv6ServerIfcListEntryReconfigure OBJECT-TYPE
    SYNTAX     INTEGER {
                  eOff (0),
                  eReject (1),
                  eAllow (2),
                  eRequire (3)
            }
    MAX-ACCESS read-write
    STATUS     current
    DESCRIPTION
            "-- empty --"
    ::= { lcsSetupIpv6Dhcpv6ServerIfcListEntry 13 }

-- {SCALAR} 1.3.6.1.4.1.2356.11.2.70.3.1.5
lcsSetupIpv6Dhcpv6ServerLimitConfirmToClientsWithAddresses OBJECT-TYPE
    SYNTAX     INTEGER {
                  eNo (0),
                  eYes (1)
            }
    MAX-ACCESS read-write
    STATUS     current
    DESCRIPTION
            "-- empty --"
    ::= { lcsSetupIpv6Dhcpv6Server 5 }

-- {TABLE} 1.3.6.1.4.1.2356.11.2.70.3.1.6
lcsSetupIpv6Dhcpv6ServerReservationsTable OBJECT-TYPE
    SYNTAX     SEQUENCE OF LcsSetupIpv6Dhcpv6ServerReservationsEntry
    MAX-ACCESS not-accessible
    STATUS     current
    DESCRIPTION
            "-- empty --"
    ::= { lcsSetupIpv6Dhcpv6Server 6 }

-- {ROW} 1.3.6.1.4.1.2356.11.2.70.3.1.6.1
lcsSetupIpv6Dhcpv6ServerReservationsEntry OBJECT-TYPE
    SYNTAX     LcsSetupIpv6Dhcpv6ServerReservationsEntry
    MAX-ACCESS not-accessible
    STATUS     current
    DESCRIPTION
            ""
    INDEX {
            lcsSetupIpv6Dhcpv6ServerReservationsEntryInterfaceNameOrRelay,
            lcsSetupIpv6Dhcpv6ServerReservationsEntryAddressOrPdPrefix,
            lcsSetupIpv6Dhcpv6ServerReservationsEntryPdSource
          }
    ::= { lcsSetupIpv6Dhcpv6ServerReservationsTable 1 }

LcsSetupIpv6Dhcpv6ServerReservationsEntry ::= SEQUENCE {
            lcsSetupIpv6Dhcpv6ServerReservationsEntryInterfaceNameOrRelay DisplayString,
            lcsSetupIpv6Dhcpv6ServerReservationsEntryAddressOrPdPrefix DisplayString,
            lcsSetupIpv6Dhcpv6ServerReservationsEntryClient-ID DisplayString,
            lcsSetupIpv6Dhcpv6ServerReservationsEntryPrefLifetime Integer32,
            lcsSetupIpv6Dhcpv6ServerReservationsEntryValidLifetime Integer32,
            lcsSetupIpv6Dhcpv6ServerReservationsEntryPdSource DisplayString,
            lcsSetupIpv6Dhcpv6ServerReservationsEntryIdentifierType INTEGER,
            lcsSetupIpv6Dhcpv6ServerReservationsEntryComment DisplayString
    }

-- {COLUMN} 1.3.6.1.4.1.2356.11.2.70.3.1.6.1.1
lcsSetupIpv6Dhcpv6ServerReservationsEntryInterfaceNameOrRelay OBJECT-TYPE
    SYNTAX     DisplayString (SIZE(0..39))
    MAX-ACCESS read-write
    STATUS     current
    DESCRIPTION
            "-- empty --"
    ::= { lcsSetupIpv6Dhcpv6ServerReservationsEntry 1 }

-- {COLUMN} 1.3.6.1.4.1.2356.11.2.70.3.1.6.1.2
lcsSetupIpv6Dhcpv6ServerReservationsEntryAddressOrPdPrefix OBJECT-TYPE
    SYNTAX     DisplayString (SIZE(0..43))
    MAX-ACCESS read-write
    STATUS     current
    DESCRIPTION
            "-- empty --"
    ::= { lcsSetupIpv6Dhcpv6ServerReservationsEntry 2 }

-- {COLUMN} 1.3.6.1.4.1.2356.11.2.70.3.1.6.1.3
lcsSetupIpv6Dhcpv6ServerReservationsEntryClient-ID OBJECT-TYPE
    SYNTAX     DisplayString (SIZE(0..127))
    MAX-ACCESS read-write
    STATUS     current
    DESCRIPTION
            "-- empty --"
    ::= { lcsSetupIpv6Dhcpv6ServerReservationsEntry 3 }

-- {COLUMN} 1.3.6.1.4.1.2356.11.2.70.3.1.6.1.5
lcsSetupIpv6Dhcpv6ServerReservationsEntryPrefLifetime OBJECT-TYPE
    SYNTAX     Integer32 (0..2147483647)
    MAX-ACCESS read-write
    STATUS     current
    DESCRIPTION
            "-- empty --"
    ::= { lcsSetupIpv6Dhcpv6ServerReservationsEntry 5 }

-- {COLUMN} 1.3.6.1.4.1.2356.11.2.70.3.1.6.1.6
lcsSetupIpv6Dhcpv6ServerReservationsEntryValidLifetime OBJECT-TYPE
    SYNTAX     Integer32 (0..2147483647)
    MAX-ACCESS read-write
    STATUS     current
    DESCRIPTION
            "-- empty --"
    ::= { lcsSetupIpv6Dhcpv6ServerReservationsEntry 6 }

-- {COLUMN} 1.3.6.1.4.1.2356.11.2.70.3.1.6.1.7
lcsSetupIpv6Dhcpv6ServerReservationsEntryPdSource OBJECT-TYPE
    SYNTAX     DisplayString (SIZE(0..16))
    MAX-ACCESS read-write
    STATUS     current
    DESCRIPTION
            "-- empty --"
    ::= { lcsSetupIpv6Dhcpv6ServerReservationsEntry 7 }

-- {COLUMN} 1.3.6.1.4.1.2356.11.2.70.3.1.6.1.8
lcsSetupIpv6Dhcpv6ServerReservationsEntryIdentifierType OBJECT-TYPE
    SYNTAX     INTEGER {
                  eClientId (0),
                  eMacAddress (1),
                  eInterfaceId (2),
                  eRemoteId (3)
            }
    MAX-ACCESS read-write
    STATUS     current
    DESCRIPTION
            "-- empty --"
    ::= { lcsSetupIpv6Dhcpv6ServerReservationsEntry 8 }

-- {COLUMN} 1.3.6.1.4.1.2356.11.2.70.3.1.6.1.9
lcsSetupIpv6Dhcpv6ServerReservationsEntryComment OBJECT-TYPE
    SYNTAX     DisplayString (SIZE(0..63))
    MAX-ACCESS read-write
    STATUS     current
    DESCRIPTION
            "-- empty --"
    ::= { lcsSetupIpv6Dhcpv6ServerReservationsEntry 9 }

-- {SCALAR} 1.3.6.1.4.1.2356.11.2.70.3.1.7
lcsSetupIpv6Dhcpv6ServerCreateAddressRoutes OBJECT-TYPE
    SYNTAX     INTEGER {
                  eNo (0),
                  eYes (1)
            }
    MAX-ACCESS read-write
    STATUS     current
    DESCRIPTION
            "-- empty --"
    ::= { lcsSetupIpv6Dhcpv6Server 7 }

-- {TABLE} 1.3.6.1.4.1.2356.11.2.70.3.1.8
lcsSetupIpv6Dhcpv6ServerAddOptTable OBJECT-TYPE
    SYNTAX     SEQUENCE OF LcsSetupIpv6Dhcpv6ServerAddOptEntry
    MAX-ACCESS not-accessible
    STATUS     current
    DESCRIPTION
            ""
    ::= { lcsSetupIpv6Dhcpv6Server 8 }

-- {ROW} 1.3.6.1.4.1.2356.11.2.70.3.1.8.1
lcsSetupIpv6Dhcpv6ServerAddOptEntry OBJECT-TYPE
    SYNTAX     LcsSetupIpv6Dhcpv6ServerAddOptEntry
    MAX-ACCESS not-accessible
    STATUS     current
    DESCRIPTION
            ""
    INDEX {
            lcsSetupIpv6Dhcpv6ServerAddOptEntryInterfaceNameOrRelay,
            lcsSetupIpv6Dhcpv6ServerAddOptEntryOptionNumber
          }
    ::= { lcsSetupIpv6Dhcpv6ServerAddOptTable 1 }

LcsSetupIpv6Dhcpv6ServerAddOptEntry ::= SEQUENCE {
            lcsSetupIpv6Dhcpv6ServerAddOptEntryInterfaceNameOrRelay DisplayString,
            lcsSetupIpv6Dhcpv6ServerAddOptEntryOptionNumber Integer32,
            lcsSetupIpv6Dhcpv6ServerAddOptEntryOptionType INTEGER,
            lcsSetupIpv6Dhcpv6ServerAddOptEntryOptionValue DisplayString
    }

-- {COLUMN} 1.3.6.1.4.1.2356.11.2.70.3.1.8.1.1
lcsSetupIpv6Dhcpv6ServerAddOptEntryInterfaceNameOrRelay OBJECT-TYPE
    SYNTAX     DisplayString (SIZE(0..39))
    MAX-ACCESS read-write
    STATUS     current
    DESCRIPTION
            "-- empty --"
    ::= { lcsSetupIpv6Dhcpv6ServerAddOptEntry 1 }

-- {COLUMN} 1.3.6.1.4.1.2356.11.2.70.3.1.8.1.2
lcsSetupIpv6Dhcpv6ServerAddOptEntryOptionNumber OBJECT-TYPE
    SYNTAX     Integer32 (0..65535)
    MAX-ACCESS read-write
    STATUS     current
    DESCRIPTION
            "-- empty --"
    ::= { lcsSetupIpv6Dhcpv6ServerAddOptEntry 2 }

-- {COLUMN} 1.3.6.1.4.1.2356.11.2.70.3.1.8.1.3
lcsSetupIpv6Dhcpv6ServerAddOptEntryOptionType OBJECT-TYPE
    SYNTAX     INTEGER {
                  eInteger8 (0),
                  eInteger16 (1),
                  eInteger32 (2),
                  eIpv6Addresses (3),
                  eDomainList (4),
                  eString (5),
                  eHexdump (6)
            }
    MAX-ACCESS read-write
    STATUS     current
    DESCRIPTION
            "-- empty --"
    ::= { lcsSetupIpv6Dhcpv6ServerAddOptEntry 3 }

-- {COLUMN} 1.3.6.1.4.1.2356.11.2.70.3.1.8.1.4
lcsSetupIpv6Dhcpv6ServerAddOptEntryOptionValue OBJECT-TYPE
    SYNTAX     DisplayString (SIZE(0..254))
    MAX-ACCESS read-write
    STATUS     current
    DESCRIPTION
            "-- empty --"
    ::= { lcsSetupIpv6Dhcpv6ServerAddOptEntry 4 }

-- {NODE} 1.3.6.1.4.1.2356.11.2.70.3.2
lcsSetupIpv6Dhcpv6Client OBJECT IDENTIFIER ::= { lcsSetupIpv6Dhcpv6 2 }

-- {TABLE} 1.3.6.1.4.1.2356.11.2.70.3.2.1
lcsSetupIpv6Dhcpv6ClientInterfaceListTable OBJECT-TYPE
    SYNTAX     SEQUENCE OF LcsSetupIpv6Dhcpv6ClientInterfaceListEntry
    MAX-ACCESS not-accessible
    STATUS     current
    DESCRIPTION
            "-- empty --"
    ::= { lcsSetupIpv6Dhcpv6Client 1 }

-- {ROW} 1.3.6.1.4.1.2356.11.2.70.3.2.1.1
lcsSetupIpv6Dhcpv6ClientInterfaceListEntry OBJECT-TYPE
    SYNTAX     LcsSetupIpv6Dhcpv6ClientInterfaceListEntry
    MAX-ACCESS not-accessible
    STATUS     current
    DESCRIPTION
            ""
    INDEX {
            lcsSetupIpv6Dhcpv6ClientInterfaceListEntryInterfaceName
          }
    ::= { lcsSetupIpv6Dhcpv6ClientInterfaceListTable 1 }

LcsSetupIpv6Dhcpv6ClientInterfaceListEntry ::= SEQUENCE {
            lcsSetupIpv6Dhcpv6ClientInterfaceListEntryInterfaceName DisplayString,
            lcsSetupIpv6Dhcpv6ClientInterfaceListEntryOperating INTEGER,
            lcsSetupIpv6Dhcpv6ClientInterfaceListEntryRequestDns INTEGER,
            lcsSetupIpv6Dhcpv6ClientInterfaceListEntryRequestAddress INTEGER,
            lcsSetupIpv6Dhcpv6ClientInterfaceListEntryRequestPd INTEGER,
            lcsSetupIpv6Dhcpv6ClientInterfaceListEntryRapidCommit INTEGER,
            lcsSetupIpv6Dhcpv6ClientInterfaceListEntrySendFqdn INTEGER,
            lcsSetupIpv6Dhcpv6ClientInterfaceListEntryAcceptReconf INTEGER,
            lcsSetupIpv6Dhcpv6ClientInterfaceListEntryRequestDomainList INTEGER,
            lcsSetupIpv6Dhcpv6ClientInterfaceListEntryRequestSntp INTEGER,
            lcsSetupIpv6Dhcpv6ClientInterfaceListEntryPdHint Integer32
    }

-- {COLUMN} 1.3.6.1.4.1.2356.11.2.70.3.2.1.1.1
lcsSetupIpv6Dhcpv6ClientInterfaceListEntryInterfaceName OBJECT-TYPE
    SYNTAX     DisplayString (SIZE(0..16))
    MAX-ACCESS read-write
    STATUS     current
    DESCRIPTION
            "-- empty --"
    ::= { lcsSetupIpv6Dhcpv6ClientInterfaceListEntry 1 }

-- {COLUMN} 1.3.6.1.4.1.2356.11.2.70.3.2.1.1.2
lcsSetupIpv6Dhcpv6ClientInterfaceListEntryOperating OBJECT-TYPE
    SYNTAX     INTEGER {
                  eNo (0),
                  eAutoconf (1),
                  eYes (2)
            }
    MAX-ACCESS read-write
    STATUS     current
    DESCRIPTION
            "-- empty --"
    ::= { lcsSetupIpv6Dhcpv6ClientInterfaceListEntry 2 }

-- {COLUMN} 1.3.6.1.4.1.2356.11.2.70.3.2.1.1.3
lcsSetupIpv6Dhcpv6ClientInterfaceListEntryRequestDns OBJECT-TYPE
    SYNTAX     INTEGER {
                  eNo (0),
                  eYes (1)
            }
    MAX-ACCESS read-write
    STATUS     current
    DESCRIPTION
            "-- empty --"
    ::= { lcsSetupIpv6Dhcpv6ClientInterfaceListEntry 3 }

-- {COLUMN} 1.3.6.1.4.1.2356.11.2.70.3.2.1.1.4
lcsSetupIpv6Dhcpv6ClientInterfaceListEntryRequestAddress OBJECT-TYPE
    SYNTAX     INTEGER {
                  eNo (0),
                  eYes (1)
            }
    MAX-ACCESS read-write
    STATUS     current
    DESCRIPTION
            "-- empty --"
    ::= { lcsSetupIpv6Dhcpv6ClientInterfaceListEntry 4 }

-- {COLUMN} 1.3.6.1.4.1.2356.11.2.70.3.2.1.1.5
lcsSetupIpv6Dhcpv6ClientInterfaceListEntryRequestPd OBJECT-TYPE
    SYNTAX     INTEGER {
                  eNo (0),
                  eYes (1)
            }
    MAX-ACCESS read-write
    STATUS     current
    DESCRIPTION
            "-- empty --"
    ::= { lcsSetupIpv6Dhcpv6ClientInterfaceListEntry 5 }

-- {COLUMN} 1.3.6.1.4.1.2356.11.2.70.3.2.1.1.6
lcsSetupIpv6Dhcpv6ClientInterfaceListEntryRapidCommit OBJECT-TYPE
    SYNTAX     INTEGER {
                  eNo (0),
                  eYes (1)
            }
    MAX-ACCESS read-write
    STATUS     current
    DESCRIPTION
            "-- empty --"
    ::= { lcsSetupIpv6Dhcpv6ClientInterfaceListEntry 6 }

-- {COLUMN} 1.3.6.1.4.1.2356.11.2.70.3.2.1.1.7
lcsSetupIpv6Dhcpv6ClientInterfaceListEntrySendFqdn OBJECT-TYPE
    SYNTAX     INTEGER {
                  eNo (0),
                  eYes (1)
            }
    MAX-ACCESS read-write
    STATUS     current
    DESCRIPTION
            "-- empty --"
    ::= { lcsSetupIpv6Dhcpv6ClientInterfaceListEntry 7 }

-- {COLUMN} 1.3.6.1.4.1.2356.11.2.70.3.2.1.1.8
lcsSetupIpv6Dhcpv6ClientInterfaceListEntryAcceptReconf OBJECT-TYPE
    SYNTAX     INTEGER {
                  eNo (0),
                  eYes (1)
            }
    MAX-ACCESS read-write
    STATUS     current
    DESCRIPTION
            "-- empty --"
    ::= { lcsSetupIpv6Dhcpv6ClientInterfaceListEntry 8 }

-- {COLUMN} 1.3.6.1.4.1.2356.11.2.70.3.2.1.1.9
lcsSetupIpv6Dhcpv6ClientInterfaceListEntryRequestDomainList OBJECT-TYPE
    SYNTAX     INTEGER {
                  eNo (0),
                  eYes (1)
            }
    MAX-ACCESS read-write
    STATUS     current
    DESCRIPTION
            "-- empty --"
    ::= { lcsSetupIpv6Dhcpv6ClientInterfaceListEntry 9 }

-- {COLUMN} 1.3.6.1.4.1.2356.11.2.70.3.2.1.1.10
lcsSetupIpv6Dhcpv6ClientInterfaceListEntryRequestSntp OBJECT-TYPE
    SYNTAX     INTEGER {
                  eNo (0),
                  eYes (1)
            }
    MAX-ACCESS read-write
    STATUS     current
    DESCRIPTION
            "-- empty --"
    ::= { lcsSetupIpv6Dhcpv6ClientInterfaceListEntry 10 }

-- {COLUMN} 1.3.6.1.4.1.2356.11.2.70.3.2.1.1.11
lcsSetupIpv6Dhcpv6ClientInterfaceListEntryPdHint OBJECT-TYPE
    SYNTAX     Integer32 (0..255)
    MAX-ACCESS read-write
    STATUS     current
    DESCRIPTION
            "-- empty --"
    ::= { lcsSetupIpv6Dhcpv6ClientInterfaceListEntry 11 }

-- {SCALAR} 1.3.6.1.4.1.2356.11.2.70.3.2.2
lcsSetupIpv6Dhcpv6ClientUserClassIdentifer OBJECT-TYPE
    SYNTAX     DisplayString (SIZE(0..253))
    MAX-ACCESS read-write
    STATUS     current
    DESCRIPTION
            "-- empty --"
    ::= { lcsSetupIpv6Dhcpv6Client 2 }

-- {SCALAR} 1.3.6.1.4.1.2356.11.2.70.3.2.3
lcsSetupIpv6Dhcpv6ClientVendorClassIdentifer OBJECT-TYPE
    SYNTAX     DisplayString (SIZE(0..253))
    MAX-ACCESS read-write
    STATUS     current
    DESCRIPTION
            "-- empty --"
    ::= { lcsSetupIpv6Dhcpv6Client 3 }

-- {SCALAR} 1.3.6.1.4.1.2356.11.2.70.3.2.4
lcsSetupIpv6Dhcpv6ClientVendorClassNumber OBJECT-TYPE
    SYNTAX     Integer32 (0..2147483647)
    MAX-ACCESS read-write
    STATUS     current
    DESCRIPTION
            "-- empty --"
    ::= { lcsSetupIpv6Dhcpv6Client 4 }

-- {NODE} 1.3.6.1.4.1.2356.11.2.70.3.3
lcsSetupIpv6Dhcpv6RelayAgent OBJECT IDENTIFIER ::= { lcsSetupIpv6Dhcpv6 3 }

-- {TABLE} 1.3.6.1.4.1.2356.11.2.70.3.3.1
lcsSetupIpv6Dhcpv6RelayAgentInterfaceListTable OBJECT-TYPE
    SYNTAX     SEQUENCE OF LcsSetupIpv6Dhcpv6RelayAgentInterfaceListEntry
    MAX-ACCESS not-accessible
    STATUS     current
    DESCRIPTION
            "-- empty --"
    ::= { lcsSetupIpv6Dhcpv6RelayAgent 1 }

-- {ROW} 1.3.6.1.4.1.2356.11.2.70.3.3.1.1
lcsSetupIpv6Dhcpv6RelayAgentInterfaceListEntry OBJECT-TYPE
    SYNTAX     LcsSetupIpv6Dhcpv6RelayAgentInterfaceListEntry
    MAX-ACCESS not-accessible
    STATUS     current
    DESCRIPTION
            ""
    INDEX {
            lcsSetupIpv6Dhcpv6RelayAgentInterfaceListEntryInterfaceName
          }
    ::= { lcsSetupIpv6Dhcpv6RelayAgentInterfaceListTable 1 }

LcsSetupIpv6Dhcpv6RelayAgentInterfaceListEntry ::= SEQUENCE {
            lcsSetupIpv6Dhcpv6RelayAgentInterfaceListEntryInterfaceName DisplayString,
            lcsSetupIpv6Dhcpv6RelayAgentInterfaceListEntryOperating INTEGER,
            lcsSetupIpv6Dhcpv6RelayAgentInterfaceListEntryInterfaceAddress DisplayString,
            lcsSetupIpv6Dhcpv6RelayAgentInterfaceListEntryDestAddress DisplayString,
            lcsSetupIpv6Dhcpv6RelayAgentInterfaceListEntryDestInterface DisplayString
    }

-- {COLUMN} 1.3.6.1.4.1.2356.11.2.70.3.3.1.1.1
lcsSetupIpv6Dhcpv6RelayAgentInterfaceListEntryInterfaceName OBJECT-TYPE
    SYNTAX     DisplayString (SIZE(0..16))
    MAX-ACCESS read-write
    STATUS     current
    DESCRIPTION
            "-- empty --"
    ::= { lcsSetupIpv6Dhcpv6RelayAgentInterfaceListEntry 1 }

-- {COLUMN} 1.3.6.1.4.1.2356.11.2.70.3.3.1.1.2
lcsSetupIpv6Dhcpv6RelayAgentInterfaceListEntryOperating OBJECT-TYPE
    SYNTAX     INTEGER {
                  eNo (0),
                  eYes (1)
            }
    MAX-ACCESS read-write
    STATUS     current
    DESCRIPTION
            "-- empty --"
    ::= { lcsSetupIpv6Dhcpv6RelayAgentInterfaceListEntry 2 }

-- {COLUMN} 1.3.6.1.4.1.2356.11.2.70.3.3.1.1.3
lcsSetupIpv6Dhcpv6RelayAgentInterfaceListEntryInterfaceAddress OBJECT-TYPE
    SYNTAX     DisplayString (SIZE(0..39))
    MAX-ACCESS read-write
    STATUS     current
    DESCRIPTION
            "-- empty --"
    ::= { lcsSetupIpv6Dhcpv6RelayAgentInterfaceListEntry 3 }

-- {COLUMN} 1.3.6.1.4.1.2356.11.2.70.3.3.1.1.4
lcsSetupIpv6Dhcpv6RelayAgentInterfaceListEntryDestAddress OBJECT-TYPE
    SYNTAX     DisplayString (SIZE(0..39))
    MAX-ACCESS read-write
    STATUS     current
    DESCRIPTION
            "-- empty --"
    ::= { lcsSetupIpv6Dhcpv6RelayAgentInterfaceListEntry 4 }

-- {COLUMN} 1.3.6.1.4.1.2356.11.2.70.3.3.1.1.5
lcsSetupIpv6Dhcpv6RelayAgentInterfaceListEntryDestInterface OBJECT-TYPE
    SYNTAX     DisplayString (SIZE(0..16))
    MAX-ACCESS read-write
    STATUS     current
    DESCRIPTION
            "-- empty --"
    ::= { lcsSetupIpv6Dhcpv6RelayAgentInterfaceListEntry 5 }

-- {SCALAR} 1.3.6.1.4.1.2356.11.2.70.3.3.2
lcsSetupIpv6Dhcpv6RelayAgentCreateAddressRoutes OBJECT-TYPE
    SYNTAX     INTEGER {
                  eNo (0),
                  eYes (1)
            }
    MAX-ACCESS read-write
    STATUS     current
    DESCRIPTION
            "-- empty --"
    ::= { lcsSetupIpv6Dhcpv6RelayAgent 2 }

-- {NODE} 1.3.6.1.4.1.2356.11.2.70.4
lcsSetupIpv6Network OBJECT IDENTIFIER ::= { lcsSetupIpv6 4 }

-- {TABLE} 1.3.6.1.4.1.2356.11.2.70.4.1
lcsSetupIpv6NetworkAddressesTable OBJECT-TYPE
    SYNTAX     SEQUENCE OF LcsSetupIpv6NetworkAddressesEntry
    MAX-ACCESS not-accessible
    STATUS     current
    DESCRIPTION
            "-- empty --"
    ::= { lcsSetupIpv6Network 1 }

-- {ROW} 1.3.6.1.4.1.2356.11.2.70.4.1.1
lcsSetupIpv6NetworkAddressesEntry OBJECT-TYPE
    SYNTAX     LcsSetupIpv6NetworkAddressesEntry
    MAX-ACCESS not-accessible
    STATUS     current
    DESCRIPTION
            ""
    INDEX {
            lcsSetupIpv6NetworkAddressesEntryInterfaceName,
            lcsSetupIpv6NetworkAddressesEntryIpv6AddressPrefixlength
          }
    ::= { lcsSetupIpv6NetworkAddressesTable 1 }

LcsSetupIpv6NetworkAddressesEntry ::= SEQUENCE {
            lcsSetupIpv6NetworkAddressesEntryInterfaceName DisplayString,
            lcsSetupIpv6NetworkAddressesEntryIpv6AddressPrefixlength DisplayString,
            lcsSetupIpv6NetworkAddressesEntryAddressType INTEGER,
            lcsSetupIpv6NetworkAddressesEntryNetworkGroup DisplayString,
            lcsSetupIpv6NetworkAddressesEntryComment DisplayString
    }

-- {COLUMN} 1.3.6.1.4.1.2356.11.2.70.4.1.1.1
lcsSetupIpv6NetworkAddressesEntryInterfaceName OBJECT-TYPE
    SYNTAX     DisplayString (SIZE(0..16))
    MAX-ACCESS read-write
    STATUS     current
    DESCRIPTION
            "-- empty --"
    ::= { lcsSetupIpv6NetworkAddressesEntry 1 }

-- {COLUMN} 1.3.6.1.4.1.2356.11.2.70.4.1.1.2
lcsSetupIpv6NetworkAddressesEntryIpv6AddressPrefixlength OBJECT-TYPE
    SYNTAX     DisplayString (SIZE(0..43))
    MAX-ACCESS read-write
    STATUS     current
    DESCRIPTION
            "-- empty --"
    ::= { lcsSetupIpv6NetworkAddressesEntry 2 }

-- {COLUMN} 1.3.6.1.4.1.2356.11.2.70.4.1.1.3
lcsSetupIpv6NetworkAddressesEntryAddressType OBJECT-TYPE
    SYNTAX     INTEGER {
                  eUnicast (0),
                  eAnycast (1),
                  eEui64 (2)
            }
    MAX-ACCESS read-write
    STATUS     current
    DESCRIPTION
            "-- empty --"
    ::= { lcsSetupIpv6NetworkAddressesEntry 3 }

-- {COLUMN} 1.3.6.1.4.1.2356.11.2.70.4.1.1.4
lcsSetupIpv6NetworkAddressesEntryNetworkGroup OBJECT-TYPE
    SYNTAX     DisplayString (SIZE(0..16))
    MAX-ACCESS read-write
    STATUS     current
    DESCRIPTION
            "-- empty --"
    ::= { lcsSetupIpv6NetworkAddressesEntry 4 }

-- {COLUMN} 1.3.6.1.4.1.2356.11.2.70.4.1.1.5
lcsSetupIpv6NetworkAddressesEntryComment OBJECT-TYPE
    SYNTAX     DisplayString (SIZE(0..64))
    MAX-ACCESS read-write
    STATUS     current
    DESCRIPTION
            "-- empty --"
    ::= { lcsSetupIpv6NetworkAddressesEntry 5 }

-- {TABLE} 1.3.6.1.4.1.2356.11.2.70.4.2
lcsSetupIpv6NetworkParameterTable OBJECT-TYPE
    SYNTAX     SEQUENCE OF LcsSetupIpv6NetworkParameterEntry
    MAX-ACCESS not-accessible
    STATUS     current
    DESCRIPTION
            "-- empty --"
    ::= { lcsSetupIpv6Network 2 }

-- {ROW} 1.3.6.1.4.1.2356.11.2.70.4.2.1
lcsSetupIpv6NetworkParameterEntry OBJECT-TYPE
    SYNTAX     LcsSetupIpv6NetworkParameterEntry
    MAX-ACCESS not-accessible
    STATUS     current
    DESCRIPTION
            ""
    INDEX {
            lcsSetupIpv6NetworkParameterEntryInterfaceName
          }
    ::= { lcsSetupIpv6NetworkParameterTable 1 }

LcsSetupIpv6NetworkParameterEntry ::= SEQUENCE {
            lcsSetupIpv6NetworkParameterEntryInterfaceName DisplayString,
            lcsSetupIpv6NetworkParameterEntryIpv6Gateway DisplayString,
            lcsSetupIpv6NetworkParameterEntryPrimaryDns DisplayString,
            lcsSetupIpv6NetworkParameterEntrySecondaryDns DisplayString
    }

-- {COLUMN} 1.3.6.1.4.1.2356.11.2.70.4.2.1.1
lcsSetupIpv6NetworkParameterEntryInterfaceName OBJECT-TYPE
    SYNTAX     DisplayString (SIZE(0..16))
    MAX-ACCESS read-write
    STATUS     current
    DESCRIPTION
            "-- empty --"
    ::= { lcsSetupIpv6NetworkParameterEntry 1 }

-- {COLUMN} 1.3.6.1.4.1.2356.11.2.70.4.2.1.2
lcsSetupIpv6NetworkParameterEntryIpv6Gateway OBJECT-TYPE
    SYNTAX     DisplayString (SIZE(0..39))
    MAX-ACCESS read-write
    STATUS     current
    DESCRIPTION
            "-- empty --"
    ::= { lcsSetupIpv6NetworkParameterEntry 2 }

-- {COLUMN} 1.3.6.1.4.1.2356.11.2.70.4.2.1.3
lcsSetupIpv6NetworkParameterEntryPrimaryDns OBJECT-TYPE
    SYNTAX     DisplayString (SIZE(0..39))
    MAX-ACCESS read-write
    STATUS     current
    DESCRIPTION
            "-- empty --"
    ::= { lcsSetupIpv6NetworkParameterEntry 3 }

-- {COLUMN} 1.3.6.1.4.1.2356.11.2.70.4.2.1.4
lcsSetupIpv6NetworkParameterEntrySecondaryDns OBJECT-TYPE
    SYNTAX     DisplayString (SIZE(0..39))
    MAX-ACCESS read-write
    STATUS     current
    DESCRIPTION
            "-- empty --"
    ::= { lcsSetupIpv6NetworkParameterEntry 4 }

-- {TABLE} 1.3.6.1.4.1.2356.11.2.70.4.3
lcsSetupIpv6NetworkLoopbackTable OBJECT-TYPE
    SYNTAX     SEQUENCE OF LcsSetupIpv6NetworkLoopbackEntry
    MAX-ACCESS not-accessible
    STATUS     current
    DESCRIPTION
            "-- empty --"
    ::= { lcsSetupIpv6Network 3 }

-- {ROW} 1.3.6.1.4.1.2356.11.2.70.4.3.1
lcsSetupIpv6NetworkLoopbackEntry OBJECT-TYPE
    SYNTAX     LcsSetupIpv6NetworkLoopbackEntry
    MAX-ACCESS not-accessible
    STATUS     current
    DESCRIPTION
            ""
    INDEX {
            lcsSetupIpv6NetworkLoopbackEntryName
          }
    ::= { lcsSetupIpv6NetworkLoopbackTable 1 }

LcsSetupIpv6NetworkLoopbackEntry ::= SEQUENCE {
            lcsSetupIpv6NetworkLoopbackEntryName DisplayString,
            lcsSetupIpv6NetworkLoopbackEntryIpv6LoopbackAddr DisplayString,
            lcsSetupIpv6NetworkLoopbackEntryRtgTag Integer32,
            lcsSetupIpv6NetworkLoopbackEntryComment DisplayString
    }

-- {COLUMN} 1.3.6.1.4.1.2356.11.2.70.4.3.1.1
lcsSetupIpv6NetworkLoopbackEntryName OBJECT-TYPE
    SYNTAX     DisplayString (SIZE(0..16))
    MAX-ACCESS read-write
    STATUS     current
    DESCRIPTION
            "-- empty --"
    ::= { lcsSetupIpv6NetworkLoopbackEntry 1 }

-- {COLUMN} 1.3.6.1.4.1.2356.11.2.70.4.3.1.2
lcsSetupIpv6NetworkLoopbackEntryIpv6LoopbackAddr OBJECT-TYPE
    SYNTAX     DisplayString (SIZE(0..39))
    MAX-ACCESS read-write
    STATUS     current
    DESCRIPTION
            "-- empty --"
    ::= { lcsSetupIpv6NetworkLoopbackEntry 2 }

-- {COLUMN} 1.3.6.1.4.1.2356.11.2.70.4.3.1.3
lcsSetupIpv6NetworkLoopbackEntryRtgTag OBJECT-TYPE
    SYNTAX     Integer32 (0..65535)
    MAX-ACCESS read-write
    STATUS     current
    DESCRIPTION
            "-- empty --"
    ::= { lcsSetupIpv6NetworkLoopbackEntry 3 }

-- {COLUMN} 1.3.6.1.4.1.2356.11.2.70.4.3.1.4
lcsSetupIpv6NetworkLoopbackEntryComment OBJECT-TYPE
    SYNTAX     DisplayString (SIZE(0..64))
    MAX-ACCESS read-write
    STATUS     current
    DESCRIPTION
            "-- empty --"
    ::= { lcsSetupIpv6NetworkLoopbackEntry 4 }

-- {NODE} 1.3.6.1.4.1.2356.11.2.70.5
lcsSetupIpv6Firewall OBJECT IDENTIFIER ::= { lcsSetupIpv6 5 }

-- {SCALAR} 1.3.6.1.4.1.2356.11.2.70.5.1
lcsSetupIpv6FirewallOperating OBJECT-TYPE
    SYNTAX     INTEGER {
                  eNo (0),
                  eYes (1)
            }
    MAX-ACCESS read-write
    STATUS     current
    DESCRIPTION
            "-- empty --"
    ::= { lcsSetupIpv6Firewall 1 }

-- {TABLE} 1.3.6.1.4.1.2356.11.2.70.5.2
lcsSetupIpv6FirewallForwardingRulesTable OBJECT-TYPE
    SYNTAX     SEQUENCE OF LcsSetupIpv6FirewallForwardingRulesEntry
    MAX-ACCESS not-accessible
    STATUS     current
    DESCRIPTION
            "-- empty --"
    ::= { lcsSetupIpv6Firewall 2 }

-- {ROW} 1.3.6.1.4.1.2356.11.2.70.5.2.1
lcsSetupIpv6FirewallForwardingRulesEntry OBJECT-TYPE
    SYNTAX     LcsSetupIpv6FirewallForwardingRulesEntry
    MAX-ACCESS not-accessible
    STATUS     current
    DESCRIPTION
            ""
    INDEX {
            lcsSetupIpv6FirewallForwardingRulesEntryName
          }
    ::= { lcsSetupIpv6FirewallForwardingRulesTable 1 }

LcsSetupIpv6FirewallForwardingRulesEntry ::= SEQUENCE {
            lcsSetupIpv6FirewallForwardingRulesEntryName DisplayString,
            lcsSetupIpv6FirewallForwardingRulesEntryFlags BITS,
            lcsSetupIpv6FirewallForwardingRulesEntryPrio Integer32,
            lcsSetupIpv6FirewallForwardingRulesEntryRtgTag Integer32,
            lcsSetupIpv6FirewallForwardingRulesEntryAction DisplayString,
            lcsSetupIpv6FirewallForwardingRulesEntryServices DisplayString,
            lcsSetupIpv6FirewallForwardingRulesEntrySourceStations DisplayString,
            lcsSetupIpv6FirewallForwardingRulesEntryDestinationStations DisplayString,
            lcsSetupIpv6FirewallForwardingRulesEntryComment DisplayString,
            lcsSetupIpv6FirewallForwardingRulesEntrySrcTag Integer32
    }

-- {COLUMN} 1.3.6.1.4.1.2356.11.2.70.5.2.1.1
lcsSetupIpv6FirewallForwardingRulesEntryName OBJECT-TYPE
    SYNTAX     DisplayString (SIZE(0..36))
    MAX-ACCESS read-write
    STATUS     current
    DESCRIPTION
            "-- empty --"
    ::= { lcsSetupIpv6FirewallForwardingRulesEntry 1 }

-- {COLUMN} 1.3.6.1.4.1.2356.11.2.70.5.2.1.2
lcsSetupIpv6FirewallForwardingRulesEntryFlags OBJECT-TYPE
    SYNTAX     BITS {
                  eNone (0),
                  eStateless (4),
                  eLinked (5),
                  eDeactivated (7)
            }
    MAX-ACCESS read-write
    STATUS     current
    DESCRIPTION
            "-- empty --"
    ::= { lcsSetupIpv6FirewallForwardingRulesEntry 2 }

-- {COLUMN} 1.3.6.1.4.1.2356.11.2.70.5.2.1.3
lcsSetupIpv6FirewallForwardingRulesEntryPrio OBJECT-TYPE
    SYNTAX     Integer32 (0..65535)
    MAX-ACCESS read-write
    STATUS     current
    DESCRIPTION
            "-- empty --"
    ::= { lcsSetupIpv6FirewallForwardingRulesEntry 3 }

-- {COLUMN} 1.3.6.1.4.1.2356.11.2.70.5.2.1.4
lcsSetupIpv6FirewallForwardingRulesEntryRtgTag OBJECT-TYPE
    SYNTAX     Integer32 (0..65535)
    MAX-ACCESS read-write
    STATUS     current
    DESCRIPTION
            "-- empty --"
    ::= { lcsSetupIpv6FirewallForwardingRulesEntry 4 }

-- {COLUMN} 1.3.6.1.4.1.2356.11.2.70.5.2.1.5
lcsSetupIpv6FirewallForwardingRulesEntryAction OBJECT-TYPE
    SYNTAX     DisplayString (SIZE(0..64))
    MAX-ACCESS read-write
    STATUS     current
    DESCRIPTION
            "-- empty --"
    ::= { lcsSetupIpv6FirewallForwardingRulesEntry 5 }

-- {COLUMN} 1.3.6.1.4.1.2356.11.2.70.5.2.1.7
lcsSetupIpv6FirewallForwardingRulesEntryServices OBJECT-TYPE
    SYNTAX     DisplayString (SIZE(0..64))
    MAX-ACCESS read-write
    STATUS     current
    DESCRIPTION
            "-- empty --"
    ::= { lcsSetupIpv6FirewallForwardingRulesEntry 7 }

-- {COLUMN} 1.3.6.1.4.1.2356.11.2.70.5.2.1.8
lcsSetupIpv6FirewallForwardingRulesEntrySourceStations OBJECT-TYPE
    SYNTAX     DisplayString (SIZE(0..64))
    MAX-ACCESS read-write
    STATUS     current
    DESCRIPTION
            "-- empty --"
    ::= { lcsSetupIpv6FirewallForwardingRulesEntry 8 }

-- {COLUMN} 1.3.6.1.4.1.2356.11.2.70.5.2.1.9
lcsSetupIpv6FirewallForwardingRulesEntryDestinationStations OBJECT-TYPE
    SYNTAX     DisplayString (SIZE(0..64))
    MAX-ACCESS read-write
    STATUS     current
    DESCRIPTION
            "-- empty --"
    ::= { lcsSetupIpv6FirewallForwardingRulesEntry 9 }

-- {COLUMN} 1.3.6.1.4.1.2356.11.2.70.5.2.1.10
lcsSetupIpv6FirewallForwardingRulesEntryComment OBJECT-TYPE
    SYNTAX     DisplayString (SIZE(0..64))
    MAX-ACCESS read-write
    STATUS     current
    DESCRIPTION
            "-- empty --"
    ::= { lcsSetupIpv6FirewallForwardingRulesEntry 10 }

-- {COLUMN} 1.3.6.1.4.1.2356.11.2.70.5.2.1.11
lcsSetupIpv6FirewallForwardingRulesEntrySrcTag OBJECT-TYPE
    SYNTAX     Integer32 (0..65535)
    MAX-ACCESS read-write
    STATUS     current
    DESCRIPTION
            "-- empty --"
    ::= { lcsSetupIpv6FirewallForwardingRulesEntry 11 }

-- {TABLE} 1.3.6.1.4.1.2356.11.2.70.5.3
lcsSetupIpv6FirewallActionListTable OBJECT-TYPE
    SYNTAX     SEQUENCE OF LcsSetupIpv6FirewallActionListEntry
    MAX-ACCESS not-accessible
    STATUS     current
    DESCRIPTION
            "-- empty --"
    ::= { lcsSetupIpv6Firewall 3 }

-- {ROW} 1.3.6.1.4.1.2356.11.2.70.5.3.1
lcsSetupIpv6FirewallActionListEntry OBJECT-TYPE
    SYNTAX     LcsSetupIpv6FirewallActionListEntry
    MAX-ACCESS not-accessible
    STATUS     current
    DESCRIPTION
            ""
    INDEX {
            lcsSetupIpv6FirewallActionListEntryName
          }
    ::= { lcsSetupIpv6FirewallActionListTable 1 }

LcsSetupIpv6FirewallActionListEntry ::= SEQUENCE {
            lcsSetupIpv6FirewallActionListEntryName DisplayString,
            lcsSetupIpv6FirewallActionListEntryDescription DisplayString
    }

-- {COLUMN} 1.3.6.1.4.1.2356.11.2.70.5.3.1.1
lcsSetupIpv6FirewallActionListEntryName OBJECT-TYPE
    SYNTAX     DisplayString (SIZE(0..36))
    MAX-ACCESS read-write
    STATUS     current
    DESCRIPTION
            "-- empty --"
    ::= { lcsSetupIpv6FirewallActionListEntry 1 }

-- {COLUMN} 1.3.6.1.4.1.2356.11.2.70.5.3.1.2
lcsSetupIpv6FirewallActionListEntryDescription OBJECT-TYPE
    SYNTAX     DisplayString (SIZE(0..252))
    MAX-ACCESS read-write
    STATUS     current
    DESCRIPTION
            "-- empty --"
    ::= { lcsSetupIpv6FirewallActionListEntry 2 }

-- {TABLE} 1.3.6.1.4.1.2356.11.2.70.5.5
lcsSetupIpv6FirewallStationListTable OBJECT-TYPE
    SYNTAX     SEQUENCE OF LcsSetupIpv6FirewallStationListEntry
    MAX-ACCESS not-accessible
    STATUS     current
    DESCRIPTION
            "-- empty --"
    ::= { lcsSetupIpv6Firewall 5 }

-- {ROW} 1.3.6.1.4.1.2356.11.2.70.5.5.1
lcsSetupIpv6FirewallStationListEntry OBJECT-TYPE
    SYNTAX     LcsSetupIpv6FirewallStationListEntry
    MAX-ACCESS not-accessible
    STATUS     current
    DESCRIPTION
            ""
    INDEX {
            lcsSetupIpv6FirewallStationListEntryName
          }
    ::= { lcsSetupIpv6FirewallStationListTable 1 }

LcsSetupIpv6FirewallStationListEntry ::= SEQUENCE {
            lcsSetupIpv6FirewallStationListEntryName DisplayString,
            lcsSetupIpv6FirewallStationListEntryDescription DisplayString
    }

-- {COLUMN} 1.3.6.1.4.1.2356.11.2.70.5.5.1.1
lcsSetupIpv6FirewallStationListEntryName OBJECT-TYPE
    SYNTAX     DisplayString (SIZE(0..36))
    MAX-ACCESS read-write
    STATUS     current
    DESCRIPTION
            "-- empty --"
    ::= { lcsSetupIpv6FirewallStationListEntry 1 }

-- {COLUMN} 1.3.6.1.4.1.2356.11.2.70.5.5.1.2
lcsSetupIpv6FirewallStationListEntryDescription OBJECT-TYPE
    SYNTAX     DisplayString (SIZE(0..252))
    MAX-ACCESS read-write
    STATUS     current
    DESCRIPTION
            "-- empty --"
    ::= { lcsSetupIpv6FirewallStationListEntry 2 }

-- {TABLE} 1.3.6.1.4.1.2356.11.2.70.5.6
lcsSetupIpv6FirewallServiceListTable OBJECT-TYPE
    SYNTAX     SEQUENCE OF LcsSetupIpv6FirewallServiceListEntry
    MAX-ACCESS not-accessible
    STATUS     current
    DESCRIPTION
            "-- empty --"
    ::= { lcsSetupIpv6Firewall 6 }

-- {ROW} 1.3.6.1.4.1.2356.11.2.70.5.6.1
lcsSetupIpv6FirewallServiceListEntry OBJECT-TYPE
    SYNTAX     LcsSetupIpv6FirewallServiceListEntry
    MAX-ACCESS not-accessible
    STATUS     current
    DESCRIPTION
            ""
    INDEX {
            lcsSetupIpv6FirewallServiceListEntryName
          }
    ::= { lcsSetupIpv6FirewallServiceListTable 1 }

LcsSetupIpv6FirewallServiceListEntry ::= SEQUENCE {
            lcsSetupIpv6FirewallServiceListEntryName DisplayString,
            lcsSetupIpv6FirewallServiceListEntryDescription DisplayString
    }

-- {COLUMN} 1.3.6.1.4.1.2356.11.2.70.5.6.1.1
lcsSetupIpv6FirewallServiceListEntryName OBJECT-TYPE
    SYNTAX     DisplayString (SIZE(0..36))
    MAX-ACCESS read-write
    STATUS     current
    DESCRIPTION
            "-- empty --"
    ::= { lcsSetupIpv6FirewallServiceListEntry 1 }

-- {COLUMN} 1.3.6.1.4.1.2356.11.2.70.5.6.1.2
lcsSetupIpv6FirewallServiceListEntryDescription OBJECT-TYPE
    SYNTAX     DisplayString (SIZE(0..252))
    MAX-ACCESS read-write
    STATUS     current
    DESCRIPTION
            "-- empty --"
    ::= { lcsSetupIpv6FirewallServiceListEntry 2 }

-- {TABLE} 1.3.6.1.4.1.2356.11.2.70.5.7
lcsSetupIpv6FirewallActionsTable OBJECT-TYPE
    SYNTAX     SEQUENCE OF LcsSetupIpv6FirewallActionsEntry
    MAX-ACCESS not-accessible
    STATUS     current
    DESCRIPTION
            "-- empty --"
    ::= { lcsSetupIpv6Firewall 7 }

-- {ROW} 1.3.6.1.4.1.2356.11.2.70.5.7.1
lcsSetupIpv6FirewallActionsEntry OBJECT-TYPE
    SYNTAX     LcsSetupIpv6FirewallActionsEntry
    MAX-ACCESS not-accessible
    STATUS     current
    DESCRIPTION
            ""
    INDEX {
            lcsSetupIpv6FirewallActionsEntryName
          }
    ::= { lcsSetupIpv6FirewallActionsTable 1 }

LcsSetupIpv6FirewallActionsEntry ::= SEQUENCE {
            lcsSetupIpv6FirewallActionsEntryName DisplayString,
            lcsSetupIpv6FirewallActionsEntryLimit Integer32,
            lcsSetupIpv6FirewallActionsEntryUnit INTEGER,
            lcsSetupIpv6FirewallActionsEntryTime INTEGER,
            lcsSetupIpv6FirewallActionsEntryContext INTEGER,
            lcsSetupIpv6FirewallActionsEntryFlags BITS,
            lcsSetupIpv6FirewallActionsEntryAction INTEGER,
            lcsSetupIpv6FirewallActionsEntryContentFilter DisplayString,
            lcsSetupIpv6FirewallActionsEntryDiffserv INTEGER,
            lcsSetupIpv6FirewallActionsEntryDscpValue Integer32,
            lcsSetupIpv6FirewallActionsEntryConditions DisplayString,
            lcsSetupIpv6FirewallActionsEntryTriggerActions DisplayString
    }

-- {COLUMN} 1.3.6.1.4.1.2356.11.2.70.5.7.1.1
lcsSetupIpv6FirewallActionsEntryName OBJECT-TYPE
    SYNTAX     DisplayString (SIZE(0..32))
    MAX-ACCESS read-write
    STATUS     current
    DESCRIPTION
            "-- empty --"
    ::= { lcsSetupIpv6FirewallActionsEntry 1 }

-- {COLUMN} 1.3.6.1.4.1.2356.11.2.70.5.7.1.2
lcsSetupIpv6FirewallActionsEntryLimit OBJECT-TYPE
    SYNTAX     Integer32 (0..2147483647)
    MAX-ACCESS read-write
    STATUS     current
    DESCRIPTION
            "-- empty --"
    ::= { lcsSetupIpv6FirewallActionsEntry 2 }

-- {COLUMN} 1.3.6.1.4.1.2356.11.2.70.5.7.1.3
lcsSetupIpv6FirewallActionsEntryUnit OBJECT-TYPE
    SYNTAX     INTEGER {
                  eKbit (0),
                  eKbytes (1),
                  ePackets (2),
                  eSessions (3),
                  eBandwidth (4)
            }
    MAX-ACCESS read-write
    STATUS     current
    DESCRIPTION
            "-- empty --"
    ::= { lcsSetupIpv6FirewallActionsEntry 3 }

-- {COLUMN} 1.3.6.1.4.1.2356.11.2.70.5.7.1.4
lcsSetupIpv6FirewallActionsEntryTime OBJECT-TYPE
    SYNTAX     INTEGER {
                  eSecond (0),
                  eMinute (1),
                  eHour (2),
                  eAbsolute (3)
            }
    MAX-ACCESS read-write
    STATUS     current
    DESCRIPTION
            "-- empty --"
    ::= { lcsSetupIpv6FirewallActionsEntry 4 }

-- {COLUMN} 1.3.6.1.4.1.2356.11.2.70.5.7.1.5
lcsSetupIpv6FirewallActionsEntryContext OBJECT-TYPE
    SYNTAX     INTEGER {
                  eSession (0),
                  eStation (1),
                  eGlobal (2)
            }
    MAX-ACCESS read-write
    STATUS     current
    DESCRIPTION
            "-- empty --"
    ::= { lcsSetupIpv6FirewallActionsEntry 5 }

-- {COLUMN} 1.3.6.1.4.1.2356.11.2.70.5.7.1.6
lcsSetupIpv6FirewallActionsEntryFlags OBJECT-TYPE
    SYNTAX     BITS {
                  eNone (0),
                  eShared (6),
                  eReset (7)
            }
    MAX-ACCESS read-write
    STATUS     current
    DESCRIPTION
            "-- empty --"
    ::= { lcsSetupIpv6FirewallActionsEntry 6 }

-- {COLUMN} 1.3.6.1.4.1.2356.11.2.70.5.7.1.7
lcsSetupIpv6FirewallActionsEntryAction OBJECT-TYPE
    SYNTAX     INTEGER {
                  eReject (0),
                  eDrop (1),
                  eAccept (2),
                  eCheck (4)
            }
    MAX-ACCESS read-write
    STATUS     current
    DESCRIPTION
            "-- empty --"
    ::= { lcsSetupIpv6FirewallActionsEntry 7 }

-- {COLUMN} 1.3.6.1.4.1.2356.11.2.70.5.7.1.10
lcsSetupIpv6FirewallActionsEntryContentFilter OBJECT-TYPE
    SYNTAX     DisplayString (SIZE(0..31))
    MAX-ACCESS read-write
    STATUS     current
    DESCRIPTION
            "-- empty --"
    ::= { lcsSetupIpv6FirewallActionsEntry 10 }

-- {COLUMN} 1.3.6.1.4.1.2356.11.2.70.5.7.1.11
lcsSetupIpv6FirewallActionsEntryDiffserv OBJECT-TYPE
    SYNTAX     INTEGER {
                  eBe (0),
                  eCs1 (32),
                  eAf11 (40),
                  eAf12 (48),
                  eAf13 (56),
                  eCs2 (64),
                  eAf21 (72),
                  eAf22 (80),
                  eAf23 (88),
                  eCs3 (96),
                  eAf31 (104),
                  eAf32 (112),
                  eAf33 (120),
                  eCs4 (128),
                  eAf41 (136),
                  eAf42 (144),
                  eAf43 (152),
                  eCs5 (160),
                  eEf (184),
                  eCs6 (192),
                  eCs7 (224),
                  eCs0 (249),
                  eNo (254),
                  eValue (255)
            }
    MAX-ACCESS read-write
    STATUS     current
    DESCRIPTION
            "-- empty --"
    ::= { lcsSetupIpv6FirewallActionsEntry 11 }

-- {COLUMN} 1.3.6.1.4.1.2356.11.2.70.5.7.1.12
lcsSetupIpv6FirewallActionsEntryDscpValue OBJECT-TYPE
    SYNTAX     Integer32 (0..255)
    MAX-ACCESS read-write
    STATUS     current
    DESCRIPTION
            "-- empty --"
    ::= { lcsSetupIpv6FirewallActionsEntry 12 }

-- {COLUMN} 1.3.6.1.4.1.2356.11.2.70.5.7.1.13
lcsSetupIpv6FirewallActionsEntryConditions OBJECT-TYPE
    SYNTAX     DisplayString (SIZE(0..32))
    MAX-ACCESS read-write
    STATUS     current
    DESCRIPTION
            "-- empty --"
    ::= { lcsSetupIpv6FirewallActionsEntry 13 }

-- {COLUMN} 1.3.6.1.4.1.2356.11.2.70.5.7.1.14
lcsSetupIpv6FirewallActionsEntryTriggerActions OBJECT-TYPE
    SYNTAX     DisplayString (SIZE(0..32))
    MAX-ACCESS read-write
    STATUS     current
    DESCRIPTION
            "-- empty --"
    ::= { lcsSetupIpv6FirewallActionsEntry 14 }

-- {TABLE} 1.3.6.1.4.1.2356.11.2.70.5.9
lcsSetupIpv6FirewallStationsTable OBJECT-TYPE
    SYNTAX     SEQUENCE OF LcsSetupIpv6FirewallStationsEntry
    MAX-ACCESS not-accessible
    STATUS     current
    DESCRIPTION
            "-- empty --"
    ::= { lcsSetupIpv6Firewall 9 }

-- {ROW} 1.3.6.1.4.1.2356.11.2.70.5.9.1
lcsSetupIpv6FirewallStationsEntry OBJECT-TYPE
    SYNTAX     LcsSetupIpv6FirewallStationsEntry
    MAX-ACCESS not-accessible
    STATUS     current
    DESCRIPTION
            ""
    INDEX {
            lcsSetupIpv6FirewallStationsEntryName
          }
    ::= { lcsSetupIpv6FirewallStationsTable 1 }

LcsSetupIpv6FirewallStationsEntry ::= SEQUENCE {
            lcsSetupIpv6FirewallStationsEntryName DisplayString,
            lcsSetupIpv6FirewallStationsEntryType INTEGER,
            lcsSetupIpv6FirewallStationsEntryLocalNetwork DisplayString,
            lcsSetupIpv6FirewallStationsEntryRemotePeerLocalHost DisplayString,
            lcsSetupIpv6FirewallStationsEntryAddressPrefix DisplayString
    }

-- {COLUMN} 1.3.6.1.4.1.2356.11.2.70.5.9.1.1
lcsSetupIpv6FirewallStationsEntryName OBJECT-TYPE
    SYNTAX     DisplayString (SIZE(0..32))
    MAX-ACCESS read-write
    STATUS     current
    DESCRIPTION
            "-- empty --"
    ::= { lcsSetupIpv6FirewallStationsEntry 1 }

-- {COLUMN} 1.3.6.1.4.1.2356.11.2.70.5.9.1.2
lcsSetupIpv6FirewallStationsEntryType OBJECT-TYPE
    SYNTAX     INTEGER {
                  eLocalNetwork (0),
                  eRemotePeer (1),
                  ePrefix (2),
                  eIdentifier (3),
                  eIpAddress (4),
                  eNamedHost (5)
            }
    MAX-ACCESS read-write
    STATUS     current
    DESCRIPTION
            "-- empty --"
    ::= { lcsSetupIpv6FirewallStationsEntry 2 }

-- {COLUMN} 1.3.6.1.4.1.2356.11.2.70.5.9.1.3
lcsSetupIpv6FirewallStationsEntryLocalNetwork OBJECT-TYPE
    SYNTAX     DisplayString (SIZE(0..16))
    MAX-ACCESS read-write
    STATUS     current
    DESCRIPTION
            "-- empty --"
    ::= { lcsSetupIpv6FirewallStationsEntry 3 }

-- {COLUMN} 1.3.6.1.4.1.2356.11.2.70.5.9.1.6
lcsSetupIpv6FirewallStationsEntryRemotePeerLocalHost OBJECT-TYPE
    SYNTAX     DisplayString (SIZE(0..64))
    MAX-ACCESS read-write
    STATUS     current
    DESCRIPTION
            "-- empty --"
    ::= { lcsSetupIpv6FirewallStationsEntry 6 }

-- {COLUMN} 1.3.6.1.4.1.2356.11.2.70.5.9.1.7
lcsSetupIpv6FirewallStationsEntryAddressPrefix OBJECT-TYPE
    SYNTAX     DisplayString (SIZE(0..43))
    MAX-ACCESS read-write
    STATUS     current
    DESCRIPTION
            "-- empty --"
    ::= { lcsSetupIpv6FirewallStationsEntry 7 }

-- {TABLE} 1.3.6.1.4.1.2356.11.2.70.5.10
lcsSetupIpv6FirewallServicesTable OBJECT-TYPE
    SYNTAX     SEQUENCE OF LcsSetupIpv6FirewallServicesEntry
    MAX-ACCESS not-accessible
    STATUS     current
    DESCRIPTION
            "-- empty --"
    ::= { lcsSetupIpv6Firewall 10 }

-- {ROW} 1.3.6.1.4.1.2356.11.2.70.5.10.1
lcsSetupIpv6FirewallServicesEntry OBJECT-TYPE
    SYNTAX     LcsSetupIpv6FirewallServicesEntry
    MAX-ACCESS not-accessible
    STATUS     current
    DESCRIPTION
            ""
    INDEX {
            lcsSetupIpv6FirewallServicesEntryName
          }
    ::= { lcsSetupIpv6FirewallServicesTable 1 }

LcsSetupIpv6FirewallServicesEntry ::= SEQUENCE {
            lcsSetupIpv6FirewallServicesEntryName DisplayString,
            lcsSetupIpv6FirewallServicesEntryProtocol INTEGER,
            lcsSetupIpv6FirewallServicesEntryPorts DisplayString,
            lcsSetupIpv6FirewallServicesEntrySrcPorts INTEGER
    }

-- {COLUMN} 1.3.6.1.4.1.2356.11.2.70.5.10.1.1
lcsSetupIpv6FirewallServicesEntryName OBJECT-TYPE
    SYNTAX     DisplayString (SIZE(0..32))
    MAX-ACCESS read-write
    STATUS     current
    DESCRIPTION
            "-- empty --"
    ::= { lcsSetupIpv6FirewallServicesEntry 1 }

-- {COLUMN} 1.3.6.1.4.1.2356.11.2.70.5.10.1.2
lcsSetupIpv6FirewallServicesEntryProtocol OBJECT-TYPE
    SYNTAX     INTEGER {
                  eTcp (2),
                  eUdp (4),
                  eTcpPlusUdp (6)
            }
    MAX-ACCESS read-write
    STATUS     current
    DESCRIPTION
            "-- empty --"
    ::= { lcsSetupIpv6FirewallServicesEntry 2 }

-- {COLUMN} 1.3.6.1.4.1.2356.11.2.70.5.10.1.3
lcsSetupIpv6FirewallServicesEntryPorts OBJECT-TYPE
    SYNTAX     DisplayString (SIZE(0..64))
    MAX-ACCESS read-write
    STATUS     current
    DESCRIPTION
            "-- empty --"
    ::= { lcsSetupIpv6FirewallServicesEntry 3 }

-- {COLUMN} 1.3.6.1.4.1.2356.11.2.70.5.10.1.4
lcsSetupIpv6FirewallServicesEntrySrcPorts OBJECT-TYPE
    SYNTAX     INTEGER {
                  eNo (0),
                  eYes (1)
            }
    MAX-ACCESS read-write
    STATUS     current
    DESCRIPTION
            "-- empty --"
    ::= { lcsSetupIpv6FirewallServicesEntry 4 }

-- {TABLE} 1.3.6.1.4.1.2356.11.2.70.5.11
lcsSetupIpv6FirewallProtocolsTable OBJECT-TYPE
    SYNTAX     SEQUENCE OF LcsSetupIpv6FirewallProtocolsEntry
    MAX-ACCESS not-accessible
    STATUS     current
    DESCRIPTION
            "-- empty --"
    ::= { lcsSetupIpv6Firewall 11 }

-- {ROW} 1.3.6.1.4.1.2356.11.2.70.5.11.1
lcsSetupIpv6FirewallProtocolsEntry OBJECT-TYPE
    SYNTAX     LcsSetupIpv6FirewallProtocolsEntry
    MAX-ACCESS not-accessible
    STATUS     current
    DESCRIPTION
            ""
    INDEX {
            lcsSetupIpv6FirewallProtocolsEntryName
          }
    ::= { lcsSetupIpv6FirewallProtocolsTable 1 }

LcsSetupIpv6FirewallProtocolsEntry ::= SEQUENCE {
            lcsSetupIpv6FirewallProtocolsEntryName DisplayString,
            lcsSetupIpv6FirewallProtocolsEntryProtocol Integer32
    }

-- {COLUMN} 1.3.6.1.4.1.2356.11.2.70.5.11.1.1
lcsSetupIpv6FirewallProtocolsEntryName OBJECT-TYPE
    SYNTAX     DisplayString (SIZE(0..32))
    MAX-ACCESS read-write
    STATUS     current
    DESCRIPTION
            "-- empty --"
    ::= { lcsSetupIpv6FirewallProtocolsEntry 1 }

-- {COLUMN} 1.3.6.1.4.1.2356.11.2.70.5.11.1.2
lcsSetupIpv6FirewallProtocolsEntryProtocol OBJECT-TYPE
    SYNTAX     Integer32 (0..2147483647)
    MAX-ACCESS read-write
    STATUS     current
    DESCRIPTION
            "-- empty --"
    ::= { lcsSetupIpv6FirewallProtocolsEntry 2 }

-- {TABLE} 1.3.6.1.4.1.2356.11.2.70.5.12
lcsSetupIpv6FirewallConditionsTable OBJECT-TYPE
    SYNTAX     SEQUENCE OF LcsSetupIpv6FirewallConditionsEntry
    MAX-ACCESS not-accessible
    STATUS     current
    DESCRIPTION
            "-- empty --"
    ::= { lcsSetupIpv6Firewall 12 }

-- {ROW} 1.3.6.1.4.1.2356.11.2.70.5.12.1
lcsSetupIpv6FirewallConditionsEntry OBJECT-TYPE
    SYNTAX     LcsSetupIpv6FirewallConditionsEntry
    MAX-ACCESS not-accessible
    STATUS     current
    DESCRIPTION
            ""
    INDEX {
            lcsSetupIpv6FirewallConditionsEntryName
          }
    ::= { lcsSetupIpv6FirewallConditionsTable 1 }

LcsSetupIpv6FirewallConditionsEntry ::= SEQUENCE {
            lcsSetupIpv6FirewallConditionsEntryName DisplayString,
            lcsSetupIpv6FirewallConditionsEntryConditions BITS,
            lcsSetupIpv6FirewallConditionsEntryTransportDirection INTEGER,
            lcsSetupIpv6FirewallConditionsEntryDiffserv INTEGER,
            lcsSetupIpv6FirewallConditionsEntryDscpValue Integer32
    }

-- {COLUMN} 1.3.6.1.4.1.2356.11.2.70.5.12.1.1
lcsSetupIpv6FirewallConditionsEntryName OBJECT-TYPE
    SYNTAX     DisplayString (SIZE(0..32))
    MAX-ACCESS read-write
    STATUS     current
    DESCRIPTION
            "-- empty --"
    ::= { lcsSetupIpv6FirewallConditionsEntry 1 }

-- {COLUMN} 1.3.6.1.4.1.2356.11.2.70.5.12.1.2
lcsSetupIpv6FirewallConditionsEntryConditions OBJECT-TYPE
    SYNTAX     BITS {
                  eNone (0),
                  eReceived (2),
                  eSent (3),
                  eVpnRoute (4),
                  eBackupConnection (5),
                  eDefaultRoute (6),
                  eNotConnected (7)
            }
    MAX-ACCESS read-write
    STATUS     current
    DESCRIPTION
            "-- empty --"
    ::= { lcsSetupIpv6FirewallConditionsEntry 2 }

-- {COLUMN} 1.3.6.1.4.1.2356.11.2.70.5.12.1.3
lcsSetupIpv6FirewallConditionsEntryTransportDirection OBJECT-TYPE
    SYNTAX     INTEGER {
                  ePhysical (0),
                  eLogical (1)
            }
    MAX-ACCESS read-write
    STATUS     current
    DESCRIPTION
            "-- empty --"
    ::= { lcsSetupIpv6FirewallConditionsEntry 3 }

-- {COLUMN} 1.3.6.1.4.1.2356.11.2.70.5.12.1.4
lcsSetupIpv6FirewallConditionsEntryDiffserv OBJECT-TYPE
    SYNTAX     INTEGER {
                  eBe (0),
                  eCs1 (32),
                  eAf11 (40),
                  eAf12 (48),
                  eAf13 (56),
                  eCs2 (64),
                  eAf21 (72),
                  eAf22 (80),
                  eAf23 (88),
                  eCs3 (96),
                  eAf31 (104),
                  eAf32 (112),
                  eAf33 (120),
                  eCs4 (128),
                  eAf41 (136),
                  eAf42 (144),
                  eAf43 (152),
                  eCs5 (160),
                  eEf (184),
                  eCs6 (192),
                  eCs7 (224),
                  eCsx (240),
                  eAf1x (241),
                  eAf2x (242),
                  eAf3x (243),
                  eAf4x (244),
                  eAfx1 (245),
                  eAfx2 (246),
                  eAfx3 (247),
                  eAfxx (248),
                  eCs0 (249),
                  eIgnore (254),
                  eValue (255)
            }
    MAX-ACCESS read-write
    STATUS     current
    DESCRIPTION
            "-- empty --"
    ::= { lcsSetupIpv6FirewallConditionsEntry 4 }

-- {COLUMN} 1.3.6.1.4.1.2356.11.2.70.5.12.1.5
lcsSetupIpv6FirewallConditionsEntryDscpValue OBJECT-TYPE
    SYNTAX     Integer32 (0..255)
    MAX-ACCESS read-write
    STATUS     current
    DESCRIPTION
            "-- empty --"
    ::= { lcsSetupIpv6FirewallConditionsEntry 5 }

-- {TABLE} 1.3.6.1.4.1.2356.11.2.70.5.13
lcsSetupIpv6FirewallTriggerActionsTable OBJECT-TYPE
    SYNTAX     SEQUENCE OF LcsSetupIpv6FirewallTriggerActionsEntry
    MAX-ACCESS not-accessible
    STATUS     current
    DESCRIPTION
            "-- empty --"
    ::= { lcsSetupIpv6Firewall 13 }

-- {ROW} 1.3.6.1.4.1.2356.11.2.70.5.13.1
lcsSetupIpv6FirewallTriggerActionsEntry OBJECT-TYPE
    SYNTAX     LcsSetupIpv6FirewallTriggerActionsEntry
    MAX-ACCESS not-accessible
    STATUS     current
    DESCRIPTION
            ""
    INDEX {
            lcsSetupIpv6FirewallTriggerActionsEntryName
          }
    ::= { lcsSetupIpv6FirewallTriggerActionsTable 1 }

LcsSetupIpv6FirewallTriggerActionsEntry ::= SEQUENCE {
            lcsSetupIpv6FirewallTriggerActionsEntryName DisplayString,
            lcsSetupIpv6FirewallTriggerActionsEntryNotifications BITS,
            lcsSetupIpv6FirewallTriggerActionsEntryDisconnect INTEGER,
            lcsSetupIpv6FirewallTriggerActionsEntryBlockSource INTEGER,
            lcsSetupIpv6FirewallTriggerActionsEntryBlockTime Integer32,
            lcsSetupIpv6FirewallTriggerActionsEntryCloseDestination INTEGER,
            lcsSetupIpv6FirewallTriggerActionsEntryCloseTime Integer32
    }

-- {COLUMN} 1.3.6.1.4.1.2356.11.2.70.5.13.1.1
lcsSetupIpv6FirewallTriggerActionsEntryName OBJECT-TYPE
    SYNTAX     DisplayString (SIZE(0..32))
    MAX-ACCESS read-write
    STATUS     current
    DESCRIPTION
            "-- empty --"
    ::= { lcsSetupIpv6FirewallTriggerActionsEntry 1 }

-- {COLUMN} 1.3.6.1.4.1.2356.11.2.70.5.13.1.2
lcsSetupIpv6FirewallTriggerActionsEntryNotifications OBJECT-TYPE
    SYNTAX     BITS {
                  eNone (0),
                  eEmail (5),
                  eSyslog (6),
                  eSnmp (7)
            }
    MAX-ACCESS read-write
    STATUS     current
    DESCRIPTION
            "-- empty --"
    ::= { lcsSetupIpv6FirewallTriggerActionsEntry 2 }

-- {COLUMN} 1.3.6.1.4.1.2356.11.2.70.5.13.1.3
lcsSetupIpv6FirewallTriggerActionsEntryDisconnect OBJECT-TYPE
    SYNTAX     INTEGER {
                  eNo (0),
                  eYes (1)
            }
    MAX-ACCESS read-write
    STATUS     current
    DESCRIPTION
            "-- empty --"
    ::= { lcsSetupIpv6FirewallTriggerActionsEntry 3 }

-- {COLUMN} 1.3.6.1.4.1.2356.11.2.70.5.13.1.4
lcsSetupIpv6FirewallTriggerActionsEntryBlockSource OBJECT-TYPE
    SYNTAX     INTEGER {
                  eNo (0),
                  eYes (1)
            }
    MAX-ACCESS read-write
    STATUS     current
    DESCRIPTION
            "-- empty --"
    ::= { lcsSetupIpv6FirewallTriggerActionsEntry 4 }

-- {COLUMN} 1.3.6.1.4.1.2356.11.2.70.5.13.1.5
lcsSetupIpv6FirewallTriggerActionsEntryBlockTime OBJECT-TYPE
    SYNTAX     Integer32 (0..2147483647)
    MAX-ACCESS read-write
    STATUS     current
    DESCRIPTION
            "-- empty --"
    ::= { lcsSetupIpv6FirewallTriggerActionsEntry 5 }

-- {COLUMN} 1.3.6.1.4.1.2356.11.2.70.5.13.1.6
lcsSetupIpv6FirewallTriggerActionsEntryCloseDestination OBJECT-TYPE
    SYNTAX     INTEGER {
                  eNo (0),
                  eYes (1)
            }
    MAX-ACCESS read-write
    STATUS     current
    DESCRIPTION
            "-- empty --"
    ::= { lcsSetupIpv6FirewallTriggerActionsEntry 6 }

-- {COLUMN} 1.3.6.1.4.1.2356.11.2.70.5.13.1.7
lcsSetupIpv6FirewallTriggerActionsEntryCloseTime OBJECT-TYPE
    SYNTAX     Integer32 (0..2147483647)
    MAX-ACCESS read-write
    STATUS     current
    DESCRIPTION
            "-- empty --"
    ::= { lcsSetupIpv6FirewallTriggerActionsEntry 7 }

-- {TABLE} 1.3.6.1.4.1.2356.11.2.70.5.14
lcsSetupIpv6FirewallIcmpServicesTable OBJECT-TYPE
    SYNTAX     SEQUENCE OF LcsSetupIpv6FirewallIcmpServicesEntry
    MAX-ACCESS not-accessible
    STATUS     current
    DESCRIPTION
            "-- empty --"
    ::= { lcsSetupIpv6Firewall 14 }

-- {ROW} 1.3.6.1.4.1.2356.11.2.70.5.14.1
lcsSetupIpv6FirewallIcmpServicesEntry OBJECT-TYPE
    SYNTAX     LcsSetupIpv6FirewallIcmpServicesEntry
    MAX-ACCESS not-accessible
    STATUS     current
    DESCRIPTION
            ""
    INDEX {
            lcsSetupIpv6FirewallIcmpServicesEntryName
          }
    ::= { lcsSetupIpv6FirewallIcmpServicesTable 1 }

LcsSetupIpv6FirewallIcmpServicesEntry ::= SEQUENCE {
            lcsSetupIpv6FirewallIcmpServicesEntryName DisplayString,
            lcsSetupIpv6FirewallIcmpServicesEntryType Integer32,
            lcsSetupIpv6FirewallIcmpServicesEntryCode Integer32
    }

-- {COLUMN} 1.3.6.1.4.1.2356.11.2.70.5.14.1.1
lcsSetupIpv6FirewallIcmpServicesEntryName OBJECT-TYPE
    SYNTAX     DisplayString (SIZE(0..32))
    MAX-ACCESS read-write
    STATUS     current
    DESCRIPTION
            "-- empty --"
    ::= { lcsSetupIpv6FirewallIcmpServicesEntry 1 }

-- {COLUMN} 1.3.6.1.4.1.2356.11.2.70.5.14.1.2
lcsSetupIpv6FirewallIcmpServicesEntryType OBJECT-TYPE
    SYNTAX     Integer32 (0..2147483647)
    MAX-ACCESS read-write
    STATUS     current
    DESCRIPTION
            "-- empty --"
    ::= { lcsSetupIpv6FirewallIcmpServicesEntry 2 }

-- {COLUMN} 1.3.6.1.4.1.2356.11.2.70.5.14.1.3
lcsSetupIpv6FirewallIcmpServicesEntryCode OBJECT-TYPE
    SYNTAX     Integer32 (0..2147483647)
    MAX-ACCESS read-write
    STATUS     current
    DESCRIPTION
            "-- empty --"
    ::= { lcsSetupIpv6FirewallIcmpServicesEntry 3 }

-- {TABLE} 1.3.6.1.4.1.2356.11.2.70.5.15
lcsSetupIpv6FirewallInboundRulesTable OBJECT-TYPE
    SYNTAX     SEQUENCE OF LcsSetupIpv6FirewallInboundRulesEntry
    MAX-ACCESS not-accessible
    STATUS     current
    DESCRIPTION
            "-- empty --"
    ::= { lcsSetupIpv6Firewall 15 }

-- {ROW} 1.3.6.1.4.1.2356.11.2.70.5.15.1
lcsSetupIpv6FirewallInboundRulesEntry OBJECT-TYPE
    SYNTAX     LcsSetupIpv6FirewallInboundRulesEntry
    MAX-ACCESS not-accessible
    STATUS     current
    DESCRIPTION
            ""
    INDEX {
            lcsSetupIpv6FirewallInboundRulesEntryName
          }
    ::= { lcsSetupIpv6FirewallInboundRulesTable 1 }

LcsSetupIpv6FirewallInboundRulesEntry ::= SEQUENCE {
            lcsSetupIpv6FirewallInboundRulesEntryName DisplayString,
            lcsSetupIpv6FirewallInboundRulesEntryActive INTEGER,
            lcsSetupIpv6FirewallInboundRulesEntryPrio Integer32,
            lcsSetupIpv6FirewallInboundRulesEntryAction DisplayString,
            lcsSetupIpv6FirewallInboundRulesEntryServices DisplayString,
            lcsSetupIpv6FirewallInboundRulesEntrySourceStations DisplayString,
            lcsSetupIpv6FirewallInboundRulesEntryComment DisplayString,
            lcsSetupIpv6FirewallInboundRulesEntrySrcTag Integer32
    }

-- {COLUMN} 1.3.6.1.4.1.2356.11.2.70.5.15.1.1
lcsSetupIpv6FirewallInboundRulesEntryName OBJECT-TYPE
    SYNTAX     DisplayString (SIZE(0..36))
    MAX-ACCESS read-write
    STATUS     current
    DESCRIPTION
            "-- empty --"
    ::= { lcsSetupIpv6FirewallInboundRulesEntry 1 }

-- {COLUMN} 1.3.6.1.4.1.2356.11.2.70.5.15.1.2
lcsSetupIpv6FirewallInboundRulesEntryActive OBJECT-TYPE
    SYNTAX     INTEGER {
                  eYes (0),
                  eNo (1)
            }
    MAX-ACCESS read-write
    STATUS     current
    DESCRIPTION
            "-- empty --"
    ::= { lcsSetupIpv6FirewallInboundRulesEntry 2 }

-- {COLUMN} 1.3.6.1.4.1.2356.11.2.70.5.15.1.3
lcsSetupIpv6FirewallInboundRulesEntryPrio OBJECT-TYPE
    SYNTAX     Integer32 (0..65535)
    MAX-ACCESS read-write
    STATUS     current
    DESCRIPTION
            "-- empty --"
    ::= { lcsSetupIpv6FirewallInboundRulesEntry 3 }

-- {COLUMN} 1.3.6.1.4.1.2356.11.2.70.5.15.1.5
lcsSetupIpv6FirewallInboundRulesEntryAction OBJECT-TYPE
    SYNTAX     DisplayString (SIZE(0..64))
    MAX-ACCESS read-write
    STATUS     current
    DESCRIPTION
            "-- empty --"
    ::= { lcsSetupIpv6FirewallInboundRulesEntry 5 }

-- {COLUMN} 1.3.6.1.4.1.2356.11.2.70.5.15.1.7
lcsSetupIpv6FirewallInboundRulesEntryServices OBJECT-TYPE
    SYNTAX     DisplayString (SIZE(0..64))
    MAX-ACCESS read-write
    STATUS     current
    DESCRIPTION
            "-- empty --"
    ::= { lcsSetupIpv6FirewallInboundRulesEntry 7 }

-- {COLUMN} 1.3.6.1.4.1.2356.11.2.70.5.15.1.8
lcsSetupIpv6FirewallInboundRulesEntrySourceStations OBJECT-TYPE
    SYNTAX     DisplayString (SIZE(0..64))
    MAX-ACCESS read-write
    STATUS     current
    DESCRIPTION
            "-- empty --"
    ::= { lcsSetupIpv6FirewallInboundRulesEntry 8 }

-- {COLUMN} 1.3.6.1.4.1.2356.11.2.70.5.15.1.10
lcsSetupIpv6FirewallInboundRulesEntryComment OBJECT-TYPE
    SYNTAX     DisplayString (SIZE(0..64))
    MAX-ACCESS read-write
    STATUS     current
    DESCRIPTION
            "-- empty --"
    ::= { lcsSetupIpv6FirewallInboundRulesEntry 10 }

-- {COLUMN} 1.3.6.1.4.1.2356.11.2.70.5.15.1.11
lcsSetupIpv6FirewallInboundRulesEntrySrcTag OBJECT-TYPE
    SYNTAX     Integer32 (0..65535)
    MAX-ACCESS read-write
    STATUS     current
    DESCRIPTION
            "-- empty --"
    ::= { lcsSetupIpv6FirewallInboundRulesEntry 11 }

-- {SCALAR} 1.3.6.1.4.1.2356.11.2.70.5.20
lcsSetupIpv6FirewallAllowRouteOptions OBJECT-TYPE
    SYNTAX     INTEGER {
                  eNo (0),
                  eYes (1)
            }
    MAX-ACCESS read-write
    STATUS     current
    DESCRIPTION
            "-- empty --"
    ::= { lcsSetupIpv6Firewall 20 }

-- {SCALAR} 1.3.6.1.4.1.2356.11.2.70.5.21
lcsSetupIpv6FirewallDestinationCacheLimit OBJECT-TYPE
    SYNTAX     Integer32 (0..2147483647)
    MAX-ACCESS read-write
    STATUS     current
    DESCRIPTION
            "-- empty --"
    ::= { lcsSetupIpv6Firewall 21 }

-- {SCALAR} 1.3.6.1.4.1.2356.11.2.70.5.25
lcsSetupIpv6FirewallDscpSupport OBJECT-TYPE
    SYNTAX     INTEGER {
                  eNo (0),
                  eYes (1)
            }
    MAX-ACCESS read-write
    STATUS     current
    DESCRIPTION
            "-- empty --"
    ::= { lcsSetupIpv6Firewall 25 }

-- {TABLE} 1.3.6.1.4.1.2356.11.2.70.6
lcsSetupIpv6LanInterfacesTable OBJECT-TYPE
    SYNTAX     SEQUENCE OF LcsSetupIpv6LanInterfacesEntry
    MAX-ACCESS not-accessible
    STATUS     current
    DESCRIPTION
            "-- empty --"
    ::= { lcsSetupIpv6 6 }

-- {ROW} 1.3.6.1.4.1.2356.11.2.70.6.1
lcsSetupIpv6LanInterfacesEntry OBJECT-TYPE
    SYNTAX     LcsSetupIpv6LanInterfacesEntry
    MAX-ACCESS not-accessible
    STATUS     current
    DESCRIPTION
            ""
    INDEX {
            lcsSetupIpv6LanInterfacesEntryInterfaceName
          }
    ::= { lcsSetupIpv6LanInterfacesTable 1 }

LcsSetupIpv6LanInterfacesEntry ::= SEQUENCE {
            lcsSetupIpv6LanInterfacesEntryInterfaceName DisplayString,
            lcsSetupIpv6LanInterfacesEntryInterfaceId INTEGER,
            lcsSetupIpv6LanInterfacesEntryVlanId Integer32,
            lcsSetupIpv6LanInterfacesEntryRtgTag Integer32,
            lcsSetupIpv6LanInterfacesEntryAutoconf INTEGER,
            lcsSetupIpv6LanInterfacesEntryAcceptRa INTEGER,
            lcsSetupIpv6LanInterfacesEntryInterfaceStatus INTEGER,
            lcsSetupIpv6LanInterfacesEntryForwarding INTEGER,
            lcsSetupIpv6LanInterfacesEntryMtu Integer32,
            lcsSetupIpv6LanInterfacesEntryFirewall INTEGER,
            lcsSetupIpv6LanInterfacesEntryComment DisplayString,
            lcsSetupIpv6LanInterfacesEntryDadAttempts Integer32,
            lcsSetupIpv6LanInterfacesEntryRsCount Integer32
    }

-- {COLUMN} 1.3.6.1.4.1.2356.11.2.70.6.1.1
lcsSetupIpv6LanInterfacesEntryInterfaceName OBJECT-TYPE
    SYNTAX     DisplayString (SIZE(0..16))
    MAX-ACCESS read-write
    STATUS     current
    DESCRIPTION
            "-- empty --"
    ::= { lcsSetupIpv6LanInterfacesEntry 1 }

-- {COLUMN} 1.3.6.1.4.1.2356.11.2.70.6.1.2
lcsSetupIpv6LanInterfacesEntryInterfaceId OBJECT-TYPE
    SYNTAX     INTEGER {
                  eLan1 (256),
                  eLan2 (257),
                  eLan3 (258),
                  eLan4 (259),
                  eLan5 (260),
                  eLan6 (261),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlan19 (1072),
                  eWlan110 (1073),
                  eWlan111 (1074),
                  eWlan112 (1075),
                  eWlan113 (1076),
                  eWlan114 (1077),
                  eWlan115 (1078),
                  eWlan116 (1079),
                  eWlan29 (1104),
                  eWlan210 (1105),
                  eWlan211 (1106),
                  eWlan212 (1107),
                  eWlan213 (1108),
                  eWlan214 (1109),
                  eWlan215 (1110),
                  eWlan216 (1111),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  eBundle1 (2048),
                  eBundle2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eL2tpEthernet1 (2560),
                  eL2tpEthernet2 (2561),
                  eL2tpEthernet3 (2562),
                  eL2tpEthernet4 (2563),
                  eL2tpEthernet5 (2564),
                  eL2tpEthernet6 (2565),
                  eL2tpEthernet7 (2566),
                  eL2tpEthernet8 (2567),
                  eL2tpEthernet9 (2568),
                  eL2tpEthernet10 (2569),
                  eL2tpEthernet11 (2570),
                  eL2tpEthernet12 (2571),
                  eL2tpEthernet13 (2572),
                  eL2tpEthernet14 (2573),
                  eL2tpEthernet15 (2574),
                  eL2tpEthernet16 (2575),
                  eXdsl1 (2816),
                  eXdsl2 (2817)
            }
    MAX-ACCESS read-write
    STATUS     current
    DESCRIPTION
            "-- empty --"
    ::= { lcsSetupIpv6LanInterfacesEntry 2 }

-- {COLUMN} 1.3.6.1.4.1.2356.11.2.70.6.1.3
lcsSetupIpv6LanInterfacesEntryVlanId OBJECT-TYPE
    SYNTAX     Integer32 (0..65535)
    MAX-ACCESS read-write
    STATUS     current
    DESCRIPTION
            "-- empty --"
    ::= { lcsSetupIpv6LanInterfacesEntry 3 }

-- {COLUMN} 1.3.6.1.4.1.2356.11.2.70.6.1.4
lcsSetupIpv6LanInterfacesEntryRtgTag OBJECT-TYPE
    SYNTAX     Integer32 (0..65535)
    MAX-ACCESS read-write
    STATUS     current
    DESCRIPTION
            "-- empty --"
    ::= { lcsSetupIpv6LanInterfacesEntry 4 }

-- {COLUMN} 1.3.6.1.4.1.2356.11.2.70.6.1.5
lcsSetupIpv6LanInterfacesEntryAutoconf OBJECT-TYPE
    SYNTAX     INTEGER {
                  eYes (0),
                  eNo (1)
            }
    MAX-ACCESS read-write
    STATUS     current
    DESCRIPTION
            "-- empty --"
    ::= { lcsSetupIpv6LanInterfacesEntry 5 }

-- {COLUMN} 1.3.6.1.4.1.2356.11.2.70.6.1.6
lcsSetupIpv6LanInterfacesEntryAcceptRa OBJECT-TYPE
    SYNTAX     INTEGER {
                  eYes (0),
                  eNo (1)
            }
    MAX-ACCESS read-write
    STATUS     current
    DESCRIPTION
            "-- empty --"
    ::= { lcsSetupIpv6LanInterfacesEntry 6 }

-- {COLUMN} 1.3.6.1.4.1.2356.11.2.70.6.1.7
lcsSetupIpv6LanInterfacesEntryInterfaceStatus OBJECT-TYPE
    SYNTAX     INTEGER {
                  eUp (1),
                  eDown (2)
            }
    MAX-ACCESS read-write
    STATUS     current
    DESCRIPTION
            "-- empty --"
    ::= { lcsSetupIpv6LanInterfacesEntry 7 }

-- {COLUMN} 1.3.6.1.4.1.2356.11.2.70.6.1.8
lcsSetupIpv6LanInterfacesEntryForwarding OBJECT-TYPE
    SYNTAX     INTEGER {
                  eYes (0),
                  eNo (1)
            }
    MAX-ACCESS read-write
    STATUS     current
    DESCRIPTION
            "-- empty --"
    ::= { lcsSetupIpv6LanInterfacesEntry 8 }

-- {COLUMN} 1.3.6.1.4.1.2356.11.2.70.6.1.9
lcsSetupIpv6LanInterfacesEntryMtu OBJECT-TYPE
    SYNTAX     Integer32 (0..65535)
    MAX-ACCESS read-write
    STATUS     current
    DESCRIPTION
            "-- empty --"
    ::= { lcsSetupIpv6LanInterfacesEntry 9 }

-- {COLUMN} 1.3.6.1.4.1.2356.11.2.70.6.1.10
lcsSetupIpv6LanInterfacesEntryFirewall OBJECT-TYPE
    SYNTAX     INTEGER {
                  eYes (0),
                  eNo (1)
            }
    MAX-ACCESS read-write
    STATUS     current
    DESCRIPTION
            "-- empty --"
    ::= { lcsSetupIpv6LanInterfacesEntry 10 }

-- {COLUMN} 1.3.6.1.4.1.2356.11.2.70.6.1.11
lcsSetupIpv6LanInterfacesEntryComment OBJECT-TYPE
    SYNTAX     DisplayString (SIZE(0..64))
    MAX-ACCESS read-write
    STATUS     current
    DESCRIPTION
            "-- empty --"
    ::= { lcsSetupIpv6LanInterfacesEntry 11 }

-- {COLUMN} 1.3.6.1.4.1.2356.11.2.70.6.1.12
lcsSetupIpv6LanInterfacesEntryDadAttempts OBJECT-TYPE
    SYNTAX     Integer32 (0..255)
    MAX-ACCESS read-write
    STATUS     current
    DESCRIPTION
            "-- empty --"
    ::= { lcsSetupIpv6LanInterfacesEntry 12 }

-- {COLUMN} 1.3.6.1.4.1.2356.11.2.70.6.1.13
lcsSetupIpv6LanInterfacesEntryRsCount OBJECT-TYPE
    SYNTAX     Integer32 (0..255)
    MAX-ACCESS read-write
    STATUS     current
    DESCRIPTION
            "-- empty --"
    ::= { lcsSetupIpv6LanInterfacesEntry 13 }

-- {TABLE} 1.3.6.1.4.1.2356.11.2.70.7
lcsSetupIpv6WanInterfacesTable OBJECT-TYPE
    SYNTAX     SEQUENCE OF LcsSetupIpv6WanInterfacesEntry
    MAX-ACCESS not-accessible
    STATUS     current
    DESCRIPTION
            "-- empty --"
    ::= { lcsSetupIpv6 7 }

-- {ROW} 1.3.6.1.4.1.2356.11.2.70.7.1
lcsSetupIpv6WanInterfacesEntry OBJECT-TYPE
    SYNTAX     LcsSetupIpv6WanInterfacesEntry
    MAX-ACCESS not-accessible
    STATUS     current
    DESCRIPTION
            ""
    INDEX {
            lcsSetupIpv6WanInterfacesEntryInterfaceName
          }
    ::= { lcsSetupIpv6WanInterfacesTable 1 }

LcsSetupIpv6WanInterfacesEntry ::= SEQUENCE {
            lcsSetupIpv6WanInterfacesEntryInterfaceName DisplayString,
            lcsSetupIpv6WanInterfacesEntryRtgTag Integer32,
            lcsSetupIpv6WanInterfacesEntryAutoconf INTEGER,
            lcsSetupIpv6WanInterfacesEntryAcceptRa INTEGER,
            lcsSetupIpv6WanInterfacesEntryInterfaceStatus INTEGER,
            lcsSetupIpv6WanInterfacesEntryForwarding INTEGER,
            lcsSetupIpv6WanInterfacesEntryFirewall INTEGER,
            lcsSetupIpv6WanInterfacesEntryComment DisplayString,
            lcsSetupIpv6WanInterfacesEntryDadAttempts Integer32,
            lcsSetupIpv6WanInterfacesEntryPdMode INTEGER,
            lcsSetupIpv6WanInterfacesEntryRsCount Integer32
    }

-- {COLUMN} 1.3.6.1.4.1.2356.11.2.70.7.1.1
lcsSetupIpv6WanInterfacesEntryInterfaceName OBJECT-TYPE
    SYNTAX     DisplayString (SIZE(0..16))
    MAX-ACCESS read-write
    STATUS     current
    DESCRIPTION
            "-- empty --"
    ::= { lcsSetupIpv6WanInterfacesEntry 1 }

-- {COLUMN} 1.3.6.1.4.1.2356.11.2.70.7.1.2
lcsSetupIpv6WanInterfacesEntryRtgTag OBJECT-TYPE
    SYNTAX     Integer32 (0..65535)
    MAX-ACCESS read-write
    STATUS     current
    DESCRIPTION
            "-- empty --"
    ::= { lcsSetupIpv6WanInterfacesEntry 2 }

-- {COLUMN} 1.3.6.1.4.1.2356.11.2.70.7.1.3
lcsSetupIpv6WanInterfacesEntryAutoconf OBJECT-TYPE
    SYNTAX     INTEGER {
                  eYes (0),
                  eNo (1)
            }
    MAX-ACCESS read-write
    STATUS     current
    DESCRIPTION
            "-- empty --"
    ::= { lcsSetupIpv6WanInterfacesEntry 3 }

-- {COLUMN} 1.3.6.1.4.1.2356.11.2.70.7.1.4
lcsSetupIpv6WanInterfacesEntryAcceptRa OBJECT-TYPE
    SYNTAX     INTEGER {
                  eYes (0),
                  eNo (1)
            }
    MAX-ACCESS read-write
    STATUS     current
    DESCRIPTION
            "-- empty --"
    ::= { lcsSetupIpv6WanInterfacesEntry 4 }

-- {COLUMN} 1.3.6.1.4.1.2356.11.2.70.7.1.5
lcsSetupIpv6WanInterfacesEntryInterfaceStatus OBJECT-TYPE
    SYNTAX     INTEGER {
                  eUp (1),
                  eDown (2)
            }
    MAX-ACCESS read-write
    STATUS     current
    DESCRIPTION
            "-- empty --"
    ::= { lcsSetupIpv6WanInterfacesEntry 5 }

-- {COLUMN} 1.3.6.1.4.1.2356.11.2.70.7.1.6
lcsSetupIpv6WanInterfacesEntryForwarding OBJECT-TYPE
    SYNTAX     INTEGER {
                  eYes (0),
                  eNo (1)
            }
    MAX-ACCESS read-write
    STATUS     current
    DESCRIPTION
            "-- empty --"
    ::= { lcsSetupIpv6WanInterfacesEntry 6 }

-- {COLUMN} 1.3.6.1.4.1.2356.11.2.70.7.1.7
lcsSetupIpv6WanInterfacesEntryFirewall OBJECT-TYPE
    SYNTAX     INTEGER {
                  eYes (0),
                  eNo (1)
            }
    MAX-ACCESS read-write
    STATUS     current
    DESCRIPTION
            "-- empty --"
    ::= { lcsSetupIpv6WanInterfacesEntry 7 }

-- {COLUMN} 1.3.6.1.4.1.2356.11.2.70.7.1.8
lcsSetupIpv6WanInterfacesEntryComment OBJECT-TYPE
    SYNTAX     DisplayString (SIZE(0..64))
    MAX-ACCESS read-write
    STATUS     current
    DESCRIPTION
            "-- empty --"
    ::= { lcsSetupIpv6WanInterfacesEntry 8 }

-- {COLUMN} 1.3.6.1.4.1.2356.11.2.70.7.1.9
lcsSetupIpv6WanInterfacesEntryDadAttempts OBJECT-TYPE
    SYNTAX     Integer32 (0..255)
    MAX-ACCESS read-write
    STATUS     current
    DESCRIPTION
            "-- empty --"
    ::= { lcsSetupIpv6WanInterfacesEntry 9 }

-- {COLUMN} 1.3.6.1.4.1.2356.11.2.70.7.1.10
lcsSetupIpv6WanInterfacesEntryPdMode OBJECT-TYPE
    SYNTAX     INTEGER {
                  eDhcpv6 (0),
                  eRouterAdv (1)
            }
    MAX-ACCESS read-write
    STATUS     current
    DESCRIPTION
            "-- empty --"
    ::= { lcsSetupIpv6WanInterfacesEntry 10 }

-- {COLUMN} 1.3.6.1.4.1.2356.11.2.70.7.1.11
lcsSetupIpv6WanInterfacesEntryRsCount OBJECT-TYPE
    SYNTAX     Integer32 (0..255)
    MAX-ACCESS read-write
    STATUS     current
    DESCRIPTION
            "-- empty --"
    ::= { lcsSetupIpv6WanInterfacesEntry 11 }

-- {SCALAR} 1.3.6.1.4.1.2356.11.2.70.10
lcsSetupIpv6Operating OBJECT-TYPE
    SYNTAX     INTEGER {
                  eNo (0),
                  eYes (1)
            }
    MAX-ACCESS read-write
    STATUS     current
    DESCRIPTION
            "-- empty --"
    ::= { lcsSetupIpv6 10 }

-- {SCALAR} 1.3.6.1.4.1.2356.11.2.70.11
lcsSetupIpv6Forwarding OBJECT-TYPE
    SYNTAX     INTEGER {
                  eNo (0),
                  eYes (1)
            }
    MAX-ACCESS read-write
    STATUS     current
    DESCRIPTION
            "-- empty --"
    ::= { lcsSetupIpv6 11 }

-- {NODE} 1.3.6.1.4.1.2356.11.2.70.12
lcsSetupIpv6Router OBJECT IDENTIFIER ::= { lcsSetupIpv6 12 }

-- {TABLE} 1.3.6.1.4.1.2356.11.2.70.12.1
lcsSetupIpv6RouterRoutingTableTable OBJECT-TYPE
    SYNTAX     SEQUENCE OF LcsSetupIpv6RouterRoutingTableEntry
    MAX-ACCESS not-accessible
    STATUS     current
    DESCRIPTION
            "-- empty --"
    ::= { lcsSetupIpv6Router 1 }

-- {ROW} 1.3.6.1.4.1.2356.11.2.70.12.1.1
lcsSetupIpv6RouterRoutingTableEntry OBJECT-TYPE
    SYNTAX     LcsSetupIpv6RouterRoutingTableEntry
    MAX-ACCESS not-accessible
    STATUS     current
    DESCRIPTION
            ""
    INDEX {
            lcsSetupIpv6RouterRoutingTableEntryPrefix,
            lcsSetupIpv6RouterRoutingTableEntryRtgTag,
            lcsSetupIpv6RouterRoutingTableEntryAdminDistance
          }
    ::= { lcsSetupIpv6RouterRoutingTableTable 1 }

LcsSetupIpv6RouterRoutingTableEntry ::= SEQUENCE {
            lcsSetupIpv6RouterRoutingTableEntryPrefix DisplayString,
            lcsSetupIpv6RouterRoutingTableEntryRtgTag Integer32,
            lcsSetupIpv6RouterRoutingTableEntryPeerOrIpv6 DisplayString,
            lcsSetupIpv6RouterRoutingTableEntryComment DisplayString,
            lcsSetupIpv6RouterRoutingTableEntryAdminDistance Integer32
    }

-- {COLUMN} 1.3.6.1.4.1.2356.11.2.70.12.1.1.1
lcsSetupIpv6RouterRoutingTableEntryPrefix OBJECT-TYPE
    SYNTAX     DisplayString (SIZE(0..43))
    MAX-ACCESS read-write
    STATUS     current
    DESCRIPTION
            "-- empty --"
    ::= { lcsSetupIpv6RouterRoutingTableEntry 1 }

-- {COLUMN} 1.3.6.1.4.1.2356.11.2.70.12.1.1.2
lcsSetupIpv6RouterRoutingTableEntryRtgTag OBJECT-TYPE
    SYNTAX     Integer32 (0..65535)
    MAX-ACCESS read-write
    STATUS     current
    DESCRIPTION
            "-- empty --"
    ::= { lcsSetupIpv6RouterRoutingTableEntry 2 }

-- {COLUMN} 1.3.6.1.4.1.2356.11.2.70.12.1.1.3
lcsSetupIpv6RouterRoutingTableEntryPeerOrIpv6 OBJECT-TYPE
    SYNTAX     DisplayString (SIZE(0..65))
    MAX-ACCESS read-write
    STATUS     current
    DESCRIPTION
            "-- empty --"
    ::= { lcsSetupIpv6RouterRoutingTableEntry 3 }

-- {COLUMN} 1.3.6.1.4.1.2356.11.2.70.12.1.1.4
lcsSetupIpv6RouterRoutingTableEntryComment OBJECT-TYPE
    SYNTAX     DisplayString (SIZE(0..64))
    MAX-ACCESS read-write
    STATUS     current
    DESCRIPTION
            "-- empty --"
    ::= { lcsSetupIpv6RouterRoutingTableEntry 4 }

-- {COLUMN} 1.3.6.1.4.1.2356.11.2.70.12.1.1.5
lcsSetupIpv6RouterRoutingTableEntryAdminDistance OBJECT-TYPE
    SYNTAX     Integer32 (0..255)
    MAX-ACCESS read-write
    STATUS     current
    DESCRIPTION
            "-- empty --"
    ::= { lcsSetupIpv6RouterRoutingTableEntry 5 }

-- {SCALAR} 1.3.6.1.4.1.2356.11.2.70.12.2
lcsSetupIpv6RouterDestCacheTimeout OBJECT-TYPE
    SYNTAX     Integer32 (0..65535)
    MAX-ACCESS read-write
    STATUS     current
    DESCRIPTION
            "-- empty --"
    ::= { lcsSetupIpv6Router 2 }

-- {TABLE} 1.3.6.1.4.1.2356.11.2.70.13
lcsSetupIpv6Icmpv6Table OBJECT-TYPE
    SYNTAX     SEQUENCE OF LcsSetupIpv6Icmpv6Entry
    MAX-ACCESS not-accessible
    STATUS     current
    DESCRIPTION
            "-- empty --"
    ::= { lcsSetupIpv6 13 }

-- {ROW} 1.3.6.1.4.1.2356.11.2.70.13.1
lcsSetupIpv6Icmpv6Entry OBJECT-TYPE
    SYNTAX     LcsSetupIpv6Icmpv6Entry
    MAX-ACCESS not-accessible
    STATUS     current
    DESCRIPTION
            ""
    INDEX {
            lcsSetupIpv6Icmpv6EntryInterfaceName
          }
    ::= { lcsSetupIpv6Icmpv6Table 1 }

LcsSetupIpv6Icmpv6Entry ::= SEQUENCE {
            lcsSetupIpv6Icmpv6EntryInterfaceName DisplayString,
            lcsSetupIpv6Icmpv6EntryErrorBandwidth Integer32,
            lcsSetupIpv6Icmpv6EntryRedirects INTEGER,
            lcsSetupIpv6Icmpv6EntryRefreshAmount Integer32,
            lcsSetupIpv6Icmpv6EntryInterval Integer32,
            lcsSetupIpv6Icmpv6EntryMode INTEGER
    }

-- {COLUMN} 1.3.6.1.4.1.2356.11.2.70.13.1.1
lcsSetupIpv6Icmpv6EntryInterfaceName OBJECT-TYPE
    SYNTAX     DisplayString (SIZE(0..16))
    MAX-ACCESS read-write
    STATUS     current
    DESCRIPTION
            "-- empty --"
    ::= { lcsSetupIpv6Icmpv6Entry 1 }

-- {COLUMN} 1.3.6.1.4.1.2356.11.2.70.13.1.2
lcsSetupIpv6Icmpv6EntryErrorBandwidth OBJECT-TYPE
    SYNTAX     Integer32 (0..2147483647)
    MAX-ACCESS read-write
    STATUS     current
    DESCRIPTION
            "-- empty --"
    ::= { lcsSetupIpv6Icmpv6Entry 2 }

-- {COLUMN} 1.3.6.1.4.1.2356.11.2.70.13.1.3
lcsSetupIpv6Icmpv6EntryRedirects OBJECT-TYPE
    SYNTAX     INTEGER {
                  eDisable (0),
                  eEnable (1)
            }
    MAX-ACCESS read-write
    STATUS     current
    DESCRIPTION
            "-- empty --"
    ::= { lcsSetupIpv6Icmpv6Entry 3 }

-- {COLUMN} 1.3.6.1.4.1.2356.11.2.70.13.1.4
lcsSetupIpv6Icmpv6EntryRefreshAmount OBJECT-TYPE
    SYNTAX     Integer32 (0..2147483647)
    MAX-ACCESS read-write
    STATUS     current
    DESCRIPTION
            "-- empty --"
    ::= { lcsSetupIpv6Icmpv6Entry 4 }

-- {COLUMN} 1.3.6.1.4.1.2356.11.2.70.13.1.5
lcsSetupIpv6Icmpv6EntryInterval OBJECT-TYPE
    SYNTAX     Integer32 (0..2147483647)
    MAX-ACCESS read-write
    STATUS     current
    DESCRIPTION
            "-- empty --"
    ::= { lcsSetupIpv6Icmpv6Entry 5 }

-- {COLUMN} 1.3.6.1.4.1.2356.11.2.70.13.1.6
lcsSetupIpv6Icmpv6EntryMode OBJECT-TYPE
    SYNTAX     INTEGER {
                  eBandwidth (0),
                  ePackets (1),
                  eDisabled (2)
            }
    MAX-ACCESS read-write
    STATUS     current
    DESCRIPTION
            "-- empty --"
    ::= { lcsSetupIpv6Icmpv6Entry 6 }

-- {TABLE} 1.3.6.1.4.1.2356.11.2.70.14
lcsSetupIpv6RasInterfacesTable OBJECT-TYPE
    SYNTAX     SEQUENCE OF LcsSetupIpv6RasInterfacesEntry
    MAX-ACCESS not-accessible
    STATUS     current
    DESCRIPTION
            "-- empty --"
    ::= { lcsSetupIpv6 14 }

-- {ROW} 1.3.6.1.4.1.2356.11.2.70.14.1
lcsSetupIpv6RasInterfacesEntry OBJECT-TYPE
    SYNTAX     LcsSetupIpv6RasInterfacesEntry
    MAX-ACCESS not-accessible
    STATUS     current
    DESCRIPTION
            ""
    INDEX {
            lcsSetupIpv6RasInterfacesEntryInterfaceName
          }
    ::= { lcsSetupIpv6RasInterfacesTable 1 }

LcsSetupIpv6RasInterfacesEntry ::= SEQUENCE {
            lcsSetupIpv6RasInterfacesEntryInterfaceName DisplayString,
            lcsSetupIpv6RasInterfacesEntryRtgTag Integer32,
            lcsSetupIpv6RasInterfacesEntryInterfaceStatus INTEGER,
            lcsSetupIpv6RasInterfacesEntryForwarding INTEGER,
            lcsSetupIpv6RasInterfacesEntryFirewall INTEGER,
            lcsSetupIpv6RasInterfacesEntryDadAttempts Integer32,
            lcsSetupIpv6RasInterfacesEntryPeerName DisplayString,
            lcsSetupIpv6RasInterfacesEntryComment DisplayString
    }

-- {COLUMN} 1.3.6.1.4.1.2356.11.2.70.14.1.1
lcsSetupIpv6RasInterfacesEntryInterfaceName OBJECT-TYPE
    SYNTAX     DisplayString (SIZE(0..16))
    MAX-ACCESS read-write
    STATUS     current
    DESCRIPTION
            "-- empty --"
    ::= { lcsSetupIpv6RasInterfacesEntry 1 }

-- {COLUMN} 1.3.6.1.4.1.2356.11.2.70.14.1.2
lcsSetupIpv6RasInterfacesEntryRtgTag OBJECT-TYPE
    SYNTAX     Integer32 (0..65535)
    MAX-ACCESS read-write
    STATUS     current
    DESCRIPTION
            "-- empty --"
    ::= { lcsSetupIpv6RasInterfacesEntry 2 }

-- {COLUMN} 1.3.6.1.4.1.2356.11.2.70.14.1.3
lcsSetupIpv6RasInterfacesEntryInterfaceStatus OBJECT-TYPE
    SYNTAX     INTEGER {
                  eUp (1),
                  eDown (2)
            }
    MAX-ACCESS read-write
    STATUS     current
    DESCRIPTION
            "-- empty --"
    ::= { lcsSetupIpv6RasInterfacesEntry 3 }

-- {COLUMN} 1.3.6.1.4.1.2356.11.2.70.14.1.4
lcsSetupIpv6RasInterfacesEntryForwarding OBJECT-TYPE
    SYNTAX     INTEGER {
                  eYes (0),
                  eNo (1)
            }
    MAX-ACCESS read-write
    STATUS     current
    DESCRIPTION
            "-- empty --"
    ::= { lcsSetupIpv6RasInterfacesEntry 4 }

-- {COLUMN} 1.3.6.1.4.1.2356.11.2.70.14.1.5
lcsSetupIpv6RasInterfacesEntryFirewall OBJECT-TYPE
    SYNTAX     INTEGER {
                  eYes (0),
                  eNo (1)
            }
    MAX-ACCESS read-write
    STATUS     current
    DESCRIPTION
            "-- empty --"
    ::= { lcsSetupIpv6RasInterfacesEntry 5 }

-- {COLUMN} 1.3.6.1.4.1.2356.11.2.70.14.1.6
lcsSetupIpv6RasInterfacesEntryDadAttempts OBJECT-TYPE
    SYNTAX     Integer32 (0..255)
    MAX-ACCESS read-write
    STATUS     current
    DESCRIPTION
            "-- empty --"
    ::= { lcsSetupIpv6RasInterfacesEntry 6 }

-- {COLUMN} 1.3.6.1.4.1.2356.11.2.70.14.1.7
lcsSetupIpv6RasInterfacesEntryPeerName OBJECT-TYPE
    SYNTAX     DisplayString (SIZE(0..16))
    MAX-ACCESS read-write
    STATUS     current
    DESCRIPTION
            "-- empty --"
    ::= { lcsSetupIpv6RasInterfacesEntry 7 }

-- {COLUMN} 1.3.6.1.4.1.2356.11.2.70.14.1.8
lcsSetupIpv6RasInterfacesEntryComment OBJECT-TYPE
    SYNTAX     DisplayString (SIZE(0..64))
    MAX-ACCESS read-write
    STATUS     current
    DESCRIPTION
            "-- empty --"
    ::= { lcsSetupIpv6RasInterfacesEntry 8 }

-- {NODE} 1.3.6.1.4.1.2356.11.2.71
lcsSetupIeee80211u OBJECT IDENTIFIER ::= { lcsSetup 71 }

-- {TABLE} 1.3.6.1.4.1.2356.11.2.71.1
lcsSetupIeee80211uAnqpProfilesTable OBJECT-TYPE
    SYNTAX     SEQUENCE OF LcsSetupIeee80211uAnqpProfilesEntry
    MAX-ACCESS not-accessible
    STATUS     current
    DESCRIPTION
            "-- empty --"
    ::= { lcsSetupIeee80211u 1 }

-- {ROW} 1.3.6.1.4.1.2356.11.2.71.1.1
lcsSetupIeee80211uAnqpProfilesEntry OBJECT-TYPE
    SYNTAX     LcsSetupIeee80211uAnqpProfilesEntry
    MAX-ACCESS not-accessible
    STATUS     current
    DESCRIPTION
            ""
    INDEX {
            lcsSetupIeee80211uAnqpProfilesEntryName
          }
    ::= { lcsSetupIeee80211uAnqpProfilesTable 1 }

LcsSetupIeee80211uAnqpProfilesEntry ::= SEQUENCE {
            lcsSetupIeee80211uAnqpProfilesEntryName DisplayString,
            lcsSetupIeee80211uAnqpProfilesEntryIncludeInBeaconOui DisplayString,
            lcsSetupIeee80211uAnqpProfilesEntryAdditionalOui DisplayString,
            lcsSetupIeee80211uAnqpProfilesEntryDomainList DisplayString,
            lcsSetupIeee80211uAnqpProfilesEntryNaiRealmList DisplayString,
            lcsSetupIeee80211uAnqpProfilesEntryCellularList DisplayString,
            lcsSetupIeee80211uAnqpProfilesEntryNetworkAuthTypeList DisplayString
    }

-- {COLUMN} 1.3.6.1.4.1.2356.11.2.71.1.1.1
lcsSetupIeee80211uAnqpProfilesEntryName OBJECT-TYPE
    SYNTAX     DisplayString (SIZE(0..32))
    MAX-ACCESS read-write
    STATUS     current
    DESCRIPTION
            "-- empty --"
    ::= { lcsSetupIeee80211uAnqpProfilesEntry 1 }

-- {COLUMN} 1.3.6.1.4.1.2356.11.2.71.1.1.2
lcsSetupIeee80211uAnqpProfilesEntryIncludeInBeaconOui OBJECT-TYPE
    SYNTAX     DisplayString (SIZE(0..65))
    MAX-ACCESS read-write
    STATUS     current
    DESCRIPTION
            "-- empty --"
    ::= { lcsSetupIeee80211uAnqpProfilesEntry 2 }

-- {COLUMN} 1.3.6.1.4.1.2356.11.2.71.1.1.3
lcsSetupIeee80211uAnqpProfilesEntryAdditionalOui OBJECT-TYPE
    SYNTAX     DisplayString (SIZE(0..65))
    MAX-ACCESS read-write
    STATUS     current
    DESCRIPTION
            "-- empty --"
    ::= { lcsSetupIeee80211uAnqpProfilesEntry 3 }

-- {COLUMN} 1.3.6.1.4.1.2356.11.2.71.1.1.4
lcsSetupIeee80211uAnqpProfilesEntryDomainList OBJECT-TYPE
    SYNTAX     DisplayString (SIZE(0..65))
    MAX-ACCESS read-write
    STATUS     current
    DESCRIPTION
            "-- empty --"
    ::= { lcsSetupIeee80211uAnqpProfilesEntry 4 }

-- {COLUMN} 1.3.6.1.4.1.2356.11.2.71.1.1.5
lcsSetupIeee80211uAnqpProfilesEntryNaiRealmList OBJECT-TYPE
    SYNTAX     DisplayString (SIZE(0..65))
    MAX-ACCESS read-write
    STATUS     current
    DESCRIPTION
            "-- empty --"
    ::= { lcsSetupIeee80211uAnqpProfilesEntry 5 }

-- {COLUMN} 1.3.6.1.4.1.2356.11.2.71.1.1.6
lcsSetupIeee80211uAnqpProfilesEntryCellularList OBJECT-TYPE
    SYNTAX     DisplayString (SIZE(0..65))
    MAX-ACCESS read-write
    STATUS     current
    DESCRIPTION
            "-- empty --"
    ::= { lcsSetupIeee80211uAnqpProfilesEntry 6 }

-- {COLUMN} 1.3.6.1.4.1.2356.11.2.71.1.1.7
lcsSetupIeee80211uAnqpProfilesEntryNetworkAuthTypeList OBJECT-TYPE
    SYNTAX     DisplayString (SIZE(0..65))
    MAX-ACCESS read-write
    STATUS     current
    DESCRIPTION
            "-- empty --"
    ::= { lcsSetupIeee80211uAnqpProfilesEntry 7 }

-- {TABLE} 1.3.6.1.4.1.2356.11.2.71.3
lcsSetupIeee80211uVenueNameTable OBJECT-TYPE
    SYNTAX     SEQUENCE OF LcsSetupIeee80211uVenueNameEntry
    MAX-ACCESS not-accessible
    STATUS     current
    DESCRIPTION
            "-- empty --"
    ::= { lcsSetupIeee80211u 3 }

-- {ROW} 1.3.6.1.4.1.2356.11.2.71.3.1
lcsSetupIeee80211uVenueNameEntry OBJECT-TYPE
    SYNTAX     LcsSetupIeee80211uVenueNameEntry
    MAX-ACCESS not-accessible
    STATUS     current
    DESCRIPTION
            ""
    INDEX {
            lcsSetupIeee80211uVenueNameEntryName,
            lcsSetupIeee80211uVenueNameEntryLanguage
          }
    ::= { lcsSetupIeee80211uVenueNameTable 1 }

LcsSetupIeee80211uVenueNameEntry ::= SEQUENCE {
            lcsSetupIeee80211uVenueNameEntryName DisplayString,
            lcsSetupIeee80211uVenueNameEntryVenueName DisplayString,
            lcsSetupIeee80211uVenueNameEntryLanguage INTEGER
    }

-- {COLUMN} 1.3.6.1.4.1.2356.11.2.71.3.1.1
lcsSetupIeee80211uVenueNameEntryName OBJECT-TYPE
    SYNTAX     DisplayString (SIZE(0..32))
    MAX-ACCESS read-write
    STATUS     current
    DESCRIPTION
            "-- empty --"
    ::= { lcsSetupIeee80211uVenueNameEntry 1 }

-- {COLUMN} 1.3.6.1.4.1.2356.11.2.71.3.1.2
lcsSetupIeee80211uVenueNameEntryVenueName OBJECT-TYPE
    SYNTAX     DisplayString (SIZE(0..65))
    MAX-ACCESS read-write
    STATUS     current
    DESCRIPTION
            "-- empty --"
    ::= { lcsSetupIeee80211uVenueNameEntry 2 }

-- {COLUMN} 1.3.6.1.4.1.2356.11.2.71.3.1.3
lcsSetupIeee80211uVenueNameEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13),
                  eKorean (14)
            }
    MAX-ACCESS read-write
    STATUS     current
    DESCRIPTION
            "-- empty --"
    ::= { lcsSetupIeee80211uVenueNameEntry 3 }

-- {TABLE} 1.3.6.1.4.1.2356.11.2.71.4
lcsSetupIeee80211uCellularNetworkInformationListTable OBJECT-TYPE
    SYNTAX     SEQUENCE OF LcsSetupIeee80211uCellularNetworkInformationListEntry
    MAX-ACCESS not-accessible
    STATUS     current
    DESCRIPTION
            "-- empty --"
    ::= { lcsSetupIeee80211u 4 }

-- {ROW} 1.3.6.1.4.1.2356.11.2.71.4.1
lcsSetupIeee80211uCellularNetworkInformationListEntry OBJECT-TYPE
    SYNTAX     LcsSetupIeee80211uCellularNetworkInformationListEntry
    MAX-ACCESS not-accessible
    STATUS     current
    DESCRIPTION
            ""
    INDEX {
            lcsSetupIeee80211uCellularNetworkInformationListEntryName
          }
    ::= { lcsSetupIeee80211uCellularNetworkInformationListTable 1 }

LcsSetupIeee80211uCellularNetworkInformationListEntry ::= SEQUENCE {
            lcsSetupIeee80211uCellularNetworkInformationListEntryName DisplayString,
            lcsSetupIeee80211uCellularNetworkInformationListEntryCountryCode DisplayString,
            lcsSetupIeee80211uCellularNetworkInformationListEntryNetworkCode DisplayString
    }

-- {COLUMN} 1.3.6.1.4.1.2356.11.2.71.4.1.1
lcsSetupIeee80211uCellularNetworkInformationListEntryName OBJECT-TYPE
    SYNTAX     DisplayString (SIZE(0..32))
    MAX-ACCESS read-write
    STATUS     current
    DESCRIPTION
            "-- empty --"
    ::= { lcsSetupIeee80211uCellularNetworkInformationListEntry 1 }

-- {COLUMN} 1.3.6.1.4.1.2356.11.2.71.4.1.2
lcsSetupIeee80211uCellularNetworkInformationListEntryCountryCode OBJECT-TYPE
    SYNTAX     DisplayString (SIZE(0..3))
    MAX-ACCESS read-write
    STATUS     current
    DESCRIPTION
            "-- empty --"
    ::= { lcsSetupIeee80211uCellularNetworkInformationListEntry 2 }

-- {COLUMN} 1.3.6.1.4.1.2356.11.2.71.4.1.3
lcsSetupIeee80211uCellularNetworkInformationListEntryNetworkCode OBJECT-TYPE
    SYNTAX     DisplayString (SIZE(0..3))
    MAX-ACCESS read-write
    STATUS     current
    DESCRIPTION
            "-- empty --"
    ::= { lcsSetupIeee80211uCellularNetworkInformationListEntry 3 }

-- {TABLE} 1.3.6.1.4.1.2356.11.2.71.5
lcsSetupIeee80211uNetworkAuthenticationTypeTable OBJECT-TYPE
    SYNTAX     SEQUENCE OF LcsSetupIeee80211uNetworkAuthenticationTypeEntry
    MAX-ACCESS not-accessible
    STATUS     current
    DESCRIPTION
            "-- empty --"
    ::= { lcsSetupIeee80211u 5 }

-- {ROW} 1.3.6.1.4.1.2356.11.2.71.5.1
lcsSetupIeee80211uNetworkAuthenticationTypeEntry OBJECT-TYPE
    SYNTAX     LcsSetupIeee80211uNetworkAuthenticationTypeEntry
    MAX-ACCESS not-accessible
    STATUS     current
    DESCRIPTION
            ""
    INDEX {
            lcsSetupIeee80211uNetworkAuthenticationTypeEntryName
          }
    ::= { lcsSetupIeee80211uNetworkAuthenticationTypeTable 1 }

LcsSetupIeee80211uNetworkAuthenticationTypeEntry ::= SEQUENCE {
            lcsSetupIeee80211uNetworkAuthenticationTypeEntryNetworkAuthType INTEGER,
            lcsSetupIeee80211uNetworkAuthenticationTypeEntryRedirectUrl DisplayString,
            lcsSetupIeee80211uNetworkAuthenticationTypeEntryName DisplayString
    }

-- {COLUMN} 1.3.6.1.4.1.2356.11.2.71.5.1.1
lcsSetupIeee80211uNetworkAuthenticationTypeEntryNetworkAuthType OBJECT-TYPE
    SYNTAX     INTEGER {
                  eAcceptTermsCond (0),
                  eOnlineEnrollment (1),
                  eHttpRedirection (2),
                  eDnsRedirection (3)
            }
    MAX-ACCESS read-write
    STATUS     current
    DESCRIPTION
            "-- empty --"
    ::= { lcsSetupIeee80211uNetworkAuthenticationTypeEntry 1 }

-- {COLUMN} 1.3.6.1.4.1.2356.11.2.71.5.1.2
lcsSetupIeee80211uNetworkAuthenticationTypeEntryRedirectUrl OBJECT-TYPE
    SYNTAX     DisplayString (SIZE(0..65))
    MAX-ACCESS read-write
    STATUS     current
    DESCRIPTION
            "-- empty --"
    ::= { lcsSetupIeee80211uNetworkAuthenticationTypeEntry 2 }

-- {COLUMN} 1.3.6.1.4.1.2356.11.2.71.5.1.3
lcsSetupIeee80211uNetworkAuthenticationTypeEntryName OBJECT-TYPE
    SYNTAX     DisplayString (SIZE(0..32))
    MAX-ACCESS read-write
    STATUS     current
    DESCRIPTION
            "-- empty --"
    ::= { lcsSetupIeee80211uNetworkAuthenticationTypeEntry 3 }

-- {NODE} 1.3.6.1.4.1.2356.11.2.71.6
lcsSetupIeee80211uAnqpGeneral OBJECT IDENTIFIER ::= { lcsSetupIeee80211u 6 }

-- {SCALAR} 1.3.6.1.4.1.2356.11.2.71.6.1
lcsSetupIeee80211uAnqpGeneralVenueGroup OBJECT-TYPE
    SYNTAX     INTEGER {
                  eUnspecified (0),
                  eAssembly (1),
                  eBusiness (2),
                  eEducational (3),
                  eFactoryAndIndustrial (4),
                  eInstitutional (5),
                  eMercantile (6),
                  eResindential (7),
                  eStorage (8),
                  eUtilityAndMiscellaneous (9),
                  eVehicular (10),
                  eOutdoor (11)
            }
    MAX-ACCESS read-write
    STATUS     current
    DESCRIPTION
            "-- empty --"
    ::= { lcsSetupIeee80211uAnqpGeneral 1 }

-- {SCALAR} 1.3.6.1.4.1.2356.11.2.71.6.2
lcsSetupIeee80211uAnqpGeneralVenueType OBJECT-TYPE
    SYNTAX     Integer32 (0..255)
    MAX-ACCESS read-write
    STATUS     current
    DESCRIPTION
            "-- empty --"
    ::= { lcsSetupIeee80211uAnqpGeneral 2 }

-- {SCALAR} 1.3.6.1.4.1.2356.11.2.71.6.5
lcsSetupIeee80211uAnqpGeneralIpv4AddrType OBJECT-TYPE
    SYNTAX     INTEGER {
                  eNotAvailable (0),
                  ePublicAddrAvailable (1),
                  ePortRestrAddrAvail (2),
                  eSingleNatPrivAddrAvail (3),
                  eDoubleNatPrivAddrAvail (4),
                  ePortRestrSingleNatAddrAvail (5),
                  ePortRestrDoubleNatAddrAvail (6),
                  eAvailabilityNotKnown (7)
            }
    MAX-ACCESS read-write
    STATUS     current
    DESCRIPTION
            "-- empty --"
    ::= { lcsSetupIeee80211uAnqpGeneral 5 }

-- {SCALAR} 1.3.6.1.4.1.2356.11.2.71.6.6
lcsSetupIeee80211uAnqpGeneralIpv6AddrType OBJECT-TYPE
    SYNTAX     INTEGER {
                  eNotAvailable (0),
                  eAvailable (1),
                  eAvailabilityNotKnown (2)
            }
    MAX-ACCESS read-write
    STATUS     current
    DESCRIPTION
            "-- empty --"
    ::= { lcsSetupIeee80211uAnqpGeneral 6 }

-- {NODE} 1.3.6.1.4.1.2356.11.2.71.7
lcsSetupIeee80211uHotspot20 OBJECT IDENTIFIER ::= { lcsSetupIeee80211u 7 }

-- {TABLE} 1.3.6.1.4.1.2356.11.2.71.7.1
lcsSetupIeee80211uHotspot20OperatorListTable OBJECT-TYPE
    SYNTAX     SEQUENCE OF LcsSetupIeee80211uHotspot20OperatorListEntry
    MAX-ACCESS not-accessible
    STATUS     current
    DESCRIPTION
            "-- empty --"
    ::= { lcsSetupIeee80211uHotspot20 1 }

-- {ROW} 1.3.6.1.4.1.2356.11.2.71.7.1.1
lcsSetupIeee80211uHotspot20OperatorListEntry OBJECT-TYPE
    SYNTAX     LcsSetupIeee80211uHotspot20OperatorListEntry
    MAX-ACCESS not-accessible
    STATUS     current
    DESCRIPTION
            ""
    INDEX {
            lcsSetupIeee80211uHotspot20OperatorListEntryName,
            lcsSetupIeee80211uHotspot20OperatorListEntryLanguage
          }
    ::= { lcsSetupIeee80211uHotspot20OperatorListTable 1 }

LcsSetupIeee80211uHotspot20OperatorListEntry ::= SEQUENCE {
            lcsSetupIeee80211uHotspot20OperatorListEntryName DisplayString,
            lcsSetupIeee80211uHotspot20OperatorListEntryOperatorName DisplayString,
            lcsSetupIeee80211uHotspot20OperatorListEntryLanguage INTEGER
    }

-- {COLUMN} 1.3.6.1.4.1.2356.11.2.71.7.1.1.1
lcsSetupIeee80211uHotspot20OperatorListEntryName OBJECT-TYPE
    SYNTAX     DisplayString (SIZE(0..32))
    MAX-ACCESS read-write
    STATUS     current
    DESCRIPTION
            "-- empty --"
    ::= { lcsSetupIeee80211uHotspot20OperatorListEntry 1 }

-- {COLUMN} 1.3.6.1.4.1.2356.11.2.71.7.1.1.2
lcsSetupIeee80211uHotspot20OperatorListEntryOperatorName OBJECT-TYPE
    SYNTAX     DisplayString (SIZE(0..65))
    MAX-ACCESS read-write
    STATUS     current
    DESCRIPTION
            "-- empty --"
    ::= { lcsSetupIeee80211uHotspot20OperatorListEntry 2 }

-- {COLUMN} 1.3.6.1.4.1.2356.11.2.71.7.1.1.4
lcsSetupIeee80211uHotspot20OperatorListEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13),
                  eKorean (14)
            }
    MAX-ACCESS read-write
    STATUS     current
    DESCRIPTION
            "-- empty --"
    ::= { lcsSetupIeee80211uHotspot20OperatorListEntry 4 }

-- {TABLE} 1.3.6.1.4.1.2356.11.2.71.7.2
lcsSetupIeee80211uHotspot20ConnectionCapabilityTable OBJECT-TYPE
    SYNTAX     SEQUENCE OF LcsSetupIeee80211uHotspot20ConnectionCapabilityEntry
    MAX-ACCESS not-accessible
    STATUS     current
    DESCRIPTION
            "-- empty --"
    ::= { lcsSetupIeee80211uHotspot20 2 }

-- {ROW} 1.3.6.1.4.1.2356.11.2.71.7.2.1
lcsSetupIeee80211uHotspot20ConnectionCapabilityEntry OBJECT-TYPE
    SYNTAX     LcsSetupIeee80211uHotspot20ConnectionCapabilityEntry
    MAX-ACCESS not-accessible
    STATUS     current
    DESCRIPTION
            ""
    INDEX {
            lcsSetupIeee80211uHotspot20ConnectionCapabilityEntryName
          }
    ::= { lcsSetupIeee80211uHotspot20ConnectionCapabilityTable 1 }

LcsSetupIeee80211uHotspot20ConnectionCapabilityEntry ::= SEQUENCE {
            lcsSetupIeee80211uHotspot20ConnectionCapabilityEntryName DisplayString
    }

-- {COLUMN} 1.3.6.1.4.1.2356.11.2.71.7.2.1.4
lcsSetupIeee80211uHotspot20ConnectionCapabilityEntryName OBJECT-TYPE
    SYNTAX     DisplayString (SIZE(0..32))
    MAX-ACCESS read-only
    STATUS     current
    DESCRIPTION
            "-- empty --"
    ::= { lcsSetupIeee80211uHotspot20ConnectionCapabilityEntry 4 }

-- {SCALAR} 1.3.6.1.4.1.2356.11.2.71.7.4
lcsSetupIeee80211uHotspot20LinkStatus OBJECT-TYPE
    SYNTAX     INTEGER {
                  eAuto (0),
                  eLinkUp (1),
                  eLinkDown (2),
                  eLinkTest (3)
            }
    MAX-ACCESS read-write
    STATUS     current
    DESCRIPTION
            "-- empty --"
    ::= { lcsSetupIeee80211uHotspot20 4 }

-- {SCALAR} 1.3.6.1.4.1.2356.11.2.71.7.7
lcsSetupIeee80211uHotspot20DownlinkSpeed OBJECT-TYPE
    SYNTAX     Integer32 (0..2147483647)
    MAX-ACCESS read-write
    STATUS     current
    DESCRIPTION
            "-- empty --"
    ::= { lcsSetupIeee80211uHotspot20 7 }

-- {SCALAR} 1.3.6.1.4.1.2356.11.2.71.7.8
lcsSetupIeee80211uHotspot20UplinkSpeed OBJECT-TYPE
    SYNTAX     Integer32 (0..2147483647)
    MAX-ACCESS read-write
    STATUS     current
    DESCRIPTION
            "-- empty --"
    ::= { lcsSetupIeee80211uHotspot20 8 }

-- {TABLE} 1.3.6.1.4.1.2356.11.2.71.7.9
lcsSetupIeee80211uHotspot20Hotspot20ProfilesTable OBJECT-TYPE
    SYNTAX     SEQUENCE OF LcsSetupIeee80211uHotspot20Hotspot20ProfilesEntry
    MAX-ACCESS not-accessible
    STATUS     current
    DESCRIPTION
            "-- empty --"
    ::= { lcsSetupIeee80211uHotspot20 9 }

-- {ROW} 1.3.6.1.4.1.2356.11.2.71.7.9.1
lcsSetupIeee80211uHotspot20Hotspot20ProfilesEntry OBJECT-TYPE
    SYNTAX     LcsSetupIeee80211uHotspot20Hotspot20ProfilesEntry
    MAX-ACCESS not-accessible
    STATUS     current
    DESCRIPTION
            ""
    INDEX {
            lcsSetupIeee80211uHotspot20Hotspot20ProfilesEntryName
          }
    ::= { lcsSetupIeee80211uHotspot20Hotspot20ProfilesTable 1 }

LcsSetupIeee80211uHotspot20Hotspot20ProfilesEntry ::= SEQUENCE {
            lcsSetupIeee80211uHotspot20Hotspot20ProfilesEntryName DisplayString,
            lcsSetupIeee80211uHotspot20Hotspot20ProfilesEntryOperatorName DisplayString,
            lcsSetupIeee80211uHotspot20Hotspot20ProfilesEntryConnectCapabil DisplayString,
            lcsSetupIeee80211uHotspot20Hotspot20ProfilesEntryOperatingClass DisplayString,
            lcsSetupIeee80211uHotspot20Hotspot20ProfilesEntryHotspot20Rls INTEGER,
            lcsSetupIeee80211uHotspot20Hotspot20ProfilesEntryDomainId Integer32,
            lcsSetupIeee80211uHotspot20Hotspot20ProfilesEntryOsuNetworkName DisplayString,
            lcsSetupIeee80211uHotspot20Hotspot20ProfilesEntryOsuProviders DisplayString
    }

-- {COLUMN} 1.3.6.1.4.1.2356.11.2.71.7.9.1.1
lcsSetupIeee80211uHotspot20Hotspot20ProfilesEntryName OBJECT-TYPE
    SYNTAX     DisplayString (SIZE(0..32))
    MAX-ACCESS read-write
    STATUS     current
    DESCRIPTION
            "-- empty --"
    ::= { lcsSetupIeee80211uHotspot20Hotspot20ProfilesEntry 1 }

-- {COLUMN} 1.3.6.1.4.1.2356.11.2.71.7.9.1.2
lcsSetupIeee80211uHotspot20Hotspot20ProfilesEntryOperatorName OBJECT-TYPE
    SYNTAX     DisplayString (SIZE(0..65))
    MAX-ACCESS read-write
    STATUS     current
    DESCRIPTION
            "-- empty --"
    ::= { lcsSetupIeee80211uHotspot20Hotspot20ProfilesEntry 2 }

-- {COLUMN} 1.3.6.1.4.1.2356.11.2.71.7.9.1.3
lcsSetupIeee80211uHotspot20Hotspot20ProfilesEntryConnectCapabil OBJECT-TYPE
    SYNTAX     DisplayString (SIZE(0..250))
    MAX-ACCESS read-write
    STATUS     current
    DESCRIPTION
            "-- empty --"
    ::= { lcsSetupIeee80211uHotspot20Hotspot20ProfilesEntry 3 }

-- {COLUMN} 1.3.6.1.4.1.2356.11.2.71.7.9.1.4
lcsSetupIeee80211uHotspot20Hotspot20ProfilesEntryOperatingClass OBJECT-TYPE
    SYNTAX     DisplayString (SIZE(0..32))
    MAX-ACCESS read-write
    STATUS     current
    DESCRIPTION
            "-- empty --"
    ::= { lcsSetupIeee80211uHotspot20Hotspot20ProfilesEntry 4 }

-- {COLUMN} 1.3.6.1.4.1.2356.11.2.71.7.9.1.5
lcsSetupIeee80211uHotspot20Hotspot20ProfilesEntryHotspot20Rls OBJECT-TYPE
    SYNTAX     INTEGER {
                  eRelease1 (0),
                  eRelease2 (1)
            }
    MAX-ACCESS read-write
    STATUS     current
    DESCRIPTION
            "Hotspot2.0 Release"
    ::= { lcsSetupIeee80211uHotspot20Hotspot20ProfilesEntry 5 }

-- {COLUMN} 1.3.6.1.4.1.2356.11.2.71.7.9.1.6
lcsSetupIeee80211uHotspot20Hotspot20ProfilesEntryDomainId OBJECT-TYPE
    SYNTAX     Integer32 (0..65535)
    MAX-ACCESS read-write
    STATUS     current
    DESCRIPTION
            "-- empty --"
    ::= { lcsSetupIeee80211uHotspot20Hotspot20ProfilesEntry 6 }

-- {COLUMN} 1.3.6.1.4.1.2356.11.2.71.7.9.1.7
lcsSetupIeee80211uHotspot20Hotspot20ProfilesEntryOsuNetworkName OBJECT-TYPE
    SYNTAX     DisplayString (SIZE(0..32))
    MAX-ACCESS read-write
    STATUS     current
    DESCRIPTION
            "-- empty --"
    ::= { lcsSetupIeee80211uHotspot20Hotspot20ProfilesEntry 7 }

-- {COLUMN} 1.3.6.1.4.1.2356.11.2.71.7.9.1.8
lcsSetupIeee80211uHotspot20Hotspot20ProfilesEntryOsuProviders OBJECT-TYPE
    SYNTAX     DisplayString (SIZE(0..250))
    MAX-ACCESS read-write
    STATUS     current
    DESCRIPTION
            "-- empty --"
    ::= { lcsSetupIeee80211uHotspot20Hotspot20ProfilesEntry 8 }

-- {TABLE} 1.3.6.1.4.1.2356.11.2.71.7.10
lcsSetupIeee80211uHotspot20OsuProvidersTable OBJECT-TYPE
    SYNTAX     SEQUENCE OF LcsSetupIeee80211uHotspot20OsuProvidersEntry
    MAX-ACCESS not-accessible
    STATUS     current
    DESCRIPTION
            "-- empty --"
    ::= { lcsSetupIeee80211uHotspot20 10 }

-- {ROW} 1.3.6.1.4.1.2356.11.2.71.7.10.1
lcsSetupIeee80211uHotspot20OsuProvidersEntry OBJECT-TYPE
    SYNTAX     LcsSetupIeee80211uHotspot20OsuProvidersEntry
    MAX-ACCESS not-accessible
    STATUS     current
    DESCRIPTION
            ""
    INDEX {
            lcsSetupIeee80211uHotspot20OsuProvidersEntryName,
            lcsSetupIeee80211uHotspot20OsuProvidersEntryLanguage
          }
    ::= { lcsSetupIeee80211uHotspot20OsuProvidersTable 1 }

LcsSetupIeee80211uHotspot20OsuProvidersEntry ::= SEQUENCE {
            lcsSetupIeee80211uHotspot20OsuProvidersEntryName DisplayString,
            lcsSetupIeee80211uHotspot20OsuProvidersEntryLanguage INTEGER,
            lcsSetupIeee80211uHotspot20OsuProvidersEntryFriendlyName DisplayString,
            lcsSetupIeee80211uHotspot20OsuProvidersEntryOsuMethods DisplayString,
            lcsSetupIeee80211uHotspot20OsuProvidersEntryUri DisplayString,
            lcsSetupIeee80211uHotspot20OsuProvidersEntryNai DisplayString,
            lcsSetupIeee80211uHotspot20OsuProvidersEntryServiceDescription DisplayString,
            lcsSetupIeee80211uHotspot20OsuProvidersEntryIconFilename INTEGER,
            lcsSetupIeee80211uHotspot20OsuProvidersEntryIconLanguage INTEGER
    }

-- {COLUMN} 1.3.6.1.4.1.2356.11.2.71.7.10.1.1
lcsSetupIeee80211uHotspot20OsuProvidersEntryName OBJECT-TYPE
    SYNTAX     DisplayString (SIZE(0..32))
    MAX-ACCESS read-write
    STATUS     current
    DESCRIPTION
            "-- empty --"
    ::= { lcsSetupIeee80211uHotspot20OsuProvidersEntry 1 }

-- {COLUMN} 1.3.6.1.4.1.2356.11.2.71.7.10.1.2
lcsSetupIeee80211uHotspot20OsuProvidersEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13),
                  eKorean (14)
            }
    MAX-ACCESS read-write
    STATUS     current
    DESCRIPTION
            "-- empty --"
    ::= { lcsSetupIeee80211uHotspot20OsuProvidersEntry 2 }

-- {COLUMN} 1.3.6.1.4.1.2356.11.2.71.7.10.1.3
lcsSetupIeee80211uHotspot20OsuProvidersEntryFriendlyName OBJECT-TYPE
    SYNTAX     DisplayString (SIZE(0..250))
    MAX-ACCESS read-write
    STATUS     current
    DESCRIPTION
            "-- empty --"
    ::= { lcsSetupIeee80211uHotspot20OsuProvidersEntry 3 }

-- {COLUMN} 1.3.6.1.4.1.2356.11.2.71.7.10.1.4
lcsSetupIeee80211uHotspot20OsuProvidersEntryOsuMethods OBJECT-TYPE
    SYNTAX     DisplayString (SIZE(0..32))
    MAX-ACCESS read-write
    STATUS     current
    DESCRIPTION
            "-- empty --"
    ::= { lcsSetupIeee80211uHotspot20OsuProvidersEntry 4 }

-- {COLUMN} 1.3.6.1.4.1.2356.11.2.71.7.10.1.5
lcsSetupIeee80211uHotspot20OsuProvidersEntryUri OBJECT-TYPE
    SYNTAX     DisplayString (SIZE(0..128))
    MAX-ACCESS read-write
    STATUS     current
    DESCRIPTION
            "-- empty --"
    ::= { lcsSetupIeee80211uHotspot20OsuProvidersEntry 5 }

-- {COLUMN} 1.3.6.1.4.1.2356.11.2.71.7.10.1.6
lcsSetupIeee80211uHotspot20OsuProvidersEntryNai OBJECT-TYPE
    SYNTAX     DisplayString (SIZE(0..65))
    MAX-ACCESS read-write
    STATUS     current
    DESCRIPTION
            "-- empty --"
    ::= { lcsSetupIeee80211uHotspot20OsuProvidersEntry 6 }

-- {COLUMN} 1.3.6.1.4.1.2356.11.2.71.7.10.1.7
lcsSetupIeee80211uHotspot20OsuProvidersEntryServiceDescription OBJECT-TYPE
    SYNTAX     DisplayString (SIZE(0..64))
    MAX-ACCESS read-write
    STATUS     current
    DESCRIPTION
            "-- empty --"
    ::= { lcsSetupIeee80211uHotspot20OsuProvidersEntry 7 }

-- {COLUMN} 1.3.6.1.4.1.2356.11.2.71.7.10.1.8
lcsSetupIeee80211uHotspot20OsuProvidersEntryIconFilename OBJECT-TYPE
    SYNTAX     INTEGER {
                  eNone (0),
                  eOsuProvImg1 (1),
                  eOsuProvImg2 (2),
                  eOsuProvImg3 (3),
                  eOsuProvImg4 (4),
                  eOsuProvImg5 (5),
                  eOsuProvImg6 (6),
                  eOsuProvImg7 (7),
                  eOsuProvImg8 (8),
                  eOsuProvImg9 (9),
                  eOsuProvImg10 (10),
                  eOsuProvImg11 (11),
                  eOsuProvImg12 (12),
                  eOsuProvImg13 (13),
                  eOsuProvImg14 (14),
                  eOsuProvImg15 (15),
                  eOsuProvImg16 (16)
            }
    MAX-ACCESS read-write
    STATUS     current
    DESCRIPTION
            "-- empty --"
    ::= { lcsSetupIeee80211uHotspot20OsuProvidersEntry 8 }

-- {COLUMN} 1.3.6.1.4.1.2356.11.2.71.7.10.1.9
lcsSetupIeee80211uHotspot20OsuProvidersEntryIconLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13),
                  eKorean (14)
            }
    MAX-ACCESS read-write
    STATUS     current
    DESCRIPTION
            "-- empty --"
    ::= { lcsSetupIeee80211uHotspot20OsuProvidersEntry 9 }

-- {TABLE} 1.3.6.1.4.1.2356.11.2.71.7.11
lcsSetupIeee80211uHotspot20OsuMethodsTable OBJECT-TYPE
    SYNTAX     SEQUENCE OF LcsSetupIeee80211uHotspot20OsuMethodsEntry
    MAX-ACCESS not-accessible
    STATUS     current
    DESCRIPTION
            "-- empty --"
    ::= { lcsSetupIeee80211uHotspot20 11 }

-- {ROW} 1.3.6.1.4.1.2356.11.2.71.7.11.1
lcsSetupIeee80211uHotspot20OsuMethodsEntry OBJECT-TYPE
    SYNTAX     LcsSetupIeee80211uHotspot20OsuMethodsEntry
    MAX-ACCESS not-accessible
    STATUS     current
    DESCRIPTION
            ""
    INDEX {
            lcsSetupIeee80211uHotspot20OsuMethodsEntryMethod
          }
    ::= { lcsSetupIeee80211uHotspot20OsuMethodsTable 1 }

LcsSetupIeee80211uHotspot20OsuMethodsEntry ::= SEQUENCE {
            lcsSetupIeee80211uHotspot20OsuMethodsEntryMethod DisplayString
    }

-- {COLUMN} 1.3.6.1.4.1.2356.11.2.71.7.11.1.1
lcsSetupIeee80211uHotspot20OsuMethodsEntryMethod OBJECT-TYPE
    SYNTAX     DisplayString (SIZE(0..32))
    MAX-ACCESS read-only
    STATUS     current
    DESCRIPTION
            "-- empty --"
    ::= { lcsSetupIeee80211uHotspot20OsuMethodsEntry 1 }

-- {SCALAR} 1.3.6.1.4.1.2356.11.2.71.7.12
lcsSetupIeee80211uHotspot20LoadMeasDuration OBJECT-TYPE
    SYNTAX     Integer32 (0..65535)
    MAX-ACCESS read-write
    STATUS     current
    DESCRIPTION
            "-- empty --"
    ::= { lcsSetupIeee80211uHotspot20 12 }

-- {TABLE} 1.3.6.1.4.1.2356.11.2.71.8
lcsSetupIeee80211uAuthParameterTable OBJECT-TYPE
    SYNTAX     SEQUENCE OF LcsSetupIeee80211uAuthParameterEntry
    MAX-ACCESS not-accessible
    STATUS     current
    DESCRIPTION
            "-- empty --"
    ::= { lcsSetupIeee80211u 8 }

-- {ROW} 1.3.6.1.4.1.2356.11.2.71.8.1
lcsSetupIeee80211uAuthParameterEntry OBJECT-TYPE
    SYNTAX     LcsSetupIeee80211uAuthParameterEntry
    MAX-ACCESS not-accessible
    STATUS     current
    DESCRIPTION
            ""
    INDEX {
            lcsSetupIeee80211uAuthParameterEntryName
          }
    ::= { lcsSetupIeee80211uAuthParameterTable 1 }

LcsSetupIeee80211uAuthParameterEntry ::= SEQUENCE {
            lcsSetupIeee80211uAuthParameterEntryName DisplayString
    }

-- {COLUMN} 1.3.6.1.4.1.2356.11.2.71.8.1.1
lcsSetupIeee80211uAuthParameterEntryName OBJECT-TYPE
    SYNTAX     DisplayString (SIZE(0..32))
    MAX-ACCESS read-only
    STATUS     current
    DESCRIPTION
            "-- empty --"
    ::= { lcsSetupIeee80211uAuthParameterEntry 1 }

-- {TABLE} 1.3.6.1.4.1.2356.11.2.71.9
lcsSetupIeee80211uNaiRealmsTable OBJECT-TYPE
    SYNTAX     SEQUENCE OF LcsSetupIeee80211uNaiRealmsEntry
    MAX-ACCESS not-accessible
    STATUS     current
    DESCRIPTION
            "-- empty --"
    ::= { lcsSetupIeee80211u 9 }

-- {ROW} 1.3.6.1.4.1.2356.11.2.71.9.1
lcsSetupIeee80211uNaiRealmsEntry OBJECT-TYPE
    SYNTAX     LcsSetupIeee80211uNaiRealmsEntry
    MAX-ACCESS not-accessible
    STATUS     current
    DESCRIPTION
            ""
    INDEX {
            lcsSetupIeee80211uNaiRealmsEntryName
          }
    ::= { lcsSetupIeee80211uNaiRealmsTable 1 }

LcsSetupIeee80211uNaiRealmsEntry ::= SEQUENCE {
            lcsSetupIeee80211uNaiRealmsEntryName DisplayString,
            lcsSetupIeee80211uNaiRealmsEntryNaiRealm DisplayString,
            lcsSetupIeee80211uNaiRealmsEntryEapMethod INTEGER,
            lcsSetupIeee80211uNaiRealmsEntryAuthParameter DisplayString
    }

-- {COLUMN} 1.3.6.1.4.1.2356.11.2.71.9.1.1
lcsSetupIeee80211uNaiRealmsEntryName OBJECT-TYPE
    SYNTAX     DisplayString (SIZE(0..32))
    MAX-ACCESS read-write
    STATUS     current
    DESCRIPTION
            "-- empty --"
    ::= { lcsSetupIeee80211uNaiRealmsEntry 1 }

-- {COLUMN} 1.3.6.1.4.1.2356.11.2.71.9.1.2
lcsSetupIeee80211uNaiRealmsEntryNaiRealm OBJECT-TYPE
    SYNTAX     DisplayString (SIZE(0..32))
    MAX-ACCESS read-write
    STATUS     current
    DESCRIPTION
            "-- empty --"
    ::= { lcsSetupIeee80211uNaiRealmsEntry 2 }

-- {COLUMN} 1.3.6.1.4.1.2356.11.2.71.9.1.3
lcsSetupIeee80211uNaiRealmsEntryEapMethod OBJECT-TYPE
    SYNTAX     INTEGER {
                  eNone (0),
                  eEapTls (13),
                  eEapSim (18),
                  eEapTtls (21),
                  eEapAka (23)
            }
    MAX-ACCESS read-write
    STATUS     current
    DESCRIPTION
            "-- empty --"
    ::= { lcsSetupIeee80211uNaiRealmsEntry 3 }

-- {COLUMN} 1.3.6.1.4.1.2356.11.2.71.9.1.4
lcsSetupIeee80211uNaiRealmsEntryAuthParameter OBJECT-TYPE
    SYNTAX     DisplayString (SIZE(0..65))
    MAX-ACCESS read-write
    STATUS     current
    DESCRIPTION
            "-- empty --"
    ::= { lcsSetupIeee80211uNaiRealmsEntry 4 }

-- {NODE} 1.3.6.1.4.1.2356.11.2.82
lcsSetupCrypto OBJECT IDENTIFIER ::= { lcsSetup 82 }

-- {NODE} 1.3.6.1.4.1.2356.11.2.82.1
lcsSetupCryptoRng OBJECT IDENTIFIER ::= { lcsSetupCrypto 1 }

-- {SCALAR} 1.3.6.1.4.1.2356.11.2.82.1.1
lcsSetupCryptoRngSeed OBJECT-TYPE
    SYNTAX     DisplayString
    MAX-ACCESS read-write
    STATUS     current
    DESCRIPTION
            "-- empty --"
    ::= { lcsSetupCryptoRng 1 }

-- {SCALAR} 1.3.6.1.4.1.2356.11.2.82.1.2
lcsSetupCryptoRngReseed OBJECT-TYPE
    SYNTAX     DisplayString
    MAX-ACCESS read-write
    STATUS     current
    DESCRIPTION
            "-- empty --"
    ::= { lcsSetupCryptoRng 2 }

-- {SCALAR} 1.3.6.1.4.1.2356.11.2.82.1.3
lcsSetupCryptoRngReset OBJECT-TYPE
    SYNTAX     DisplayString
    MAX-ACCESS read-write
    STATUS     current
    DESCRIPTION
            "-- empty --"
    ::= { lcsSetupCryptoRng 3 }

-- {SCALAR} 1.3.6.1.4.1.2356.11.2.82.1.4
lcsSetupCryptoRngWriteInterval OBJECT-TYPE
    SYNTAX     Integer32 (0..2147483647)
    MAX-ACCESS read-write
    STATUS     current
    DESCRIPTION
            "-- empty --"
    ::= { lcsSetupCryptoRng 4 }

-- {NODE} 1.3.6.1.4.1.2356.11.2.83
lcsSetupSms OBJECT IDENTIFIER ::= { lcsSetup 83 }

-- {SCALAR} 1.3.6.1.4.1.2356.11.2.83.1
lcsSetupSmsSmscAddress OBJECT-TYPE
    SYNTAX     DisplayString (SIZE(0..31))
    MAX-ACCESS read-write
    STATUS     current
    DESCRIPTION
            "-- empty --"
    ::= { lcsSetupSms 1 }

-- {SCALAR} 1.3.6.1.4.1.2356.11.2.83.2
lcsSetupSmsInboxLimit OBJECT-TYPE
    SYNTAX     Integer32 (0..2147483647)
    MAX-ACCESS read-write
    STATUS     current
    DESCRIPTION
            "-- empty --"
    ::= { lcsSetupSms 2 }

-- {SCALAR} 1.3.6.1.4.1.2356.11.2.83.3
lcsSetupSmsOutboxLimit OBJECT-TYPE
    SYNTAX     Integer32 (0..2147483647)
    MAX-ACCESS read-write
    STATUS     current
    DESCRIPTION
            "-- empty --"
    ::= { lcsSetupSms 3 }

-- {SCALAR} 1.3.6.1.4.1.2356.11.2.83.4
lcsSetupSmsOutboxPreservation OBJECT-TYPE
    SYNTAX     INTEGER {
                  eNone (0),
                  eUnconfirmed (1),
                  eAll (2)
            }
    MAX-ACCESS read-write
    STATUS     current
    DESCRIPTION
            "-- empty --"
    ::= { lcsSetupSms 4 }

-- {SCALAR} 1.3.6.1.4.1.2356.11.2.83.5
lcsSetupSmsMailForwardAddr OBJECT-TYPE
    SYNTAX     DisplayString (SIZE(0..63))
    MAX-ACCESS read-write
    STATUS     current
    DESCRIPTION
            "-- empty --"
    ::= { lcsSetupSms 5 }

-- {SCALAR} 1.3.6.1.4.1.2356.11.2.83.6
lcsSetupSmsSmsForwardAddr OBJECT-TYPE
    SYNTAX     DisplayString (SIZE(0..31))
    MAX-ACCESS read-write
    STATUS     current
    DESCRIPTION
            "-- empty --"
    ::= { lcsSetupSms 6 }

-- {SCALAR} 1.3.6.1.4.1.2356.11.2.83.7
lcsSetupSmsSmsForwardLimit OBJECT-TYPE
    SYNTAX     Integer32 (0..2147483647)
    MAX-ACCESS read-write
    STATUS     current
    DESCRIPTION
            "-- empty --"
    ::= { lcsSetupSms 7 }

-- {SCALAR} 1.3.6.1.4.1.2356.11.2.83.8
lcsSetupSmsSyslog OBJECT-TYPE
    SYNTAX     INTEGER {
                  eNo (0),
                  eSenderonly (1),
                  eFull (2)
            }
    MAX-ACCESS read-write
    STATUS     current
    DESCRIPTION
            "-- empty --"
    ::= { lcsSetupSms 8 }

-- {SCALAR} 1.3.6.1.4.1.2356.11.2.83.9
lcsSetupSmsMaxSendAttempts OBJECT-TYPE
    SYNTAX     Integer32 (0..2147483647)
    MAX-ACCESS read-write
    STATUS     current
    DESCRIPTION
            "-- empty --"
    ::= { lcsSetupSms 9 }

-- {NODE} 1.3.6.1.4.1.2356.11.2.88
lcsSetupWirelessEpaper OBJECT IDENTIFIER ::= { lcsSetup 88 }

-- {SCALAR} 1.3.6.1.4.1.2356.11.2.88.1
lcsSetupWirelessEpaperOperating OBJECT-TYPE
    SYNTAX     INTEGER {
                  eOff (0),
                  eManual (1),
                  eManaged (2)
            }
    MAX-ACCESS read-write
    STATUS     current
    DESCRIPTION
            "-- empty --"
    ::= { lcsSetupWirelessEpaper 1 }

-- {SCALAR} 1.3.6.1.4.1.2356.11.2.88.2
lcsSetupWirelessEpaperPort OBJECT-TYPE
    SYNTAX     Integer32 (0..65535)
    MAX-ACCESS read-write
    STATUS     current
    DESCRIPTION
            "-- empty --"
    ::= { lcsSetupWirelessEpaper 2 }

-- {SCALAR} 1.3.6.1.4.1.2356.11.2.88.3
lcsSetupWirelessEpaperChannel OBJECT-TYPE
    SYNTAX     INTEGER {
                  e2404mhz (0),
                  e2410mhz (1),
                  e2422mhz (2),
                  e2425mhz (3),
                  e2442mhz (4),
                  e2450mhz (5),
                  e2462mhz (6),
                  e2470mhz (7),
                  e2474mhz (8),
                  e2477mhz (9),
                  e2480mhz (10),
                  eAuto (255)
            }
    MAX-ACCESS read-write
    STATUS     current
    DESCRIPTION
            "-- empty --"
    ::= { lcsSetupWirelessEpaper 3 }

-- {NODE} 1.3.6.1.4.1.2356.11.2.88.4
lcsSetupWirelessEpaperCoord OBJECT IDENTIFIER ::= { lcsSetupWirelessEpaper 4 }

-- {SCALAR} 1.3.6.1.4.1.2356.11.2.88.4.1
lcsSetupWirelessEpaperCoordOperating OBJECT-TYPE
    SYNTAX     INTEGER {
                  eNo (0),
                  eYes (1)
            }
    MAX-ACCESS read-write
    STATUS     current
    DESCRIPTION
            "-- empty --"
    ::= { lcsSetupWirelessEpaperCoord 1 }

-- {SCALAR} 1.3.6.1.4.1.2356.11.2.88.4.2
lcsSetupWirelessEpaperCoordNetwork OBJECT-TYPE
    SYNTAX     DisplayString (SIZE(0..16))
    MAX-ACCESS read-write
    STATUS     current
    DESCRIPTION
            "-- empty --"
    ::= { lcsSetupWirelessEpaperCoord 2 }

-- {SCALAR} 1.3.6.1.4.1.2356.11.2.88.4.3
lcsSetupWirelessEpaperCoordAnnounceAddress OBJECT-TYPE
    SYNTAX     DisplayString (SIZE(0..39))
    MAX-ACCESS read-write
    STATUS     current
    DESCRIPTION
            "-- empty --"
    ::= { lcsSetupWirelessEpaperCoord 3 }

-- {SCALAR} 1.3.6.1.4.1.2356.11.2.88.4.4
lcsSetupWirelessEpaperCoordAnnouncePort OBJECT-TYPE
    SYNTAX     Integer32 (0..65535)
    MAX-ACCESS read-write
    STATUS     current
    DESCRIPTION
            "-- empty --"
    ::= { lcsSetupWirelessEpaperCoord 4 }

-- {SCALAR} 1.3.6.1.4.1.2356.11.2.88.4.5
lcsSetupWirelessEpaperCoordAnnounceInterval OBJECT-TYPE
    SYNTAX     Integer32 (0..2147483647)
    MAX-ACCESS read-write
    STATUS     current
    DESCRIPTION
            "-- empty --"
    ::= { lcsSetupWirelessEpaperCoord 5 }

-- {SCALAR} 1.3.6.1.4.1.2356.11.2.88.4.6
lcsSetupWirelessEpaperCoordAnnounceTimeoutFactor OBJECT-TYPE
    SYNTAX     Integer32 (0..65535)
    MAX-ACCESS read-write
    STATUS     current
    DESCRIPTION
            "-- empty --"
    ::= { lcsSetupWirelessEpaperCoord 6 }

-- {SCALAR} 1.3.6.1.4.1.2356.11.2.88.4.7
lcsSetupWirelessEpaperCoordAnnounceTimeoutInterval OBJECT-TYPE
    SYNTAX     Integer32 (0..2147483647)
    MAX-ACCESS read-write
    STATUS     current
    DESCRIPTION
            "-- empty --"
    ::= { lcsSetupWirelessEpaperCoord 7 }

-- {SCALAR} 1.3.6.1.4.1.2356.11.2.88.4.8
lcsSetupWirelessEpaperCoordAnnounceMasterBackoffInterval OBJECT-TYPE
    SYNTAX     Integer32 (0..255)
    MAX-ACCESS read-write
    STATUS     current
    DESCRIPTION
            "-- empty --"
    ::= { lcsSetupWirelessEpaperCoord 8 }

-- {SCALAR} 1.3.6.1.4.1.2356.11.2.88.4.9
lcsSetupWirelessEpaperCoordCoordinationPort OBJECT-TYPE
    SYNTAX     Integer32 (0..65535)
    MAX-ACCESS read-write
    STATUS     current
    DESCRIPTION
            "-- empty --"
    ::= { lcsSetupWirelessEpaperCoord 9 }

-- {SCALAR} 1.3.6.1.4.1.2356.11.2.88.4.10
lcsSetupWirelessEpaperCoordCoordinationKeepAliveInterval OBJECT-TYPE
    SYNTAX     Integer32 (0..2147483647)
    MAX-ACCESS read-write
    STATUS     current
    DESCRIPTION
            "-- empty --"
    ::= { lcsSetupWirelessEpaperCoord 10 }

-- {SCALAR} 1.3.6.1.4.1.2356.11.2.88.4.11
lcsSetupWirelessEpaperCoordCoordinationReconnectInterval OBJECT-TYPE
    SYNTAX     Integer32 (0..2147483647)
    MAX-ACCESS read-write
    STATUS     current
    DESCRIPTION
            "-- empty --"
    ::= { lcsSetupWirelessEpaperCoord 11 }

-- {SCALAR} 1.3.6.1.4.1.2356.11.2.88.4.12
lcsSetupWirelessEpaperCoordAssignmentSwitchThreshold OBJECT-TYPE
    SYNTAX     Integer32 (0..255)
    MAX-ACCESS read-write
    STATUS     current
    DESCRIPTION
            "-- empty --"
    ::= { lcsSetupWirelessEpaperCoord 12 }

-- {SCALAR} 1.3.6.1.4.1.2356.11.2.88.4.13
lcsSetupWirelessEpaperCoordAssessmentWlanDistanceWeight OBJECT-TYPE
    SYNTAX     Integer32 (0..255)
    MAX-ACCESS read-write
    STATUS     current
    DESCRIPTION
            "-- empty --"
    ::= { lcsSetupWirelessEpaperCoord 13 }

-- {SCALAR} 1.3.6.1.4.1.2356.11.2.88.4.14
lcsSetupWirelessEpaperCoordAssessmentPreferredChannelWeight OBJECT-TYPE
    SYNTAX     Integer32 (0..255)
    MAX-ACCESS read-write
    STATUS     current
    DESCRIPTION
            "-- empty --"
    ::= { lcsSetupWirelessEpaperCoord 14 }

-- {NODE} 1.3.6.1.4.1.2356.11.2.93
lcsSetupRoutProt OBJECT IDENTIFIER ::= { lcsSetup 93 }

-- {NODE} 1.3.6.1.4.1.2356.11.2.93.1
lcsSetupRoutProtBgp OBJECT IDENTIFIER ::= { lcsSetupRoutProt 1 }

-- {TABLE} 1.3.6.1.4.1.2356.11.2.93.1.1
lcsSetupRoutProtBgpBgpInstanceTable OBJECT-TYPE
    SYNTAX     SEQUENCE OF LcsSetupRoutProtBgpBgpInstanceEntry
    MAX-ACCESS not-accessible
    STATUS     current
    DESCRIPTION
            "-- empty --"
    ::= { lcsSetupRoutProtBgp 1 }

-- {ROW} 1.3.6.1.4.1.2356.11.2.93.1.1.1
lcsSetupRoutProtBgpBgpInstanceEntry OBJECT-TYPE
    SYNTAX     LcsSetupRoutProtBgpBgpInstanceEntry
    MAX-ACCESS not-accessible
    STATUS     current
    DESCRIPTION
            ""
    INDEX {
            lcsSetupRoutProtBgpBgpInstanceEntryName
          }
    ::= { lcsSetupRoutProtBgpBgpInstanceTable 1 }

LcsSetupRoutProtBgpBgpInstanceEntry ::= SEQUENCE {
            lcsSetupRoutProtBgpBgpInstanceEntryName DisplayString,
            lcsSetupRoutProtBgpBgpInstanceEntryOperating INTEGER,
            lcsSetupRoutProtBgpBgpInstanceEntryAsNumber Integer32,
            lcsSetupRoutProtBgpBgpInstanceEntryRouterId DisplayString,
            lcsSetupRoutProtBgpBgpInstanceEntrySyslog INTEGER,
            lcsSetupRoutProtBgpBgpInstanceEntryPort Integer32,
            lcsSetupRoutProtBgpBgpInstanceEntryComment DisplayString,
            lcsSetupRoutProtBgpBgpInstanceEntryCheckFirstAs INTEGER,
            lcsSetupRoutProtBgpBgpInstanceEntryAsPathLimit Integer32,
            lcsSetupRoutProtBgpBgpInstanceEntryClusterId DisplayString,
            lcsSetupRoutProtBgpBgpInstanceEntryRouteReflector INTEGER,
            lcsSetupRoutProtBgpBgpInstanceEntryTxLoopDetection INTEGER
    }

-- {COLUMN} 1.3.6.1.4.1.2356.11.2.93.1.1.1.1
lcsSetupRoutProtBgpBgpInstanceEntryName OBJECT-TYPE
    SYNTAX     DisplayString (SIZE(0..16))
    MAX-ACCESS read-write
    STATUS     current
    DESCRIPTION
            "-- empty --"
    ::= { lcsSetupRoutProtBgpBgpInstanceEntry 1 }

-- {COLUMN} 1.3.6.1.4.1.2356.11.2.93.1.1.1.2
lcsSetupRoutProtBgpBgpInstanceEntryOperating OBJECT-TYPE
    SYNTAX     INTEGER {
                  eNo (0),
                  eYes (1)
            }
    MAX-ACCESS read-write
    STATUS     current
    DESCRIPTION
            "-- empty --"
    ::= { lcsSetupRoutProtBgpBgpInstanceEntry 2 }

-- {COLUMN} 1.3.6.1.4.1.2356.11.2.93.1.1.1.3
lcsSetupRoutProtBgpBgpInstanceEntryAsNumber OBJECT-TYPE
    SYNTAX     Integer32 (0..2147483647)
    MAX-ACCESS read-write
    STATUS     current
    DESCRIPTION
            "-- empty --"
    ::= { lcsSetupRoutProtBgpBgpInstanceEntry 3 }

-- {COLUMN} 1.3.6.1.4.1.2356.11.2.93.1.1.1.4
lcsSetupRoutProtBgpBgpInstanceEntryRouterId OBJECT-TYPE
    SYNTAX     DisplayString (SIZE(0..15))
    MAX-ACCESS read-write
    STATUS     current
    DESCRIPTION
            "-- empty --"
    ::= { lcsSetupRoutProtBgpBgpInstanceEntry 4 }

-- {COLUMN} 1.3.6.1.4.1.2356.11.2.93.1.1.1.5
lcsSetupRoutProtBgpBgpInstanceEntrySyslog OBJECT-TYPE
    SYNTAX     INTEGER {
                  eNo (0),
                  eYes (1)
            }
    MAX-ACCESS read-write
    STATUS     current
    DESCRIPTION
            "-- empty --"
    ::= { lcsSetupRoutProtBgpBgpInstanceEntry 5 }

-- {COLUMN} 1.3.6.1.4.1.2356.11.2.93.1.1.1.6
lcsSetupRoutProtBgpBgpInstanceEntryPort OBJECT-TYPE
    SYNTAX     Integer32 (0..65535)
    MAX-ACCESS read-write
    STATUS     current
    DESCRIPTION
            "-- empty --"
    ::= { lcsSetupRoutProtBgpBgpInstanceEntry 6 }

-- {COLUMN} 1.3.6.1.4.1.2356.11.2.93.1.1.1.7
lcsSetupRoutProtBgpBgpInstanceEntryComment OBJECT-TYPE
    SYNTAX     DisplayString (SIZE(0..254))
    MAX-ACCESS read-write
    STATUS     current
    DESCRIPTION
            "-- empty --"
    ::= { lcsSetupRoutProtBgpBgpInstanceEntry 7 }

-- {COLUMN} 1.3.6.1.4.1.2356.11.2.93.1.1.1.8
lcsSetupRoutProtBgpBgpInstanceEntryCheckFirstAs OBJECT-TYPE
    SYNTAX     INTEGER {
                  eNo (0),
                  eYes (1)
            }
    MAX-ACCESS read-write
    STATUS     current
    DESCRIPTION
            "-- empty --"
    ::= { lcsSetupRoutProtBgpBgpInstanceEntry 8 }

-- {COLUMN} 1.3.6.1.4.1.2356.11.2.93.1.1.1.9
lcsSetupRoutProtBgpBgpInstanceEntryAsPathLimit OBJECT-TYPE
    SYNTAX     Integer32 (0..255)
    MAX-ACCESS read-write
    STATUS     current
    DESCRIPTION
            "-- empty --"
    ::= { lcsSetupRoutProtBgpBgpInstanceEntry 9 }

-- {COLUMN} 1.3.6.1.4.1.2356.11.2.93.1.1.1.10
lcsSetupRoutProtBgpBgpInstanceEntryClusterId OBJECT-TYPE
    SYNTAX     DisplayString (SIZE(0..15))
    MAX-ACCESS read-write
    STATUS     current
    DESCRIPTION
            "-- empty --"
    ::= { lcsSetupRoutProtBgpBgpInstanceEntry 10 }

-- {COLUMN} 1.3.6.1.4.1.2356.11.2.93.1.1.1.11
lcsSetupRoutProtBgpBgpInstanceEntryRouteReflector OBJECT-TYPE
    SYNTAX     INTEGER {
                  eNo (0),
                  eYes (1)
            }
    MAX-ACCESS read-write
    STATUS     current
    DESCRIPTION
            "-- empty --"
    ::= { lcsSetupRoutProtBgpBgpInstanceEntry 11 }

-- {COLUMN} 1.3.6.1.4.1.2356.11.2.93.1.1.1.12
lcsSetupRoutProtBgpBgpInstanceEntryTxLoopDetection OBJECT-TYPE
    SYNTAX     INTEGER {
                  eNo (0),
                  eYes (1)
            }
    MAX-ACCESS read-write
    STATUS     current
    DESCRIPTION
            "-- empty --"
    ::= { lcsSetupRoutProtBgpBgpInstanceEntry 12 }

-- {TABLE} 1.3.6.1.4.1.2356.11.2.93.1.2
lcsSetupRoutProtBgpNeighborsTable OBJECT-TYPE
    SYNTAX     SEQUENCE OF LcsSetupRoutProtBgpNeighborsEntry
    MAX-ACCESS not-accessible
    STATUS     current
    DESCRIPTION
            "-- empty --"
    ::= { lcsSetupRoutProtBgp 2 }

-- {ROW} 1.3.6.1.4.1.2356.11.2.93.1.2.1
lcsSetupRoutProtBgpNeighborsEntry OBJECT-TYPE
    SYNTAX     LcsSetupRoutProtBgpNeighborsEntry
    MAX-ACCESS not-accessible
    STATUS     current
    DESCRIPTION
            ""
    INDEX {
            lcsSetupRoutProtBgpNeighborsEntryIpAddress,
            lcsSetupRoutProtBgpNeighborsEntryPort,
            lcsSetupRoutProtBgpNeighborsEntryLoopbackAddress,
            lcsSetupRoutProtBgpNeighborsEntryRtgTag,
            lcsSetupRoutProtBgpNeighborsEntryRemoteAs
          }
    ::= { lcsSetupRoutProtBgpNeighborsTable 1 }

LcsSetupRoutProtBgpNeighborsEntry ::= SEQUENCE {
            lcsSetupRoutProtBgpNeighborsEntryIpAddress DisplayString,
            lcsSetupRoutProtBgpNeighborsEntryPort Integer32,
            lcsSetupRoutProtBgpNeighborsEntryLoopbackAddress DisplayString,
            lcsSetupRoutProtBgpNeighborsEntryRtgTag Integer32,
            lcsSetupRoutProtBgpNeighborsEntryRemoteAs Integer32,
            lcsSetupRoutProtBgpNeighborsEntryName DisplayString,
            lcsSetupRoutProtBgpNeighborsEntryOperating INTEGER,
            lcsSetupRoutProtBgpNeighborsEntryPassword DisplayString,
            lcsSetupRoutProtBgpNeighborsEntryNeighborProfile DisplayString,
            lcsSetupRoutProtBgpNeighborsEntryConnectionMode INTEGER,
            lcsSetupRoutProtBgpNeighborsEntryConnectionDelay Integer32,
            lcsSetupRoutProtBgpNeighborsEntryInstanceName DisplayString,
            lcsSetupRoutProtBgpNeighborsEntryInboundPolicy DisplayString,
            lcsSetupRoutProtBgpNeighborsEntryOutboundPolicy DisplayString,
            lcsSetupRoutProtBgpNeighborsEntryComment DisplayString,
            lcsSetupRoutProtBgpNeighborsEntryRouteReflectorClient INTEGER
    }

-- {COLUMN} 1.3.6.1.4.1.2356.11.2.93.1.2.1.1
lcsSetupRoutProtBgpNeighborsEntryIpAddress OBJECT-TYPE
    SYNTAX     DisplayString (SIZE(0..56))
    MAX-ACCESS read-write
    STATUS     current
    DESCRIPTION
            "-- empty --"
    ::= { lcsSetupRoutProtBgpNeighborsEntry 1 }

-- {COLUMN} 1.3.6.1.4.1.2356.11.2.93.1.2.1.2
lcsSetupRoutProtBgpNeighborsEntryPort OBJECT-TYPE
    SYNTAX     Integer32 (0..65535)
    MAX-ACCESS read-write
    STATUS     current
    DESCRIPTION
            "-- empty --"
    ::= { lcsSetupRoutProtBgpNeighborsEntry 2 }

-- {COLUMN} 1.3.6.1.4.1.2356.11.2.93.1.2.1.3
lcsSetupRoutProtBgpNeighborsEntryLoopbackAddress OBJECT-TYPE
    SYNTAX     DisplayString (SIZE(0..56))
    MAX-ACCESS read-write
    STATUS     current
    DESCRIPTION
            "-- empty --"
    ::= { lcsSetupRoutProtBgpNeighborsEntry 3 }

-- {COLUMN} 1.3.6.1.4.1.2356.11.2.93.1.2.1.4
lcsSetupRoutProtBgpNeighborsEntryRtgTag OBJECT-TYPE
    SYNTAX     Integer32 (0..65535)
    MAX-ACCESS read-write
    STATUS     current
    DESCRIPTION
            "-- empty --"
    ::= { lcsSetupRoutProtBgpNeighborsEntry 4 }

-- {COLUMN} 1.3.6.1.4.1.2356.11.2.93.1.2.1.5
lcsSetupRoutProtBgpNeighborsEntryRemoteAs OBJECT-TYPE
    SYNTAX     Integer32 (0..2147483647)
    MAX-ACCESS read-write
    STATUS     current
    DESCRIPTION
            "-- empty --"
    ::= { lcsSetupRoutProtBgpNeighborsEntry 5 }

-- {COLUMN} 1.3.6.1.4.1.2356.11.2.93.1.2.1.6
lcsSetupRoutProtBgpNeighborsEntryName OBJECT-TYPE
    SYNTAX     DisplayString (SIZE(0..16))
    MAX-ACCESS read-write
    STATUS     current
    DESCRIPTION
            "-- empty --"
    ::= { lcsSetupRoutProtBgpNeighborsEntry 6 }

-- {COLUMN} 1.3.6.1.4.1.2356.11.2.93.1.2.1.7
lcsSetupRoutProtBgpNeighborsEntryOperating OBJECT-TYPE
    SYNTAX     INTEGER {
                  eNo (0),
                  eYes (1)
            }
    MAX-ACCESS read-write
    STATUS     current
    DESCRIPTION
            "-- empty --"
    ::= { lcsSetupRoutProtBgpNeighborsEntry 7 }

-- {COLUMN} 1.3.6.1.4.1.2356.11.2.93.1.2.1.8
lcsSetupRoutProtBgpNeighborsEntryPassword OBJECT-TYPE
    SYNTAX     DisplayString (SIZE(0..16))
    MAX-ACCESS read-write
    STATUS     current
    DESCRIPTION
            "-- empty --"
    ::= { lcsSetupRoutProtBgpNeighborsEntry 8 }

-- {COLUMN} 1.3.6.1.4.1.2356.11.2.93.1.2.1.9
lcsSetupRoutProtBgpNeighborsEntryNeighborProfile OBJECT-TYPE
    SYNTAX     DisplayString (SIZE(0..16))
    MAX-ACCESS read-write
    STATUS     current
    DESCRIPTION
            "-- empty --"
    ::= { lcsSetupRoutProtBgpNeighborsEntry 9 }

-- {COLUMN} 1.3.6.1.4.1.2356.11.2.93.1.2.1.10
lcsSetupRoutProtBgpNeighborsEntryConnectionMode OBJECT-TYPE
    SYNTAX     INTEGER {
                  eActive (0),
                  ePassive (1),
                  eDelayed (2)
            }
    MAX-ACCESS read-write
    STATUS     current
    DESCRIPTION
            "-- empty --"
    ::= { lcsSetupRoutProtBgpNeighborsEntry 10 }

-- {COLUMN} 1.3.6.1.4.1.2356.11.2.93.1.2.1.11
lcsSetupRoutProtBgpNeighborsEntryConnectionDelay OBJECT-TYPE
    SYNTAX     Integer32 (0..65535)
    MAX-ACCESS read-write
    STATUS     current
    DESCRIPTION
            "-- empty --"
    ::= { lcsSetupRoutProtBgpNeighborsEntry 11 }

-- {COLUMN} 1.3.6.1.4.1.2356.11.2.93.1.2.1.12
lcsSetupRoutProtBgpNeighborsEntryInstanceName OBJECT-TYPE
    SYNTAX     DisplayString (SIZE(0..16))
    MAX-ACCESS read-write
    STATUS     current
    DESCRIPTION
            "-- empty --"
    ::= { lcsSetupRoutProtBgpNeighborsEntry 12 }

-- {COLUMN} 1.3.6.1.4.1.2356.11.2.93.1.2.1.13
lcsSetupRoutProtBgpNeighborsEntryInboundPolicy OBJECT-TYPE
    SYNTAX     DisplayString (SIZE(0..16))
    MAX-ACCESS read-write
    STATUS     current
    DESCRIPTION
            "-- empty --"
    ::= { lcsSetupRoutProtBgpNeighborsEntry 13 }

-- {COLUMN} 1.3.6.1.4.1.2356.11.2.93.1.2.1.14
lcsSetupRoutProtBgpNeighborsEntryOutboundPolicy OBJECT-TYPE
    SYNTAX     DisplayString (SIZE(0..16))
    MAX-ACCESS read-write
    STATUS     current
    DESCRIPTION
            "-- empty --"
    ::= { lcsSetupRoutProtBgpNeighborsEntry 14 }

-- {COLUMN} 1.3.6.1.4.1.2356.11.2.93.1.2.1.15
lcsSetupRoutProtBgpNeighborsEntryComment OBJECT-TYPE
    SYNTAX     DisplayString (SIZE(0..254))
    MAX-ACCESS read-write
    STATUS     current
    DESCRIPTION
            "-- empty --"
    ::= { lcsSetupRoutProtBgpNeighborsEntry 15 }

-- {COLUMN} 1.3.6.1.4.1.2356.11.2.93.1.2.1.16
lcsSetupRoutProtBgpNeighborsEntryRouteReflectorClient OBJECT-TYPE
    SYNTAX     INTEGER {
                  eNo (0),
                  eYes (1)
            }
    MAX-ACCESS read-write
    STATUS     current
    DESCRIPTION
            "-- empty --"
    ::= { lcsSetupRoutProtBgpNeighborsEntry 16 }

-- {TABLE} 1.3.6.1.4.1.2356.11.2.93.1.3
lcsSetupRoutProtBgpNeighborProfilesTable OBJECT-TYPE
    SYNTAX     SEQUENCE OF LcsSetupRoutProtBgpNeighborProfilesEntry
    MAX-ACCESS not-accessible
    STATUS     current
    DESCRIPTION
            "-- empty --"
    ::= { lcsSetupRoutProtBgp 3 }

-- {ROW} 1.3.6.1.4.1.2356.11.2.93.1.3.1
lcsSetupRoutProtBgpNeighborProfilesEntry OBJECT-TYPE
    SYNTAX     LcsSetupRoutProtBgpNeighborProfilesEntry
    MAX-ACCESS not-accessible
    STATUS     current
    DESCRIPTION
            ""
    INDEX {
            lcsSetupRoutProtBgpNeighborProfilesEntryName
          }
    ::= { lcsSetupRoutProtBgpNeighborProfilesTable 1 }

LcsSetupRoutProtBgpNeighborProfilesEntry ::= SEQUENCE {
            lcsSetupRoutProtBgpNeighborProfilesEntryName DisplayString,
            lcsSetupRoutProtBgpNeighborProfilesEntryRouteUpdateDelay Integer32,
            lcsSetupRoutProtBgpNeighborProfilesEntrySendTtl Integer32,
            lcsSetupRoutProtBgpNeighborProfilesEntryRecvTtl Integer32,
            lcsSetupRoutProtBgpNeighborProfilesEntryKeepalive Integer32,
            lcsSetupRoutProtBgpNeighborProfilesEntryHoldtime Integer32,
            lcsSetupRoutProtBgpNeighborProfilesEntryFilterPrivateAs INTEGER,
            lcsSetupRoutProtBgpNeighborProfilesEntryAsOverride INTEGER,
            lcsSetupRoutProtBgpNeighborProfilesEntrySoftReconfiguration INTEGER,
            lcsSetupRoutProtBgpNeighborProfilesEntryComment DisplayString,
            lcsSetupRoutProtBgpNeighborProfilesEntrySendDefaultRoute INTEGER,
            lcsSetupRoutProtBgpNeighborProfilesEntryConnectRetryTime Integer32
    }

-- {COLUMN} 1.3.6.1.4.1.2356.11.2.93.1.3.1.1
lcsSetupRoutProtBgpNeighborProfilesEntryName OBJECT-TYPE
    SYNTAX     DisplayString (SIZE(0..16))
    MAX-ACCESS read-write
    STATUS     current
    DESCRIPTION
            "-- empty --"
    ::= { lcsSetupRoutProtBgpNeighborProfilesEntry 1 }

-- {COLUMN} 1.3.6.1.4.1.2356.11.2.93.1.3.1.2
lcsSetupRoutProtBgpNeighborProfilesEntryRouteUpdateDelay OBJECT-TYPE
    SYNTAX     Integer32 (0..65535)
    MAX-ACCESS read-write
    STATUS     current
    DESCRIPTION
            "-- empty --"
    ::= { lcsSetupRoutProtBgpNeighborProfilesEntry 2 }

-- {COLUMN} 1.3.6.1.4.1.2356.11.2.93.1.3.1.3
lcsSetupRoutProtBgpNeighborProfilesEntrySendTtl OBJECT-TYPE
    SYNTAX     Integer32 (0..255)
    MAX-ACCESS read-write
    STATUS     current
    DESCRIPTION
            "-- empty --"
    ::= { lcsSetupRoutProtBgpNeighborProfilesEntry 3 }

-- {COLUMN} 1.3.6.1.4.1.2356.11.2.93.1.3.1.4
lcsSetupRoutProtBgpNeighborProfilesEntryRecvTtl OBJECT-TYPE
    SYNTAX     Integer32 (0..255)
    MAX-ACCESS read-write
    STATUS     current
    DESCRIPTION
            "-- empty --"
    ::= { lcsSetupRoutProtBgpNeighborProfilesEntry 4 }

-- {COLUMN} 1.3.6.1.4.1.2356.11.2.93.1.3.1.5
lcsSetupRoutProtBgpNeighborProfilesEntryKeepalive OBJECT-TYPE
    SYNTAX     Integer32 (0..65535)
    MAX-ACCESS read-write
    STATUS     current
    DESCRIPTION
            "-- empty --"
    ::= { lcsSetupRoutProtBgpNeighborProfilesEntry 5 }

-- {COLUMN} 1.3.6.1.4.1.2356.11.2.93.1.3.1.6
lcsSetupRoutProtBgpNeighborProfilesEntryHoldtime OBJECT-TYPE
    SYNTAX     Integer32 (0..65535)
    MAX-ACCESS read-write
    STATUS     current
    DESCRIPTION
            "-- empty --"
    ::= { lcsSetupRoutProtBgpNeighborProfilesEntry 6 }

-- {COLUMN} 1.3.6.1.4.1.2356.11.2.93.1.3.1.7
lcsSetupRoutProtBgpNeighborProfilesEntryFilterPrivateAs OBJECT-TYPE
    SYNTAX     INTEGER {
                  eNo (0),
                  eRemove (1),
                  eReplace (2)
            }
    MAX-ACCESS read-write
    STATUS     current
    DESCRIPTION
            "-- empty --"
    ::= { lcsSetupRoutProtBgpNeighborProfilesEntry 7 }

-- {COLUMN} 1.3.6.1.4.1.2356.11.2.93.1.3.1.8
lcsSetupRoutProtBgpNeighborProfilesEntryAsOverride OBJECT-TYPE
    SYNTAX     INTEGER {
                  eNo (0),
                  eYes (1)
            }
    MAX-ACCESS read-write
    STATUS     current
    DESCRIPTION
            "-- empty --"
    ::= { lcsSetupRoutProtBgpNeighborProfilesEntry 8 }

-- {COLUMN} 1.3.6.1.4.1.2356.11.2.93.1.3.1.9
lcsSetupRoutProtBgpNeighborProfilesEntrySoftReconfiguration OBJECT-TYPE
    SYNTAX     INTEGER {
                  eNo (0),
                  eYes (1)
            }
    MAX-ACCESS read-write
    STATUS     current
    DESCRIPTION
            "-- empty --"
    ::= { lcsSetupRoutProtBgpNeighborProfilesEntry 9 }

-- {COLUMN} 1.3.6.1.4.1.2356.11.2.93.1.3.1.10
lcsSetupRoutProtBgpNeighborProfilesEntryComment OBJECT-TYPE
    SYNTAX     DisplayString (SIZE(0..254))
    MAX-ACCESS read-write
    STATUS     current
    DESCRIPTION
            "-- empty --"
    ::= { lcsSetupRoutProtBgpNeighborProfilesEntry 10 }

-- {COLUMN} 1.3.6.1.4.1.2356.11.2.93.1.3.1.11
lcsSetupRoutProtBgpNeighborProfilesEntrySendDefaultRoute OBJECT-TYPE
    SYNTAX     INTEGER {
                  eNo (0),
                  eYes (1)
            }
    MAX-ACCESS read-write
    STATUS     current
    DESCRIPTION
            "-- empty --"
    ::= { lcsSetupRoutProtBgpNeighborProfilesEntry 11 }

-- {COLUMN} 1.3.6.1.4.1.2356.11.2.93.1.3.1.12
lcsSetupRoutProtBgpNeighborProfilesEntryConnectRetryTime OBJECT-TYPE
    SYNTAX     Integer32 (0..65535)
    MAX-ACCESS read-write
    STATUS     current
    DESCRIPTION
            "-- empty --"
    ::= { lcsSetupRoutProtBgpNeighborProfilesEntry 12 }

-- {NODE} 1.3.6.1.4.1.2356.11.2.93.1.4
lcsSetupRoutProtBgpAddressfamily OBJECT IDENTIFIER ::= { lcsSetupRoutProtBgp 4 }

-- {TABLE} 1.3.6.1.4.1.2356.11.2.93.1.4.1
lcsSetupRoutProtBgpAddressfamilyIpv4Table OBJECT-TYPE
    SYNTAX     SEQUENCE OF LcsSetupRoutProtBgpAddressfamilyIpv4Entry
    MAX-ACCESS not-accessible
    STATUS     current
    DESCRIPTION
            "-- empty --"
    ::= { lcsSetupRoutProtBgpAddressfamily 1 }

-- {ROW} 1.3.6.1.4.1.2356.11.2.93.1.4.1.1
lcsSetupRoutProtBgpAddressfamilyIpv4Entry OBJECT-TYPE
    SYNTAX     LcsSetupRoutProtBgpAddressfamilyIpv4Entry
    MAX-ACCESS not-accessible
    STATUS     current
    DESCRIPTION
            ""
    INDEX {
            lcsSetupRoutProtBgpAddressfamilyIpv4EntryNeighborProfile
          }
    ::= { lcsSetupRoutProtBgpAddressfamilyIpv4Table 1 }

LcsSetupRoutProtBgpAddressfamilyIpv4Entry ::= SEQUENCE {
            lcsSetupRoutProtBgpAddressfamilyIpv4EntryNeighborProfile DisplayString,
            lcsSetupRoutProtBgpAddressfamilyIpv4EntryRtgTag Integer32,
            lcsSetupRoutProtBgpAddressfamilyIpv4EntryOperating INTEGER,
            lcsSetupRoutProtBgpAddressfamilyIpv4EntryCommunities BITS,
            lcsSetupRoutProtBgpAddressfamilyIpv4EntryNexthopSelf INTEGER,
            lcsSetupRoutProtBgpAddressfamilyIpv4EntryWeight Integer32,
            lcsSetupRoutProtBgpAddressfamilyIpv4EntryLocalPref Integer32,
            lcsSetupRoutProtBgpAddressfamilyIpv4EntryPrefixLimit Integer32,
            lcsSetupRoutProtBgpAddressfamilyIpv4EntryRouteRedistribute BITS,
            lcsSetupRoutProtBgpAddressfamilyIpv4EntryComment DisplayString,
            lcsSetupRoutProtBgpAddressfamilyIpv4EntryRedistributionFilter DisplayString,
            lcsSetupRoutProtBgpAddressfamilyIpv4EntryDefaultAction INTEGER
    }

-- {COLUMN} 1.3.6.1.4.1.2356.11.2.93.1.4.1.1.1
lcsSetupRoutProtBgpAddressfamilyIpv4EntryNeighborProfile OBJECT-TYPE
    SYNTAX     DisplayString (SIZE(0..16))
    MAX-ACCESS read-write
    STATUS     current
    DESCRIPTION
            "-- empty --"
    ::= { lcsSetupRoutProtBgpAddressfamilyIpv4Entry 1 }

-- {COLUMN} 1.3.6.1.4.1.2356.11.2.93.1.4.1.1.2
lcsSetupRoutProtBgpAddressfamilyIpv4EntryRtgTag OBJECT-TYPE
    SYNTAX     Integer32 (0..65535)
    MAX-ACCESS read-write
    STATUS     current
    DESCRIPTION
            "-- empty --"
    ::= { lcsSetupRoutProtBgpAddressfamilyIpv4Entry 2 }

-- {COLUMN} 1.3.6.1.4.1.2356.11.2.93.1.4.1.1.3
lcsSetupRoutProtBgpAddressfamilyIpv4EntryOperating OBJECT-TYPE
    SYNTAX     INTEGER {
                  eNo (0),
                  eYes (1)
            }
    MAX-ACCESS read-write
    STATUS     current
    DESCRIPTION
            "-- empty --"
    ::= { lcsSetupRoutProtBgpAddressfamilyIpv4Entry 3 }

-- {COLUMN} 1.3.6.1.4.1.2356.11.2.93.1.4.1.1.4
lcsSetupRoutProtBgpAddressfamilyIpv4EntryCommunities OBJECT-TYPE
    SYNTAX     BITS {
                  eExtended (6),
                  eStandard (7)
            }
    MAX-ACCESS read-write
    STATUS     current
    DESCRIPTION
            "-- empty --"
    ::= { lcsSetupRoutProtBgpAddressfamilyIpv4Entry 4 }

-- {COLUMN} 1.3.6.1.4.1.2356.11.2.93.1.4.1.1.5
lcsSetupRoutProtBgpAddressfamilyIpv4EntryNexthopSelf OBJECT-TYPE
    SYNTAX     INTEGER {
                  eNo (0),
                  eYes (1),
                  eAlways (2)
            }
    MAX-ACCESS read-write
    STATUS     current
    DESCRIPTION
            "-- empty --"
    ::= { lcsSetupRoutProtBgpAddressfamilyIpv4Entry 5 }

-- {COLUMN} 1.3.6.1.4.1.2356.11.2.93.1.4.1.1.6
lcsSetupRoutProtBgpAddressfamilyIpv4EntryWeight OBJECT-TYPE
    SYNTAX     Integer32 (0..65535)
    MAX-ACCESS read-write
    STATUS     current
    DESCRIPTION
            "-- empty --"
    ::= { lcsSetupRoutProtBgpAddressfamilyIpv4Entry 6 }

-- {COLUMN} 1.3.6.1.4.1.2356.11.2.93.1.4.1.1.7
lcsSetupRoutProtBgpAddressfamilyIpv4EntryLocalPref OBJECT-TYPE
    SYNTAX     Integer32 (0..2147483647)
    MAX-ACCESS read-write
    STATUS     current
    DESCRIPTION
            "-- empty --"
    ::= { lcsSetupRoutProtBgpAddressfamilyIpv4Entry 7 }

-- {COLUMN} 1.3.6.1.4.1.2356.11.2.93.1.4.1.1.8
lcsSetupRoutProtBgpAddressfamilyIpv4EntryPrefixLimit OBJECT-TYPE
    SYNTAX     Integer32 (0..2147483647)
    MAX-ACCESS read-write
    STATUS     current
    DESCRIPTION
            "-- empty --"
    ::= { lcsSetupRoutProtBgpAddressfamilyIpv4Entry 8 }

-- {COLUMN} 1.3.6.1.4.1.2356.11.2.93.1.4.1.1.9
lcsSetupRoutProtBgpAddressfamilyIpv4EntryRouteRedistribute OBJECT-TYPE
    SYNTAX     BITS {
                  eLisp (3),
                  eOspf (4),
                  eRip (5),
                  eConnected (6),
                  eStatic (7)
            }
    MAX-ACCESS read-write
    STATUS     current
    DESCRIPTION
            "-- empty --"
    ::= { lcsSetupRoutProtBgpAddressfamilyIpv4Entry 9 }

-- {COLUMN} 1.3.6.1.4.1.2356.11.2.93.1.4.1.1.10
lcsSetupRoutProtBgpAddressfamilyIpv4EntryComment OBJECT-TYPE
    SYNTAX     DisplayString (SIZE(0..254))
    MAX-ACCESS read-write
    STATUS     current
    DESCRIPTION
            "-- empty --"
    ::= { lcsSetupRoutProtBgpAddressfamilyIpv4Entry 10 }

-- {COLUMN} 1.3.6.1.4.1.2356.11.2.93.1.4.1.1.11
lcsSetupRoutProtBgpAddressfamilyIpv4EntryRedistributionFilter OBJECT-TYPE
    SYNTAX     DisplayString (SIZE(0..16))
    MAX-ACCESS read-write
    STATUS     current
    DESCRIPTION
            "-- empty --"
    ::= { lcsSetupRoutProtBgpAddressfamilyIpv4Entry 11 }

-- {COLUMN} 1.3.6.1.4.1.2356.11.2.93.1.4.1.1.12
lcsSetupRoutProtBgpAddressfamilyIpv4EntryDefaultAction OBJECT-TYPE
    SYNTAX     INTEGER {
                  eAccept (0),
                  eDeny (1)
            }
    MAX-ACCESS read-write
    STATUS     current
    DESCRIPTION
            "-- empty --"
    ::= { lcsSetupRoutProtBgpAddressfamilyIpv4Entry 12 }

-- {TABLE} 1.3.6.1.4.1.2356.11.2.93.1.4.2
lcsSetupRoutProtBgpAddressfamilyIpv6Table OBJECT-TYPE
    SYNTAX     SEQUENCE OF LcsSetupRoutProtBgpAddressfamilyIpv6Entry
    MAX-ACCESS not-accessible
    STATUS     current
    DESCRIPTION
            "-- empty --"
    ::= { lcsSetupRoutProtBgpAddressfamily 2 }

-- {ROW} 1.3.6.1.4.1.2356.11.2.93.1.4.2.1
lcsSetupRoutProtBgpAddressfamilyIpv6Entry OBJECT-TYPE
    SYNTAX     LcsSetupRoutProtBgpAddressfamilyIpv6Entry
    MAX-ACCESS not-accessible
    STATUS     current
    DESCRIPTION
            ""
    INDEX {
            lcsSetupRoutProtBgpAddressfamilyIpv6EntryNeighborProfile
          }
    ::= { lcsSetupRoutProtBgpAddressfamilyIpv6Table 1 }

LcsSetupRoutProtBgpAddressfamilyIpv6Entry ::= SEQUENCE {
            lcsSetupRoutProtBgpAddressfamilyIpv6EntryNeighborProfile DisplayString,
            lcsSetupRoutProtBgpAddressfamilyIpv6EntryRtgTag Integer32,
            lcsSetupRoutProtBgpAddressfamilyIpv6EntryOperating INTEGER,
            lcsSetupRoutProtBgpAddressfamilyIpv6EntryCommunities BITS,
            lcsSetupRoutProtBgpAddressfamilyIpv6EntryNexthopSelf INTEGER,
            lcsSetupRoutProtBgpAddressfamilyIpv6EntryWeight Integer32,
            lcsSetupRoutProtBgpAddressfamilyIpv6EntryLocalPref Integer32,
            lcsSetupRoutProtBgpAddressfamilyIpv6EntryPrefixLimit Integer32,
            lcsSetupRoutProtBgpAddressfamilyIpv6EntryRouteRedistribute BITS,
            lcsSetupRoutProtBgpAddressfamilyIpv6EntryComment DisplayString,
            lcsSetupRoutProtBgpAddressfamilyIpv6EntryRedistributionFilter DisplayString,
            lcsSetupRoutProtBgpAddressfamilyIpv6EntryDefaultAction INTEGER
    }

-- {COLUMN} 1.3.6.1.4.1.2356.11.2.93.1.4.2.1.1
lcsSetupRoutProtBgpAddressfamilyIpv6EntryNeighborProfile OBJECT-TYPE
    SYNTAX     DisplayString (SIZE(0..16))
    MAX-ACCESS read-write
    STATUS     current
    DESCRIPTION
            "-- empty --"
    ::= { lcsSetupRoutProtBgpAddressfamilyIpv6Entry 1 }

-- {COLUMN} 1.3.6.1.4.1.2356.11.2.93.1.4.2.1.2
lcsSetupRoutProtBgpAddressfamilyIpv6EntryRtgTag OBJECT-TYPE
    SYNTAX     Integer32 (0..65535)
    MAX-ACCESS read-write
    STATUS     current
    DESCRIPTION
            "-- empty --"
    ::= { lcsSetupRoutProtBgpAddressfamilyIpv6Entry 2 }

-- {COLUMN} 1.3.6.1.4.1.2356.11.2.93.1.4.2.1.3
lcsSetupRoutProtBgpAddressfamilyIpv6EntryOperating OBJECT-TYPE
    SYNTAX     INTEGER {
                  eNo (0),
                  eYes (1)
            }
    MAX-ACCESS read-write
    STATUS     current
    DESCRIPTION
            "-- empty --"
    ::= { lcsSetupRoutProtBgpAddressfamilyIpv6Entry 3 }

-- {COLUMN} 1.3.6.1.4.1.2356.11.2.93.1.4.2.1.4
lcsSetupRoutProtBgpAddressfamilyIpv6EntryCommunities OBJECT-TYPE
    SYNTAX     BITS {
                  eExtended (6),
                  eStandard (7)
            }
    MAX-ACCESS read-write
    STATUS     current
    DESCRIPTION
            "-- empty --"
    ::= { lcsSetupRoutProtBgpAddressfamilyIpv6Entry 4 }

-- {COLUMN} 1.3.6.1.4.1.2356.11.2.93.1.4.2.1.5
lcsSetupRoutProtBgpAddressfamilyIpv6EntryNexthopSelf OBJECT-TYPE
    SYNTAX     INTEGER {
                  eNo (0),
                  eYes (1),
                  eAlways (2)
            }
    MAX-ACCESS read-write
    STATUS     current
    DESCRIPTION
            "-- empty --"
    ::= { lcsSetupRoutProtBgpAddressfamilyIpv6Entry 5 }

-- {COLUMN} 1.3.6.1.4.1.2356.11.2.93.1.4.2.1.6
lcsSetupRoutProtBgpAddressfamilyIpv6EntryWeight OBJECT-TYPE
    SYNTAX     Integer32 (0..65535)
    MAX-ACCESS read-write
    STATUS     current
    DESCRIPTION
            "-- empty --"
    ::= { lcsSetupRoutProtBgpAddressfamilyIpv6Entry 6 }

-- {COLUMN} 1.3.6.1.4.1.2356.11.2.93.1.4.2.1.7
lcsSetupRoutProtBgpAddressfamilyIpv6EntryLocalPref OBJECT-TYPE
    SYNTAX     Integer32 (0..2147483647)
    MAX-ACCESS read-write
    STATUS     current
    DESCRIPTION
            "-- empty --"
    ::= { lcsSetupRoutProtBgpAddressfamilyIpv6Entry 7 }

-- {COLUMN} 1.3.6.1.4.1.2356.11.2.93.1.4.2.1.8
lcsSetupRoutProtBgpAddressfamilyIpv6EntryPrefixLimit OBJECT-TYPE
    SYNTAX     Integer32 (0..2147483647)
    MAX-ACCESS read-write
    STATUS     current
    DESCRIPTION
            "-- empty --"
    ::= { lcsSetupRoutProtBgpAddressfamilyIpv6Entry 8 }

-- {COLUMN} 1.3.6.1.4.1.2356.11.2.93.1.4.2.1.9
lcsSetupRoutProtBgpAddressfamilyIpv6EntryRouteRedistribute OBJECT-TYPE
    SYNTAX     BITS {
                  eLisp (3),
                  eOspf (4),
                  eConnected (6),
                  eStatic (7)
            }
    MAX-ACCESS read-write
    STATUS     current
    DESCRIPTION
            "-- empty --"
    ::= { lcsSetupRoutProtBgpAddressfamilyIpv6Entry 9 }

-- {COLUMN} 1.3.6.1.4.1.2356.11.2.93.1.4.2.1.10
lcsSetupRoutProtBgpAddressfamilyIpv6EntryComment OBJECT-TYPE
    SYNTAX     DisplayString (SIZE(0..254))
    MAX-ACCESS read-write
    STATUS     current
    DESCRIPTION
            "-- empty --"
    ::= { lcsSetupRoutProtBgpAddressfamilyIpv6Entry 10 }

-- {COLUMN} 1.3.6.1.4.1.2356.11.2.93.1.4.2.1.11
lcsSetupRoutProtBgpAddressfamilyIpv6EntryRedistributionFilter OBJECT-TYPE
    SYNTAX     DisplayString (SIZE(0..16))
    MAX-ACCESS read-write
    STATUS     current
    DESCRIPTION
            "-- empty --"
    ::= { lcsSetupRoutProtBgpAddressfamilyIpv6Entry 11 }

-- {COLUMN} 1.3.6.1.4.1.2356.11.2.93.1.4.2.1.12
lcsSetupRoutProtBgpAddressfamilyIpv6EntryDefaultAction OBJECT-TYPE
    SYNTAX     INTEGER {
                  eAccept (0),
                  eDeny (1)
            }
    MAX-ACCESS read-write
    STATUS     current
    DESCRIPTION
            "-- empty --"
    ::= { lcsSetupRoutProtBgpAddressfamilyIpv6Entry 12 }

-- {NODE} 1.3.6.1.4.1.2356.11.2.93.1.5
lcsSetupRoutProtBgpPolicy OBJECT IDENTIFIER ::= { lcsSetupRoutProtBgp 5 }

-- {SCALAR} 1.3.6.1.4.1.2356.11.2.93.1.5.1
lcsSetupRoutProtBgpPolicyDefault OBJECT-TYPE
    SYNTAX     INTEGER {
                  eDeny (0),
                  ePermit (1)
            }
    MAX-ACCESS read-write
    STATUS     current
    DESCRIPTION
            "-- empty --"
    ::= { lcsSetupRoutProtBgpPolicy 1 }

-- {NODE} 1.3.6.1.4.1.2356.11.2.93.1.5.2
lcsSetupRoutProtBgpPolicyOverrides OBJECT IDENTIFIER ::= { lcsSetupRoutProtBgpPolicy 2 }

-- {TABLE} 1.3.6.1.4.1.2356.11.2.93.1.5.2.1
lcsSetupRoutProtBgpPolicyOverridesBasicTable OBJECT-TYPE
    SYNTAX     SEQUENCE OF LcsSetupRoutProtBgpPolicyOverridesBasicEntry
    MAX-ACCESS not-accessible
    STATUS     current
    DESCRIPTION
            "-- empty --"
    ::= { lcsSetupRoutProtBgpPolicyOverrides 1 }

-- {ROW} 1.3.6.1.4.1.2356.11.2.93.1.5.2.1.1
lcsSetupRoutProtBgpPolicyOverridesBasicEntry OBJECT-TYPE
    SYNTAX     LcsSetupRoutProtBgpPolicyOverridesBasicEntry
    MAX-ACCESS not-accessible
    STATUS     current
    DESCRIPTION
            ""
    INDEX {
            lcsSetupRoutProtBgpPolicyOverridesBasicEntryName
          }
    ::= { lcsSetupRoutProtBgpPolicyOverridesBasicTable 1 }

LcsSetupRoutProtBgpPolicyOverridesBasicEntry ::= SEQUENCE {
            lcsSetupRoutProtBgpPolicyOverridesBasicEntryName DisplayString,
            lcsSetupRoutProtBgpPolicyOverridesBasicEntrySetWeight Integer32,
            lcsSetupRoutProtBgpPolicyOverridesBasicEntrySetLocalPref Integer32,
            lcsSetupRoutProtBgpPolicyOverridesBasicEntryRemoveMed INTEGER,
            lcsSetupRoutProtBgpPolicyOverridesBasicEntrySetMed Integer32,
            lcsSetupRoutProtBgpPolicyOverridesBasicEntrySetNexthop DisplayString,
            lcsSetupRoutProtBgpPolicyOverridesBasicEntryComment DisplayString,
            lcsSetupRoutProtBgpPolicyOverridesBasicEntrySetLinkLocalNexthop DisplayString,
            lcsSetupRoutProtBgpPolicyOverridesBasicEntrySetAdminDistance Integer32
    }

-- {COLUMN} 1.3.6.1.4.1.2356.11.2.93.1.5.2.1.1.1
lcsSetupRoutProtBgpPolicyOverridesBasicEntryName OBJECT-TYPE
    SYNTAX     DisplayString (SIZE(0..16))
    MAX-ACCESS read-write
    STATUS     current
    DESCRIPTION
            "-- empty --"
    ::= { lcsSetupRoutProtBgpPolicyOverridesBasicEntry 1 }

-- {COLUMN} 1.3.6.1.4.1.2356.11.2.93.1.5.2.1.1.2
lcsSetupRoutProtBgpPolicyOverridesBasicEntrySetWeight OBJECT-TYPE
    SYNTAX     Integer32 (0..65535)
    MAX-ACCESS read-write
    STATUS     current
    DESCRIPTION
            "-- empty --"
    ::= { lcsSetupRoutProtBgpPolicyOverridesBasicEntry 2 }

-- {COLUMN} 1.3.6.1.4.1.2356.11.2.93.1.5.2.1.1.3
lcsSetupRoutProtBgpPolicyOverridesBasicEntrySetLocalPref OBJECT-TYPE
    SYNTAX     Integer32 (0..2147483647)
    MAX-ACCESS read-write
    STATUS     current
    DESCRIPTION
            "-- empty --"
    ::= { lcsSetupRoutProtBgpPolicyOverridesBasicEntry 3 }

-- {COLUMN} 1.3.6.1.4.1.2356.11.2.93.1.5.2.1.1.4
lcsSetupRoutProtBgpPolicyOverridesBasicEntryRemoveMed OBJECT-TYPE
    SYNTAX     INTEGER {
                  eNo (0),
                  eYes (1)
            }
    MAX-ACCESS read-write
    STATUS     current
    DESCRIPTION
            "-- empty --"
    ::= { lcsSetupRoutProtBgpPolicyOverridesBasicEntry 4 }

-- {COLUMN} 1.3.6.1.4.1.2356.11.2.93.1.5.2.1.1.5
lcsSetupRoutProtBgpPolicyOverridesBasicEntrySetMed OBJECT-TYPE
    SYNTAX     Integer32 (0..2147483647)
    MAX-ACCESS read-write
    STATUS     current
    DESCRIPTION
            "-- empty --"
    ::= { lcsSetupRoutProtBgpPolicyOverridesBasicEntry 5 }

-- {COLUMN} 1.3.6.1.4.1.2356.11.2.93.1.5.2.1.1.6
lcsSetupRoutProtBgpPolicyOverridesBasicEntrySetNexthop OBJECT-TYPE
    SYNTAX     DisplayString (SIZE(0..39))
    MAX-ACCESS read-write
    STATUS     current
    DESCRIPTION
            "-- empty --"
    ::= { lcsSetupRoutProtBgpPolicyOverridesBasicEntry 6 }

-- {COLUMN} 1.3.6.1.4.1.2356.11.2.93.1.5.2.1.1.7
lcsSetupRoutProtBgpPolicyOverridesBasicEntryComment OBJECT-TYPE
    SYNTAX     DisplayString (SIZE(0..254))
    MAX-ACCESS read-write
    STATUS     current
    DESCRIPTION
            "-- empty --"
    ::= { lcsSetupRoutProtBgpPolicyOverridesBasicEntry 7 }

-- {COLUMN} 1.3.6.1.4.1.2356.11.2.93.1.5.2.1.1.8
lcsSetupRoutProtBgpPolicyOverridesBasicEntrySetLinkLocalNexthop OBJECT-TYPE
    SYNTAX     DisplayString (SIZE(0..39))
    MAX-ACCESS read-write
    STATUS     current
    DESCRIPTION
            "-- empty --"
    ::= { lcsSetupRoutProtBgpPolicyOverridesBasicEntry 8 }

-- {COLUMN} 1.3.6.1.4.1.2356.11.2.93.1.5.2.1.1.9
lcsSetupRoutProtBgpPolicyOverridesBasicEntrySetAdminDistance OBJECT-TYPE
    SYNTAX     Integer32 (0..255)
    MAX-ACCESS read-write
    STATUS     current
    DESCRIPTION
            "-- empty --"
    ::= { lcsSetupRoutProtBgpPolicyOverridesBasicEntry 9 }

-- {TABLE} 1.3.6.1.4.1.2356.11.2.93.1.5.2.2
lcsSetupRoutProtBgpPolicyOverridesAsPathTable OBJECT-TYPE
    SYNTAX     SEQUENCE OF LcsSetupRoutProtBgpPolicyOverridesAsPathEntry
    MAX-ACCESS not-accessible
    STATUS     current
    DESCRIPTION
            "-- empty --"
    ::= { lcsSetupRoutProtBgpPolicyOverrides 2 }

-- {ROW} 1.3.6.1.4.1.2356.11.2.93.1.5.2.2.1
lcsSetupRoutProtBgpPolicyOverridesAsPathEntry OBJECT-TYPE
    SYNTAX     LcsSetupRoutProtBgpPolicyOverridesAsPathEntry
    MAX-ACCESS not-accessible
    STATUS     current
    DESCRIPTION
            ""
    INDEX {
            lcsSetupRoutProtBgpPolicyOverridesAsPathEntryName
          }
    ::= { lcsSetupRoutProtBgpPolicyOverridesAsPathTable 1 }

LcsSetupRoutProtBgpPolicyOverridesAsPathEntry ::= SEQUENCE {
            lcsSetupRoutProtBgpPolicyOverridesAsPathEntryName DisplayString,
            lcsSetupRoutProtBgpPolicyOverridesAsPathEntryFilterPrivateAs INTEGER,
            lcsSetupRoutProtBgpPolicyOverridesAsPathEntryReplace DisplayString,
            lcsSetupRoutProtBgpPolicyOverridesAsPathEntryPrepend DisplayString,
            lcsSetupRoutProtBgpPolicyOverridesAsPathEntryPrependCount Integer32,
            lcsSetupRoutProtBgpPolicyOverridesAsPathEntryComment DisplayString
    }

-- {COLUMN} 1.3.6.1.4.1.2356.11.2.93.1.5.2.2.1.1
lcsSetupRoutProtBgpPolicyOverridesAsPathEntryName OBJECT-TYPE
    SYNTAX     DisplayString (SIZE(0..16))
    MAX-ACCESS read-write
    STATUS     current
    DESCRIPTION
            "-- empty --"
    ::= { lcsSetupRoutProtBgpPolicyOverridesAsPathEntry 1 }

-- {COLUMN} 1.3.6.1.4.1.2356.11.2.93.1.5.2.2.1.2
lcsSetupRoutProtBgpPolicyOverridesAsPathEntryFilterPrivateAs OBJECT-TYPE
    SYNTAX     INTEGER {
                  eNo (0),
                  eRemove (1),
                  eReplace (2)
            }
    MAX-ACCESS read-write
    STATUS     current
    DESCRIPTION
            "-- empty --"
    ::= { lcsSetupRoutProtBgpPolicyOverridesAsPathEntry 2 }

-- {COLUMN} 1.3.6.1.4.1.2356.11.2.93.1.5.2.2.1.3
lcsSetupRoutProtBgpPolicyOverridesAsPathEntryReplace OBJECT-TYPE
    SYNTAX     DisplayString (SIZE(0..62))
    MAX-ACCESS read-write
    STATUS     current
    DESCRIPTION
            "-- empty --"
    ::= { lcsSetupRoutProtBgpPolicyOverridesAsPathEntry 3 }

-- {COLUMN} 1.3.6.1.4.1.2356.11.2.93.1.5.2.2.1.4
lcsSetupRoutProtBgpPolicyOverridesAsPathEntryPrepend OBJECT-TYPE
    SYNTAX     DisplayString (SIZE(0..10))
    MAX-ACCESS read-write
    STATUS     current
    DESCRIPTION
            "-- empty --"
    ::= { lcsSetupRoutProtBgpPolicyOverridesAsPathEntry 4 }

-- {COLUMN} 1.3.6.1.4.1.2356.11.2.93.1.5.2.2.1.5
lcsSetupRoutProtBgpPolicyOverridesAsPathEntryPrependCount OBJECT-TYPE
    SYNTAX     Integer32 (0..255)
    MAX-ACCESS read-write
    STATUS     current
    DESCRIPTION
            "-- empty --"
    ::= { lcsSetupRoutProtBgpPolicyOverridesAsPathEntry 5 }

-- {COLUMN} 1.3.6.1.4.1.2356.11.2.93.1.5.2.2.1.6
lcsSetupRoutProtBgpPolicyOverridesAsPathEntryComment OBJECT-TYPE
    SYNTAX     DisplayString (SIZE(0..254))
    MAX-ACCESS read-write
    STATUS     current
    DESCRIPTION
            "-- empty --"
    ::= { lcsSetupRoutProtBgpPolicyOverridesAsPathEntry 6 }

-- {TABLE} 1.3.6.1.4.1.2356.11.2.93.1.5.2.3
lcsSetupRoutProtBgpPolicyOverridesCommunitiesTable OBJECT-TYPE
    SYNTAX     SEQUENCE OF LcsSetupRoutProtBgpPolicyOverridesCommunitiesEntry
    MAX-ACCESS not-accessible
    STATUS     current
    DESCRIPTION
            "-- empty --"
    ::= { lcsSetupRoutProtBgpPolicyOverrides 3 }

-- {ROW} 1.3.6.1.4.1.2356.11.2.93.1.5.2.3.1
lcsSetupRoutProtBgpPolicyOverridesCommunitiesEntry OBJECT-TYPE
    SYNTAX     LcsSetupRoutProtBgpPolicyOverridesCommunitiesEntry
    MAX-ACCESS not-accessible
    STATUS     current
    DESCRIPTION
            ""
    INDEX {
            lcsSetupRoutProtBgpPolicyOverridesCommunitiesEntryName
          }
    ::= { lcsSetupRoutProtBgpPolicyOverridesCommunitiesTable 1 }

LcsSetupRoutProtBgpPolicyOverridesCommunitiesEntry ::= SEQUENCE {
            lcsSetupRoutProtBgpPolicyOverridesCommunitiesEntryName DisplayString,
            lcsSetupRoutProtBgpPolicyOverridesCommunitiesEntryClear INTEGER,
            lcsSetupRoutProtBgpPolicyOverridesCommunitiesEntryAdd DisplayString,
            lcsSetupRoutProtBgpPolicyOverridesCommunitiesEntryRemove DisplayString,
            lcsSetupRoutProtBgpPolicyOverridesCommunitiesEntryComment DisplayString
    }

-- {COLUMN} 1.3.6.1.4.1.2356.11.2.93.1.5.2.3.1.1
lcsSetupRoutProtBgpPolicyOverridesCommunitiesEntryName OBJECT-TYPE
    SYNTAX     DisplayString (SIZE(0..16))
    MAX-ACCESS read-write
    STATUS     current
    DESCRIPTION
            "-- empty --"
    ::= { lcsSetupRoutProtBgpPolicyOverridesCommunitiesEntry 1 }

-- {COLUMN} 1.3.6.1.4.1.2356.11.2.93.1.5.2.3.1.2
lcsSetupRoutProtBgpPolicyOverridesCommunitiesEntryClear OBJECT-TYPE
    SYNTAX     INTEGER {
                  eNo (0),
                  eYes (1)
            }
    MAX-ACCESS read-write
    STATUS     current
    DESCRIPTION
            "-- empty --"
    ::= { lcsSetupRoutProtBgpPolicyOverridesCommunitiesEntry 2 }

-- {COLUMN} 1.3.6.1.4.1.2356.11.2.93.1.5.2.3.1.3
lcsSetupRoutProtBgpPolicyOverridesCommunitiesEntryAdd OBJECT-TYPE
    SYNTAX     DisplayString (SIZE(0..62))
    MAX-ACCESS read-write
    STATUS     current
    DESCRIPTION
            "-- empty --"
    ::= { lcsSetupRoutProtBgpPolicyOverridesCommunitiesEntry 3 }

-- {COLUMN} 1.3.6.1.4.1.2356.11.2.93.1.5.2.3.1.4
lcsSetupRoutProtBgpPolicyOverridesCommunitiesEntryRemove OBJECT-TYPE
    SYNTAX     DisplayString (SIZE(0..62))
    MAX-ACCESS read-write
    STATUS     current
    DESCRIPTION
            "-- empty --"
    ::= { lcsSetupRoutProtBgpPolicyOverridesCommunitiesEntry 4 }

-- {COLUMN} 1.3.6.1.4.1.2356.11.2.93.1.5.2.3.1.5
lcsSetupRoutProtBgpPolicyOverridesCommunitiesEntryComment OBJECT-TYPE
    SYNTAX     DisplayString (SIZE(0..254))
    MAX-ACCESS read-write
    STATUS     current
    DESCRIPTION
            "-- empty --"
    ::= { lcsSetupRoutProtBgpPolicyOverridesCommunitiesEntry 5 }

-- {TABLE} 1.3.6.1.4.1.2356.11.2.93.1.5.3
lcsSetupRoutProtBgpPolicyActionsTable OBJECT-TYPE
    SYNTAX     SEQUENCE OF LcsSetupRoutProtBgpPolicyActionsEntry
    MAX-ACCESS not-accessible
    STATUS     current
    DESCRIPTION
            "-- empty --"
    ::= { lcsSetupRoutProtBgpPolicy 3 }

-- {ROW} 1.3.6.1.4.1.2356.11.2.93.1.5.3.1
lcsSetupRoutProtBgpPolicyActionsEntry OBJECT-TYPE
    SYNTAX     LcsSetupRoutProtBgpPolicyActionsEntry
    MAX-ACCESS not-accessible
    STATUS     current
    DESCRIPTION
            ""
    INDEX {
            lcsSetupRoutProtBgpPolicyActionsEntryName
          }
    ::= { lcsSetupRoutProtBgpPolicyActionsTable 1 }

LcsSetupRoutProtBgpPolicyActionsEntry ::= SEQUENCE {
            lcsSetupRoutProtBgpPolicyActionsEntryName DisplayString,
            lcsSetupRoutProtBgpPolicyActionsEntryBasic DisplayString,
            lcsSetupRoutProtBgpPolicyActionsEntryAsPath DisplayString,
            lcsSetupRoutProtBgpPolicyActionsEntryCommunities DisplayString,
            lcsSetupRoutProtBgpPolicyActionsEntryComment DisplayString
    }

-- {COLUMN} 1.3.6.1.4.1.2356.11.2.93.1.5.3.1.1
lcsSetupRoutProtBgpPolicyActionsEntryName OBJECT-TYPE
    SYNTAX     DisplayString (SIZE(0..16))
    MAX-ACCESS read-write
    STATUS     current
    DESCRIPTION
            "-- empty --"
    ::= { lcsSetupRoutProtBgpPolicyActionsEntry 1 }

-- {COLUMN} 1.3.6.1.4.1.2356.11.2.93.1.5.3.1.2
lcsSetupRoutProtBgpPolicyActionsEntryBasic OBJECT-TYPE
    SYNTAX     DisplayString (SIZE(0..16))
    MAX-ACCESS read-write
    STATUS     current
    DESCRIPTION
            "-- empty --"
    ::= { lcsSetupRoutProtBgpPolicyActionsEntry 2 }

-- {COLUMN} 1.3.6.1.4.1.2356.11.2.93.1.5.3.1.3
lcsSetupRoutProtBgpPolicyActionsEntryAsPath OBJECT-TYPE
    SYNTAX     DisplayString (SIZE(0..16))
    MAX-ACCESS read-write
    STATUS     current
    DESCRIPTION
            "-- empty --"
    ::= { lcsSetupRoutProtBgpPolicyActionsEntry 3 }

-- {COLUMN} 1.3.6.1.4.1.2356.11.2.93.1.5.3.1.4
lcsSetupRoutProtBgpPolicyActionsEntryCommunities OBJECT-TYPE
    SYNTAX     DisplayString (SIZE(0..16))
    MAX-ACCESS read-write
    STATUS     current
    DESCRIPTION
            "-- empty --"
    ::= { lcsSetupRoutProtBgpPolicyActionsEntry 4 }

-- {COLUMN} 1.3.6.1.4.1.2356.11.2.93.1.5.3.1.5
lcsSetupRoutProtBgpPolicyActionsEntryComment OBJECT-TYPE
    SYNTAX     DisplayString (SIZE(0..254))
    MAX-ACCESS read-write
    STATUS     current
    DESCRIPTION
            "-- empty --"
    ::= { lcsSetupRoutProtBgpPolicyActionsEntry 5 }

-- {NODE} 1.3.6.1.4.1.2356.11.2.93.1.5.4
lcsSetupRoutProtBgpPolicyLists OBJECT IDENTIFIER ::= { lcsSetupRoutProtBgpPolicy 4 }

-- {TABLE} 1.3.6.1.4.1.2356.11.2.93.1.5.4.1
lcsSetupRoutProtBgpPolicyListsPrefixTable OBJECT-TYPE
    SYNTAX     SEQUENCE OF LcsSetupRoutProtBgpPolicyListsPrefixEntry
    MAX-ACCESS not-accessible
    STATUS     current
    DESCRIPTION
            "-- empty --"
    ::= { lcsSetupRoutProtBgpPolicyLists 1 }

-- {ROW} 1.3.6.1.4.1.2356.11.2.93.1.5.4.1.1
lcsSetupRoutProtBgpPolicyListsPrefixEntry OBJECT-TYPE
    SYNTAX     LcsSetupRoutProtBgpPolicyListsPrefixEntry
    MAX-ACCESS not-accessible
    STATUS     current
    DESCRIPTION
            ""
    INDEX {
            lcsSetupRoutProtBgpPolicyListsPrefixEntryName,
            lcsSetupRoutProtBgpPolicyListsPrefixEntryIpAddress
          }
    ::= { lcsSetupRoutProtBgpPolicyListsPrefixTable 1 }

LcsSetupRoutProtBgpPolicyListsPrefixEntry ::= SEQUENCE {
            lcsSetupRoutProtBgpPolicyListsPrefixEntryName DisplayString,
            lcsSetupRoutProtBgpPolicyListsPrefixEntryIpAddress DisplayString,
            lcsSetupRoutProtBgpPolicyListsPrefixEntryPrefixLength Integer32,
            lcsSetupRoutProtBgpPolicyListsPrefixEntryLengthMin Integer32,
            lcsSetupRoutProtBgpPolicyListsPrefixEntryLengthMax Integer32,
            lcsSetupRoutProtBgpPolicyListsPrefixEntryComment DisplayString
    }

-- {COLUMN} 1.3.6.1.4.1.2356.11.2.93.1.5.4.1.1.1
lcsSetupRoutProtBgpPolicyListsPrefixEntryName OBJECT-TYPE
    SYNTAX     DisplayString (SIZE(0..16))
    MAX-ACCESS read-write
    STATUS     current
    DESCRIPTION
            "-- empty --"
    ::= { lcsSetupRoutProtBgpPolicyListsPrefixEntry 1 }

-- {COLUMN} 1.3.6.1.4.1.2356.11.2.93.1.5.4.1.1.2
lcsSetupRoutProtBgpPolicyListsPrefixEntryIpAddress OBJECT-TYPE
    SYNTAX     DisplayString (SIZE(0..39))
    MAX-ACCESS read-write
    STATUS     current
    DESCRIPTION
            "-- empty --"
    ::= { lcsSetupRoutProtBgpPolicyListsPrefixEntry 2 }

-- {COLUMN} 1.3.6.1.4.1.2356.11.2.93.1.5.4.1.1.3
lcsSetupRoutProtBgpPolicyListsPrefixEntryPrefixLength OBJECT-TYPE
    SYNTAX     Integer32 (0..255)
    MAX-ACCESS read-write
    STATUS     current
    DESCRIPTION
            "-- empty --"
    ::= { lcsSetupRoutProtBgpPolicyListsPrefixEntry 3 }

-- {COLUMN} 1.3.6.1.4.1.2356.11.2.93.1.5.4.1.1.4
lcsSetupRoutProtBgpPolicyListsPrefixEntryLengthMin OBJECT-TYPE
    SYNTAX     Integer32 (0..255)
    MAX-ACCESS read-write
    STATUS     current
    DESCRIPTION
            "-- empty --"
    ::= { lcsSetupRoutProtBgpPolicyListsPrefixEntry 4 }

-- {COLUMN} 1.3.6.1.4.1.2356.11.2.93.1.5.4.1.1.5
lcsSetupRoutProtBgpPolicyListsPrefixEntryLengthMax OBJECT-TYPE
    SYNTAX     Integer32 (0..255)
    MAX-ACCESS read-write
    STATUS     current
    DESCRIPTION
            "-- empty --"
    ::= { lcsSetupRoutProtBgpPolicyListsPrefixEntry 5 }

-- {COLUMN} 1.3.6.1.4.1.2356.11.2.93.1.5.4.1.1.6
lcsSetupRoutProtBgpPolicyListsPrefixEntryComment OBJECT-TYPE
    SYNTAX     DisplayString (SIZE(0..254))
    MAX-ACCESS read-write
    STATUS     current
    DESCRIPTION
            "-- empty --"
    ::= { lcsSetupRoutProtBgpPolicyListsPrefixEntry 6 }

-- {TABLE} 1.3.6.1.4.1.2356.11.2.93.1.5.4.2
lcsSetupRoutProtBgpPolicyListsAsPathTable OBJECT-TYPE
    SYNTAX     SEQUENCE OF LcsSetupRoutProtBgpPolicyListsAsPathEntry
    MAX-ACCESS not-accessible
    STATUS     current
    DESCRIPTION
            "-- empty --"
    ::= { lcsSetupRoutProtBgpPolicyLists 2 }

-- {ROW} 1.3.6.1.4.1.2356.11.2.93.1.5.4.2.1
lcsSetupRoutProtBgpPolicyListsAsPathEntry OBJECT-TYPE
    SYNTAX     LcsSetupRoutProtBgpPolicyListsAsPathEntry
    MAX-ACCESS not-accessible
    STATUS     current
    DESCRIPTION
            ""
    INDEX {
            lcsSetupRoutProtBgpPolicyListsAsPathEntryName
          }
    ::= { lcsSetupRoutProtBgpPolicyListsAsPathTable 1 }

LcsSetupRoutProtBgpPolicyListsAsPathEntry ::= SEQUENCE {
            lcsSetupRoutProtBgpPolicyListsAsPathEntryName DisplayString,
            lcsSetupRoutProtBgpPolicyListsAsPathEntryAsPathRegex DisplayString,
            lcsSetupRoutProtBgpPolicyListsAsPathEntryRegexMatch INTEGER,
            lcsSetupRoutProtBgpPolicyListsAsPathEntryComment DisplayString
    }

-- {COLUMN} 1.3.6.1.4.1.2356.11.2.93.1.5.4.2.1.1
lcsSetupRoutProtBgpPolicyListsAsPathEntryName OBJECT-TYPE
    SYNTAX     DisplayString (SIZE(0..16))
    MAX-ACCESS read-write
    STATUS     current
    DESCRIPTION
            "-- empty --"
    ::= { lcsSetupRoutProtBgpPolicyListsAsPathEntry 1 }

-- {COLUMN} 1.3.6.1.4.1.2356.11.2.93.1.5.4.2.1.2
lcsSetupRoutProtBgpPolicyListsAsPathEntryAsPathRegex OBJECT-TYPE
    SYNTAX     DisplayString (SIZE(0..62))
    MAX-ACCESS read-write
    STATUS     current
    DESCRIPTION
            "-- empty --"
    ::= { lcsSetupRoutProtBgpPolicyListsAsPathEntry 2 }

-- {COLUMN} 1.3.6.1.4.1.2356.11.2.93.1.5.4.2.1.3
lcsSetupRoutProtBgpPolicyListsAsPathEntryRegexMatch OBJECT-TYPE
    SYNTAX     INTEGER {
                  eFull (0),
                  ePartial (1)
            }
    MAX-ACCESS read-write
    STATUS     current
    DESCRIPTION
            "-- empty --"
    ::= { lcsSetupRoutProtBgpPolicyListsAsPathEntry 3 }

-- {COLUMN} 1.3.6.1.4.1.2356.11.2.93.1.5.4.2.1.4
lcsSetupRoutProtBgpPolicyListsAsPathEntryComment OBJECT-TYPE
    SYNTAX     DisplayString (SIZE(0..254))
    MAX-ACCESS read-write
    STATUS     current
    DESCRIPTION
            "-- empty --"
    ::= { lcsSetupRoutProtBgpPolicyListsAsPathEntry 4 }

-- {TABLE} 1.3.6.1.4.1.2356.11.2.93.1.5.4.3
lcsSetupRoutProtBgpPolicyListsCommunitiesTable OBJECT-TYPE
    SYNTAX     SEQUENCE OF LcsSetupRoutProtBgpPolicyListsCommunitiesEntry
    MAX-ACCESS not-accessible
    STATUS     current
    DESCRIPTION
            "-- empty --"
    ::= { lcsSetupRoutProtBgpPolicyLists 3 }

-- {ROW} 1.3.6.1.4.1.2356.11.2.93.1.5.4.3.1
lcsSetupRoutProtBgpPolicyListsCommunitiesEntry OBJECT-TYPE
    SYNTAX     LcsSetupRoutProtBgpPolicyListsCommunitiesEntry
    MAX-ACCESS not-accessible
    STATUS     current
    DESCRIPTION
            ""
    INDEX {
            lcsSetupRoutProtBgpPolicyListsCommunitiesEntryName,
            lcsSetupRoutProtBgpPolicyListsCommunitiesEntryCommunities
          }
    ::= { lcsSetupRoutProtBgpPolicyListsCommunitiesTable 1 }

LcsSetupRoutProtBgpPolicyListsCommunitiesEntry ::= SEQUENCE {
            lcsSetupRoutProtBgpPolicyListsCommunitiesEntryName DisplayString,
            lcsSetupRoutProtBgpPolicyListsCommunitiesEntryCommunities DisplayString,
            lcsSetupRoutProtBgpPolicyListsCommunitiesEntryComment DisplayString
    }

-- {COLUMN} 1.3.6.1.4.1.2356.11.2.93.1.5.4.3.1.1
lcsSetupRoutProtBgpPolicyListsCommunitiesEntryName OBJECT-TYPE
    SYNTAX     DisplayString (SIZE(0..16))
    MAX-ACCESS read-write
    STATUS     current
    DESCRIPTION
            "-- empty --"
    ::= { lcsSetupRoutProtBgpPolicyListsCommunitiesEntry 1 }

-- {COLUMN} 1.3.6.1.4.1.2356.11.2.93.1.5.4.3.1.2
lcsSetupRoutProtBgpPolicyListsCommunitiesEntryCommunities OBJECT-TYPE
    SYNTAX     DisplayString (SIZE(0..62))
    MAX-ACCESS read-write
    STATUS     current
    DESCRIPTION
            "-- empty --"
    ::= { lcsSetupRoutProtBgpPolicyListsCommunitiesEntry 2 }

-- {COLUMN} 1.3.6.1.4.1.2356.11.2.93.1.5.4.3.1.3
lcsSetupRoutProtBgpPolicyListsCommunitiesEntryComment OBJECT-TYPE
    SYNTAX     DisplayString (SIZE(0..254))
    MAX-ACCESS read-write
    STATUS     current
    DESCRIPTION
            "-- empty --"
    ::= { lcsSetupRoutProtBgpPolicyListsCommunitiesEntry 3 }

-- {TABLE} 1.3.6.1.4.1.2356.11.2.93.1.5.5
lcsSetupRoutProtBgpPolicyMatchesTable OBJECT-TYPE
    SYNTAX     SEQUENCE OF LcsSetupRoutProtBgpPolicyMatchesEntry
    MAX-ACCESS not-accessible
    STATUS     current
    DESCRIPTION
            "-- empty --"
    ::= { lcsSetupRoutProtBgpPolicy 5 }

-- {ROW} 1.3.6.1.4.1.2356.11.2.93.1.5.5.1
lcsSetupRoutProtBgpPolicyMatchesEntry OBJECT-TYPE
    SYNTAX     LcsSetupRoutProtBgpPolicyMatchesEntry
    MAX-ACCESS not-accessible
    STATUS     current
    DESCRIPTION
            ""
    INDEX {
            lcsSetupRoutProtBgpPolicyMatchesEntryName
          }
    ::= { lcsSetupRoutProtBgpPolicyMatchesTable 1 }

LcsSetupRoutProtBgpPolicyMatchesEntry ::= SEQUENCE {
            lcsSetupRoutProtBgpPolicyMatchesEntryName DisplayString,
            lcsSetupRoutProtBgpPolicyMatchesEntryPrefix DisplayString,
            lcsSetupRoutProtBgpPolicyMatchesEntryAsPath DisplayString,
            lcsSetupRoutProtBgpPolicyMatchesEntryCommunities DisplayString,
            lcsSetupRoutProtBgpPolicyMatchesEntryComment DisplayString
    }

-- {COLUMN} 1.3.6.1.4.1.2356.11.2.93.1.5.5.1.1
lcsSetupRoutProtBgpPolicyMatchesEntryName OBJECT-TYPE
    SYNTAX     DisplayString (SIZE(0..16))
    MAX-ACCESS read-write
    STATUS     current
    DESCRIPTION
            "-- empty --"
    ::= { lcsSetupRoutProtBgpPolicyMatchesEntry 1 }

-- {COLUMN} 1.3.6.1.4.1.2356.11.2.93.1.5.5.1.2
lcsSetupRoutProtBgpPolicyMatchesEntryPrefix OBJECT-TYPE
    SYNTAX     DisplayString (SIZE(0..16))
    MAX-ACCESS read-write
    STATUS     current
    DESCRIPTION
            "-- empty --"
    ::= { lcsSetupRoutProtBgpPolicyMatchesEntry 2 }

-- {COLUMN} 1.3.6.1.4.1.2356.11.2.93.1.5.5.1.3
lcsSetupRoutProtBgpPolicyMatchesEntryAsPath OBJECT-TYPE
    SYNTAX     DisplayString (SIZE(0..80))
    MAX-ACCESS read-write
    STATUS     current
    DESCRIPTION
            "-- empty --"
    ::= { lcsSetupRoutProtBgpPolicyMatchesEntry 3 }

-- {COLUMN} 1.3.6.1.4.1.2356.11.2.93.1.5.5.1.4
lcsSetupRoutProtBgpPolicyMatchesEntryCommunities OBJECT-TYPE
    SYNTAX     DisplayString (SIZE(0..80))
    MAX-ACCESS read-write
    STATUS     current
    DESCRIPTION
            "-- empty --"
    ::= { lcsSetupRoutProtBgpPolicyMatchesEntry 4 }

-- {COLUMN} 1.3.6.1.4.1.2356.11.2.93.1.5.5.1.5
lcsSetupRoutProtBgpPolicyMatchesEntryComment OBJECT-TYPE
    SYNTAX     DisplayString (SIZE(0..254))
    MAX-ACCESS read-write
    STATUS     current
    DESCRIPTION
            "-- empty --"
    ::= { lcsSetupRoutProtBgpPolicyMatchesEntry 5 }

-- {TABLE} 1.3.6.1.4.1.2356.11.2.93.1.5.6
lcsSetupRoutProtBgpPolicyFiltersTable OBJECT-TYPE
    SYNTAX     SEQUENCE OF LcsSetupRoutProtBgpPolicyFiltersEntry
    MAX-ACCESS not-accessible
    STATUS     current
    DESCRIPTION
            "-- empty --"
    ::= { lcsSetupRoutProtBgpPolicy 6 }

-- {ROW} 1.3.6.1.4.1.2356.11.2.93.1.5.6.1
lcsSetupRoutProtBgpPolicyFiltersEntry OBJECT-TYPE
    SYNTAX     LcsSetupRoutProtBgpPolicyFiltersEntry
    MAX-ACCESS not-accessible
    STATUS     current
    DESCRIPTION
            ""
    INDEX {
            lcsSetupRoutProtBgpPolicyFiltersEntryName,
            lcsSetupRoutProtBgpPolicyFiltersEntryPriority
          }
    ::= { lcsSetupRoutProtBgpPolicyFiltersTable 1 }

LcsSetupRoutProtBgpPolicyFiltersEntry ::= SEQUENCE {
            lcsSetupRoutProtBgpPolicyFiltersEntryName DisplayString,
            lcsSetupRoutProtBgpPolicyFiltersEntryPriority Integer32,
            lcsSetupRoutProtBgpPolicyFiltersEntryAddressfamily BITS,
            lcsSetupRoutProtBgpPolicyFiltersEntryMatch DisplayString,
            lcsSetupRoutProtBgpPolicyFiltersEntryPolicy INTEGER,
            lcsSetupRoutProtBgpPolicyFiltersEntryAction DisplayString,
            lcsSetupRoutProtBgpPolicyFiltersEntryComment DisplayString
    }

-- {COLUMN} 1.3.6.1.4.1.2356.11.2.93.1.5.6.1.1
lcsSetupRoutProtBgpPolicyFiltersEntryName OBJECT-TYPE
    SYNTAX     DisplayString (SIZE(0..16))
    MAX-ACCESS read-write
    STATUS     current
    DESCRIPTION
            "-- empty --"
    ::= { lcsSetupRoutProtBgpPolicyFiltersEntry 1 }

-- {COLUMN} 1.3.6.1.4.1.2356.11.2.93.1.5.6.1.2
lcsSetupRoutProtBgpPolicyFiltersEntryPriority OBJECT-TYPE
    SYNTAX     Integer32 (0..2147483647)
    MAX-ACCESS read-write
    STATUS     current
    DESCRIPTION
            "-- empty --"
    ::= { lcsSetupRoutProtBgpPolicyFiltersEntry 2 }

-- {COLUMN} 1.3.6.1.4.1.2356.11.2.93.1.5.6.1.3
lcsSetupRoutProtBgpPolicyFiltersEntryAddressfamily OBJECT-TYPE
    SYNTAX     BITS {
                  eIpv6 (6),
                  eIpv4 (7)
            }
    MAX-ACCESS read-write
    STATUS     current
    DESCRIPTION
            "-- empty --"
    ::= { lcsSetupRoutProtBgpPolicyFiltersEntry 3 }

-- {COLUMN} 1.3.6.1.4.1.2356.11.2.93.1.5.6.1.4
lcsSetupRoutProtBgpPolicyFiltersEntryMatch OBJECT-TYPE
    SYNTAX     DisplayString (SIZE(0..80))
    MAX-ACCESS read-write
    STATUS     current
    DESCRIPTION
            "-- empty --"
    ::= { lcsSetupRoutProtBgpPolicyFiltersEntry 4 }

-- {COLUMN} 1.3.6.1.4.1.2356.11.2.93.1.5.6.1.5
lcsSetupRoutProtBgpPolicyFiltersEntryPolicy OBJECT-TYPE
    SYNTAX     INTEGER {
                  eDeny (0),
                  ePermit (1)
            }
    MAX-ACCESS read-write
    STATUS     current
    DESCRIPTION
            "-- empty --"
    ::= { lcsSetupRoutProtBgpPolicyFiltersEntry 5 }

-- {COLUMN} 1.3.6.1.4.1.2356.11.2.93.1.5.6.1.6
lcsSetupRoutProtBgpPolicyFiltersEntryAction OBJECT-TYPE
    SYNTAX     DisplayString (SIZE(0..16))
    MAX-ACCESS read-write
    STATUS     current
    DESCRIPTION
            "-- empty --"
    ::= { lcsSetupRoutProtBgpPolicyFiltersEntry 6 }

-- {COLUMN} 1.3.6.1.4.1.2356.11.2.93.1.5.6.1.7
lcsSetupRoutProtBgpPolicyFiltersEntryComment OBJECT-TYPE
    SYNTAX     DisplayString (SIZE(0..254))
    MAX-ACCESS read-write
    STATUS     current
    DESCRIPTION
            "-- empty --"
    ::= { lcsSetupRoutProtBgpPolicyFiltersEntry 7 }

-- {NODE} 1.3.6.1.4.1.2356.11.2.93.1.6
lcsSetupRoutProtBgpNetworks OBJECT IDENTIFIER ::= { lcsSetupRoutProtBgp 6 }

-- {TABLE} 1.3.6.1.4.1.2356.11.2.93.1.6.1
lcsSetupRoutProtBgpNetworksIpv4Table OBJECT-TYPE
    SYNTAX     SEQUENCE OF LcsSetupRoutProtBgpNetworksIpv4Entry
    MAX-ACCESS not-accessible
    STATUS     current
    DESCRIPTION
            "-- empty --"
    ::= { lcsSetupRoutProtBgpNetworks 1 }

-- {ROW} 1.3.6.1.4.1.2356.11.2.93.1.6.1.1
lcsSetupRoutProtBgpNetworksIpv4Entry OBJECT-TYPE
    SYNTAX     LcsSetupRoutProtBgpNetworksIpv4Entry
    MAX-ACCESS not-accessible
    STATUS     current
    DESCRIPTION
            ""
    INDEX {
            lcsSetupRoutProtBgpNetworksIpv4EntryIpAddress,
            lcsSetupRoutProtBgpNetworksIpv4EntryNetmask,
            lcsSetupRoutProtBgpNetworksIpv4EntryRtgTag
          }
    ::= { lcsSetupRoutProtBgpNetworksIpv4Table 1 }

LcsSetupRoutProtBgpNetworksIpv4Entry ::= SEQUENCE {
            lcsSetupRoutProtBgpNetworksIpv4EntryIpAddress DisplayString,
            lcsSetupRoutProtBgpNetworksIpv4EntryNetmask DisplayString,
            lcsSetupRoutProtBgpNetworksIpv4EntryRtgTag Integer32,
            lcsSetupRoutProtBgpNetworksIpv4EntryType INTEGER,
            lcsSetupRoutProtBgpNetworksIpv4EntryComment DisplayString
    }

-- {COLUMN} 1.3.6.1.4.1.2356.11.2.93.1.6.1.1.1
lcsSetupRoutProtBgpNetworksIpv4EntryIpAddress OBJECT-TYPE
    SYNTAX     DisplayString (SIZE(0..15))
    MAX-ACCESS read-write
    STATUS     current
    DESCRIPTION
            "-- empty --"
    ::= { lcsSetupRoutProtBgpNetworksIpv4Entry 1 }

-- {COLUMN} 1.3.6.1.4.1.2356.11.2.93.1.6.1.1.2
lcsSetupRoutProtBgpNetworksIpv4EntryNetmask OBJECT-TYPE
    SYNTAX     DisplayString (SIZE(0..15))
    MAX-ACCESS read-write
    STATUS     current
    DESCRIPTION
            "-- empty --"
    ::= { lcsSetupRoutProtBgpNetworksIpv4Entry 2 }

-- {COLUMN} 1.3.6.1.4.1.2356.11.2.93.1.6.1.1.3
lcsSetupRoutProtBgpNetworksIpv4EntryRtgTag OBJECT-TYPE
    SYNTAX     Integer32 (0..65535)
    MAX-ACCESS read-write
    STATUS     current
    DESCRIPTION
            "-- empty --"
    ::= { lcsSetupRoutProtBgpNetworksIpv4Entry 3 }

-- {COLUMN} 1.3.6.1.4.1.2356.11.2.93.1.6.1.1.4
lcsSetupRoutProtBgpNetworksIpv4EntryType OBJECT-TYPE
    SYNTAX     INTEGER {
                  eStatic (0),
                  eDynamic (1)
            }
    MAX-ACCESS read-write
    STATUS     current
    DESCRIPTION
            "-- empty --"
    ::= { lcsSetupRoutProtBgpNetworksIpv4Entry 4 }

-- {COLUMN} 1.3.6.1.4.1.2356.11.2.93.1.6.1.1.5
lcsSetupRoutProtBgpNetworksIpv4EntryComment OBJECT-TYPE
    SYNTAX     DisplayString (SIZE(0..254))
    MAX-ACCESS read-write
    STATUS     current
    DESCRIPTION
            "-- empty --"
    ::= { lcsSetupRoutProtBgpNetworksIpv4Entry 5 }

-- {TABLE} 1.3.6.1.4.1.2356.11.2.93.1.6.2
lcsSetupRoutProtBgpNetworksIpv6Table OBJECT-TYPE
    SYNTAX     SEQUENCE OF LcsSetupRoutProtBgpNetworksIpv6Entry
    MAX-ACCESS not-accessible
    STATUS     current
    DESCRIPTION
            "-- empty --"
    ::= { lcsSetupRoutProtBgpNetworks 2 }

-- {ROW} 1.3.6.1.4.1.2356.11.2.93.1.6.2.1
lcsSetupRoutProtBgpNetworksIpv6Entry OBJECT-TYPE
    SYNTAX     LcsSetupRoutProtBgpNetworksIpv6Entry
    MAX-ACCESS not-accessible
    STATUS     current
    DESCRIPTION
            ""
    INDEX {
            lcsSetupRoutProtBgpNetworksIpv6EntryPrefix,
            lcsSetupRoutProtBgpNetworksIpv6EntryPrefixLength,
            lcsSetupRoutProtBgpNetworksIpv6EntryRtgTag
          }
    ::= { lcsSetupRoutProtBgpNetworksIpv6Table 1 }

LcsSetupRoutProtBgpNetworksIpv6Entry ::= SEQUENCE {
            lcsSetupRoutProtBgpNetworksIpv6EntryPrefix DisplayString,
            lcsSetupRoutProtBgpNetworksIpv6EntryPrefixLength Integer32,
            lcsSetupRoutProtBgpNetworksIpv6EntryRtgTag Integer32,
            lcsSetupRoutProtBgpNetworksIpv6EntryType INTEGER,
            lcsSetupRoutProtBgpNetworksIpv6EntryComment DisplayString
    }

-- {COLUMN} 1.3.6.1.4.1.2356.11.2.93.1.6.2.1.1
lcsSetupRoutProtBgpNetworksIpv6EntryPrefix OBJECT-TYPE
    SYNTAX     DisplayString (SIZE(0..39))
    MAX-ACCESS read-write
    STATUS     current
    DESCRIPTION
            "-- empty --"
    ::= { lcsSetupRoutProtBgpNetworksIpv6Entry 1 }

-- {COLUMN} 1.3.6.1.4.1.2356.11.2.93.1.6.2.1.2
lcsSetupRoutProtBgpNetworksIpv6EntryPrefixLength OBJECT-TYPE
    SYNTAX     Integer32 (0..255)
    MAX-ACCESS read-write
    STATUS     current
    DESCRIPTION
            "-- empty --"
    ::= { lcsSetupRoutProtBgpNetworksIpv6Entry 2 }

-- {COLUMN} 1.3.6.1.4.1.2356.11.2.93.1.6.2.1.3
lcsSetupRoutProtBgpNetworksIpv6EntryRtgTag OBJECT-TYPE
    SYNTAX     Integer32 (0..65535)
    MAX-ACCESS read-write
    STATUS     current
    DESCRIPTION
            "-- empty --"
    ::= { lcsSetupRoutProtBgpNetworksIpv6Entry 3 }

-- {COLUMN} 1.3.6.1.4.1.2356.11.2.93.1.6.2.1.4
lcsSetupRoutProtBgpNetworksIpv6EntryType OBJECT-TYPE
    SYNTAX     INTEGER {
                  eStatic (0),
                  eDynamic (1)
            }
    MAX-ACCESS read-write
    STATUS     current
    DESCRIPTION
            "-- empty --"
    ::= { lcsSetupRoutProtBgpNetworksIpv6Entry 4 }

-- {COLUMN} 1.3.6.1.4.1.2356.11.2.93.1.6.2.1.5
lcsSetupRoutProtBgpNetworksIpv6EntryComment OBJECT-TYPE
    SYNTAX     DisplayString (SIZE(0..254))
    MAX-ACCESS read-write
    STATUS     current
    DESCRIPTION
            "-- empty --"
    ::= { lcsSetupRoutProtBgpNetworksIpv6Entry 5 }

-- {SCALAR} 1.3.6.1.4.1.2356.11.2.93.1.7
lcsSetupRoutProtBgpOperating OBJECT-TYPE
    SYNTAX     INTEGER {
                  eNo (0),
                  eYes (1)
            }
    MAX-ACCESS read-write
    STATUS     current
    DESCRIPTION
            "-- empty --"
    ::= { lcsSetupRoutProtBgp 7 }

-- {SCALAR} 1.3.6.1.4.1.2356.11.2.93.1.8
lcsSetupRoutProtBgpAutoRestart OBJECT-TYPE
    SYNTAX     INTEGER {
                  eNo (0),
                  eYes (1)
            }
    MAX-ACCESS read-write
    STATUS     current
    DESCRIPTION
            "-- empty --"
    ::= { lcsSetupRoutProtBgp 8 }

-- {SCALAR} 1.3.6.1.4.1.2356.11.2.93.1.9
lcsSetupRoutProtBgpManualStart OBJECT-TYPE
    SYNTAX     DisplayString
    MAX-ACCESS read-write
    STATUS     current
    DESCRIPTION
            "-- empty --"
    ::= { lcsSetupRoutProtBgp 9 }

-- {SCALAR} 1.3.6.1.4.1.2356.11.2.93.1.10
lcsSetupRoutProtBgpManualStop OBJECT-TYPE
    SYNTAX     DisplayString
    MAX-ACCESS read-write
    STATUS     current
    DESCRIPTION
            "-- empty --"
    ::= { lcsSetupRoutProtBgp 10 }

-- {SCALAR} 1.3.6.1.4.1.2356.11.2.93.1.11
lcsSetupRoutProtBgpActiveStart OBJECT-TYPE
    SYNTAX     DisplayString
    MAX-ACCESS read-write
    STATUS     current
    DESCRIPTION
            "-- empty --"
    ::= { lcsSetupRoutProtBgp 11 }

-- {SCALAR} 1.3.6.1.4.1.2356.11.2.93.1.12
lcsSetupRoutProtBgpRestart OBJECT-TYPE
    SYNTAX     DisplayString
    MAX-ACCESS read-write
    STATUS     current
    DESCRIPTION
            "-- empty --"
    ::= { lcsSetupRoutProtBgp 12 }

-- {SCALAR} 1.3.6.1.4.1.2356.11.2.93.1.13
lcsSetupRoutProtBgpGlobalReadOnlyTimer OBJECT-TYPE
    SYNTAX     Integer32 (0..65535)
    MAX-ACCESS read-write
    STATUS     current
    DESCRIPTION
            "-- empty --"
    ::= { lcsSetupRoutProtBgp 13 }

-- {SCALAR} 1.3.6.1.4.1.2356.11.2.93.1.14
lcsSetupRoutProtBgpPeerReadOnlyTimer OBJECT-TYPE
    SYNTAX     Integer32 (0..65535)
    MAX-ACCESS read-write
    STATUS     current
    DESCRIPTION
            "-- empty --"
    ::= { lcsSetupRoutProtBgp 14 }

-- {SCALAR} 1.3.6.1.4.1.2356.11.2.93.1.15
lcsSetupRoutProtBgpSendRefreshRequest OBJECT-TYPE
    SYNTAX     DisplayString
    MAX-ACCESS read-write
    STATUS     current
    DESCRIPTION
            "-- empty --"
    ::= { lcsSetupRoutProtBgp 15 }

-- {NODE} 1.3.6.1.4.1.2356.11.2.93.2
lcsSetupRoutProtRouteMonitor OBJECT IDENTIFIER ::= { lcsSetupRoutProt 2 }

-- {TABLE} 1.3.6.1.4.1.2356.11.2.93.2.1
lcsSetupRoutProtRouteMonitorMonitorTableTable OBJECT-TYPE
    SYNTAX     SEQUENCE OF LcsSetupRoutProtRouteMonitorMonitorTableEntry
    MAX-ACCESS not-accessible
    STATUS     current
    DESCRIPTION
            "-- empty --"
    ::= { lcsSetupRoutProtRouteMonitor 1 }

-- {ROW} 1.3.6.1.4.1.2356.11.2.93.2.1.1
lcsSetupRoutProtRouteMonitorMonitorTableEntry OBJECT-TYPE
    SYNTAX     LcsSetupRoutProtRouteMonitorMonitorTableEntry
    MAX-ACCESS not-accessible
    STATUS     current
    DESCRIPTION
            ""
    INDEX {
            lcsSetupRoutProtRouteMonitorMonitorTableEntryBackupPeer,
            lcsSetupRoutProtRouteMonitorMonitorTableEntryPrefix,
            lcsSetupRoutProtRouteMonitorMonitorTableEntryRtgTag
          }
    ::= { lcsSetupRoutProtRouteMonitorMonitorTableTable 1 }

LcsSetupRoutProtRouteMonitorMonitorTableEntry ::= SEQUENCE {
            lcsSetupRoutProtRouteMonitorMonitorTableEntryBackupPeer DisplayString,
            lcsSetupRoutProtRouteMonitorMonitorTableEntryPrefix DisplayString,
            lcsSetupRoutProtRouteMonitorMonitorTableEntryRtgTag Integer32,
            lcsSetupRoutProtRouteMonitorMonitorTableEntryUpDelay Integer32,
            lcsSetupRoutProtRouteMonitorMonitorTableEntryDownDelay Integer32,
            lcsSetupRoutProtRouteMonitorMonitorTableEntryActive INTEGER,
            lcsSetupRoutProtRouteMonitorMonitorTableEntryComment DisplayString
    }

-- {COLUMN} 1.3.6.1.4.1.2356.11.2.93.2.1.1.1
lcsSetupRoutProtRouteMonitorMonitorTableEntryBackupPeer OBJECT-TYPE
    SYNTAX     DisplayString (SIZE(0..16))
    MAX-ACCESS read-write
    STATUS     current
    DESCRIPTION
            "-- empty --"
    ::= { lcsSetupRoutProtRouteMonitorMonitorTableEntry 1 }

-- {COLUMN} 1.3.6.1.4.1.2356.11.2.93.2.1.1.2
lcsSetupRoutProtRouteMonitorMonitorTableEntryPrefix OBJECT-TYPE
    SYNTAX     DisplayString (SIZE(0..43))
    MAX-ACCESS read-write
    STATUS     current
    DESCRIPTION
            "-- empty --"
    ::= { lcsSetupRoutProtRouteMonitorMonitorTableEntry 2 }

-- {COLUMN} 1.3.6.1.4.1.2356.11.2.93.2.1.1.3
lcsSetupRoutProtRouteMonitorMonitorTableEntryRtgTag OBJECT-TYPE
    SYNTAX     Integer32 (0..65535)
    MAX-ACCESS read-write
    STATUS     current
    DESCRIPTION
            "-- empty --"
    ::= { lcsSetupRoutProtRouteMonitorMonitorTableEntry 3 }

-- {COLUMN} 1.3.6.1.4.1.2356.11.2.93.2.1.1.4
lcsSetupRoutProtRouteMonitorMonitorTableEntryUpDelay OBJECT-TYPE
    SYNTAX     Integer32 (0..2147483647)
    MAX-ACCESS read-write
    STATUS     current
    DESCRIPTION
            "-- empty --"
    ::= { lcsSetupRoutProtRouteMonitorMonitorTableEntry 4 }

-- {COLUMN} 1.3.6.1.4.1.2356.11.2.93.2.1.1.5
lcsSetupRoutProtRouteMonitorMonitorTableEntryDownDelay OBJECT-TYPE
    SYNTAX     Integer32 (0..2147483647)
    MAX-ACCESS read-write
    STATUS     current
    DESCRIPTION
            "-- empty --"
    ::= { lcsSetupRoutProtRouteMonitorMonitorTableEntry 5 }

-- {COLUMN} 1.3.6.1.4.1.2356.11.2.93.2.1.1.6
lcsSetupRoutProtRouteMonitorMonitorTableEntryActive OBJECT-TYPE
    SYNTAX     INTEGER {
                  eNo (0),
                  eYes (1)
            }
    MAX-ACCESS read-write
    STATUS     current
    DESCRIPTION
            "-- empty --"
    ::= { lcsSetupRoutProtRouteMonitorMonitorTableEntry 6 }

-- {COLUMN} 1.3.6.1.4.1.2356.11.2.93.2.1.1.7
lcsSetupRoutProtRouteMonitorMonitorTableEntryComment OBJECT-TYPE
    SYNTAX     DisplayString (SIZE(0..254))
    MAX-ACCESS read-write
    STATUS     current
    DESCRIPTION
            "-- empty --"
    ::= { lcsSetupRoutProtRouteMonitorMonitorTableEntry 7 }

-- {SCALAR} 1.3.6.1.4.1.2356.11.2.93.2.2
lcsSetupRoutProtRouteMonitorOperating OBJECT-TYPE
    SYNTAX     INTEGER {
                  eNo (0),
                  eYes (1)
            }
    MAX-ACCESS read-write
    STATUS     current
    DESCRIPTION
            "-- empty --"
    ::= { lcsSetupRoutProtRouteMonitor 2 }

-- {NODE} 1.3.6.1.4.1.2356.11.2.93.3
lcsSetupRoutProtOspf OBJECT IDENTIFIER ::= { lcsSetupRoutProt 3 }

-- {TABLE} 1.3.6.1.4.1.2356.11.2.93.3.1
lcsSetupRoutProtOspfOspfInstanceTable OBJECT-TYPE
    SYNTAX     SEQUENCE OF LcsSetupRoutProtOspfOspfInstanceEntry
    MAX-ACCESS not-accessible
    STATUS     current
    DESCRIPTION
            "-- empty --"
    ::= { lcsSetupRoutProtOspf 1 }

-- {ROW} 1.3.6.1.4.1.2356.11.2.93.3.1.1
lcsSetupRoutProtOspfOspfInstanceEntry OBJECT-TYPE
    SYNTAX     LcsSetupRoutProtOspfOspfInstanceEntry
    MAX-ACCESS not-accessible
    STATUS     current
    DESCRIPTION
            ""
    INDEX {
            lcsSetupRoutProtOspfOspfInstanceEntryOspfInstance
          }
    ::= { lcsSetupRoutProtOspfOspfInstanceTable 1 }

LcsSetupRoutProtOspfOspfInstanceEntry ::= SEQUENCE {
            lcsSetupRoutProtOspfOspfInstanceEntryOspfInstance DisplayString,
            lcsSetupRoutProtOspfOspfInstanceEntryOperating INTEGER,
            lcsSetupRoutProtOspfOspfInstanceEntryRouterId IpAddress,
            lcsSetupRoutProtOspfOspfInstanceEntryRtgTag Integer32,
            lcsSetupRoutProtOspfOspfInstanceEntryAdvertiseDefaultRoute INTEGER,
            lcsSetupRoutProtOspfOspfInstanceEntryIntraAreaDistance Integer32,
            lcsSetupRoutProtOspfOspfInstanceEntryInterAreaDistance Integer32,
            lcsSetupRoutProtOspfOspfInstanceEntryExternalDistance Integer32
    }

-- {COLUMN} 1.3.6.1.4.1.2356.11.2.93.3.1.1.1
lcsSetupRoutProtOspfOspfInstanceEntryOspfInstance OBJECT-TYPE
    SYNTAX     DisplayString (SIZE(0..16))
    MAX-ACCESS read-write
    STATUS     current
    DESCRIPTION
            "-- empty --"
    ::= { lcsSetupRoutProtOspfOspfInstanceEntry 1 }

-- {COLUMN} 1.3.6.1.4.1.2356.11.2.93.3.1.1.2
lcsSetupRoutProtOspfOspfInstanceEntryOperating OBJECT-TYPE
    SYNTAX     INTEGER {
                  eNo (0),
                  eYes (1)
            }
    MAX-ACCESS read-write
    STATUS     current
    DESCRIPTION
            "-- empty --"
    ::= { lcsSetupRoutProtOspfOspfInstanceEntry 2 }

-- {COLUMN} 1.3.6.1.4.1.2356.11.2.93.3.1.1.3
lcsSetupRoutProtOspfOspfInstanceEntryRouterId OBJECT-TYPE
    SYNTAX     IpAddress
    MAX-ACCESS read-write
    STATUS     current
    DESCRIPTION
            "-- empty --"
    ::= { lcsSetupRoutProtOspfOspfInstanceEntry 3 }

-- {COLUMN} 1.3.6.1.4.1.2356.11.2.93.3.1.1.5
lcsSetupRoutProtOspfOspfInstanceEntryRtgTag OBJECT-TYPE
    SYNTAX     Integer32 (0..65535)
    MAX-ACCESS read-write
    STATUS     current
    DESCRIPTION
            "-- empty --"
    ::= { lcsSetupRoutProtOspfOspfInstanceEntry 5 }

-- {COLUMN} 1.3.6.1.4.1.2356.11.2.93.3.1.1.6
lcsSetupRoutProtOspfOspfInstanceEntryAdvertiseDefaultRoute OBJECT-TYPE
    SYNTAX     INTEGER {
                  eNo (0),
                  eYes (1),
                  eDynamic (2)
            }
    MAX-ACCESS read-write
    STATUS     current
    DESCRIPTION
            "-- empty --"
    ::= { lcsSetupRoutProtOspfOspfInstanceEntry 6 }

-- {COLUMN} 1.3.6.1.4.1.2356.11.2.93.3.1.1.7
lcsSetupRoutProtOspfOspfInstanceEntryIntraAreaDistance OBJECT-TYPE
    SYNTAX     Integer32 (0..255)
    MAX-ACCESS read-write
    STATUS     current
    DESCRIPTION
            "-- empty --"
    ::= { lcsSetupRoutProtOspfOspfInstanceEntry 7 }

-- {COLUMN} 1.3.6.1.4.1.2356.11.2.93.3.1.1.8
lcsSetupRoutProtOspfOspfInstanceEntryInterAreaDistance OBJECT-TYPE
    SYNTAX     Integer32 (0..255)
    MAX-ACCESS read-write
    STATUS     current
    DESCRIPTION
            "-- empty --"
    ::= { lcsSetupRoutProtOspfOspfInstanceEntry 8 }

-- {COLUMN} 1.3.6.1.4.1.2356.11.2.93.3.1.1.9
lcsSetupRoutProtOspfOspfInstanceEntryExternalDistance OBJECT-TYPE
    SYNTAX     Integer32 (0..255)
    MAX-ACCESS read-write
    STATUS     current
    DESCRIPTION
            "-- empty --"
    ::= { lcsSetupRoutProtOspfOspfInstanceEntry 9 }

-- {TABLE} 1.3.6.1.4.1.2356.11.2.93.3.2
lcsSetupRoutProtOspfAreasTable OBJECT-TYPE
    SYNTAX     SEQUENCE OF LcsSetupRoutProtOspfAreasEntry
    MAX-ACCESS not-accessible
    STATUS     current
    DESCRIPTION
            "-- empty --"
    ::= { lcsSetupRoutProtOspf 2 }

-- {ROW} 1.3.6.1.4.1.2356.11.2.93.3.2.1
lcsSetupRoutProtOspfAreasEntry OBJECT-TYPE
    SYNTAX     LcsSetupRoutProtOspfAreasEntry
    MAX-ACCESS not-accessible
    STATUS     current
    DESCRIPTION
            ""
    INDEX {
            lcsSetupRoutProtOspfAreasEntryOspfInstance,
            lcsSetupRoutProtOspfAreasEntryAreaId
          }
    ::= { lcsSetupRoutProtOspfAreasTable 1 }

LcsSetupRoutProtOspfAreasEntry ::= SEQUENCE {
            lcsSetupRoutProtOspfAreasEntryOspfInstance DisplayString,
            lcsSetupRoutProtOspfAreasEntryAreaId IpAddress,
            lcsSetupRoutProtOspfAreasEntryType INTEGER,
            lcsSetupRoutProtOspfAreasEntryStubDefaultCost Integer32
    }

-- {COLUMN} 1.3.6.1.4.1.2356.11.2.93.3.2.1.1
lcsSetupRoutProtOspfAreasEntryOspfInstance OBJECT-TYPE
    SYNTAX     DisplayString (SIZE(0..16))
    MAX-ACCESS read-write
    STATUS     current
    DESCRIPTION
            "-- empty --"
    ::= { lcsSetupRoutProtOspfAreasEntry 1 }

-- {COLUMN} 1.3.6.1.4.1.2356.11.2.93.3.2.1.2
lcsSetupRoutProtOspfAreasEntryAreaId OBJECT-TYPE
    SYNTAX     IpAddress
    MAX-ACCESS read-write
    STATUS     current
    DESCRIPTION
            "-- empty --"
    ::= { lcsSetupRoutProtOspfAreasEntry 2 }

-- {COLUMN} 1.3.6.1.4.1.2356.11.2.93.3.2.1.3
lcsSetupRoutProtOspfAreasEntryType OBJECT-TYPE
    SYNTAX     INTEGER {
                  eNormal (0),
                  eStub (1)
            }
    MAX-ACCESS read-write
    STATUS     current
    DESCRIPTION
            "-- empty --"
    ::= { lcsSetupRoutProtOspfAreasEntry 3 }

-- {COLUMN} 1.3.6.1.4.1.2356.11.2.93.3.2.1.4
lcsSetupRoutProtOspfAreasEntryStubDefaultCost OBJECT-TYPE
    SYNTAX     Integer32 (0..2147483647)
    MAX-ACCESS read-write
    STATUS     current
    DESCRIPTION
            "-- empty --"
    ::= { lcsSetupRoutProtOspfAreasEntry 4 }

-- {TABLE} 1.3.6.1.4.1.2356.11.2.93.3.3
lcsSetupRoutProtOspfAreaAddressAggregationTable OBJECT-TYPE
    SYNTAX     SEQUENCE OF LcsSetupRoutProtOspfAreaAddressAggregationEntry
    MAX-ACCESS not-accessible
    STATUS     current
    DESCRIPTION
            "-- empty --"
    ::= { lcsSetupRoutProtOspf 3 }

-- {ROW} 1.3.6.1.4.1.2356.11.2.93.3.3.1
lcsSetupRoutProtOspfAreaAddressAggregationEntry OBJECT-TYPE
    SYNTAX     LcsSetupRoutProtOspfAreaAddressAggregationEntry
    MAX-ACCESS not-accessible
    STATUS     current
    DESCRIPTION
            ""
    INDEX {
            lcsSetupRoutProtOspfAreaAddressAggregationEntryOspfInstance,
            lcsSetupRoutProtOspfAreaAddressAggregationEntryAreaId,
            lcsSetupRoutProtOspfAreaAddressAggregationEntryIpAddress,
            lcsSetupRoutProtOspfAreaAddressAggregationEntryIpNetmask
          }
    ::= { lcsSetupRoutProtOspfAreaAddressAggregationTable 1 }

LcsSetupRoutProtOspfAreaAddressAggregationEntry ::= SEQUENCE {
            lcsSetupRoutProtOspfAreaAddressAggregationEntryOspfInstance DisplayString,
            lcsSetupRoutProtOspfAreaAddressAggregationEntryAreaId IpAddress,
            lcsSetupRoutProtOspfAreaAddressAggregationEntryIpAddress DisplayString,
            lcsSetupRoutProtOspfAreaAddressAggregationEntryIpNetmask DisplayString,
            lcsSetupRoutProtOspfAreaAddressAggregationEntryAdvertise INTEGER
    }

-- {COLUMN} 1.3.6.1.4.1.2356.11.2.93.3.3.1.1
lcsSetupRoutProtOspfAreaAddressAggregationEntryOspfInstance OBJECT-TYPE
    SYNTAX     DisplayString (SIZE(0..16))
    MAX-ACCESS read-write
    STATUS     current
    DESCRIPTION
            "-- empty --"
    ::= { lcsSetupRoutProtOspfAreaAddressAggregationEntry 1 }

-- {COLUMN} 1.3.6.1.4.1.2356.11.2.93.3.3.1.2
lcsSetupRoutProtOspfAreaAddressAggregationEntryAreaId OBJECT-TYPE
    SYNTAX     IpAddress
    MAX-ACCESS read-write
    STATUS     current
    DESCRIPTION
            "-- empty --"
    ::= { lcsSetupRoutProtOspfAreaAddressAggregationEntry 2 }

-- {COLUMN} 1.3.6.1.4.1.2356.11.2.93.3.3.1.3
lcsSetupRoutProtOspfAreaAddressAggregationEntryIpAddress OBJECT-TYPE
    SYNTAX     DisplayString (SIZE(0..39))
    MAX-ACCESS read-write
    STATUS     current
    DESCRIPTION
            "-- empty --"
    ::= { lcsSetupRoutProtOspfAreaAddressAggregationEntry 3 }

-- {COLUMN} 1.3.6.1.4.1.2356.11.2.93.3.3.1.4
lcsSetupRoutProtOspfAreaAddressAggregationEntryIpNetmask OBJECT-TYPE
    SYNTAX     DisplayString (SIZE(0..39))
    MAX-ACCESS read-write
    STATUS     current
    DESCRIPTION
            "-- empty --"
    ::= { lcsSetupRoutProtOspfAreaAddressAggregationEntry 4 }

-- {COLUMN} 1.3.6.1.4.1.2356.11.2.93.3.3.1.5
lcsSetupRoutProtOspfAreaAddressAggregationEntryAdvertise OBJECT-TYPE
    SYNTAX     INTEGER {
                  eNo (0),
                  eYes (1)
            }
    MAX-ACCESS read-write
    STATUS     current
    DESCRIPTION
            "-- empty --"
    ::= { lcsSetupRoutProtOspfAreaAddressAggregationEntry 5 }

-- {TABLE} 1.3.6.1.4.1.2356.11.2.93.3.4
lcsSetupRoutProtOspfInterfacesTable OBJECT-TYPE
    SYNTAX     SEQUENCE OF LcsSetupRoutProtOspfInterfacesEntry
    MAX-ACCESS not-accessible
    STATUS     current
    DESCRIPTION
            "-- empty --"
    ::= { lcsSetupRoutProtOspf 4 }

-- {ROW} 1.3.6.1.4.1.2356.11.2.93.3.4.1
lcsSetupRoutProtOspfInterfacesEntry OBJECT-TYPE
    SYNTAX     LcsSetupRoutProtOspfInterfacesEntry
    MAX-ACCESS not-accessible
    STATUS     current
    DESCRIPTION
            ""
    INDEX {
            lcsSetupRoutProtOspfInterfacesEntryInterface,
            lcsSetupRoutProtOspfInterfacesEntryOspfInstance
          }
    ::= { lcsSetupRoutProtOspfInterfacesTable 1 }

LcsSetupRoutProtOspfInterfacesEntry ::= SEQUENCE {
            lcsSetupRoutProtOspfInterfacesEntryInterface DisplayString,
            lcsSetupRoutProtOspfInterfacesEntryOspfInstance DisplayString,
            lcsSetupRoutProtOspfInterfacesEntryAreaId IpAddress,
            lcsSetupRoutProtOspfInterfacesEntryType INTEGER,
            lcsSetupRoutProtOspfInterfacesEntryOutputCost Integer32,
            lcsSetupRoutProtOspfInterfacesEntryRxmtInterval Integer32,
            lcsSetupRoutProtOspfInterfacesEntryInfTransDelay Integer32,
            lcsSetupRoutProtOspfInterfacesEntryRouterPriority Integer32,
            lcsSetupRoutProtOspfInterfacesEntryHelloInterval Integer32,
            lcsSetupRoutProtOspfInterfacesEntryRouterDeadInterval Integer32,
            lcsSetupRoutProtOspfInterfacesEntryAuthenticationType INTEGER,
            lcsSetupRoutProtOspfInterfacesEntryAuthenticationKey DisplayString,
            lcsSetupRoutProtOspfInterfacesEntryPassive INTEGER,
            lcsSetupRoutProtOspfInterfacesEntryMtuIgnore INTEGER
    }

-- {COLUMN} 1.3.6.1.4.1.2356.11.2.93.3.4.1.1
lcsSetupRoutProtOspfInterfacesEntryInterface OBJECT-TYPE
    SYNTAX     DisplayString (SIZE(0..16))
    MAX-ACCESS read-write
    STATUS     current
    DESCRIPTION
            "-- empty --"
    ::= { lcsSetupRoutProtOspfInterfacesEntry 1 }

-- {COLUMN} 1.3.6.1.4.1.2356.11.2.93.3.4.1.2
lcsSetupRoutProtOspfInterfacesEntryOspfInstance OBJECT-TYPE
    SYNTAX     DisplayString (SIZE(0..16))
    MAX-ACCESS read-write
    STATUS     current
    DESCRIPTION
            "-- empty --"
    ::= { lcsSetupRoutProtOspfInterfacesEntry 2 }

-- {COLUMN} 1.3.6.1.4.1.2356.11.2.93.3.4.1.3
lcsSetupRoutProtOspfInterfacesEntryAreaId OBJECT-TYPE
    SYNTAX     IpAddress
    MAX-ACCESS read-write
    STATUS     current
    DESCRIPTION
            "-- empty --"
    ::= { lcsSetupRoutProtOspfInterfacesEntry 3 }

-- {COLUMN} 1.3.6.1.4.1.2356.11.2.93.3.4.1.4
lcsSetupRoutProtOspfInterfacesEntryType OBJECT-TYPE
    SYNTAX     INTEGER {
                  eBroadcast (0),
                  ePointToPoint (1),
                  eNbma (2),
                  ePointToMultipoint (3)
            }
    MAX-ACCESS read-write
    STATUS     current
    DESCRIPTION
            "-- empty --"
    ::= { lcsSetupRoutProtOspfInterfacesEntry 4 }

-- {COLUMN} 1.3.6.1.4.1.2356.11.2.93.3.4.1.5
lcsSetupRoutProtOspfInterfacesEntryOutputCost OBJECT-TYPE
    SYNTAX     Integer32 (0..2147483647)
    MAX-ACCESS read-write
    STATUS     current
    DESCRIPTION
            "-- empty --"
    ::= { lcsSetupRoutProtOspfInterfacesEntry 5 }

-- {COLUMN} 1.3.6.1.4.1.2356.11.2.93.3.4.1.6
lcsSetupRoutProtOspfInterfacesEntryRxmtInterval OBJECT-TYPE
    SYNTAX     Integer32 (0..2147483647)
    MAX-ACCESS read-write
    STATUS     current
    DESCRIPTION
            "-- empty --"
    ::= { lcsSetupRoutProtOspfInterfacesEntry 6 }

-- {COLUMN} 1.3.6.1.4.1.2356.11.2.93.3.4.1.7
lcsSetupRoutProtOspfInterfacesEntryInfTransDelay OBJECT-TYPE
    SYNTAX     Integer32 (0..2147483647)
    MAX-ACCESS read-write
    STATUS     current
    DESCRIPTION
            "-- empty --"
    ::= { lcsSetupRoutProtOspfInterfacesEntry 7 }

-- {COLUMN} 1.3.6.1.4.1.2356.11.2.93.3.4.1.8
lcsSetupRoutProtOspfInterfacesEntryRouterPriority OBJECT-TYPE
    SYNTAX     Integer32 (0..255)
    MAX-ACCESS read-write
    STATUS     current
    DESCRIPTION
            "-- empty --"
    ::= { lcsSetupRoutProtOspfInterfacesEntry 8 }

-- {COLUMN} 1.3.6.1.4.1.2356.11.2.93.3.4.1.9
lcsSetupRoutProtOspfInterfacesEntryHelloInterval OBJECT-TYPE
    SYNTAX     Integer32 (0..2147483647)
    MAX-ACCESS read-write
    STATUS     current
    DESCRIPTION
            "-- empty --"
    ::= { lcsSetupRoutProtOspfInterfacesEntry 9 }

-- {COLUMN} 1.3.6.1.4.1.2356.11.2.93.3.4.1.10
lcsSetupRoutProtOspfInterfacesEntryRouterDeadInterval OBJECT-TYPE
    SYNTAX     Integer32 (0..2147483647)
    MAX-ACCESS read-write
    STATUS     current
    DESCRIPTION
            "-- empty --"
    ::= { lcsSetupRoutProtOspfInterfacesEntry 10 }

-- {COLUMN} 1.3.6.1.4.1.2356.11.2.93.3.4.1.11
lcsSetupRoutProtOspfInterfacesEntryAuthenticationType OBJECT-TYPE
    SYNTAX     INTEGER {
                  eNull (0),
                  eSimplePassword (1),
                  eCryptographicMd5 (2)
            }
    MAX-ACCESS read-write
    STATUS     current
    DESCRIPTION
            "-- empty --"
    ::= { lcsSetupRoutProtOspfInterfacesEntry 11 }

-- {COLUMN} 1.3.6.1.4.1.2356.11.2.93.3.4.1.12
lcsSetupRoutProtOspfInterfacesEntryAuthenticationKey OBJECT-TYPE
    SYNTAX     DisplayString (SIZE(0..16))
    MAX-ACCESS read-write
    STATUS     current
    DESCRIPTION
            "-- empty --"
    ::= { lcsSetupRoutProtOspfInterfacesEntry 12 }

-- {COLUMN} 1.3.6.1.4.1.2356.11.2.93.3.4.1.13
lcsSetupRoutProtOspfInterfacesEntryPassive OBJECT-TYPE
    SYNTAX     INTEGER {
                  eNo (0),
                  eYes (1)
            }
    MAX-ACCESS read-write
    STATUS     current
    DESCRIPTION
            "-- empty --"
    ::= { lcsSetupRoutProtOspfInterfacesEntry 13 }

-- {COLUMN} 1.3.6.1.4.1.2356.11.2.93.3.4.1.14
lcsSetupRoutProtOspfInterfacesEntryMtuIgnore OBJECT-TYPE
    SYNTAX     INTEGER {
                  eNo (0),
                  eYes (1)
            }
    MAX-ACCESS read-write
    STATUS     current
    DESCRIPTION
            "-- empty --"
    ::= { lcsSetupRoutProtOspfInterfacesEntry 14 }

-- {TABLE} 1.3.6.1.4.1.2356.11.2.93.3.5
lcsSetupRoutProtOspfVirtualLinksTable OBJECT-TYPE
    SYNTAX     SEQUENCE OF LcsSetupRoutProtOspfVirtualLinksEntry
    MAX-ACCESS not-accessible
    STATUS     current
    DESCRIPTION
            "-- empty --"
    ::= { lcsSetupRoutProtOspf 5 }

-- {ROW} 1.3.6.1.4.1.2356.11.2.93.3.5.1
lcsSetupRoutProtOspfVirtualLinksEntry OBJECT-TYPE
    SYNTAX     LcsSetupRoutProtOspfVirtualLinksEntry
    MAX-ACCESS not-accessible
    STATUS     current
    DESCRIPTION
            ""
    INDEX {
            lcsSetupRoutProtOspfVirtualLinksEntryOspfInstance,
            lcsSetupRoutProtOspfVirtualLinksEntryTransitAreaId,
            lcsSetupRoutProtOspfVirtualLinksEntryRouterId
          }
    ::= { lcsSetupRoutProtOspfVirtualLinksTable 1 }

LcsSetupRoutProtOspfVirtualLinksEntry ::= SEQUENCE {
            lcsSetupRoutProtOspfVirtualLinksEntryOspfInstance DisplayString,
            lcsSetupRoutProtOspfVirtualLinksEntryTransitAreaId IpAddress,
            lcsSetupRoutProtOspfVirtualLinksEntryRouterId IpAddress,
            lcsSetupRoutProtOspfVirtualLinksEntryAuthenticationType INTEGER,
            lcsSetupRoutProtOspfVirtualLinksEntryAuthenticationKey DisplayString,
            lcsSetupRoutProtOspfVirtualLinksEntryRxmtInterval Integer32,
            lcsSetupRoutProtOspfVirtualLinksEntryHelloInterval Integer32,
            lcsSetupRoutProtOspfVirtualLinksEntryRouterDeadInterval Integer32
    }

-- {COLUMN} 1.3.6.1.4.1.2356.11.2.93.3.5.1.1
lcsSetupRoutProtOspfVirtualLinksEntryOspfInstance OBJECT-TYPE
    SYNTAX     DisplayString (SIZE(0..16))
    MAX-ACCESS read-write
    STATUS     current
    DESCRIPTION
            "-- empty --"
    ::= { lcsSetupRoutProtOspfVirtualLinksEntry 1 }

-- {COLUMN} 1.3.6.1.4.1.2356.11.2.93.3.5.1.2
lcsSetupRoutProtOspfVirtualLinksEntryTransitAreaId OBJECT-TYPE
    SYNTAX     IpAddress
    MAX-ACCESS read-write
    STATUS     current
    DESCRIPTION
            "-- empty --"
    ::= { lcsSetupRoutProtOspfVirtualLinksEntry 2 }

-- {COLUMN} 1.3.6.1.4.1.2356.11.2.93.3.5.1.3
lcsSetupRoutProtOspfVirtualLinksEntryRouterId OBJECT-TYPE
    SYNTAX     IpAddress
    MAX-ACCESS read-write
    STATUS     current
    DESCRIPTION
            "-- empty --"
    ::= { lcsSetupRoutProtOspfVirtualLinksEntry 3 }

-- {COLUMN} 1.3.6.1.4.1.2356.11.2.93.3.5.1.4
lcsSetupRoutProtOspfVirtualLinksEntryAuthenticationType OBJECT-TYPE
    SYNTAX     INTEGER {
                  eNull (0),
                  eSimplePassword (1),
                  eCryptographicMd5 (2)
            }
    MAX-ACCESS read-write
    STATUS     current
    DESCRIPTION
            "-- empty --"
    ::= { lcsSetupRoutProtOspfVirtualLinksEntry 4 }

-- {COLUMN} 1.3.6.1.4.1.2356.11.2.93.3.5.1.5
lcsSetupRoutProtOspfVirtualLinksEntryAuthenticationKey OBJECT-TYPE
    SYNTAX     DisplayString (SIZE(0..16))
    MAX-ACCESS read-write
    STATUS     current
    DESCRIPTION
            "-- empty --"
    ::= { lcsSetupRoutProtOspfVirtualLinksEntry 5 }

-- {COLUMN} 1.3.6.1.4.1.2356.11.2.93.3.5.1.6
lcsSetupRoutProtOspfVirtualLinksEntryRxmtInterval OBJECT-TYPE
    SYNTAX     Integer32 (0..2147483647)
    MAX-ACCESS read-write
    STATUS     current
    DESCRIPTION
            "-- empty --"
    ::= { lcsSetupRoutProtOspfVirtualLinksEntry 6 }

-- {COLUMN} 1.3.6.1.4.1.2356.11.2.93.3.5.1.7
lcsSetupRoutProtOspfVirtualLinksEntryHelloInterval OBJECT-TYPE
    SYNTAX     Integer32 (0..2147483647)
    MAX-ACCESS read-write
    STATUS     current
    DESCRIPTION
            "-- empty --"
    ::= { lcsSetupRoutProtOspfVirtualLinksEntry 7 }

-- {COLUMN} 1.3.6.1.4.1.2356.11.2.93.3.5.1.8
lcsSetupRoutProtOspfVirtualLinksEntryRouterDeadInterval OBJECT-TYPE
    SYNTAX     Integer32 (0..2147483647)
    MAX-ACCESS read-write
    STATUS     current
    DESCRIPTION
            "-- empty --"
    ::= { lcsSetupRoutProtOspfVirtualLinksEntry 8 }

-- {TABLE} 1.3.6.1.4.1.2356.11.2.93.3.6
lcsSetupRoutProtOspfNbmaNeighborsTable OBJECT-TYPE
    SYNTAX     SEQUENCE OF LcsSetupRoutProtOspfNbmaNeighborsEntry
    MAX-ACCESS not-accessible
    STATUS     current
    DESCRIPTION
            "-- empty --"
    ::= { lcsSetupRoutProtOspf 6 }

-- {ROW} 1.3.6.1.4.1.2356.11.2.93.3.6.1
lcsSetupRoutProtOspfNbmaNeighborsEntry OBJECT-TYPE
    SYNTAX     LcsSetupRoutProtOspfNbmaNeighborsEntry
    MAX-ACCESS not-accessible
    STATUS     current
    DESCRIPTION
            ""
    INDEX {
            lcsSetupRoutProtOspfNbmaNeighborsEntryOspfInstance,
            lcsSetupRoutProtOspfNbmaNeighborsEntryInterface,
            lcsSetupRoutProtOspfNbmaNeighborsEntryIpAddress
          }
    ::= { lcsSetupRoutProtOspfNbmaNeighborsTable 1 }

LcsSetupRoutProtOspfNbmaNeighborsEntry ::= SEQUENCE {
            lcsSetupRoutProtOspfNbmaNeighborsEntryOspfInstance DisplayString,
            lcsSetupRoutProtOspfNbmaNeighborsEntryInterface DisplayString,
            lcsSetupRoutProtOspfNbmaNeighborsEntryIpAddress IpAddress,
            lcsSetupRoutProtOspfNbmaNeighborsEntryPollInterval Integer32,
            lcsSetupRoutProtOspfNbmaNeighborsEntryEligibleAsDesignatedRouter INTEGER
    }

-- {COLUMN} 1.3.6.1.4.1.2356.11.2.93.3.6.1.1
lcsSetupRoutProtOspfNbmaNeighborsEntryOspfInstance OBJECT-TYPE
    SYNTAX     DisplayString (SIZE(0..16))
    MAX-ACCESS read-write
    STATUS     current
    DESCRIPTION
            "-- empty --"
    ::= { lcsSetupRoutProtOspfNbmaNeighborsEntry 1 }

-- {COLUMN} 1.3.6.1.4.1.2356.11.2.93.3.6.1.2
lcsSetupRoutProtOspfNbmaNeighborsEntryInterface OBJECT-TYPE
    SYNTAX     DisplayString (SIZE(0..16))
    MAX-ACCESS read-write
    STATUS     current
    DESCRIPTION
            "-- empty --"
    ::= { lcsSetupRoutProtOspfNbmaNeighborsEntry 2 }

-- {COLUMN} 1.3.6.1.4.1.2356.11.2.93.3.6.1.3
lcsSetupRoutProtOspfNbmaNeighborsEntryIpAddress OBJECT-TYPE
    SYNTAX     IpAddress
    MAX-ACCESS read-write
    STATUS     current
    DESCRIPTION
            "-- empty --"
    ::= { lcsSetupRoutProtOspfNbmaNeighborsEntry 3 }

-- {COLUMN} 1.3.6.1.4.1.2356.11.2.93.3.6.1.4
lcsSetupRoutProtOspfNbmaNeighborsEntryPollInterval OBJECT-TYPE
    SYNTAX     Integer32 (0..2147483647)
    MAX-ACCESS read-write
    STATUS     current
    DESCRIPTION
            "-- empty --"
    ::= { lcsSetupRoutProtOspfNbmaNeighborsEntry 4 }

-- {COLUMN} 1.3.6.1.4.1.2356.11.2.93.3.6.1.5
lcsSetupRoutProtOspfNbmaNeighborsEntryEligibleAsDesignatedRouter OBJECT-TYPE
    SYNTAX     INTEGER {
                  eNo (0),
                  eYes (1)
            }
    MAX-ACCESS read-write
    STATUS     current
    DESCRIPTION
            "-- empty --"
    ::= { lcsSetupRoutProtOspfNbmaNeighborsEntry 5 }

-- {TABLE} 1.3.6.1.4.1.2356.11.2.93.3.7
lcsSetupRoutProtOspfPTMpNbrsTable OBJECT-TYPE
    SYNTAX     SEQUENCE OF LcsSetupRoutProtOspfPTMpNbrsEntry
    MAX-ACCESS not-accessible
    STATUS     current
    DESCRIPTION
            ""
    ::= { lcsSetupRoutProtOspf 7 }

-- {ROW} 1.3.6.1.4.1.2356.11.2.93.3.7.1
lcsSetupRoutProtOspfPTMpNbrsEntry OBJECT-TYPE
    SYNTAX     LcsSetupRoutProtOspfPTMpNbrsEntry
    MAX-ACCESS not-accessible
    STATUS     current
    DESCRIPTION
            ""
    INDEX {
            lcsSetupRoutProtOspfPTMpNbrsEntryOspfInstance,
            lcsSetupRoutProtOspfPTMpNbrsEntryInterface,
            lcsSetupRoutProtOspfPTMpNbrsEntryIpAddress
          }
    ::= { lcsSetupRoutProtOspfPTMpNbrsTable 1 }

LcsSetupRoutProtOspfPTMpNbrsEntry ::= SEQUENCE {
            lcsSetupRoutProtOspfPTMpNbrsEntryOspfInstance DisplayString,
            lcsSetupRoutProtOspfPTMpNbrsEntryInterface DisplayString,
            lcsSetupRoutProtOspfPTMpNbrsEntryIpAddress IpAddress,
            lcsSetupRoutProtOspfPTMpNbrsEntryPollInterval Integer32
    }

-- {COLUMN} 1.3.6.1.4.1.2356.11.2.93.3.7.1.1
lcsSetupRoutProtOspfPTMpNbrsEntryOspfInstance OBJECT-TYPE
    SYNTAX     DisplayString (SIZE(0..16))
    MAX-ACCESS read-write
    STATUS     current
    DESCRIPTION
            "-- empty --"
    ::= { lcsSetupRoutProtOspfPTMpNbrsEntry 1 }

-- {COLUMN} 1.3.6.1.4.1.2356.11.2.93.3.7.1.2
lcsSetupRoutProtOspfPTMpNbrsEntryInterface OBJECT-TYPE
    SYNTAX     DisplayString (SIZE(0..16))
    MAX-ACCESS read-write
    STATUS     current
    DESCRIPTION
            "-- empty --"
    ::= { lcsSetupRoutProtOspfPTMpNbrsEntry 2 }

-- {COLUMN} 1.3.6.1.4.1.2356.11.2.93.3.7.1.3
lcsSetupRoutProtOspfPTMpNbrsEntryIpAddress OBJECT-TYPE
    SYNTAX     IpAddress
    MAX-ACCESS read-write
    STATUS     current
    DESCRIPTION
            "-- empty --"
    ::= { lcsSetupRoutProtOspfPTMpNbrsEntry 3 }

-- {COLUMN} 1.3.6.1.4.1.2356.11.2.93.3.7.1.4
lcsSetupRoutProtOspfPTMpNbrsEntryPollInterval OBJECT-TYPE
    SYNTAX     Integer32 (0..2147483647)
    MAX-ACCESS read-write
    STATUS     current
    DESCRIPTION
            "-- empty --"
    ::= { lcsSetupRoutProtOspfPTMpNbrsEntry 4 }

-- {SCALAR} 1.3.6.1.4.1.2356.11.2.93.3.8
lcsSetupRoutProtOspfOperating OBJECT-TYPE
    SYNTAX     INTEGER {
                  eNo (0),
                  eYes (1)
            }
    MAX-ACCESS read-write
    STATUS     current
    DESCRIPTION
            "-- empty --"
    ::= { lcsSetupRoutProtOspf 8 }

-- {NODE} 1.3.6.1.4.1.2356.11.2.93.3.9
lcsSetupRoutProtOspfRtRedist OBJECT IDENTIFIER ::= { lcsSetupRoutProtOspf 9 }

-- {TABLE} 1.3.6.1.4.1.2356.11.2.93.3.9.1
lcsSetupRoutProtOspfRtRedistBgpTable OBJECT-TYPE
    SYNTAX     SEQUENCE OF LcsSetupRoutProtOspfRtRedistBgpEntry
    MAX-ACCESS not-accessible
    STATUS     current
    DESCRIPTION
            "-- empty --"
    ::= { lcsSetupRoutProtOspfRtRedist 1 }

-- {ROW} 1.3.6.1.4.1.2356.11.2.93.3.9.1.1
lcsSetupRoutProtOspfRtRedistBgpEntry OBJECT-TYPE
    SYNTAX     LcsSetupRoutProtOspfRtRedistBgpEntry
    MAX-ACCESS not-accessible
    STATUS     current
    DESCRIPTION
            ""
    INDEX {
            lcsSetupRoutProtOspfRtRedistBgpEntryOspfInstance,
            lcsSetupRoutProtOspfRtRedistBgpEntryBgpInstance,
            lcsSetupRoutProtOspfRtRedistBgpEntryFilterList
          }
    ::= { lcsSetupRoutProtOspfRtRedistBgpTable 1 }

LcsSetupRoutProtOspfRtRedistBgpEntry ::= SEQUENCE {
            lcsSetupRoutProtOspfRtRedistBgpEntryOspfInstance DisplayString,
            lcsSetupRoutProtOspfRtRedistBgpEntryBgpInstance DisplayString,
            lcsSetupRoutProtOspfRtRedistBgpEntryFilterList DisplayString,
            lcsSetupRoutProtOspfRtRedistBgpEntryMetricSource INTEGER,
            lcsSetupRoutProtOspfRtRedistBgpEntryConstantMetric Integer32,
            lcsSetupRoutProtOspfRtRedistBgpEntryPathType INTEGER,
            lcsSetupRoutProtOspfRtRedistBgpEntryExtRtgTag Integer32,
            lcsSetupRoutProtOspfRtRedistBgpEntryDefaultAction INTEGER
    }

-- {COLUMN} 1.3.6.1.4.1.2356.11.2.93.3.9.1.1.1
lcsSetupRoutProtOspfRtRedistBgpEntryOspfInstance OBJECT-TYPE
    SYNTAX     DisplayString (SIZE(0..16))
    MAX-ACCESS read-write
    STATUS     current
    DESCRIPTION
            "-- empty --"
    ::= { lcsSetupRoutProtOspfRtRedistBgpEntry 1 }

-- {COLUMN} 1.3.6.1.4.1.2356.11.2.93.3.9.1.1.2
lcsSetupRoutProtOspfRtRedistBgpEntryBgpInstance OBJECT-TYPE
    SYNTAX     DisplayString (SIZE(0..16))
    MAX-ACCESS read-write
    STATUS     current
    DESCRIPTION
            "-- empty --"
    ::= { lcsSetupRoutProtOspfRtRedistBgpEntry 2 }

-- {COLUMN} 1.3.6.1.4.1.2356.11.2.93.3.9.1.1.3
lcsSetupRoutProtOspfRtRedistBgpEntryFilterList OBJECT-TYPE
    SYNTAX     DisplayString (SIZE(0..16))
    MAX-ACCESS read-write
    STATUS     current
    DESCRIPTION
            "-- empty --"
    ::= { lcsSetupRoutProtOspfRtRedistBgpEntry 3 }

-- {COLUMN} 1.3.6.1.4.1.2356.11.2.93.3.9.1.1.4
lcsSetupRoutProtOspfRtRedistBgpEntryMetricSource OBJECT-TYPE
    SYNTAX     INTEGER {
                  eConstant (0),
                  eProtocol (1)
            }
    MAX-ACCESS read-write
    STATUS     current
    DESCRIPTION
            "-- empty --"
    ::= { lcsSetupRoutProtOspfRtRedistBgpEntry 4 }

-- {COLUMN} 1.3.6.1.4.1.2356.11.2.93.3.9.1.1.5
lcsSetupRoutProtOspfRtRedistBgpEntryConstantMetric OBJECT-TYPE
    SYNTAX     Integer32 (0..2147483647)
    MAX-ACCESS read-write
    STATUS     current
    DESCRIPTION
            "-- empty --"
    ::= { lcsSetupRoutProtOspfRtRedistBgpEntry 5 }

-- {COLUMN} 1.3.6.1.4.1.2356.11.2.93.3.9.1.1.6
lcsSetupRoutProtOspfRtRedistBgpEntryPathType OBJECT-TYPE
    SYNTAX     INTEGER {
                  eExternalType1 (1),
                  eExternalType2 (2)
            }
    MAX-ACCESS read-write
    STATUS     current
    DESCRIPTION
            "-- empty --"
    ::= { lcsSetupRoutProtOspfRtRedistBgpEntry 6 }

-- {COLUMN} 1.3.6.1.4.1.2356.11.2.93.3.9.1.1.7
lcsSetupRoutProtOspfRtRedistBgpEntryExtRtgTag OBJECT-TYPE
    SYNTAX     Integer32 (0..2147483647)
    MAX-ACCESS read-write
    STATUS     current
    DESCRIPTION
            ""
    ::= { lcsSetupRoutProtOspfRtRedistBgpEntry 7 }

-- {COLUMN} 1.3.6.1.4.1.2356.11.2.93.3.9.1.1.8
lcsSetupRoutProtOspfRtRedistBgpEntryDefaultAction OBJECT-TYPE
    SYNTAX     INTEGER {
                  eAccept (0),
                  eDeny (1)
            }
    MAX-ACCESS read-write
    STATUS     current
    DESCRIPTION
            "-- empty --"
    ::= { lcsSetupRoutProtOspfRtRedistBgpEntry 8 }

-- {TABLE} 1.3.6.1.4.1.2356.11.2.93.3.9.2
lcsSetupRoutProtOspfRtRedistConnectedTable OBJECT-TYPE
    SYNTAX     SEQUENCE OF LcsSetupRoutProtOspfRtRedistConnectedEntry
    MAX-ACCESS not-accessible
    STATUS     current
    DESCRIPTION
            "-- empty --"
    ::= { lcsSetupRoutProtOspfRtRedist 2 }

-- {ROW} 1.3.6.1.4.1.2356.11.2.93.3.9.2.1
lcsSetupRoutProtOspfRtRedistConnectedEntry OBJECT-TYPE
    SYNTAX     LcsSetupRoutProtOspfRtRedistConnectedEntry
    MAX-ACCESS not-accessible
    STATUS     current
    DESCRIPTION
            ""
    INDEX {
            lcsSetupRoutProtOspfRtRedistConnectedEntryOspfInstance,
            lcsSetupRoutProtOspfRtRedistConnectedEntryFilterList
          }
    ::= { lcsSetupRoutProtOspfRtRedistConnectedTable 1 }

LcsSetupRoutProtOspfRtRedistConnectedEntry ::= SEQUENCE {
            lcsSetupRoutProtOspfRtRedistConnectedEntryOspfInstance DisplayString,
            lcsSetupRoutProtOspfRtRedistConnectedEntryFilterList DisplayString,
            lcsSetupRoutProtOspfRtRedistConnectedEntryMetricSource INTEGER,
            lcsSetupRoutProtOspfRtRedistConnectedEntryConstantMetric Integer32,
            lcsSetupRoutProtOspfRtRedistConnectedEntryPathType INTEGER,
            lcsSetupRoutProtOspfRtRedistConnectedEntryExtRtgTag Integer32,
            lcsSetupRoutProtOspfRtRedistConnectedEntryDefaultAction INTEGER
    }

-- {COLUMN} 1.3.6.1.4.1.2356.11.2.93.3.9.2.1.1
lcsSetupRoutProtOspfRtRedistConnectedEntryOspfInstance OBJECT-TYPE
    SYNTAX     DisplayString (SIZE(0..16))
    MAX-ACCESS read-write
    STATUS     current
    DESCRIPTION
            "-- empty --"
    ::= { lcsSetupRoutProtOspfRtRedistConnectedEntry 1 }

-- {COLUMN} 1.3.6.1.4.1.2356.11.2.93.3.9.2.1.2
lcsSetupRoutProtOspfRtRedistConnectedEntryFilterList OBJECT-TYPE
    SYNTAX     DisplayString (SIZE(0..16))
    MAX-ACCESS read-write
    STATUS     current
    DESCRIPTION
            "-- empty --"
    ::= { lcsSetupRoutProtOspfRtRedistConnectedEntry 2 }

-- {COLUMN} 1.3.6.1.4.1.2356.11.2.93.3.9.2.1.3
lcsSetupRoutProtOspfRtRedistConnectedEntryMetricSource OBJECT-TYPE
    SYNTAX     INTEGER {
                  eConstant (0),
                  eProtocol (1)
            }
    MAX-ACCESS read-write
    STATUS     current
    DESCRIPTION
            "-- empty --"
    ::= { lcsSetupRoutProtOspfRtRedistConnectedEntry 3 }

-- {COLUMN} 1.3.6.1.4.1.2356.11.2.93.3.9.2.1.4
lcsSetupRoutProtOspfRtRedistConnectedEntryConstantMetric OBJECT-TYPE
    SYNTAX     Integer32 (0..2147483647)
    MAX-ACCESS read-write
    STATUS     current
    DESCRIPTION
            "-- empty --"
    ::= { lcsSetupRoutProtOspfRtRedistConnectedEntry 4 }

-- {COLUMN} 1.3.6.1.4.1.2356.11.2.93.3.9.2.1.5
lcsSetupRoutProtOspfRtRedistConnectedEntryPathType OBJECT-TYPE
    SYNTAX     INTEGER {
                  eExternalType1 (1),
                  eExternalType2 (2)
            }
    MAX-ACCESS read-write
    STATUS     current
    DESCRIPTION
            "-- empty --"
    ::= { lcsSetupRoutProtOspfRtRedistConnectedEntry 5 }

-- {COLUMN} 1.3.6.1.4.1.2356.11.2.93.3.9.2.1.6
lcsSetupRoutProtOspfRtRedistConnectedEntryExtRtgTag OBJECT-TYPE
    SYNTAX     Integer32 (0..2147483647)
    MAX-ACCESS read-write
    STATUS     current
    DESCRIPTION
            ""
    ::= { lcsSetupRoutProtOspfRtRedistConnectedEntry 6 }

-- {COLUMN} 1.3.6.1.4.1.2356.11.2.93.3.9.2.1.7
lcsSetupRoutProtOspfRtRedistConnectedEntryDefaultAction OBJECT-TYPE
    SYNTAX     INTEGER {
                  eAccept (0),
                  eDeny (1)
            }
    MAX-ACCESS read-write
    STATUS     current
    DESCRIPTION
            "-- empty --"
    ::= { lcsSetupRoutProtOspfRtRedistConnectedEntry 7 }

-- {TABLE} 1.3.6.1.4.1.2356.11.2.93.3.9.4
lcsSetupRoutProtOspfRtRedistStaticTable OBJECT-TYPE
    SYNTAX     SEQUENCE OF LcsSetupRoutProtOspfRtRedistStaticEntry
    MAX-ACCESS not-accessible
    STATUS     current
    DESCRIPTION
            "-- empty --"
    ::= { lcsSetupRoutProtOspfRtRedist 4 }

-- {ROW} 1.3.6.1.4.1.2356.11.2.93.3.9.4.1
lcsSetupRoutProtOspfRtRedistStaticEntry OBJECT-TYPE
    SYNTAX     LcsSetupRoutProtOspfRtRedistStaticEntry
    MAX-ACCESS not-accessible
    STATUS     current
    DESCRIPTION
            ""
    INDEX {
            lcsSetupRoutProtOspfRtRedistStaticEntryOspfInstance,
            lcsSetupRoutProtOspfRtRedistStaticEntryFilterList
          }
    ::= { lcsSetupRoutProtOspfRtRedistStaticTable 1 }

LcsSetupRoutProtOspfRtRedistStaticEntry ::= SEQUENCE {
            lcsSetupRoutProtOspfRtRedistStaticEntryOspfInstance DisplayString,
            lcsSetupRoutProtOspfRtRedistStaticEntryFilterList DisplayString,
            lcsSetupRoutProtOspfRtRedistStaticEntryMetricSource INTEGER,
            lcsSetupRoutProtOspfRtRedistStaticEntryConstantMetric Integer32,
            lcsSetupRoutProtOspfRtRedistStaticEntryPathType INTEGER,
            lcsSetupRoutProtOspfRtRedistStaticEntryExtRtgTag Integer32,
            lcsSetupRoutProtOspfRtRedistStaticEntryDefaultAction INTEGER
    }

-- {COLUMN} 1.3.6.1.4.1.2356.11.2.93.3.9.4.1.1
lcsSetupRoutProtOspfRtRedistStaticEntryOspfInstance OBJECT-TYPE
    SYNTAX     DisplayString (SIZE(0..16))
    MAX-ACCESS read-write
    STATUS     current
    DESCRIPTION
            "-- empty --"
    ::= { lcsSetupRoutProtOspfRtRedistStaticEntry 1 }

-- {COLUMN} 1.3.6.1.4.1.2356.11.2.93.3.9.4.1.2
lcsSetupRoutProtOspfRtRedistStaticEntryFilterList OBJECT-TYPE
    SYNTAX     DisplayString (SIZE(0..16))
    MAX-ACCESS read-write
    STATUS     current
    DESCRIPTION
            "-- empty --"
    ::= { lcsSetupRoutProtOspfRtRedistStaticEntry 2 }

-- {COLUMN} 1.3.6.1.4.1.2356.11.2.93.3.9.4.1.3
lcsSetupRoutProtOspfRtRedistStaticEntryMetricSource OBJECT-TYPE
    SYNTAX     INTEGER {
                  eConstant (0),
                  eProtocol (1)
            }
    MAX-ACCESS read-write
    STATUS     current
    DESCRIPTION
            "-- empty --"
    ::= { lcsSetupRoutProtOspfRtRedistStaticEntry 3 }

-- {COLUMN} 1.3.6.1.4.1.2356.11.2.93.3.9.4.1.4
lcsSetupRoutProtOspfRtRedistStaticEntryConstantMetric OBJECT-TYPE
    SYNTAX     Integer32 (0..2147483647)
    MAX-ACCESS read-write
    STATUS     current
    DESCRIPTION
            "-- empty --"
    ::= { lcsSetupRoutProtOspfRtRedistStaticEntry 4 }

-- {COLUMN} 1.3.6.1.4.1.2356.11.2.93.3.9.4.1.5
lcsSetupRoutProtOspfRtRedistStaticEntryPathType OBJECT-TYPE
    SYNTAX     INTEGER {
                  eExternalType1 (1),
                  eExternalType2 (2)
            }
    MAX-ACCESS read-write
    STATUS     current
    DESCRIPTION
            "-- empty --"
    ::= { lcsSetupRoutProtOspfRtRedistStaticEntry 5 }

-- {COLUMN} 1.3.6.1.4.1.2356.11.2.93.3.9.4.1.6
lcsSetupRoutProtOspfRtRedistStaticEntryExtRtgTag OBJECT-TYPE
    SYNTAX     Integer32 (0..2147483647)
    MAX-ACCESS read-write
    STATUS     current
    DESCRIPTION
            ""
    ::= { lcsSetupRoutProtOspfRtRedistStaticEntry 6 }

-- {COLUMN} 1.3.6.1.4.1.2356.11.2.93.3.9.4.1.7
lcsSetupRoutProtOspfRtRedistStaticEntryDefaultAction OBJECT-TYPE
    SYNTAX     INTEGER {
                  eAccept (0),
                  eDeny (1)
            }
    MAX-ACCESS read-write
    STATUS     current
    DESCRIPTION
            "-- empty --"
    ::= { lcsSetupRoutProtOspfRtRedistStaticEntry 7 }

-- {NODE} 1.3.6.1.4.1.2356.11.2.93.4
lcsSetupRoutProtLisp OBJECT IDENTIFIER ::= { lcsSetupRoutProt 4 }

-- {TABLE} 1.3.6.1.4.1.2356.11.2.93.4.1
lcsSetupRoutProtLispInstancesTable OBJECT-TYPE
    SYNTAX     SEQUENCE OF LcsSetupRoutProtLispInstancesEntry
    MAX-ACCESS not-accessible
    STATUS     current
    DESCRIPTION
            "-- empty --"
    ::= { lcsSetupRoutProtLisp 1 }

-- {ROW} 1.3.6.1.4.1.2356.11.2.93.4.1.1
lcsSetupRoutProtLispInstancesEntry OBJECT-TYPE
    SYNTAX     LcsSetupRoutProtLispInstancesEntry
    MAX-ACCESS not-accessible
    STATUS     current
    DESCRIPTION
            ""
    INDEX {
            lcsSetupRoutProtLispInstancesEntryName
          }
    ::= { lcsSetupRoutProtLispInstancesTable 1 }

LcsSetupRoutProtLispInstancesEntry ::= SEQUENCE {
            lcsSetupRoutProtLispInstancesEntryName DisplayString,
            lcsSetupRoutProtLispInstancesEntryOperating INTEGER,
            lcsSetupRoutProtLispInstancesEntryEidRtgTag Integer32,
            lcsSetupRoutProtLispInstancesEntryRlocRtgTag Integer32,
            lcsSetupRoutProtLispInstancesEntryInstanceId Integer32,
            lcsSetupRoutProtLispInstancesEntryProbingMethod INTEGER,
            lcsSetupRoutProtLispInstancesEntryIpv4 DisplayString,
            lcsSetupRoutProtLispInstancesEntryIpv6 DisplayString,
            lcsSetupRoutProtLispInstancesEntryAdminDistance Integer32,
            lcsSetupRoutProtLispInstancesEntryAcceptUnknownItrs INTEGER
    }

-- {COLUMN} 1.3.6.1.4.1.2356.11.2.93.4.1.1.1
lcsSetupRoutProtLispInstancesEntryName OBJECT-TYPE
    SYNTAX     DisplayString (SIZE(0..24))
    MAX-ACCESS read-write
    STATUS     current
    DESCRIPTION
            "-- empty --"
    ::= { lcsSetupRoutProtLispInstancesEntry 1 }

-- {COLUMN} 1.3.6.1.4.1.2356.11.2.93.4.1.1.2
lcsSetupRoutProtLispInstancesEntryOperating OBJECT-TYPE
    SYNTAX     INTEGER {
                  eNo (0),
                  eYes (1)
            }
    MAX-ACCESS read-write
    STATUS     current
    DESCRIPTION
            "-- empty --"
    ::= { lcsSetupRoutProtLispInstancesEntry 2 }

-- {COLUMN} 1.3.6.1.4.1.2356.11.2.93.4.1.1.3
lcsSetupRoutProtLispInstancesEntryEidRtgTag OBJECT-TYPE
    SYNTAX     Integer32 (0..2147483647)
    MAX-ACCESS read-write
    STATUS     current
    DESCRIPTION
            "-- empty --"
    ::= { lcsSetupRoutProtLispInstancesEntry 3 }

-- {COLUMN} 1.3.6.1.4.1.2356.11.2.93.4.1.1.4
lcsSetupRoutProtLispInstancesEntryRlocRtgTag OBJECT-TYPE
    SYNTAX     Integer32 (0..2147483647)
    MAX-ACCESS read-write
    STATUS     current
    DESCRIPTION
            "-- empty --"
    ::= { lcsSetupRoutProtLispInstancesEntry 4 }

-- {COLUMN} 1.3.6.1.4.1.2356.11.2.93.4.1.1.5
lcsSetupRoutProtLispInstancesEntryInstanceId OBJECT-TYPE
    SYNTAX     Integer32 (0..2147483647)
    MAX-ACCESS read-write
    STATUS     current
    DESCRIPTION
            "-- empty --"
    ::= { lcsSetupRoutProtLispInstancesEntry 5 }

-- {COLUMN} 1.3.6.1.4.1.2356.11.2.93.4.1.1.6
lcsSetupRoutProtLispInstancesEntryProbingMethod OBJECT-TYPE
    SYNTAX     INTEGER {
                  eOff (0),
                  eRlocProbing (1)
            }
    MAX-ACCESS read-write
    STATUS     current
    DESCRIPTION
            "-- empty --"
    ::= { lcsSetupRoutProtLispInstancesEntry 6 }

-- {COLUMN} 1.3.6.1.4.1.2356.11.2.93.4.1.1.7
lcsSetupRoutProtLispInstancesEntryIpv4 OBJECT-TYPE
    SYNTAX     DisplayString (SIZE(0..16))
    MAX-ACCESS read-write
    STATUS     current
    DESCRIPTION
            "-- empty --"
    ::= { lcsSetupRoutProtLispInstancesEntry 7 }

-- {COLUMN} 1.3.6.1.4.1.2356.11.2.93.4.1.1.8
lcsSetupRoutProtLispInstancesEntryIpv6 OBJECT-TYPE
    SYNTAX     DisplayString (SIZE(0..16))
    MAX-ACCESS read-write
    STATUS     current
    DESCRIPTION
            "-- empty --"
    ::= { lcsSetupRoutProtLispInstancesEntry 8 }

-- {COLUMN} 1.3.6.1.4.1.2356.11.2.93.4.1.1.9
lcsSetupRoutProtLispInstancesEntryAdminDistance OBJECT-TYPE
    SYNTAX     Integer32 (0..255)
    MAX-ACCESS read-write
    STATUS     current
    DESCRIPTION
            "-- empty --"
    ::= { lcsSetupRoutProtLispInstancesEntry 9 }

-- {COLUMN} 1.3.6.1.4.1.2356.11.2.93.4.1.1.10
lcsSetupRoutProtLispInstancesEntryAcceptUnknownItrs OBJECT-TYPE
    SYNTAX     INTEGER {
                  eNo (0),
                  eYes (1)
            }
    MAX-ACCESS read-write
    STATUS     current
    DESCRIPTION
            "-- empty --"
    ::= { lcsSetupRoutProtLispInstancesEntry 10 }

-- {TABLE} 1.3.6.1.4.1.2356.11.2.93.4.2
lcsSetupRoutProtLispEidMappingTable OBJECT-TYPE
    SYNTAX     SEQUENCE OF LcsSetupRoutProtLispEidMappingEntry
    MAX-ACCESS not-accessible
    STATUS     current
    DESCRIPTION
            "-- empty --"
    ::= { lcsSetupRoutProtLisp 2 }

-- {ROW} 1.3.6.1.4.1.2356.11.2.93.4.2.1
lcsSetupRoutProtLispEidMappingEntry OBJECT-TYPE
    SYNTAX     LcsSetupRoutProtLispEidMappingEntry
    MAX-ACCESS not-accessible
    STATUS     current
    DESCRIPTION
            ""
    INDEX {
            lcsSetupRoutProtLispEidMappingEntryName,
            lcsSetupRoutProtLispEidMappingEntryEidAddressType,
            lcsSetupRoutProtLispEidMappingEntryEidPrefix,
            lcsSetupRoutProtLispEidMappingEntryLocatorAddressType,
            lcsSetupRoutProtLispEidMappingEntryLocator
          }
    ::= { lcsSetupRoutProtLispEidMappingTable 1 }

LcsSetupRoutProtLispEidMappingEntry ::= SEQUENCE {
            lcsSetupRoutProtLispEidMappingEntryName DisplayString,
            lcsSetupRoutProtLispEidMappingEntryEidAddressType BITS,
            lcsSetupRoutProtLispEidMappingEntryEidPrefix DisplayString,
            lcsSetupRoutProtLispEidMappingEntryLocatorAddressType BITS,
            lcsSetupRoutProtLispEidMappingEntryLocator DisplayString,
            lcsSetupRoutProtLispEidMappingEntryOperating INTEGER,
            lcsSetupRoutProtLispEidMappingEntryPriority Integer32,
            lcsSetupRoutProtLispEidMappingEntryWeight Integer32,
            lcsSetupRoutProtLispEidMappingEntryComment DisplayString
    }

-- {COLUMN} 1.3.6.1.4.1.2356.11.2.93.4.2.1.1
lcsSetupRoutProtLispEidMappingEntryName OBJECT-TYPE
    SYNTAX     DisplayString (SIZE(0..24))
    MAX-ACCESS read-write
    STATUS     current
    DESCRIPTION
            "-- empty --"
    ::= { lcsSetupRoutProtLispEidMappingEntry 1 }

-- {COLUMN} 1.3.6.1.4.1.2356.11.2.93.4.2.1.2
lcsSetupRoutProtLispEidMappingEntryEidAddressType OBJECT-TYPE
    SYNTAX     BITS {
                  eIpv6 (6),
                  eIpv4 (7)
            }
    MAX-ACCESS read-write
    STATUS     current
    DESCRIPTION
            "-- empty --"
    ::= { lcsSetupRoutProtLispEidMappingEntry 2 }

-- {COLUMN} 1.3.6.1.4.1.2356.11.2.93.4.2.1.3
lcsSetupRoutProtLispEidMappingEntryEidPrefix OBJECT-TYPE
    SYNTAX     DisplayString (SIZE(0..43))
    MAX-ACCESS read-write
    STATUS     current
    DESCRIPTION
            "-- empty --"
    ::= { lcsSetupRoutProtLispEidMappingEntry 3 }

-- {COLUMN} 1.3.6.1.4.1.2356.11.2.93.4.2.1.4
lcsSetupRoutProtLispEidMappingEntryLocatorAddressType OBJECT-TYPE
    SYNTAX     BITS {
                  eIpv6 (6),
                  eIpv4 (7)
            }
    MAX-ACCESS read-write
    STATUS     current
    DESCRIPTION
            "-- empty --"
    ::= { lcsSetupRoutProtLispEidMappingEntry 4 }

-- {COLUMN} 1.3.6.1.4.1.2356.11.2.93.4.2.1.5
lcsSetupRoutProtLispEidMappingEntryLocator OBJECT-TYPE
    SYNTAX     DisplayString (SIZE(0..39))
    MAX-ACCESS read-write
    STATUS     current
    DESCRIPTION
            "-- empty --"
    ::= { lcsSetupRoutProtLispEidMappingEntry 5 }

-- {COLUMN} 1.3.6.1.4.1.2356.11.2.93.4.2.1.6
lcsSetupRoutProtLispEidMappingEntryOperating OBJECT-TYPE
    SYNTAX     INTEGER {
                  eNo (0),
                  eYes (1)
            }
    MAX-ACCESS read-write
    STATUS     current
    DESCRIPTION
            "-- empty --"
    ::= { lcsSetupRoutProtLispEidMappingEntry 6 }

-- {COLUMN} 1.3.6.1.4.1.2356.11.2.93.4.2.1.7
lcsSetupRoutProtLispEidMappingEntryPriority OBJECT-TYPE
    SYNTAX     Integer32 (0..255)
    MAX-ACCESS read-write
    STATUS     current
    DESCRIPTION
            "-- empty --"
    ::= { lcsSetupRoutProtLispEidMappingEntry 7 }

-- {COLUMN} 1.3.6.1.4.1.2356.11.2.93.4.2.1.8
lcsSetupRoutProtLispEidMappingEntryWeight OBJECT-TYPE
    SYNTAX     Integer32 (0..255)
    MAX-ACCESS read-write
    STATUS     current
    DESCRIPTION
            "-- empty --"
    ::= { lcsSetupRoutProtLispEidMappingEntry 8 }

-- {COLUMN} 1.3.6.1.4.1.2356.11.2.93.4.2.1.9
lcsSetupRoutProtLispEidMappingEntryComment OBJECT-TYPE
    SYNTAX     DisplayString (SIZE(0..25))
    MAX-ACCESS read-write
    STATUS     current
    DESCRIPTION
            "-- empty --"
    ::= { lcsSetupRoutProtLispEidMappingEntry 9 }

-- {TABLE} 1.3.6.1.4.1.2356.11.2.93.4.3
lcsSetupRoutProtLispItrSettingsTable OBJECT-TYPE
    SYNTAX     SEQUENCE OF LcsSetupRoutProtLispItrSettingsEntry
    MAX-ACCESS not-accessible
    STATUS     current
    DESCRIPTION
            "-- empty --"
    ::= { lcsSetupRoutProtLisp 3 }

-- {ROW} 1.3.6.1.4.1.2356.11.2.93.4.3.1
lcsSetupRoutProtLispItrSettingsEntry OBJECT-TYPE
    SYNTAX     LcsSetupRoutProtLispItrSettingsEntry
    MAX-ACCESS not-accessible
    STATUS     current
    DESCRIPTION
            ""
    INDEX {
            lcsSetupRoutProtLispItrSettingsEntryName
          }
    ::= { lcsSetupRoutProtLispItrSettingsTable 1 }

LcsSetupRoutProtLispItrSettingsEntry ::= SEQUENCE {
            lcsSetupRoutProtLispItrSettingsEntryName DisplayString,
            lcsSetupRoutProtLispItrSettingsEntryMapResolver DisplayString,
            lcsSetupRoutProtLispItrSettingsEntryOperating INTEGER,
            lcsSetupRoutProtLispItrSettingsEntryLoopbackAddress DisplayString,
            lcsSetupRoutProtLispItrSettingsEntryRtgTag Integer32,
            lcsSetupRoutProtLispItrSettingsEntryMapResolverRetries Integer32,
            lcsSetupRoutProtLispItrSettingsEntryMapRequestRouteIpv4 DisplayString,
            lcsSetupRoutProtLispItrSettingsEntryMapRequestRouteIpv6 DisplayString
    }

-- {COLUMN} 1.3.6.1.4.1.2356.11.2.93.4.3.1.1
lcsSetupRoutProtLispItrSettingsEntryName OBJECT-TYPE
    SYNTAX     DisplayString (SIZE(0..24))
    MAX-ACCESS read-write
    STATUS     current
    DESCRIPTION
            "-- empty --"
    ::= { lcsSetupRoutProtLispItrSettingsEntry 1 }

-- {COLUMN} 1.3.6.1.4.1.2356.11.2.93.4.3.1.2
lcsSetupRoutProtLispItrSettingsEntryMapResolver OBJECT-TYPE
    SYNTAX     DisplayString (SIZE(0..39))
    MAX-ACCESS read-write
    STATUS     current
    DESCRIPTION
            "-- empty --"
    ::= { lcsSetupRoutProtLispItrSettingsEntry 2 }

-- {COLUMN} 1.3.6.1.4.1.2356.11.2.93.4.3.1.3
lcsSetupRoutProtLispItrSettingsEntryOperating OBJECT-TYPE
    SYNTAX     INTEGER {
                  eNo (0),
                  eYes (1)
            }
    MAX-ACCESS read-write
    STATUS     current
    DESCRIPTION
            "-- empty --"
    ::= { lcsSetupRoutProtLispItrSettingsEntry 3 }

-- {COLUMN} 1.3.6.1.4.1.2356.11.2.93.4.3.1.4
lcsSetupRoutProtLispItrSettingsEntryLoopbackAddress OBJECT-TYPE
    SYNTAX     DisplayString (SIZE(0..16))
    MAX-ACCESS read-write
    STATUS     current
    DESCRIPTION
            "-- empty --"
    ::= { lcsSetupRoutProtLispItrSettingsEntry 4 }

-- {COLUMN} 1.3.6.1.4.1.2356.11.2.93.4.3.1.5
lcsSetupRoutProtLispItrSettingsEntryRtgTag OBJECT-TYPE
    SYNTAX     Integer32 (0..65535)
    MAX-ACCESS read-write
    STATUS     current
    DESCRIPTION
            "-- empty --"
    ::= { lcsSetupRoutProtLispItrSettingsEntry 5 }

-- {COLUMN} 1.3.6.1.4.1.2356.11.2.93.4.3.1.6
lcsSetupRoutProtLispItrSettingsEntryMapResolverRetries OBJECT-TYPE
    SYNTAX     Integer32 (0..255)
    MAX-ACCESS read-write
    STATUS     current
    DESCRIPTION
            "-- empty --"
    ::= { lcsSetupRoutProtLispItrSettingsEntry 6 }

-- {COLUMN} 1.3.6.1.4.1.2356.11.2.93.4.3.1.7
lcsSetupRoutProtLispItrSettingsEntryMapRequestRouteIpv4 OBJECT-TYPE
    SYNTAX     DisplayString (SIZE(0..18))
    MAX-ACCESS read-write
    STATUS     current
    DESCRIPTION
            "-- empty --"
    ::= { lcsSetupRoutProtLispItrSettingsEntry 7 }

-- {COLUMN} 1.3.6.1.4.1.2356.11.2.93.4.3.1.8
lcsSetupRoutProtLispItrSettingsEntryMapRequestRouteIpv6 OBJECT-TYPE
    SYNTAX     DisplayString (SIZE(0..43))
    MAX-ACCESS read-write
    STATUS     current
    DESCRIPTION
            "-- empty --"
    ::= { lcsSetupRoutProtLispItrSettingsEntry 8 }

-- {TABLE} 1.3.6.1.4.1.2356.11.2.93.4.4
lcsSetupRoutProtLispEtrSettingsTable OBJECT-TYPE
    SYNTAX     SEQUENCE OF LcsSetupRoutProtLispEtrSettingsEntry
    MAX-ACCESS not-accessible
    STATUS     current
    DESCRIPTION
            "-- empty --"
    ::= { lcsSetupRoutProtLisp 4 }

-- {ROW} 1.3.6.1.4.1.2356.11.2.93.4.4.1
lcsSetupRoutProtLispEtrSettingsEntry OBJECT-TYPE
    SYNTAX     LcsSetupRoutProtLispEtrSettingsEntry
    MAX-ACCESS not-accessible
    STATUS     current
    DESCRIPTION
            ""
    INDEX {
            lcsSetupRoutProtLispEtrSettingsEntryName
          }
    ::= { lcsSetupRoutProtLispEtrSettingsTable 1 }

LcsSetupRoutProtLispEtrSettingsEntry ::= SEQUENCE {
            lcsSetupRoutProtLispEtrSettingsEntryName DisplayString,
            lcsSetupRoutProtLispEtrSettingsEntryMapServer DisplayString,
            lcsSetupRoutProtLispEtrSettingsEntryOperating INTEGER,
            lcsSetupRoutProtLispEtrSettingsEntryLoopbackAddress DisplayString,
            lcsSetupRoutProtLispEtrSettingsEntryRtgTag Integer32,
            lcsSetupRoutProtLispEtrSettingsEntryMapCacheTtlMinutes Integer32,
            lcsSetupRoutProtLispEtrSettingsEntryMapRegisterIntervalSeconds Integer32,
            lcsSetupRoutProtLispEtrSettingsEntryKeyType INTEGER,
            lcsSetupRoutProtLispEtrSettingsEntryKey DisplayString,
            lcsSetupRoutProtLispEtrSettingsEntryProxyReply INTEGER,
            lcsSetupRoutProtLispEtrSettingsEntryMapServerBackup DisplayString
    }

-- {COLUMN} 1.3.6.1.4.1.2356.11.2.93.4.4.1.1
lcsSetupRoutProtLispEtrSettingsEntryName OBJECT-TYPE
    SYNTAX     DisplayString (SIZE(0..24))
    MAX-ACCESS read-write
    STATUS     current
    DESCRIPTION
            "-- empty --"
    ::= { lcsSetupRoutProtLispEtrSettingsEntry 1 }

-- {COLUMN} 1.3.6.1.4.1.2356.11.2.93.4.4.1.2
lcsSetupRoutProtLispEtrSettingsEntryMapServer OBJECT-TYPE
    SYNTAX     DisplayString (SIZE(0..39))
    MAX-ACCESS read-write
    STATUS     current
    DESCRIPTION
            "-- empty --"
    ::= { lcsSetupRoutProtLispEtrSettingsEntry 2 }

-- {COLUMN} 1.3.6.1.4.1.2356.11.2.93.4.4.1.3
lcsSetupRoutProtLispEtrSettingsEntryOperating OBJECT-TYPE
    SYNTAX     INTEGER {
                  eNo (0),
                  eYes (1)
            }
    MAX-ACCESS read-write
    STATUS     current
    DESCRIPTION
            "-- empty --"
    ::= { lcsSetupRoutProtLispEtrSettingsEntry 3 }

-- {COLUMN} 1.3.6.1.4.1.2356.11.2.93.4.4.1.4
lcsSetupRoutProtLispEtrSettingsEntryLoopbackAddress OBJECT-TYPE
    SYNTAX     DisplayString (SIZE(0..16))
    MAX-ACCESS read-write
    STATUS     current
    DESCRIPTION
            "-- empty --"
    ::= { lcsSetupRoutProtLispEtrSettingsEntry 4 }

-- {COLUMN} 1.3.6.1.4.1.2356.11.2.93.4.4.1.5
lcsSetupRoutProtLispEtrSettingsEntryRtgTag OBJECT-TYPE
    SYNTAX     Integer32 (0..65535)
    MAX-ACCESS read-write
    STATUS     current
    DESCRIPTION
            "-- empty --"
    ::= { lcsSetupRoutProtLispEtrSettingsEntry 5 }

-- {COLUMN} 1.3.6.1.4.1.2356.11.2.93.4.4.1.6
lcsSetupRoutProtLispEtrSettingsEntryMapCacheTtlMinutes OBJECT-TYPE
    SYNTAX     Integer32 (0..2147483647)
    MAX-ACCESS read-write
    STATUS     current
    DESCRIPTION
            "-- empty --"
    ::= { lcsSetupRoutProtLispEtrSettingsEntry 6 }

-- {COLUMN} 1.3.6.1.4.1.2356.11.2.93.4.4.1.7
lcsSetupRoutProtLispEtrSettingsEntryMapRegisterIntervalSeconds OBJECT-TYPE
    SYNTAX     Integer32 (0..2147483647)
    MAX-ACCESS read-write
    STATUS     current
    DESCRIPTION
            "-- empty --"
    ::= { lcsSetupRoutProtLispEtrSettingsEntry 7 }

-- {COLUMN} 1.3.6.1.4.1.2356.11.2.93.4.4.1.8
lcsSetupRoutProtLispEtrSettingsEntryKeyType OBJECT-TYPE
    SYNTAX     INTEGER {
                  eNone (0),
                  eHmacSha196 (1),
                  eHmacSha256128 (2)
            }
    MAX-ACCESS read-write
    STATUS     current
    DESCRIPTION
            "-- empty --"
    ::= { lcsSetupRoutProtLispEtrSettingsEntry 8 }

-- {COLUMN} 1.3.6.1.4.1.2356.11.2.93.4.4.1.9
lcsSetupRoutProtLispEtrSettingsEntryKey OBJECT-TYPE
    SYNTAX     DisplayString (SIZE(0..24))
    MAX-ACCESS read-write
    STATUS     current
    DESCRIPTION
            "-- empty --"
    ::= { lcsSetupRoutProtLispEtrSettingsEntry 9 }

-- {COLUMN} 1.3.6.1.4.1.2356.11.2.93.4.4.1.10
lcsSetupRoutProtLispEtrSettingsEntryProxyReply OBJECT-TYPE
    SYNTAX     INTEGER {
                  eNo (0),
                  eYes (1)
            }
    MAX-ACCESS read-write
    STATUS     current
    DESCRIPTION
            "-- empty --"
    ::= { lcsSetupRoutProtLispEtrSettingsEntry 10 }

-- {COLUMN} 1.3.6.1.4.1.2356.11.2.93.4.4.1.11
lcsSetupRoutProtLispEtrSettingsEntryMapServerBackup OBJECT-TYPE
    SYNTAX     DisplayString (SIZE(0..39))
    MAX-ACCESS read-write
    STATUS     current
    DESCRIPTION
            "-- empty --"
    ::= { lcsSetupRoutProtLispEtrSettingsEntry 11 }

-- {SCALAR} 1.3.6.1.4.1.2356.11.2.93.4.5
lcsSetupRoutProtLispOperating OBJECT-TYPE
    SYNTAX     INTEGER {
                  eNo (0),
                  eYes (1)
            }
    MAX-ACCESS read-write
    STATUS     current
    DESCRIPTION
            "-- empty --"
    ::= { lcsSetupRoutProtLisp 5 }

-- {SCALAR} 1.3.6.1.4.1.2356.11.2.93.4.7
lcsSetupRoutProtLispDisableTtlPropagation OBJECT-TYPE
    SYNTAX     INTEGER {
                  eNo (0),
                  eYes (1)
            }
    MAX-ACCESS read-write
    STATUS     current
    DESCRIPTION
            "-- empty --"
    ::= { lcsSetupRoutProtLisp 7 }

-- {SCALAR} 1.3.6.1.4.1.2356.11.2.93.4.8
lcsSetupRoutProtLispMapCacheLimit OBJECT-TYPE
    SYNTAX     Integer32 (0..65535)
    MAX-ACCESS read-write
    STATUS     current
    DESCRIPTION
            "-- empty --"
    ::= { lcsSetupRoutProtLisp 8 }

-- {TABLE} 1.3.6.1.4.1.2356.11.2.93.4.9
lcsSetupRoutProtLispNativeForwardTable OBJECT-TYPE
    SYNTAX     SEQUENCE OF LcsSetupRoutProtLispNativeForwardEntry
    MAX-ACCESS not-accessible
    STATUS     current
    DESCRIPTION
            "-- empty --"
    ::= { lcsSetupRoutProtLisp 9 }

-- {ROW} 1.3.6.1.4.1.2356.11.2.93.4.9.1
lcsSetupRoutProtLispNativeForwardEntry OBJECT-TYPE
    SYNTAX     LcsSetupRoutProtLispNativeForwardEntry
    MAX-ACCESS not-accessible
    STATUS     current
    DESCRIPTION
            ""
    INDEX {
            lcsSetupRoutProtLispNativeForwardEntryName
          }
    ::= { lcsSetupRoutProtLispNativeForwardTable 1 }

LcsSetupRoutProtLispNativeForwardEntry ::= SEQUENCE {
            lcsSetupRoutProtLispNativeForwardEntryName DisplayString,
            lcsSetupRoutProtLispNativeForwardEntryType INTEGER,
            lcsSetupRoutProtLispNativeForwardEntryProxyXtr DisplayString,
            lcsSetupRoutProtLispNativeForwardEntryInterface DisplayString
    }

-- {COLUMN} 1.3.6.1.4.1.2356.11.2.93.4.9.1.1
lcsSetupRoutProtLispNativeForwardEntryName OBJECT-TYPE
    SYNTAX     DisplayString (SIZE(0..24))
    MAX-ACCESS read-write
    STATUS     current
    DESCRIPTION
            "-- empty --"
    ::= { lcsSetupRoutProtLispNativeForwardEntry 1 }

-- {COLUMN} 1.3.6.1.4.1.2356.11.2.93.4.9.1.3
lcsSetupRoutProtLispNativeForwardEntryType OBJECT-TYPE
    SYNTAX     INTEGER {
                  eNone (0),
                  eProxyxtr (1),
                  eInterface (2)
            }
    MAX-ACCESS read-write
    STATUS     current
    DESCRIPTION
            "-- empty --"
    ::= { lcsSetupRoutProtLispNativeForwardEntry 3 }

-- {COLUMN} 1.3.6.1.4.1.2356.11.2.93.4.9.1.4
lcsSetupRoutProtLispNativeForwardEntryProxyXtr OBJECT-TYPE
    SYNTAX     DisplayString (SIZE(0..39))
    MAX-ACCESS read-write
    STATUS     current
    DESCRIPTION
            "-- empty --"
    ::= { lcsSetupRoutProtLispNativeForwardEntry 4 }

-- {COLUMN} 1.3.6.1.4.1.2356.11.2.93.4.9.1.5
lcsSetupRoutProtLispNativeForwardEntryInterface OBJECT-TYPE
    SYNTAX     DisplayString (SIZE(0..16))
    MAX-ACCESS read-write
    STATUS     current
    DESCRIPTION
            "-- empty --"
    ::= { lcsSetupRoutProtLispNativeForwardEntry 5 }

-- {TABLE} 1.3.6.1.4.1.2356.11.2.93.4.10
lcsSetupRoutProtLispRedistributionTable OBJECT-TYPE
    SYNTAX     SEQUENCE OF LcsSetupRoutProtLispRedistributionEntry
    MAX-ACCESS not-accessible
    STATUS     current
    DESCRIPTION
            "-- empty --"
    ::= { lcsSetupRoutProtLisp 10 }

-- {ROW} 1.3.6.1.4.1.2356.11.2.93.4.10.1
lcsSetupRoutProtLispRedistributionEntry OBJECT-TYPE
    SYNTAX     LcsSetupRoutProtLispRedistributionEntry
    MAX-ACCESS not-accessible
    STATUS     current
    DESCRIPTION
            ""
    INDEX {
            lcsSetupRoutProtLispRedistributionEntryName,
            lcsSetupRoutProtLispRedistributionEntryFilterList
          }
    ::= { lcsSetupRoutProtLispRedistributionTable 1 }

LcsSetupRoutProtLispRedistributionEntry ::= SEQUENCE {
            lcsSetupRoutProtLispRedistributionEntryName DisplayString,
            lcsSetupRoutProtLispRedistributionEntrySource BITS,
            lcsSetupRoutProtLispRedistributionEntryDestination INTEGER,
            lcsSetupRoutProtLispRedistributionEntryLocator DisplayString,
            lcsSetupRoutProtLispRedistributionEntryLocatorAddressType BITS,
            lcsSetupRoutProtLispRedistributionEntryPriority Integer32,
            lcsSetupRoutProtLispRedistributionEntryWeight Integer32,
            lcsSetupRoutProtLispRedistributionEntryFilterList DisplayString
    }

-- {COLUMN} 1.3.6.1.4.1.2356.11.2.93.4.10.1.1
lcsSetupRoutProtLispRedistributionEntryName OBJECT-TYPE
    SYNTAX     DisplayString (SIZE(0..24))
    MAX-ACCESS read-write
    STATUS     current
    DESCRIPTION
            "-- empty --"
    ::= { lcsSetupRoutProtLispRedistributionEntry 1 }

-- {COLUMN} 1.3.6.1.4.1.2356.11.2.93.4.10.1.2
lcsSetupRoutProtLispRedistributionEntrySource OBJECT-TYPE
    SYNTAX     BITS {
                  eBgp (4),
                  eOspf (5),
                  eStatic (6),
                  eConnected (7)
            }
    MAX-ACCESS read-write
    STATUS     current
    DESCRIPTION
            "-- empty --"
    ::= { lcsSetupRoutProtLispRedistributionEntry 2 }

-- {COLUMN} 1.3.6.1.4.1.2356.11.2.93.4.10.1.3
lcsSetupRoutProtLispRedistributionEntryDestination OBJECT-TYPE
    SYNTAX     INTEGER {
                  eMapCache (1),
                  eEidTable (2)
            }
    MAX-ACCESS read-write
    STATUS     current
    DESCRIPTION
            "-- empty --"
    ::= { lcsSetupRoutProtLispRedistributionEntry 3 }

-- {COLUMN} 1.3.6.1.4.1.2356.11.2.93.4.10.1.4
lcsSetupRoutProtLispRedistributionEntryLocator OBJECT-TYPE
    SYNTAX     DisplayString (SIZE(0..39))
    MAX-ACCESS read-write
    STATUS     current
    DESCRIPTION
            "-- empty --"
    ::= { lcsSetupRoutProtLispRedistributionEntry 4 }

-- {COLUMN} 1.3.6.1.4.1.2356.11.2.93.4.10.1.5
lcsSetupRoutProtLispRedistributionEntryLocatorAddressType OBJECT-TYPE
    SYNTAX     BITS {
                  eIpv6 (6),
                  eIpv4 (7)
            }
    MAX-ACCESS read-write
    STATUS     current
    DESCRIPTION
            "-- empty --"
    ::= { lcsSetupRoutProtLispRedistributionEntry 5 }

-- {COLUMN} 1.3.6.1.4.1.2356.11.2.93.4.10.1.6
lcsSetupRoutProtLispRedistributionEntryPriority OBJECT-TYPE
    SYNTAX     Integer32 (0..255)
    MAX-ACCESS read-write
    STATUS     current
    DESCRIPTION
            "-- empty --"
    ::= { lcsSetupRoutProtLispRedistributionEntry 6 }

-- {COLUMN} 1.3.6.1.4.1.2356.11.2.93.4.10.1.7
lcsSetupRoutProtLispRedistributionEntryWeight OBJECT-TYPE
    SYNTAX     Integer32 (0..255)
    MAX-ACCESS read-write
    STATUS     current
    DESCRIPTION
            "-- empty --"
    ::= { lcsSetupRoutProtLispRedistributionEntry 7 }

-- {COLUMN} 1.3.6.1.4.1.2356.11.2.93.4.10.1.8
lcsSetupRoutProtLispRedistributionEntryFilterList OBJECT-TYPE
    SYNTAX     DisplayString (SIZE(0..16))
    MAX-ACCESS read-write
    STATUS     current
    DESCRIPTION
            "-- empty --"
    ::= { lcsSetupRoutProtLispRedistributionEntry 8 }

-- {NODE} 1.3.6.1.4.1.2356.11.2.93.5
lcsSetupRoutProtFilter OBJECT IDENTIFIER ::= { lcsSetupRoutProt 5 }

-- {TABLE} 1.3.6.1.4.1.2356.11.2.93.5.1
lcsSetupRoutProtFilterPrefixListTable OBJECT-TYPE
    SYNTAX     SEQUENCE OF LcsSetupRoutProtFilterPrefixListEntry
    MAX-ACCESS not-accessible
    STATUS     current
    DESCRIPTION
            "-- empty --"
    ::= { lcsSetupRoutProtFilter 1 }

-- {ROW} 1.3.6.1.4.1.2356.11.2.93.5.1.1
lcsSetupRoutProtFilterPrefixListEntry OBJECT-TYPE
    SYNTAX     LcsSetupRoutProtFilterPrefixListEntry
    MAX-ACCESS not-accessible
    STATUS     current
    DESCRIPTION
            ""
    INDEX {
            lcsSetupRoutProtFilterPrefixListEntryName,
            lcsSetupRoutProtFilterPrefixListEntryIpAddress
          }
    ::= { lcsSetupRoutProtFilterPrefixListTable 1 }

LcsSetupRoutProtFilterPrefixListEntry ::= SEQUENCE {
            lcsSetupRoutProtFilterPrefixListEntryName DisplayString,
            lcsSetupRoutProtFilterPrefixListEntryIpAddress IpAddress,
            lcsSetupRoutProtFilterPrefixListEntryPrefixLength Integer32,
            lcsSetupRoutProtFilterPrefixListEntryLengthMin Integer32,
            lcsSetupRoutProtFilterPrefixListEntryLengthMax Integer32,
            lcsSetupRoutProtFilterPrefixListEntryComment DisplayString
    }

-- {COLUMN} 1.3.6.1.4.1.2356.11.2.93.5.1.1.1
lcsSetupRoutProtFilterPrefixListEntryName OBJECT-TYPE
    SYNTAX     DisplayString (SIZE(0..16))
    MAX-ACCESS read-write
    STATUS     current
    DESCRIPTION
            "-- empty --"
    ::= { lcsSetupRoutProtFilterPrefixListEntry 1 }

-- {COLUMN} 1.3.6.1.4.1.2356.11.2.93.5.1.1.2
lcsSetupRoutProtFilterPrefixListEntryIpAddress OBJECT-TYPE
    SYNTAX     IpAddress
    MAX-ACCESS read-write
    STATUS     current
    DESCRIPTION
            "-- empty --"
    ::= { lcsSetupRoutProtFilterPrefixListEntry 2 }

-- {COLUMN} 1.3.6.1.4.1.2356.11.2.93.5.1.1.3
lcsSetupRoutProtFilterPrefixListEntryPrefixLength OBJECT-TYPE
    SYNTAX     Integer32 (0..255)
    MAX-ACCESS read-write
    STATUS     current
    DESCRIPTION
            "-- empty --"
    ::= { lcsSetupRoutProtFilterPrefixListEntry 3 }

-- {COLUMN} 1.3.6.1.4.1.2356.11.2.93.5.1.1.4
lcsSetupRoutProtFilterPrefixListEntryLengthMin OBJECT-TYPE
    SYNTAX     Integer32 (0..255)
    MAX-ACCESS read-write
    STATUS     current
    DESCRIPTION
            "-- empty --"
    ::= { lcsSetupRoutProtFilterPrefixListEntry 4 }

-- {COLUMN} 1.3.6.1.4.1.2356.11.2.93.5.1.1.5
lcsSetupRoutProtFilterPrefixListEntryLengthMax OBJECT-TYPE
    SYNTAX     Integer32 (0..255)
    MAX-ACCESS read-write
    STATUS     current
    DESCRIPTION
            "-- empty --"
    ::= { lcsSetupRoutProtFilterPrefixListEntry 5 }

-- {COLUMN} 1.3.6.1.4.1.2356.11.2.93.5.1.1.6
lcsSetupRoutProtFilterPrefixListEntryComment OBJECT-TYPE
    SYNTAX     DisplayString (SIZE(0..254))
    MAX-ACCESS read-write
    STATUS     current
    DESCRIPTION
            "-- empty --"
    ::= { lcsSetupRoutProtFilterPrefixListEntry 6 }

-- {NODE} 1.3.6.1.4.1.2356.11.2.96
lcsSetupIperf OBJECT IDENTIFIER ::= { lcsSetup 96 }

-- {NODE} 1.3.6.1.4.1.2356.11.2.96.1
lcsSetupIperfServerDaemon OBJECT IDENTIFIER ::= { lcsSetupIperf 1 }

-- {SCALAR} 1.3.6.1.4.1.2356.11.2.96.1.1
lcsSetupIperfServerDaemonOperating OBJECT-TYPE
    SYNTAX     INTEGER {
                  eNo (0),
                  eYes (1)
            }
    MAX-ACCESS read-write
    STATUS     current
    DESCRIPTION
            "-- empty --"
    ::= { lcsSetupIperfServerDaemon 1 }

-- {SCALAR} 1.3.6.1.4.1.2356.11.2.96.1.2
lcsSetupIperfServerDaemonTransport OBJECT-TYPE
    SYNTAX     BITS {
                  eTcp (6),
                  eUdp (7)
            }
    MAX-ACCESS read-write
    STATUS     current
    DESCRIPTION
            "-- empty --"
    ::= { lcsSetupIperfServerDaemon 2 }

-- {SCALAR} 1.3.6.1.4.1.2356.11.2.96.1.3
lcsSetupIperfServerDaemonPort OBJECT-TYPE
    SYNTAX     Integer32 (0..65535)
    MAX-ACCESS read-write
    STATUS     current
    DESCRIPTION
            "-- empty --"
    ::= { lcsSetupIperfServerDaemon 3 }

-- {SCALAR} 1.3.6.1.4.1.2356.11.2.96.2
lcsSetupIperfIpv4WanAccess OBJECT-TYPE
    SYNTAX     INTEGER {
                  eNo (0),
                  eVpn (1),
                  eYes (2)
            }
    MAX-ACCESS read-write
    STATUS     current
    DESCRIPTION
            "-- empty --"
    ::= { lcsSetupIperf 2 }

-- {TABLE} 1.3.6.1.4.1.2356.11.2.96.3
lcsSetupIperfIpv4AccessListTable OBJECT-TYPE
    SYNTAX     SEQUENCE OF LcsSetupIperfIpv4AccessListEntry
    MAX-ACCESS not-accessible
    STATUS     current
    DESCRIPTION
            "-- empty --"
    ::= { lcsSetupIperf 3 }

-- {ROW} 1.3.6.1.4.1.2356.11.2.96.3.1
lcsSetupIperfIpv4AccessListEntry OBJECT-TYPE
    SYNTAX     LcsSetupIperfIpv4AccessListEntry
    MAX-ACCESS not-accessible
    STATUS     current
    DESCRIPTION
            ""
    INDEX {
            lcsSetupIperfIpv4AccessListEntryIpAddress,
            lcsSetupIperfIpv4AccessListEntryIpNetmask,
            lcsSetupIperfIpv4AccessListEntryRtgTag
          }
    ::= { lcsSetupIperfIpv4AccessListTable 1 }

LcsSetupIperfIpv4AccessListEntry ::= SEQUENCE {
            lcsSetupIperfIpv4AccessListEntryIpAddress DisplayString,
            lcsSetupIperfIpv4AccessListEntryIpNetmask DisplayString,
            lcsSetupIperfIpv4AccessListEntryRtgTag Integer32,
            lcsSetupIperfIpv4AccessListEntryComment DisplayString
    }

-- {COLUMN} 1.3.6.1.4.1.2356.11.2.96.3.1.1
lcsSetupIperfIpv4AccessListEntryIpAddress OBJECT-TYPE
    SYNTAX     DisplayString (SIZE(0..15))
    MAX-ACCESS read-write
    STATUS     current
    DESCRIPTION
            "-- empty --"
    ::= { lcsSetupIperfIpv4AccessListEntry 1 }

-- {COLUMN} 1.3.6.1.4.1.2356.11.2.96.3.1.2
lcsSetupIperfIpv4AccessListEntryIpNetmask OBJECT-TYPE
    SYNTAX     DisplayString (SIZE(0..15))
    MAX-ACCESS read-write
    STATUS     current
    DESCRIPTION
            "-- empty --"
    ::= { lcsSetupIperfIpv4AccessListEntry 2 }

-- {COLUMN} 1.3.6.1.4.1.2356.11.2.96.3.1.3
lcsSetupIperfIpv4AccessListEntryRtgTag OBJECT-TYPE
    SYNTAX     Integer32 (0..65535)
    MAX-ACCESS read-write
    STATUS     current
    DESCRIPTION
            "-- empty --"
    ::= { lcsSetupIperfIpv4AccessListEntry 3 }

-- {COLUMN} 1.3.6.1.4.1.2356.11.2.96.3.1.4
lcsSetupIperfIpv4AccessListEntryComment OBJECT-TYPE
    SYNTAX     DisplayString (SIZE(0..64))
    MAX-ACCESS read-write
    STATUS     current
    DESCRIPTION
            "-- empty --"
    ::= { lcsSetupIperfIpv4AccessListEntry 4 }

-- {NODE} 1.3.6.1.4.1.2356.11.2.97
lcsSetupBatteryPack OBJECT IDENTIFIER ::= { lcsSetup 97 }

-- {SCALAR} 1.3.6.1.4.1.2356.11.2.97.1
lcsSetupBatteryPackOperating OBJECT-TYPE
    SYNTAX     INTEGER {
                  eNo (0),
                  eYes (1)
            }
    MAX-ACCESS read-write
    STATUS     current
    DESCRIPTION
            "-- empty --"
    ::= { lcsSetupBatteryPack 1 }

-- {SCALAR} 1.3.6.1.4.1.2356.11.2.97.2
lcsSetupBatteryPackEmailAddress OBJECT-TYPE
    SYNTAX     DisplayString (SIZE(0..253))
    MAX-ACCESS read-write
    STATUS     current
    DESCRIPTION
            "-- empty --"
    ::= { lcsSetupBatteryPack 2 }

-- {SCALAR} 1.3.6.1.4.1.2356.11.2.97.3
lcsSetupBatteryPackRestart OBJECT-TYPE
    SYNTAX     DisplayString
    MAX-ACCESS read-write
    STATUS     current
    DESCRIPTION
            "-- empty --"
    ::= { lcsSetupBatteryPack 3 }

-- {TABLE} 1.3.6.1.4.1.2356.11.2.97.4
lcsSetupBatteryPackAlertingTable OBJECT-TYPE
    SYNTAX     SEQUENCE OF LcsSetupBatteryPackAlertingEntry
    MAX-ACCESS not-accessible
    STATUS     current
    DESCRIPTION
            "-- empty --"
    ::= { lcsSetupBatteryPack 4 }

-- {ROW} 1.3.6.1.4.1.2356.11.2.97.4.1
lcsSetupBatteryPackAlertingEntry OBJECT-TYPE
    SYNTAX     LcsSetupBatteryPackAlertingEntry
    MAX-ACCESS not-accessible
    STATUS     current
    DESCRIPTION
            ""
    INDEX {
            lcsSetupBatteryPackAlertingEntryEvent
          }
    ::= { lcsSetupBatteryPackAlertingTable 1 }

LcsSetupBatteryPackAlertingEntry ::= SEQUENCE {
            lcsSetupBatteryPackAlertingEntryEvent DisplayString,
            lcsSetupBatteryPackAlertingEntryMail INTEGER,
            lcsSetupBatteryPackAlertingEntrySnmp INTEGER,
            lcsSetupBatteryPackAlertingEntrySyslog INTEGER
    }

-- {COLUMN} 1.3.6.1.4.1.2356.11.2.97.4.1.1
lcsSetupBatteryPackAlertingEntryEvent OBJECT-TYPE
    SYNTAX     DisplayString (SIZE(0..14))
    MAX-ACCESS read-only
    STATUS     current
    DESCRIPTION
            "-- empty --"
    ::= { lcsSetupBatteryPackAlertingEntry 1 }

-- {COLUMN} 1.3.6.1.4.1.2356.11.2.97.4.1.2
lcsSetupBatteryPackAlertingEntryMail OBJECT-TYPE
    SYNTAX     INTEGER {
                  eNo (0),
                  eYes (1)
            }
    MAX-ACCESS read-write
    STATUS     current
    DESCRIPTION
            "-- empty --"
    ::= { lcsSetupBatteryPackAlertingEntry 2 }

-- {COLUMN} 1.3.6.1.4.1.2356.11.2.97.4.1.3
lcsSetupBatteryPackAlertingEntrySnmp OBJECT-TYPE
    SYNTAX     INTEGER {
                  eNo (0),
                  eYes (1)
            }
    MAX-ACCESS read-write
    STATUS     current
    DESCRIPTION
            "-- empty --"
    ::= { lcsSetupBatteryPackAlertingEntry 3 }

-- {COLUMN} 1.3.6.1.4.1.2356.11.2.97.4.1.4
lcsSetupBatteryPackAlertingEntrySyslog OBJECT-TYPE
    SYNTAX     INTEGER {
                  eNo (0),
                  eYes (1)
            }
    MAX-ACCESS read-write
    STATUS     current
    DESCRIPTION
            "-- empty --"
    ::= { lcsSetupBatteryPackAlertingEntry 4 }

-- {SCALAR} 1.3.6.1.4.1.2356.11.2.97.5
lcsSetupBatteryPackDischarge OBJECT-TYPE
    SYNTAX     DisplayString
    MAX-ACCESS read-write
    STATUS     current
    DESCRIPTION
            "-- empty --"
    ::= { lcsSetupBatteryPack 5 }

-- {NODE} 1.3.6.1.4.1.2356.11.2.100
lcsSetupLbs OBJECT IDENTIFIER ::= { lcsSetup 100 }

-- {SCALAR} 1.3.6.1.4.1.2356.11.2.100.1
lcsSetupLbsOperating OBJECT-TYPE
    SYNTAX     INTEGER {
                  eNo (0),
                  eYes (1)
            }
    MAX-ACCESS read-write
    STATUS     current
    DESCRIPTION
            "-- empty --"
    ::= { lcsSetupLbs 1 }

-- {SCALAR} 1.3.6.1.4.1.2356.11.2.100.2
lcsSetupLbsDescription OBJECT-TYPE
    SYNTAX     DisplayString (SIZE(0..251))
    MAX-ACCESS read-write
    STATUS     current
    DESCRIPTION
            "-- empty --"
    ::= { lcsSetupLbs 2 }

-- {SCALAR} 1.3.6.1.4.1.2356.11.2.100.3
lcsSetupLbsFloor OBJECT-TYPE
    SYNTAX     Integer32 (-32768..32767)
    MAX-ACCESS read-write
    STATUS     current
    DESCRIPTION
            "-- empty --"
    ::= { lcsSetupLbs 3 }

-- {SCALAR} 1.3.6.1.4.1.2356.11.2.100.4
lcsSetupLbsHeight OBJECT-TYPE
    SYNTAX     Integer32 (-32768..32767)
    MAX-ACCESS read-write
    STATUS     current
    DESCRIPTION
            "-- empty --"
    ::= { lcsSetupLbs 4 }

-- {TABLE} 1.3.6.1.4.1.2356.11.2.100.5
lcsSetupLbsCoordinatesTable OBJECT-TYPE
    SYNTAX     SEQUENCE OF LcsSetupLbsCoordinatesEntry
    MAX-ACCESS not-accessible
    STATUS     current
    DESCRIPTION
            "-- empty --"
    ::= { lcsSetupLbs 5 }

-- {ROW} 1.3.6.1.4.1.2356.11.2.100.5.1
lcsSetupLbsCoordinatesEntry OBJECT-TYPE
    SYNTAX     LcsSetupLbsCoordinatesEntry
    MAX-ACCESS not-accessible
    STATUS     current
    DESCRIPTION
            ""
    INDEX {
            lcsSetupLbsCoordinatesEntryOrientation
          }
    ::= { lcsSetupLbsCoordinatesTable 1 }

LcsSetupLbsCoordinatesEntry ::= SEQUENCE {
            lcsSetupLbsCoordinatesEntryOrientation INTEGER,
            lcsSetupLbsCoordinatesEntryDegree Integer32,
            lcsSetupLbsCoordinatesEntryMinute Integer32,
            lcsSetupLbsCoordinatesEntrySecond Integer32,
            lcsSetupLbsCoordinatesEntryHemisphere INTEGER,
            lcsSetupLbsCoordinatesEntryDecimalDegree DisplayString
    }

-- {COLUMN} 1.3.6.1.4.1.2356.11.2.100.5.1.1
lcsSetupLbsCoordinatesEntryOrientation OBJECT-TYPE
    SYNTAX     INTEGER {
                  eLatitude (1),
                  eLongitude (2)
            }
    MAX-ACCESS read-only
    STATUS     current
    DESCRIPTION
            "-- empty --"
    ::= { lcsSetupLbsCoordinatesEntry 1 }

-- {COLUMN} 1.3.6.1.4.1.2356.11.2.100.5.1.2
lcsSetupLbsCoordinatesEntryDegree OBJECT-TYPE
    SYNTAX     Integer32 (0..255)
    MAX-ACCESS read-write
    STATUS     current
    DESCRIPTION
            "-- empty --"
    ::= { lcsSetupLbsCoordinatesEntry 2 }

-- {COLUMN} 1.3.6.1.4.1.2356.11.2.100.5.1.3
lcsSetupLbsCoordinatesEntryMinute OBJECT-TYPE
    SYNTAX     Integer32 (0..255)
    MAX-ACCESS read-write
    STATUS     current
    DESCRIPTION
            "-- empty --"
    ::= { lcsSetupLbsCoordinatesEntry 3 }

-- {COLUMN} 1.3.6.1.4.1.2356.11.2.100.5.1.4
lcsSetupLbsCoordinatesEntrySecond OBJECT-TYPE
    SYNTAX     Integer32 (0..2147483647)
    MAX-ACCESS read-write
    STATUS     current
    DESCRIPTION
            "-- empty --"
    ::= { lcsSetupLbsCoordinatesEntry 4 }

-- {COLUMN} 1.3.6.1.4.1.2356.11.2.100.5.1.5
lcsSetupLbsCoordinatesEntryHemisphere OBJECT-TYPE
    SYNTAX     INTEGER {
                  eN (1),
                  eS (2),
                  eW (3),
                  eE (4)
            }
    MAX-ACCESS read-write
    STATUS     current
    DESCRIPTION
            "-- empty --"
    ::= { lcsSetupLbsCoordinatesEntry 5 }

-- {COLUMN} 1.3.6.1.4.1.2356.11.2.100.5.1.6
lcsSetupLbsCoordinatesEntryDecimalDegree OBJECT-TYPE
    SYNTAX     DisplayString (SIZE(0..12))
    MAX-ACCESS read-write
    STATUS     current
    DESCRIPTION
            "-- empty --"
    ::= { lcsSetupLbsCoordinatesEntry 6 }

-- {SCALAR} 1.3.6.1.4.1.2356.11.2.100.6
lcsSetupLbsLbsServerAddress OBJECT-TYPE
    SYNTAX     DisplayString (SIZE(0..64))
    MAX-ACCESS read-write
    STATUS     current
    DESCRIPTION
            "-- empty --"
    ::= { lcsSetupLbs 6 }

-- {SCALAR} 1.3.6.1.4.1.2356.11.2.100.7
lcsSetupLbsLbsServerPort OBJECT-TYPE
    SYNTAX     Integer32 (-32768..32767)
    MAX-ACCESS read-write
    STATUS     current
    DESCRIPTION
            "-- empty --"
    ::= { lcsSetupLbs 7 }

-- {SCALAR} 1.3.6.1.4.1.2356.11.2.100.8
lcsSetupLbsUseTlsConnection OBJECT-TYPE
    SYNTAX     INTEGER {
                  eNo (0),
                  eYes (1)
            }
    MAX-ACCESS read-write
    STATUS     current
    DESCRIPTION
            "-- empty --"
    ::= { lcsSetupLbs 8 }

-- {NODE} 1.3.6.1.4.1.2356.11.2.100.9
lcsSetupLbsTlsClientSettings OBJECT IDENTIFIER ::= { lcsSetupLbs 9 }

-- {SCALAR} 1.3.6.1.4.1.2356.11.2.100.9.1
lcsSetupLbsTlsClientSettingsVersions OBJECT-TYPE
    SYNTAX     BITS {
                  eTlsv13 (27),
                  eTlsv12 (28),
                  eTlsv11 (29),
                  eTlsv1 (30),
                  eSslv3 (31)
            }
    MAX-ACCESS read-write
    STATUS     current
    DESCRIPTION
            "-- empty --"
    ::= { lcsSetupLbsTlsClientSettings 1 }

-- {SCALAR} 1.3.6.1.4.1.2356.11.2.100.9.2
lcsSetupLbsTlsClientSettingsKeyexAlgorithms OBJECT-TYPE
    SYNTAX     BITS {
                  eEcdhe (27),
                  eDhe (29),
                  eRsa (31)
            }
    MAX-ACCESS read-write
    STATUS     current
    DESCRIPTION
            "-- empty --"
    ::= { lcsSetupLbsTlsClientSettings 2 }

-- {SCALAR} 1.3.6.1.4.1.2356.11.2.100.9.3
lcsSetupLbsTlsClientSettingsCryptoAlgorithms OBJECT-TYPE
    SYNTAX     BITS {
                  eAesgcm256 (20),
                  eAesgcm128 (21),
                  eAes256 (22),
                  eAes128 (23)
            }
    MAX-ACCESS read-write
    STATUS     current
    DESCRIPTION
            "-- empty --"
    ::= { lcsSetupLbsTlsClientSettings 3 }

-- {SCALAR} 1.3.6.1.4.1.2356.11.2.100.9.4
lcsSetupLbsTlsClientSettingsHashAlgorithms OBJECT-TYPE
    SYNTAX     BITS {
                  eSha384 (26),
                  eSha256 (27),
                  eSha1 (29),
                  eMd5 (30)
            }
    MAX-ACCESS read-write
    STATUS     current
    DESCRIPTION
            "-- empty --"
    ::= { lcsSetupLbsTlsClientSettings 4 }

-- {SCALAR} 1.3.6.1.4.1.2356.11.2.100.9.5
lcsSetupLbsTlsClientSettingsPreferPfs OBJECT-TYPE
    SYNTAX     BITS {
                  eNo (0),
                  eYes (7)
            }
    MAX-ACCESS read-write
    STATUS     current
    DESCRIPTION
            "-- empty --"
    ::= { lcsSetupLbsTlsClientSettings 5 }

-- {SCALAR} 1.3.6.1.4.1.2356.11.2.100.9.7
lcsSetupLbsTlsClientSettingsEllipticCurves OBJECT-TYPE
    SYNTAX     BITS {
                  eEcdhX25519 (28),
                  eSecp521r1 (29),
                  eSecp384r1 (30),
                  eSecp256r1 (31)
            }
    MAX-ACCESS read-write
    STATUS     current
    DESCRIPTION
            "-- empty --"
    ::= { lcsSetupLbsTlsClientSettings 7 }

-- {SCALAR} 1.3.6.1.4.1.2356.11.2.100.9.21
lcsSetupLbsTlsClientSettingsSigHashAlgs OBJECT-TYPE
    SYNTAX     BITS {
                  eSha512Ecdsa (20),
                  eSha384Ecdsa (21),
                  eSha256Ecdsa (22),
                  eSha224Ecdsa (23),
                  eSha1Ecdsa (24),
                  eMd5Ecdsa (25),
                  eSha512Rsa (26),
                  eSha384Rsa (27),
                  eSha256Rsa (28),
                  eSha224Rsa (29),
                  eSha1Rsa (30),
                  eMd5Rsa (31)
            }
    MAX-ACCESS read-write
    STATUS     current
    DESCRIPTION
            "list of allowed signature/hash algorithms"
    ::= { lcsSetupLbsTlsClientSettings 21 }

-- {SCALAR} 1.3.6.1.4.1.2356.11.2.100.10
lcsSetupLbsLoopbackAddress OBJECT-TYPE
    SYNTAX     DisplayString (SIZE(0..16))
    MAX-ACCESS read-write
    STATUS     current
    DESCRIPTION
            "-- empty --"
    ::= { lcsSetupLbs 10 }

-- {SCALAR} 1.3.6.1.4.1.2356.11.2.100.11
lcsSetupLbsCacheOperating OBJECT-TYPE
    SYNTAX     INTEGER {
                  eNo (0),
                  eYes (1)
            }
    MAX-ACCESS read-write
    STATUS     current
    DESCRIPTION
            "-- empty --"
    ::= { lcsSetupLbs 11 }

-- {SCALAR} 1.3.6.1.4.1.2356.11.2.100.12
lcsSetupLbsCacheSize OBJECT-TYPE
    SYNTAX     Integer32 (0..2147483647)
    MAX-ACCESS read-write
    STATUS     current
    DESCRIPTION
            "-- empty --"
    ::= { lcsSetupLbs 12 }

-- {SCALAR} 1.3.6.1.4.1.2356.11.2.100.13
lcsSetupLbsUserName OBJECT-TYPE
    SYNTAX     DisplayString (SIZE(0..64))
    MAX-ACCESS read-write
    STATUS     current
    DESCRIPTION
            "-- empty --"
    ::= { lcsSetupLbs 13 }

-- {SCALAR} 1.3.6.1.4.1.2356.11.2.100.14
lcsSetupLbsPassword OBJECT-TYPE
    SYNTAX     DisplayString (SIZE(0..32))
    MAX-ACCESS read-write
    STATUS     current
    DESCRIPTION
            "-- empty --"
    ::= { lcsSetupLbs 14 }

-- {SCALAR} 1.3.6.1.4.1.2356.11.2.100.15
lcsSetupLbsAggregation OBJECT-TYPE
    SYNTAX     INTEGER {
                  eNo (0),
                  eYes (1)
            }
    MAX-ACCESS read-write
    STATUS     current
    DESCRIPTION
            "-- empty --"
    ::= { lcsSetupLbs 15 }

-- {NODE} 1.3.6.1.4.1.2356.11.2.100.16
lcsSetupLbsMeasurementsFields OBJECT IDENTIFIER ::= { lcsSetupLbs 16 }

-- {SCALAR} 1.3.6.1.4.1.2356.11.2.100.16.1
lcsSetupLbsMeasurementsFieldsSequenceNumberTransmit OBJECT-TYPE
    SYNTAX     INTEGER {
                  eNo (0),
                  eYes (1)
            }
    MAX-ACCESS read-write
    STATUS     current
    DESCRIPTION
            "-- empty --"
    ::= { lcsSetupLbsMeasurementsFields 1 }

-- {SCALAR} 1.3.6.1.4.1.2356.11.2.100.16.2
lcsSetupLbsMeasurementsFieldsSsidTransmit OBJECT-TYPE
    SYNTAX     INTEGER {
                  eNo (0),
                  eYes (1)
            }
    MAX-ACCESS read-write
    STATUS     current
    DESCRIPTION
            "-- empty --"
    ::= { lcsSetupLbsMeasurementsFields 2 }

-- {SCALAR} 1.3.6.1.4.1.2356.11.2.100.16.3
lcsSetupLbsMeasurementsFieldsInterfaceIdentifierTransmit OBJECT-TYPE
    SYNTAX     INTEGER {
                  eNo (0),
                  eYes (1)
            }
    MAX-ACCESS read-write
    STATUS     current
    DESCRIPTION
            "-- empty --"
    ::= { lcsSetupLbsMeasurementsFields 3 }

-- {SCALAR} 1.3.6.1.4.1.2356.11.2.100.16.4
lcsSetupLbsMeasurementsFieldsBssidTransmit OBJECT-TYPE
    SYNTAX     INTEGER {
                  eNo (0),
                  eYes (1)
            }
    MAX-ACCESS read-write
    STATUS     current
    DESCRIPTION
            "-- empty --"
    ::= { lcsSetupLbsMeasurementsFields 4 }

-- {SCALAR} 1.3.6.1.4.1.2356.11.2.100.16.5
lcsSetupLbsMeasurementsFieldsSignalLevelTransmit OBJECT-TYPE
    SYNTAX     INTEGER {
                  eNo (0),
                  eYes (1)
            }
    MAX-ACCESS read-write
    STATUS     current
    DESCRIPTION
            "-- empty --"
    ::= { lcsSetupLbsMeasurementsFields 5 }

-- {SCALAR} 1.3.6.1.4.1.2356.11.2.100.16.6
lcsSetupLbsMeasurementsFieldsFrequencyTransmit OBJECT-TYPE
    SYNTAX     INTEGER {
                  eNo (0),
                  eYes (1)
            }
    MAX-ACCESS read-write
    STATUS     current
    DESCRIPTION
            "-- empty --"
    ::= { lcsSetupLbsMeasurementsFields 6 }

-- {SCALAR} 1.3.6.1.4.1.2356.11.2.100.16.7
lcsSetupLbsMeasurementsFieldsNoiseTransmit OBJECT-TYPE
    SYNTAX     INTEGER {
                  eNo (0),
                  eYes (1)
            }
    MAX-ACCESS read-write
    STATUS     current
    DESCRIPTION
            "-- empty --"
    ::= { lcsSetupLbsMeasurementsFields 7 }

-- {SCALAR} 1.3.6.1.4.1.2356.11.2.100.16.8
lcsSetupLbsMeasurementsFieldsWlanFrameTypeTransmit OBJECT-TYPE
    SYNTAX     INTEGER {
                  eNo (0),
                  eYes (1)
            }
    MAX-ACCESS read-write
    STATUS     current
    DESCRIPTION
            "-- empty --"
    ::= { lcsSetupLbsMeasurementsFields 8 }

-- {NODE} 1.3.6.1.4.1.2356.11.2.101
lcsSetupLay7AppDet OBJECT IDENTIFIER ::= { lcsSetup 101 }

-- {SCALAR} 1.3.6.1.4.1.2356.11.2.101.1
lcsSetupLay7AppDetOperating OBJECT-TYPE
    SYNTAX     INTEGER {
                  eNo (0),
                  eYes (1)
            }
    MAX-ACCESS read-write
    STATUS     current
    DESCRIPTION
            "-- empty --"
    ::= { lcsSetupLay7AppDet 1 }

-- {TABLE} 1.3.6.1.4.1.2356.11.2.101.2
lcsSetupLay7AppDetIpPortApplicationsTable OBJECT-TYPE
    SYNTAX     SEQUENCE OF LcsSetupLay7AppDetIpPortApplicationsEntry
    MAX-ACCESS not-accessible
    STATUS     current
    DESCRIPTION
            "-- empty --"
    ::= { lcsSetupLay7AppDet 2 }

-- {ROW} 1.3.6.1.4.1.2356.11.2.101.2.1
lcsSetupLay7AppDetIpPortApplicationsEntry OBJECT-TYPE
    SYNTAX     LcsSetupLay7AppDetIpPortApplicationsEntry
    MAX-ACCESS not-accessible
    STATUS     current
    DESCRIPTION
            ""
    INDEX {
            lcsSetupLay7AppDetIpPortApplicationsEntryAppname
          }
    ::= { lcsSetupLay7AppDetIpPortApplicationsTable 1 }

LcsSetupLay7AppDetIpPortApplicationsEntry ::= SEQUENCE {
            lcsSetupLay7AppDetIpPortApplicationsEntryAppname DisplayString,
            lcsSetupLay7AppDetIpPortApplicationsEntryTargets DisplayString,
            lcsSetupLay7AppDetIpPortApplicationsEntryPorts DisplayString
    }

-- {COLUMN} 1.3.6.1.4.1.2356.11.2.101.2.1.1
lcsSetupLay7AppDetIpPortApplicationsEntryAppname OBJECT-TYPE
    SYNTAX     DisplayString (SIZE(0..64))
    MAX-ACCESS read-write
    STATUS     current
    DESCRIPTION
            "Application name"
    ::= { lcsSetupLay7AppDetIpPortApplicationsEntry 1 }

-- {COLUMN} 1.3.6.1.4.1.2356.11.2.101.2.1.2
lcsSetupLay7AppDetIpPortApplicationsEntryTargets OBJECT-TYPE
    SYNTAX     DisplayString (SIZE(0..254))
    MAX-ACCESS read-write
    STATUS     current
    DESCRIPTION
            "-- empty --"
    ::= { lcsSetupLay7AppDetIpPortApplicationsEntry 2 }

-- {COLUMN} 1.3.6.1.4.1.2356.11.2.101.2.1.3
lcsSetupLay7AppDetIpPortApplicationsEntryPorts OBJECT-TYPE
    SYNTAX     DisplayString (SIZE(0..32))
    MAX-ACCESS read-write
    STATUS     current
    DESCRIPTION
            "-- empty --"
    ::= { lcsSetupLay7AppDetIpPortApplicationsEntry 3 }

-- {TABLE} 1.3.6.1.4.1.2356.11.2.101.4
lcsSetupLay7AppDetPortTableTable OBJECT-TYPE
    SYNTAX     SEQUENCE OF LcsSetupLay7AppDetPortTableEntry
    MAX-ACCESS not-accessible
    STATUS     current
    DESCRIPTION
            "-- empty --"
    ::= { lcsSetupLay7AppDet 4 }

-- {ROW} 1.3.6.1.4.1.2356.11.2.101.4.1
lcsSetupLay7AppDetPortTableEntry OBJECT-TYPE
    SYNTAX     LcsSetupLay7AppDetPortTableEntry
    MAX-ACCESS not-accessible
    STATUS     current
    DESCRIPTION
            ""
    INDEX {
            lcsSetupLay7AppDetPortTableEntryPort
          }
    ::= { lcsSetupLay7AppDetPortTableTable 1 }

LcsSetupLay7AppDetPortTableEntry ::= SEQUENCE {
            lcsSetupLay7AppDetPortTableEntryPort DisplayString,
            lcsSetupLay7AppDetPortTableEntryActive INTEGER
    }

-- {COLUMN} 1.3.6.1.4.1.2356.11.2.101.4.1.2
lcsSetupLay7AppDetPortTableEntryPort OBJECT-TYPE
    SYNTAX     DisplayString (SIZE(0..18))
    MAX-ACCESS read-only
    STATUS     current
    DESCRIPTION
            "-- empty --"
    ::= { lcsSetupLay7AppDetPortTableEntry 2 }

-- {COLUMN} 1.3.6.1.4.1.2356.11.2.101.4.1.3
lcsSetupLay7AppDetPortTableEntryActive OBJECT-TYPE
    SYNTAX     INTEGER {
                  eNo (0),
                  eYes (1)
            }
    MAX-ACCESS read-write
    STATUS     current
    DESCRIPTION
            "-- empty --"
    ::= { lcsSetupLay7AppDetPortTableEntry 3 }

-- {SCALAR} 1.3.6.1.4.1.2356.11.2.101.5
lcsSetupLay7AppDetStatusUpMin OBJECT-TYPE
    SYNTAX     Integer32 (0..65535)
    MAX-ACCESS read-write
    STATUS     current
    DESCRIPTION
            "Status Update In Minute"
    ::= { lcsSetupLay7AppDet 5 }

-- {SCALAR} 1.3.6.1.4.1.2356.11.2.101.6
lcsSetupLay7AppDetMaxQueueLength OBJECT-TYPE
    SYNTAX     Integer32 (0..65535)
    MAX-ACCESS read-write
    STATUS     current
    DESCRIPTION
            "-- empty --"
    ::= { lcsSetupLay7AppDet 6 }

-- {SCALAR} 1.3.6.1.4.1.2356.11.2.101.7
lcsSetupLay7AppDetDeleteValues OBJECT-TYPE
    SYNTAX     DisplayString
    MAX-ACCESS read-write
    STATUS     current
    DESCRIPTION
            "-- empty --"
    ::= { lcsSetupLay7AppDet 7 }

-- {TABLE} 1.3.6.1.4.1.2356.11.2.101.8
lcsSetupLay7AppDetHttpHttpsTrackingTable OBJECT-TYPE
    SYNTAX     SEQUENCE OF LcsSetupLay7AppDetHttpHttpsTrackingEntry
    MAX-ACCESS not-accessible
    STATUS     current
    DESCRIPTION
            "-- empty --"
    ::= { lcsSetupLay7AppDet 8 }

-- {ROW} 1.3.6.1.4.1.2356.11.2.101.8.1
lcsSetupLay7AppDetHttpHttpsTrackingEntry OBJECT-TYPE
    SYNTAX     LcsSetupLay7AppDetHttpHttpsTrackingEntry
    MAX-ACCESS not-accessible
    STATUS     current
    DESCRIPTION
            ""
    INDEX {
            lcsSetupLay7AppDetHttpHttpsTrackingEntryApplicationName
          }
    ::= { lcsSetupLay7AppDetHttpHttpsTrackingTable 1 }

LcsSetupLay7AppDetHttpHttpsTrackingEntry ::= SEQUENCE {
            lcsSetupLay7AppDetHttpHttpsTrackingEntryApplicationName DisplayString,
            lcsSetupLay7AppDetHttpHttpsTrackingEntryTargets DisplayString,
            lcsSetupLay7AppDetHttpHttpsTrackingEntryPrio Integer32
    }

-- {COLUMN} 1.3.6.1.4.1.2356.11.2.101.8.1.1
lcsSetupLay7AppDetHttpHttpsTrackingEntryApplicationName OBJECT-TYPE
    SYNTAX     DisplayString (SIZE(0..64))
    MAX-ACCESS read-write
    STATUS     current
    DESCRIPTION
            "-- empty --"
    ::= { lcsSetupLay7AppDetHttpHttpsTrackingEntry 1 }

-- {COLUMN} 1.3.6.1.4.1.2356.11.2.101.8.1.2
lcsSetupLay7AppDetHttpHttpsTrackingEntryTargets OBJECT-TYPE
    SYNTAX     DisplayString (SIZE(0..254))
    MAX-ACCESS read-write
    STATUS     current
    DESCRIPTION
            "-- empty --"
    ::= { lcsSetupLay7AppDetHttpHttpsTrackingEntry 2 }

-- {COLUMN} 1.3.6.1.4.1.2356.11.2.101.8.1.3
lcsSetupLay7AppDetHttpHttpsTrackingEntryPrio OBJECT-TYPE
    SYNTAX     Integer32 (0..65535)
    MAX-ACCESS read-write
    STATUS     current
    DESCRIPTION
            "-- empty --"
    ::= { lcsSetupLay7AppDetHttpHttpsTrackingEntry 3 }

-- {TABLE} 1.3.6.1.4.1.2356.11.2.101.11
lcsSetupLay7AppDetVlanTable OBJECT-TYPE
    SYNTAX     SEQUENCE OF LcsSetupLay7AppDetVlanEntry
    MAX-ACCESS not-accessible
    STATUS     current
    DESCRIPTION
            "-- empty --"
    ::= { lcsSetupLay7AppDet 11 }

-- {ROW} 1.3.6.1.4.1.2356.11.2.101.11.1
lcsSetupLay7AppDetVlanEntry OBJECT-TYPE
    SYNTAX     LcsSetupLay7AppDetVlanEntry
    MAX-ACCESS not-accessible
    STATUS     current
    DESCRIPTION
            ""
    INDEX {
            lcsSetupLay7AppDetVlanEntryVlanId
          }
    ::= { lcsSetupLay7AppDetVlanTable 1 }

LcsSetupLay7AppDetVlanEntry ::= SEQUENCE {
            lcsSetupLay7AppDetVlanEntryVlanId Integer32,
            lcsSetupLay7AppDetVlanEntryTrackUser INTEGER,
            lcsSetupLay7AppDetVlanEntryTrackingActive INTEGER
    }

-- {COLUMN} 1.3.6.1.4.1.2356.11.2.101.11.1.1
lcsSetupLay7AppDetVlanEntryVlanId OBJECT-TYPE
    SYNTAX     Integer32 (0..65535)
    MAX-ACCESS read-write
    STATUS     current
    DESCRIPTION
            "-- empty --"
    ::= { lcsSetupLay7AppDetVlanEntry 1 }

-- {COLUMN} 1.3.6.1.4.1.2356.11.2.101.11.1.2
lcsSetupLay7AppDetVlanEntryTrackUser OBJECT-TYPE
    SYNTAX     INTEGER {
                  eNo (0),
                  eYes (1)
            }
    MAX-ACCESS read-write
    STATUS     current
    DESCRIPTION
            "-- empty --"
    ::= { lcsSetupLay7AppDetVlanEntry 2 }

-- {COLUMN} 1.3.6.1.4.1.2356.11.2.101.11.1.3
lcsSetupLay7AppDetVlanEntryTrackingActive OBJECT-TYPE
    SYNTAX     INTEGER {
                  eNo (0),
                  eYes (1)
            }
    MAX-ACCESS read-write
    STATUS     current
    DESCRIPTION
            "-- empty --"
    ::= { lcsSetupLay7AppDetVlanEntry 3 }

-- {SCALAR} 1.3.6.1.4.1.2356.11.2.101.12
lcsSetupLay7AppDetSaveInMin OBJECT-TYPE
    SYNTAX     Integer32 (0..65535)
    MAX-ACCESS read-write
    STATUS     current
    DESCRIPTION
            "-- empty --"
    ::= { lcsSetupLay7AppDet 12 }

-- {NODE} 1.3.6.1.4.1.2356.11.2.102
lcsSetupLmc OBJECT IDENTIFIER ::= { lcsSetup 102 }

-- {SCALAR} 1.3.6.1.4.1.2356.11.2.102.1
lcsSetupLmcOperating OBJECT-TYPE
    SYNTAX     INTEGER {
                  eNo (0),
                  eYes (1),
                  eOnlyWithoutWlc (2)
            }
    MAX-ACCESS read-write
    STATUS     current
    DESCRIPTION
            "-- empty --"
    ::= { lcsSetupLmc 1 }

-- {SCALAR} 1.3.6.1.4.1.2356.11.2.102.7
lcsSetupLmcDeleteCertificate OBJECT-TYPE
    SYNTAX     DisplayString
    MAX-ACCESS read-write
    STATUS     current
    DESCRIPTION
            "-- empty --"
    ::= { lcsSetupLmc 7 }

-- {SCALAR} 1.3.6.1.4.1.2356.11.2.102.8
lcsSetupLmcDhcpClientAutoRenew OBJECT-TYPE
    SYNTAX     INTEGER {
                  eNo (0),
                  eYes (1)
            }
    MAX-ACCESS read-write
    STATUS     current
    DESCRIPTION
            "-- empty --"
    ::= { lcsSetupLmc 8 }

-- {SCALAR} 1.3.6.1.4.1.2356.11.2.102.12
lcsSetupLmcLoopbackAddress OBJECT-TYPE
    SYNTAX     DisplayString (SIZE(0..16))
    MAX-ACCESS read-write
    STATUS     current
    DESCRIPTION
            "-- empty --"
    ::= { lcsSetupLmc 12 }

-- {SCALAR} 1.3.6.1.4.1.2356.11.2.102.13
lcsSetupLmcConfigurationViaDhcp OBJECT-TYPE
    SYNTAX     INTEGER {
                  eNo (0),
                  eYes (1)
            }
    MAX-ACCESS read-write
    STATUS     current
    DESCRIPTION
            "-- empty --"
    ::= { lcsSetupLmc 13 }

-- {NODE} 1.3.6.1.4.1.2356.11.2.102.14
lcsSetupLmcDhcpStatus OBJECT IDENTIFIER ::= { lcsSetupLmc 14 }

-- {SCALAR} 1.3.6.1.4.1.2356.11.2.102.14.5
lcsSetupLmcDhcpStatusDhcpLmcDomain OBJECT-TYPE
    SYNTAX     DisplayString (SIZE(0..254))
    MAX-ACCESS read-only
    STATUS     current
    DESCRIPTION
            "-- empty --"
    ::= { lcsSetupLmcDhcpStatus 5 }

-- {SCALAR} 1.3.6.1.4.1.2356.11.2.102.14.6
lcsSetupLmcDhcpStatusDhcpRolloutProjectId OBJECT-TYPE
    SYNTAX     DisplayString (SIZE(0..36))
    MAX-ACCESS read-only
    STATUS     current
    DESCRIPTION
            "-- empty --"
    ::= { lcsSetupLmcDhcpStatus 6 }

-- {SCALAR} 1.3.6.1.4.1.2356.11.2.102.14.7
lcsSetupLmcDhcpStatusDhcpRolloutLocationId OBJECT-TYPE
    SYNTAX     DisplayString (SIZE(0..36))
    MAX-ACCESS read-only
    STATUS     current
    DESCRIPTION
            "-- empty --"
    ::= { lcsSetupLmcDhcpStatus 7 }

-- {SCALAR} 1.3.6.1.4.1.2356.11.2.102.15
lcsSetupLmcLmcDomain OBJECT-TYPE
    SYNTAX     DisplayString (SIZE(0..255))
    MAX-ACCESS read-write
    STATUS     current
    DESCRIPTION
            "-- empty --"
    ::= { lcsSetupLmc 15 }

-- {SCALAR} 1.3.6.1.4.1.2356.11.2.102.16
lcsSetupLmcRolloutProjectId OBJECT-TYPE
    SYNTAX     DisplayString (SIZE(0..36))
    MAX-ACCESS read-write
    STATUS     current
    DESCRIPTION
            "-- empty --"
    ::= { lcsSetupLmc 16 }

-- {SCALAR} 1.3.6.1.4.1.2356.11.2.102.17
lcsSetupLmcRolloutLocationId OBJECT-TYPE
    SYNTAX     DisplayString (SIZE(0..36))
    MAX-ACCESS read-write
    STATUS     current
    DESCRIPTION
            "-- empty --"
    ::= { lcsSetupLmc 17 }

-- {SCALAR} 1.3.6.1.4.1.2356.11.2.102.18
lcsSetupLmcRolloutDeviceRole OBJECT-TYPE
    SYNTAX     DisplayString (SIZE(0..36))
    MAX-ACCESS read-write
    STATUS     current
    DESCRIPTION
            "-- empty --"
    ::= { lcsSetupLmc 18 }

-- {NODE} 1.3.6.1.4.1.2356.11.2.103
lcsSetupProvisioningServer OBJECT IDENTIFIER ::= { lcsSetup 103 }

-- {SCALAR} 1.3.6.1.4.1.2356.11.2.103.1
lcsSetupProvisioningServerOperating OBJECT-TYPE
    SYNTAX     INTEGER {
                  eNo (0),
                  eYes (1)
            }
    MAX-ACCESS read-write
    STATUS     current
    DESCRIPTION
            "-- empty --"
    ::= { lcsSetupProvisioningServer 1 }

-- {SCALAR} 1.3.6.1.4.1.2356.11.2.103.2
lcsSetupProvisioningServerPort OBJECT-TYPE
    SYNTAX     Integer32 (0..65535)
    MAX-ACCESS read-write
    STATUS     current
    DESCRIPTION
            "-- empty --"
    ::= { lcsSetupProvisioningServer 2 }

-- {SCALAR} 1.3.6.1.4.1.2356.11.2.103.3
lcsSetupProvisioningServerUrl OBJECT-TYPE
    SYNTAX     DisplayString (SIZE(0..128))
    MAX-ACCESS read-write
    STATUS     current
    DESCRIPTION
            "-- empty --"
    ::= { lcsSetupProvisioningServer 3 }

-- {SCALAR} 1.3.6.1.4.1.2356.11.2.103.4
lcsSetupProvisioningServerUrlViaDhcp OBJECT-TYPE
    SYNTAX     INTEGER {
                  eNo (0),
                  eYes (1)
            }
    MAX-ACCESS read-write
    STATUS     current
    DESCRIPTION
            "-- empty --"
    ::= { lcsSetupProvisioningServer 4 }

-- {SCALAR} 1.3.6.1.4.1.2356.11.2.103.5
lcsSetupProvisioningServerSecurePort OBJECT-TYPE
    SYNTAX     Integer32 (0..65535)
    MAX-ACCESS read-write
    STATUS     current
    DESCRIPTION
            "-- empty --"
    ::= { lcsSetupProvisioningServer 5 }

-- {SCALAR} 1.3.6.1.4.1.2356.11.2.103.6
lcsSetupProvisioningServerPollingInMinutes OBJECT-TYPE
    SYNTAX     Integer32 (0..65535)
    MAX-ACCESS read-write
    STATUS     current
    DESCRIPTION
            "-- empty --"
    ::= { lcsSetupProvisioningServer 6 }

-- {SCALAR} 1.3.6.1.4.1.2356.11.2.103.7
lcsSetupProvisioningServerUpdateServer OBJECT-TYPE
    SYNTAX     DisplayString (SIZE(0..128))
    MAX-ACCESS read-write
    STATUS     current
    DESCRIPTION
            "-- empty --"
    ::= { lcsSetupProvisioningServer 7 }

-- {NODE} 1.3.6.1.4.1.2356.11.2.104
lcsSetupBonjourProxy OBJECT IDENTIFIER ::= { lcsSetup 104 }

-- {SCALAR} 1.3.6.1.4.1.2356.11.2.104.1
lcsSetupBonjourProxyOperating OBJECT-TYPE
    SYNTAX     INTEGER {
                  eNo (0),
                  eYes (1)
            }
    MAX-ACCESS read-write
    STATUS     current
    DESCRIPTION
            "-- empty --"
    ::= { lcsSetupBonjourProxy 1 }

-- {SCALAR} 1.3.6.1.4.1.2356.11.2.104.2
lcsSetupBonjourProxyQueryClientInterval OBJECT-TYPE
    SYNTAX     Integer32 (0..255)
    MAX-ACCESS read-write
    STATUS     current
    DESCRIPTION
            "-- empty --"
    ::= { lcsSetupBonjourProxy 2 }

-- {TABLE} 1.3.6.1.4.1.2356.11.2.104.3
lcsSetupBonjourProxyNetworkListTable OBJECT-TYPE
    SYNTAX     SEQUENCE OF LcsSetupBonjourProxyNetworkListEntry
    MAX-ACCESS not-accessible
    STATUS     current
    DESCRIPTION
            "-- empty --"
    ::= { lcsSetupBonjourProxy 3 }

-- {ROW} 1.3.6.1.4.1.2356.11.2.104.3.1
lcsSetupBonjourProxyNetworkListEntry OBJECT-TYPE
    SYNTAX     LcsSetupBonjourProxyNetworkListEntry
    MAX-ACCESS not-accessible
    STATUS     current
    DESCRIPTION
            ""
    INDEX {
            lcsSetupBonjourProxyNetworkListEntryName
          }
    ::= { lcsSetupBonjourProxyNetworkListTable 1 }

LcsSetupBonjourProxyNetworkListEntry ::= SEQUENCE {
            lcsSetupBonjourProxyNetworkListEntryName DisplayString,
            lcsSetupBonjourProxyNetworkListEntryActive INTEGER,
            lcsSetupBonjourProxyNetworkListEntryServerInterface DisplayString,
            lcsSetupBonjourProxyNetworkListEntryClientInterface DisplayString,
            lcsSetupBonjourProxyNetworkListEntryServices DisplayString,
            lcsSetupBonjourProxyNetworkListEntryComment DisplayString
    }

-- {COLUMN} 1.3.6.1.4.1.2356.11.2.104.3.1.1
lcsSetupBonjourProxyNetworkListEntryName OBJECT-TYPE
    SYNTAX     DisplayString (SIZE(0..16))
    MAX-ACCESS read-write
    STATUS     current
    DESCRIPTION
            "-- empty --"
    ::= { lcsSetupBonjourProxyNetworkListEntry 1 }

-- {COLUMN} 1.3.6.1.4.1.2356.11.2.104.3.1.2
lcsSetupBonjourProxyNetworkListEntryActive OBJECT-TYPE
    SYNTAX     INTEGER {
                  eNo (0),
                  eYes (1)
            }
    MAX-ACCESS read-write
    STATUS     current
    DESCRIPTION
            "-- empty --"
    ::= { lcsSetupBonjourProxyNetworkListEntry 2 }

-- {COLUMN} 1.3.6.1.4.1.2356.11.2.104.3.1.3
lcsSetupBonjourProxyNetworkListEntryServerInterface OBJECT-TYPE
    SYNTAX     DisplayString (SIZE(0..16))
    MAX-ACCESS read-write
    STATUS     current
    DESCRIPTION
            "-- empty --"
    ::= { lcsSetupBonjourProxyNetworkListEntry 3 }

-- {COLUMN} 1.3.6.1.4.1.2356.11.2.104.3.1.4
lcsSetupBonjourProxyNetworkListEntryClientInterface OBJECT-TYPE
    SYNTAX     DisplayString (SIZE(0..16))
    MAX-ACCESS read-write
    STATUS     current
    DESCRIPTION
            "-- empty --"
    ::= { lcsSetupBonjourProxyNetworkListEntry 4 }

-- {COLUMN} 1.3.6.1.4.1.2356.11.2.104.3.1.5
lcsSetupBonjourProxyNetworkListEntryServices OBJECT-TYPE
    SYNTAX     DisplayString (SIZE(0..16))
    MAX-ACCESS read-write
    STATUS     current
    DESCRIPTION
            "-- empty --"
    ::= { lcsSetupBonjourProxyNetworkListEntry 5 }

-- {COLUMN} 1.3.6.1.4.1.2356.11.2.104.3.1.6
lcsSetupBonjourProxyNetworkListEntryComment OBJECT-TYPE
    SYNTAX     DisplayString (SIZE(0..64))
    MAX-ACCESS read-write
    STATUS     current
    DESCRIPTION
            "-- empty --"
    ::= { lcsSetupBonjourProxyNetworkListEntry 6 }

-- {TABLE} 1.3.6.1.4.1.2356.11.2.104.4
lcsSetupBonjourProxyServiceListTable OBJECT-TYPE
    SYNTAX     SEQUENCE OF LcsSetupBonjourProxyServiceListEntry
    MAX-ACCESS not-accessible
    STATUS     current
    DESCRIPTION
            "-- empty --"
    ::= { lcsSetupBonjourProxy 4 }

-- {ROW} 1.3.6.1.4.1.2356.11.2.104.4.1
lcsSetupBonjourProxyServiceListEntry OBJECT-TYPE
    SYNTAX     LcsSetupBonjourProxyServiceListEntry
    MAX-ACCESS not-accessible
    STATUS     current
    DESCRIPTION
            ""
    INDEX {
            lcsSetupBonjourProxyServiceListEntryName
          }
    ::= { lcsSetupBonjourProxyServiceListTable 1 }

LcsSetupBonjourProxyServiceListEntry ::= SEQUENCE {
            lcsSetupBonjourProxyServiceListEntryName DisplayString,
            lcsSetupBonjourProxyServiceListEntryServices DisplayString
    }

-- {COLUMN} 1.3.6.1.4.1.2356.11.2.104.4.1.1
lcsSetupBonjourProxyServiceListEntryName OBJECT-TYPE
    SYNTAX     DisplayString (SIZE(0..36))
    MAX-ACCESS read-write
    STATUS     current
    DESCRIPTION
            "-- empty --"
    ::= { lcsSetupBonjourProxyServiceListEntry 1 }

-- {COLUMN} 1.3.6.1.4.1.2356.11.2.104.4.1.2
lcsSetupBonjourProxyServiceListEntryServices OBJECT-TYPE
    SYNTAX     DisplayString (SIZE(0..252))
    MAX-ACCESS read-write
    STATUS     current
    DESCRIPTION
            "-- empty --"
    ::= { lcsSetupBonjourProxyServiceListEntry 2 }

-- {TABLE} 1.3.6.1.4.1.2356.11.2.104.5
lcsSetupBonjourProxyServicesTable OBJECT-TYPE
    SYNTAX     SEQUENCE OF LcsSetupBonjourProxyServicesEntry
    MAX-ACCESS not-accessible
    STATUS     current
    DESCRIPTION
            "-- empty --"
    ::= { lcsSetupBonjourProxy 5 }

-- {ROW} 1.3.6.1.4.1.2356.11.2.104.5.1
lcsSetupBonjourProxyServicesEntry OBJECT-TYPE
    SYNTAX     LcsSetupBonjourProxyServicesEntry
    MAX-ACCESS not-accessible
    STATUS     current
    DESCRIPTION
            ""
    INDEX {
            lcsSetupBonjourProxyServicesEntryName
          }
    ::= { lcsSetupBonjourProxyServicesTable 1 }

LcsSetupBonjourProxyServicesEntry ::= SEQUENCE {
            lcsSetupBonjourProxyServicesEntryName DisplayString,
            lcsSetupBonjourProxyServicesEntryServiceType DisplayString,
            lcsSetupBonjourProxyServicesEntryComment DisplayString
    }

-- {COLUMN} 1.3.6.1.4.1.2356.11.2.104.5.1.1
lcsSetupBonjourProxyServicesEntryName OBJECT-TYPE
    SYNTAX     DisplayString (SIZE(0..16))
    MAX-ACCESS read-write
    STATUS     current
    DESCRIPTION
            "-- empty --"
    ::= { lcsSetupBonjourProxyServicesEntry 1 }

-- {COLUMN} 1.3.6.1.4.1.2356.11.2.104.5.1.2
lcsSetupBonjourProxyServicesEntryServiceType OBJECT-TYPE
    SYNTAX     DisplayString (SIZE(0..252))
    MAX-ACCESS read-write
    STATUS     current
    DESCRIPTION
            "-- empty --"
    ::= { lcsSetupBonjourProxyServicesEntry 2 }

-- {COLUMN} 1.3.6.1.4.1.2356.11.2.104.5.1.6
lcsSetupBonjourProxyServicesEntryComment OBJECT-TYPE
    SYNTAX     DisplayString (SIZE(0..64))
    MAX-ACCESS read-write
    STATUS     current
    DESCRIPTION
            "-- empty --"
    ::= { lcsSetupBonjourProxyServicesEntry 6 }

-- {TABLE} 1.3.6.1.4.1.2356.11.2.104.6
lcsSetupBonjourProxyQueryClientTable OBJECT-TYPE
    SYNTAX     SEQUENCE OF LcsSetupBonjourProxyQueryClientEntry
    MAX-ACCESS not-accessible
    STATUS     current
    DESCRIPTION
            "-- empty --"
    ::= { lcsSetupBonjourProxy 6 }

-- {ROW} 1.3.6.1.4.1.2356.11.2.104.6.1
lcsSetupBonjourProxyQueryClientEntry OBJECT-TYPE
    SYNTAX     LcsSetupBonjourProxyQueryClientEntry
    MAX-ACCESS not-accessible
    STATUS     current
    DESCRIPTION
            ""
    INDEX {
            lcsSetupBonjourProxyQueryClientEntryName
          }
    ::= { lcsSetupBonjourProxyQueryClientTable 1 }

LcsSetupBonjourProxyQueryClientEntry ::= SEQUENCE {
            lcsSetupBonjourProxyQueryClientEntryName DisplayString,
            lcsSetupBonjourProxyQueryClientEntryActive INTEGER,
            lcsSetupBonjourProxyQueryClientEntryServerInterface DisplayString,
            lcsSetupBonjourProxyQueryClientEntryServices DisplayString
    }

-- {COLUMN} 1.3.6.1.4.1.2356.11.2.104.6.1.1
lcsSetupBonjourProxyQueryClientEntryName OBJECT-TYPE
    SYNTAX     DisplayString (SIZE(0..16))
    MAX-ACCESS read-write
    STATUS     current
    DESCRIPTION
            "-- empty --"
    ::= { lcsSetupBonjourProxyQueryClientEntry 1 }

-- {COLUMN} 1.3.6.1.4.1.2356.11.2.104.6.1.2
lcsSetupBonjourProxyQueryClientEntryActive OBJECT-TYPE
    SYNTAX     INTEGER {
                  eNo (0),
                  eYes (1)
            }
    MAX-ACCESS read-write
    STATUS     current
    DESCRIPTION
            "-- empty --"
    ::= { lcsSetupBonjourProxyQueryClientEntry 2 }

-- {COLUMN} 1.3.6.1.4.1.2356.11.2.104.6.1.3
lcsSetupBonjourProxyQueryClientEntryServerInterface OBJECT-TYPE
    SYNTAX     DisplayString (SIZE(0..16))
    MAX-ACCESS read-write
    STATUS     current
    DESCRIPTION
            "-- empty --"
    ::= { lcsSetupBonjourProxyQueryClientEntry 3 }

-- {COLUMN} 1.3.6.1.4.1.2356.11.2.104.6.1.4
lcsSetupBonjourProxyQueryClientEntryServices OBJECT-TYPE
    SYNTAX     DisplayString (SIZE(0..16))
    MAX-ACCESS read-write
    STATUS     current
    DESCRIPTION
            "-- empty --"
    ::= { lcsSetupBonjourProxyQueryClientEntry 4 }

-- {SCALAR} 1.3.6.1.4.1.2356.11.2.104.7
lcsSetupBonjourProxyInstanceLimit OBJECT-TYPE
    SYNTAX     Integer32 (0..2147483647)
    MAX-ACCESS read-write
    STATUS     current
    DESCRIPTION
            "-- empty --"
    ::= { lcsSetupBonjourProxy 7 }

-- {SCALAR} 1.3.6.1.4.1.2356.11.2.104.8
lcsSetupBonjourProxyAutoQueryServices OBJECT-TYPE
    SYNTAX     INTEGER {
                  eNo (0),
                  eYes (1)
            }
    MAX-ACCESS read-write
    STATUS     current
    DESCRIPTION
            "-- empty --"
    ::= { lcsSetupBonjourProxy 8 }

-- {NODE} 1.3.6.1.4.1.2356.11.2.105
lcsSetupOam OBJECT IDENTIFIER ::= { lcsSetup 105 }

-- {TABLE} 1.3.6.1.4.1.2356.11.2.105.1
lcsSetupOamInterfacesTable OBJECT-TYPE
    SYNTAX     SEQUENCE OF LcsSetupOamInterfacesEntry
    MAX-ACCESS not-accessible
    STATUS     current
    DESCRIPTION
            "-- empty --"
    ::= { lcsSetupOam 1 }

-- {ROW} 1.3.6.1.4.1.2356.11.2.105.1.1
lcsSetupOamInterfacesEntry OBJECT-TYPE
    SYNTAX     LcsSetupOamInterfacesEntry
    MAX-ACCESS not-accessible
    STATUS     current
    DESCRIPTION
            ""
    INDEX {
            lcsSetupOamInterfacesEntryName
          }
    ::= { lcsSetupOamInterfacesTable 1 }

LcsSetupOamInterfacesEntry ::= SEQUENCE {
            lcsSetupOamInterfacesEntryName DisplayString,
            lcsSetupOamInterfacesEntryOperating INTEGER,
            lcsSetupOamInterfacesEntryMode INTEGER
    }

-- {COLUMN} 1.3.6.1.4.1.2356.11.2.105.1.1.1
lcsSetupOamInterfacesEntryName OBJECT-TYPE
    SYNTAX     DisplayString (SIZE(0..18))
    MAX-ACCESS read-write
    STATUS     current
    DESCRIPTION
            "-- empty --"
    ::= { lcsSetupOamInterfacesEntry 1 }

-- {COLUMN} 1.3.6.1.4.1.2356.11.2.105.1.1.2
lcsSetupOamInterfacesEntryOperating OBJECT-TYPE
    SYNTAX     INTEGER {
                  eNo (0),
                  eYes (1)
            }
    MAX-ACCESS read-write
    STATUS     current
    DESCRIPTION
            "-- empty --"
    ::= { lcsSetupOamInterfacesEntry 2 }

-- {COLUMN} 1.3.6.1.4.1.2356.11.2.105.1.1.3
lcsSetupOamInterfacesEntryMode OBJECT-TYPE
    SYNTAX     INTEGER {
                  ePassive (0),
                  eActive (1)
            }
    MAX-ACCESS read-write
    STATUS     current
    DESCRIPTION
            "-- empty --"
    ::= { lcsSetupOamInterfacesEntry 3 }

-- {NODE} 1.3.6.1.4.1.2356.11.2.106
lcsSetupHardwareControl OBJECT IDENTIFIER ::= { lcsSetup 106 }

-- {SCALAR} 1.3.6.1.4.1.2356.11.2.106.1
lcsSetupHardwareControlMonitoringActive OBJECT-TYPE
    SYNTAX     INTEGER {
                  eNo (0),
                  eYes (1)
            }
    MAX-ACCESS read-write
    STATUS     current
    DESCRIPTION
            "-- empty --"
    ::= { lcsSetupHardwareControl 1 }

-- {TABLE} 1.3.6.1.4.1.2356.11.2.106.2
lcsSetupHardwareControlHeatingTable OBJECT-TYPE
    SYNTAX     SEQUENCE OF LcsSetupHardwareControlHeatingEntry
    MAX-ACCESS not-accessible
    STATUS     current
    DESCRIPTION
            "-- empty --"
    ::= { lcsSetupHardwareControl 2 }

-- {ROW} 1.3.6.1.4.1.2356.11.2.106.2.1
lcsSetupHardwareControlHeatingEntry OBJECT-TYPE
    SYNTAX     LcsSetupHardwareControlHeatingEntry
    MAX-ACCESS not-accessible
    STATUS     current
    DESCRIPTION
            ""
    INDEX {
            lcsSetupHardwareControlHeatingEntrySource
          }
    ::= { lcsSetupHardwareControlHeatingTable 1 }

LcsSetupHardwareControlHeatingEntry ::= SEQUENCE {
            lcsSetupHardwareControlHeatingEntrySource INTEGER,
            lcsSetupHardwareControlHeatingEntryTempMaxHeatDegrees Integer32,
            lcsSetupHardwareControlHeatingEntryTempNoHeatDegrees Integer32,
            lcsSetupHardwareControlHeatingEntryPowerMaxPercent Integer32
    }

-- {COLUMN} 1.3.6.1.4.1.2356.11.2.106.2.1.1
lcsSetupHardwareControlHeatingEntrySource OBJECT-TYPE
    SYNTAX     INTEGER {
                  eAfe (1),
                  eDfe (2)
            }
    MAX-ACCESS read-only
    STATUS     current
    DESCRIPTION
            "-- empty --"
    ::= { lcsSetupHardwareControlHeatingEntry 1 }

-- {COLUMN} 1.3.6.1.4.1.2356.11.2.106.2.1.2
lcsSetupHardwareControlHeatingEntryTempMaxHeatDegrees OBJECT-TYPE
    SYNTAX     Integer32 (-32768..32767)
    MAX-ACCESS read-write
    STATUS     current
    DESCRIPTION
            "-- empty --"
    ::= { lcsSetupHardwareControlHeatingEntry 2 }

-- {COLUMN} 1.3.6.1.4.1.2356.11.2.106.2.1.3
lcsSetupHardwareControlHeatingEntryTempNoHeatDegrees OBJECT-TYPE
    SYNTAX     Integer32 (-32768..32767)
    MAX-ACCESS read-write
    STATUS     current
    DESCRIPTION
            "-- empty --"
    ::= { lcsSetupHardwareControlHeatingEntry 3 }

-- {COLUMN} 1.3.6.1.4.1.2356.11.2.106.2.1.4
lcsSetupHardwareControlHeatingEntryPowerMaxPercent OBJECT-TYPE
    SYNTAX     Integer32 (-32768..32767)
    MAX-ACCESS read-write
    STATUS     current
    DESCRIPTION
            "-- empty --"
    ::= { lcsSetupHardwareControlHeatingEntry 4 }

-- {TABLE} 1.3.6.1.4.1.2356.11.2.106.4
lcsSetupHardwareControlOvertempShutdownTable OBJECT-TYPE
    SYNTAX     SEQUENCE OF LcsSetupHardwareControlOvertempShutdownEntry
    MAX-ACCESS not-accessible
    STATUS     current
    DESCRIPTION
            "-- empty --"
    ::= { lcsSetupHardwareControl 4 }

-- {ROW} 1.3.6.1.4.1.2356.11.2.106.4.1
lcsSetupHardwareControlOvertempShutdownEntry OBJECT-TYPE
    SYNTAX     LcsSetupHardwareControlOvertempShutdownEntry
    MAX-ACCESS not-accessible
    STATUS     current
    DESCRIPTION
            ""
    INDEX {
            lcsSetupHardwareControlOvertempShutdownEntrySensor
          }
    ::= { lcsSetupHardwareControlOvertempShutdownTable 1 }

LcsSetupHardwareControlOvertempShutdownEntry ::= SEQUENCE {
            lcsSetupHardwareControlOvertempShutdownEntrySensor INTEGER,
            lcsSetupHardwareControlOvertempShutdownEntryShutdownDegrees Integer32,
            lcsSetupHardwareControlOvertempShutdownEntryRestartDegrees Integer32
    }

-- {COLUMN} 1.3.6.1.4.1.2356.11.2.106.4.1.1
lcsSetupHardwareControlOvertempShutdownEntrySensor OBJECT-TYPE
    SYNTAX     INTEGER {
                  eTemperatureBoard (1),
                  eTemperatureCpu (2)
            }
    MAX-ACCESS read-only
    STATUS     current
    DESCRIPTION
            "-- empty --"
    ::= { lcsSetupHardwareControlOvertempShutdownEntry 1 }

-- {COLUMN} 1.3.6.1.4.1.2356.11.2.106.4.1.2
lcsSetupHardwareControlOvertempShutdownEntryShutdownDegrees OBJECT-TYPE
    SYNTAX     Integer32 (-32768..32767)
    MAX-ACCESS read-write
    STATUS     current
    DESCRIPTION
            "-- empty --"
    ::= { lcsSetupHardwareControlOvertempShutdownEntry 2 }

-- {COLUMN} 1.3.6.1.4.1.2356.11.2.106.4.1.3
lcsSetupHardwareControlOvertempShutdownEntryRestartDegrees OBJECT-TYPE
    SYNTAX     Integer32 (-32768..32767)
    MAX-ACCESS read-write
    STATUS     current
    DESCRIPTION
            "-- empty --"
    ::= { lcsSetupHardwareControlOvertempShutdownEntry 3 }

-- {NODE} 1.3.6.1.4.1.2356.11.2.107
lcsSetupAfu OBJECT IDENTIFIER ::= { lcsSetup 107 }

-- {SCALAR} 1.3.6.1.4.1.2356.11.2.107.1
lcsSetupAfuMode OBJECT-TYPE
    SYNTAX     INTEGER {
                  eManual (0),
                  eCheck (1),
                  eCheckAndUpdate (2)
            }
    MAX-ACCESS read-write
    STATUS     current
    DESCRIPTION
            "-- empty --"
    ::= { lcsSetupAfu 1 }

-- {SCALAR} 1.3.6.1.4.1.2356.11.2.107.2
lcsSetupAfuCheckFirmwareNow OBJECT-TYPE
    SYNTAX     DisplayString
    MAX-ACCESS read-write
    STATUS     current
    DESCRIPTION
            "-- empty --"
    ::= { lcsSetupAfu 2 }

-- {SCALAR} 1.3.6.1.4.1.2356.11.2.107.3
lcsSetupAfuUpdateFirmwareNow OBJECT-TYPE
    SYNTAX     DisplayString
    MAX-ACCESS read-write
    STATUS     current
    DESCRIPTION
            "-- empty --"
    ::= { lcsSetupAfu 3 }

-- {SCALAR} 1.3.6.1.4.1.2356.11.2.107.4
lcsSetupAfuCancelCurrentAction OBJECT-TYPE
    SYNTAX     DisplayString
    MAX-ACCESS read-write
    STATUS     current
    DESCRIPTION
            "-- empty --"
    ::= { lcsSetupAfu 4 }

-- {SCALAR} 1.3.6.1.4.1.2356.11.2.107.5
lcsSetupAfuResetUpdaterConfig OBJECT-TYPE
    SYNTAX     DisplayString
    MAX-ACCESS read-write
    STATUS     current
    DESCRIPTION
            "-- empty --"
    ::= { lcsSetupAfu 5 }

-- {SCALAR} 1.3.6.1.4.1.2356.11.2.107.6
lcsSetupAfuBaseUrl OBJECT-TYPE
    SYNTAX     DisplayString (SIZE(0..252))
    MAX-ACCESS read-write
    STATUS     current
    DESCRIPTION
            "-- empty --"
    ::= { lcsSetupAfu 6 }

-- {SCALAR} 1.3.6.1.4.1.2356.11.2.107.7
lcsSetupAfuCheckInterval OBJECT-TYPE
    SYNTAX     INTEGER {
                  eDaily (0),
                  eWeekly (1)
            }
    MAX-ACCESS read-write
    STATUS     current
    DESCRIPTION
            "-- empty --"
    ::= { lcsSetupAfu 7 }

-- {SCALAR} 1.3.6.1.4.1.2356.11.2.107.8
lcsSetupAfuVersionPolicy OBJECT-TYPE
    SYNTAX     INTEGER {
                  eLatest (0),
                  eCurrent (1),
                  eSecurityUpdatesOnly (2),
                  eLatestWithoutRel (3)
            }
    MAX-ACCESS read-write
    STATUS     current
    DESCRIPTION
            "-- empty --"
    ::= { lcsSetupAfu 8 }

-- {SCALAR} 1.3.6.1.4.1.2356.11.2.107.9
lcsSetupAfuLoopbackAddr OBJECT-TYPE
    SYNTAX     DisplayString (SIZE(0..16))
    MAX-ACCESS read-write
    STATUS     current
    DESCRIPTION
            "-- empty --"
    ::= { lcsSetupAfu 9 }

-- {SCALAR} 1.3.6.1.4.1.2356.11.2.107.10
lcsSetupAfuCheckTimeBegin OBJECT-TYPE
    SYNTAX     Integer32 (0..255)
    MAX-ACCESS read-write
    STATUS     current
    DESCRIPTION
            "-- empty --"
    ::= { lcsSetupAfu 10 }

-- {SCALAR} 1.3.6.1.4.1.2356.11.2.107.11
lcsSetupAfuCheckTimeEnd OBJECT-TYPE
    SYNTAX     Integer32 (0..255)
    MAX-ACCESS read-write
    STATUS     current
    DESCRIPTION
            "-- empty --"
    ::= { lcsSetupAfu 11 }

-- {SCALAR} 1.3.6.1.4.1.2356.11.2.107.12
lcsSetupAfuInstallTimeBegin OBJECT-TYPE
    SYNTAX     Integer32 (0..255)
    MAX-ACCESS read-write
    STATUS     current
    DESCRIPTION
            "-- empty --"
    ::= { lcsSetupAfu 12 }

-- {SCALAR} 1.3.6.1.4.1.2356.11.2.107.13
lcsSetupAfuInstallTimeEnd OBJECT-TYPE
    SYNTAX     Integer32 (0..255)
    MAX-ACCESS read-write
    STATUS     current
    DESCRIPTION
            "-- empty --"
    ::= { lcsSetupAfu 13 }

-- {SCALAR} 1.3.6.1.4.1.2356.11.2.107.14
lcsSetupAfuEMailNotification OBJECT-TYPE
    SYNTAX     INTEGER {
                  eNo (0),
                  eYes (1)
            }
    MAX-ACCESS read-write
    STATUS     current
    DESCRIPTION
            "-- empty --"
    ::= { lcsSetupAfu 14 }

-- {SCALAR} 1.3.6.1.4.1.2356.11.2.107.15
lcsSetupAfuEMailAddress OBJECT-TYPE
    SYNTAX     DisplayString (SIZE(0..63))
    MAX-ACCESS read-write
    STATUS     current
    DESCRIPTION
            "-- empty --"
    ::= { lcsSetupAfu 15 }

-- {NODE} 1.3.6.1.4.1.2356.11.2.108
lcsSetupMCast OBJECT IDENTIFIER ::= { lcsSetup 108 }

-- {NODE} 1.3.6.1.4.1.2356.11.2.108.1
lcsSetupMCastIgmp OBJECT IDENTIFIER ::= { lcsSetupMCast 1 }

-- {TABLE} 1.3.6.1.4.1.2356.11.2.108.1.1
lcsSetupMCastIgmpIgmpProxyTable OBJECT-TYPE
    SYNTAX     SEQUENCE OF LcsSetupMCastIgmpIgmpProxyEntry
    MAX-ACCESS not-accessible
    STATUS     current
    DESCRIPTION
            "-- empty --"
    ::= { lcsSetupMCastIgmp 1 }

-- {ROW} 1.3.6.1.4.1.2356.11.2.108.1.1.1
lcsSetupMCastIgmpIgmpProxyEntry OBJECT-TYPE
    SYNTAX     LcsSetupMCastIgmpIgmpProxyEntry
    MAX-ACCESS not-accessible
    STATUS     current
    DESCRIPTION
            ""
    INDEX {
            lcsSetupMCastIgmpIgmpProxyEntryDownstreamInterface,
            lcsSetupMCastIgmpIgmpProxyEntryUpstreamInterface
          }
    ::= { lcsSetupMCastIgmpIgmpProxyTable 1 }

LcsSetupMCastIgmpIgmpProxyEntry ::= SEQUENCE {
            lcsSetupMCastIgmpIgmpProxyEntryDownstreamInterface DisplayString,
            lcsSetupMCastIgmpIgmpProxyEntryUpstreamInterface DisplayString,
            lcsSetupMCastIgmpIgmpProxyEntryGroupFilter DisplayString
    }

-- {COLUMN} 1.3.6.1.4.1.2356.11.2.108.1.1.1.1
lcsSetupMCastIgmpIgmpProxyEntryDownstreamInterface OBJECT-TYPE
    SYNTAX     DisplayString (SIZE(0..16))
    MAX-ACCESS read-write
    STATUS     current
    DESCRIPTION
            "-- empty --"
    ::= { lcsSetupMCastIgmpIgmpProxyEntry 1 }

-- {COLUMN} 1.3.6.1.4.1.2356.11.2.108.1.1.1.2
lcsSetupMCastIgmpIgmpProxyEntryUpstreamInterface OBJECT-TYPE
    SYNTAX     DisplayString (SIZE(0..16))
    MAX-ACCESS read-write
    STATUS     current
    DESCRIPTION
            "-- empty --"
    ::= { lcsSetupMCastIgmpIgmpProxyEntry 2 }

-- {COLUMN} 1.3.6.1.4.1.2356.11.2.108.1.1.1.3
lcsSetupMCastIgmpIgmpProxyEntryGroupFilter OBJECT-TYPE
    SYNTAX     DisplayString (SIZE(0..16))
    MAX-ACCESS read-write
    STATUS     current
    DESCRIPTION
            "-- empty --"
    ::= { lcsSetupMCastIgmpIgmpProxyEntry 3 }

-- {TABLE} 1.3.6.1.4.1.2356.11.2.108.1.3
lcsSetupMCastIgmpSsmRangesTable OBJECT-TYPE
    SYNTAX     SEQUENCE OF LcsSetupMCastIgmpSsmRangesEntry
    MAX-ACCESS not-accessible
    STATUS     current
    DESCRIPTION
            "-- empty --"
    ::= { lcsSetupMCastIgmp 3 }

-- {ROW} 1.3.6.1.4.1.2356.11.2.108.1.3.1
lcsSetupMCastIgmpSsmRangesEntry OBJECT-TYPE
    SYNTAX     LcsSetupMCastIgmpSsmRangesEntry
    MAX-ACCESS not-accessible
    STATUS     current
    DESCRIPTION
            ""
    INDEX {
            lcsSetupMCastIgmpSsmRangesEntryPrefix
          }
    ::= { lcsSetupMCastIgmpSsmRangesTable 1 }

LcsSetupMCastIgmpSsmRangesEntry ::= SEQUENCE {
            lcsSetupMCastIgmpSsmRangesEntryPrefix DisplayString
    }

-- {COLUMN} 1.3.6.1.4.1.2356.11.2.108.1.3.1.1
lcsSetupMCastIgmpSsmRangesEntryPrefix OBJECT-TYPE
    SYNTAX     DisplayString (SIZE(0..18))
    MAX-ACCESS read-write
    STATUS     current
    DESCRIPTION
            "-- empty --"
    ::= { lcsSetupMCastIgmpSsmRangesEntry 1 }

-- {TABLE} 1.3.6.1.4.1.2356.11.2.108.1.4
lcsSetupMCastIgmpSsmSourceIpListTable OBJECT-TYPE
    SYNTAX     SEQUENCE OF LcsSetupMCastIgmpSsmSourceIpListEntry
    MAX-ACCESS not-accessible
    STATUS     current
    DESCRIPTION
            "-- empty --"
    ::= { lcsSetupMCastIgmp 4 }

-- {ROW} 1.3.6.1.4.1.2356.11.2.108.1.4.1
lcsSetupMCastIgmpSsmSourceIpListEntry OBJECT-TYPE
    SYNTAX     LcsSetupMCastIgmpSsmSourceIpListEntry
    MAX-ACCESS not-accessible
    STATUS     current
    DESCRIPTION
            ""
    INDEX {
            lcsSetupMCastIgmpSsmSourceIpListEntryName,
            lcsSetupMCastIgmpSsmSourceIpListEntryIpAddress
          }
    ::= { lcsSetupMCastIgmpSsmSourceIpListTable 1 }

LcsSetupMCastIgmpSsmSourceIpListEntry ::= SEQUENCE {
            lcsSetupMCastIgmpSsmSourceIpListEntryName DisplayString,
            lcsSetupMCastIgmpSsmSourceIpListEntryIpAddress IpAddress
    }

-- {COLUMN} 1.3.6.1.4.1.2356.11.2.108.1.4.1.1
lcsSetupMCastIgmpSsmSourceIpListEntryName OBJECT-TYPE
    SYNTAX     DisplayString (SIZE(0..16))
    MAX-ACCESS read-write
    STATUS     current
    DESCRIPTION
            "-- empty --"
    ::= { lcsSetupMCastIgmpSsmSourceIpListEntry 1 }

-- {COLUMN} 1.3.6.1.4.1.2356.11.2.108.1.4.1.2
lcsSetupMCastIgmpSsmSourceIpListEntryIpAddress OBJECT-TYPE
    SYNTAX     IpAddress
    MAX-ACCESS read-write
    STATUS     current
    DESCRIPTION
            "-- empty --"
    ::= { lcsSetupMCastIgmpSsmSourceIpListEntry 2 }

-- {TABLE} 1.3.6.1.4.1.2356.11.2.108.1.5
lcsSetupMCastIgmpStaticRoutesTable OBJECT-TYPE
    SYNTAX     SEQUENCE OF LcsSetupMCastIgmpStaticRoutesEntry
    MAX-ACCESS not-accessible
    STATUS     current
    DESCRIPTION
            "-- empty --"
    ::= { lcsSetupMCastIgmp 5 }

-- {ROW} 1.3.6.1.4.1.2356.11.2.108.1.5.1
lcsSetupMCastIgmpStaticRoutesEntry OBJECT-TYPE
    SYNTAX     LcsSetupMCastIgmpStaticRoutesEntry
    MAX-ACCESS not-accessible
    STATUS     current
    DESCRIPTION
            ""
    INDEX {
            lcsSetupMCastIgmpStaticRoutesEntryUpstreamInterface,
            lcsSetupMCastIgmpStaticRoutesEntryGroup,
            lcsSetupMCastIgmpStaticRoutesEntryDownstreamInterface
          }
    ::= { lcsSetupMCastIgmpStaticRoutesTable 1 }

LcsSetupMCastIgmpStaticRoutesEntry ::= SEQUENCE {
            lcsSetupMCastIgmpStaticRoutesEntryUpstreamInterface DisplayString,
            lcsSetupMCastIgmpStaticRoutesEntryGroup IpAddress,
            lcsSetupMCastIgmpStaticRoutesEntryDownstreamInterface DisplayString,
            lcsSetupMCastIgmpStaticRoutesEntryMode INTEGER,
            lcsSetupMCastIgmpStaticRoutesEntrySsmSourceIpList DisplayString
    }

-- {COLUMN} 1.3.6.1.4.1.2356.11.2.108.1.5.1.1
lcsSetupMCastIgmpStaticRoutesEntryUpstreamInterface OBJECT-TYPE
    SYNTAX     DisplayString (SIZE(0..16))
    MAX-ACCESS read-write
    STATUS     current
    DESCRIPTION
            "-- empty --"
    ::= { lcsSetupMCastIgmpStaticRoutesEntry 1 }

-- {COLUMN} 1.3.6.1.4.1.2356.11.2.108.1.5.1.2
lcsSetupMCastIgmpStaticRoutesEntryGroup OBJECT-TYPE
    SYNTAX     IpAddress
    MAX-ACCESS read-write
    STATUS     current
    DESCRIPTION
            "-- empty --"
    ::= { lcsSetupMCastIgmpStaticRoutesEntry 2 }

-- {COLUMN} 1.3.6.1.4.1.2356.11.2.108.1.5.1.3
lcsSetupMCastIgmpStaticRoutesEntryDownstreamInterface OBJECT-TYPE
    SYNTAX     DisplayString (SIZE(0..16))
    MAX-ACCESS read-write
    STATUS     current
    DESCRIPTION
            "-- empty --"
    ::= { lcsSetupMCastIgmpStaticRoutesEntry 3 }

-- {COLUMN} 1.3.6.1.4.1.2356.11.2.108.1.5.1.4
lcsSetupMCastIgmpStaticRoutesEntryMode OBJECT-TYPE
    SYNTAX     INTEGER {
                  eInclude (1),
                  eExclude (2)
            }
    MAX-ACCESS read-write
    STATUS     current
    DESCRIPTION
            "-- empty --"
    ::= { lcsSetupMCastIgmpStaticRoutesEntry 4 }

-- {COLUMN} 1.3.6.1.4.1.2356.11.2.108.1.5.1.5
lcsSetupMCastIgmpStaticRoutesEntrySsmSourceIpList OBJECT-TYPE
    SYNTAX     DisplayString (SIZE(0..16))
    MAX-ACCESS read-write
    STATUS     current
    DESCRIPTION
            "-- empty --"
    ::= { lcsSetupMCastIgmpStaticRoutesEntry 5 }

-- {TABLE} 1.3.6.1.4.1.2356.11.2.108.1.6
lcsSetupMCastIgmpParameterTable OBJECT-TYPE
    SYNTAX     SEQUENCE OF LcsSetupMCastIgmpParameterEntry
    MAX-ACCESS not-accessible
    STATUS     current
    DESCRIPTION
            "-- empty --"
    ::= { lcsSetupMCastIgmp 6 }

-- {ROW} 1.3.6.1.4.1.2356.11.2.108.1.6.1
lcsSetupMCastIgmpParameterEntry OBJECT-TYPE
    SYNTAX     LcsSetupMCastIgmpParameterEntry
    MAX-ACCESS not-accessible
    STATUS     current
    DESCRIPTION
            ""
    INDEX {
            lcsSetupMCastIgmpParameterEntryInterface
          }
    ::= { lcsSetupMCastIgmpParameterTable 1 }

LcsSetupMCastIgmpParameterEntry ::= SEQUENCE {
            lcsSetupMCastIgmpParameterEntryInterface DisplayString,
            lcsSetupMCastIgmpParameterEntryRobustnessVariable Integer32,
            lcsSetupMCastIgmpParameterEntryUnsolicitedReportInterval Integer32,
            lcsSetupMCastIgmpParameterEntryQueryInterval Integer32,
            lcsSetupMCastIgmpParameterEntryQueryResponseInterval Integer32,
            lcsSetupMCastIgmpParameterEntryStartupQueryInterval Integer32,
            lcsSetupMCastIgmpParameterEntryStartupQueryCount Integer32,
            lcsSetupMCastIgmpParameterEntryLastListenerQueryInterval Integer32,
            lcsSetupMCastIgmpParameterEntryLastListenerQueryCount Integer32,
            lcsSetupMCastIgmpParameterEntryIgmpCompatibilityMode INTEGER,
            lcsSetupMCastIgmpParameterEntryQuickLeave INTEGER
    }

-- {COLUMN} 1.3.6.1.4.1.2356.11.2.108.1.6.1.1
lcsSetupMCastIgmpParameterEntryInterface OBJECT-TYPE
    SYNTAX     DisplayString (SIZE(0..16))
    MAX-ACCESS read-write
    STATUS     current
    DESCRIPTION
            "-- empty --"
    ::= { lcsSetupMCastIgmpParameterEntry 1 }

-- {COLUMN} 1.3.6.1.4.1.2356.11.2.108.1.6.1.2
lcsSetupMCastIgmpParameterEntryRobustnessVariable OBJECT-TYPE
    SYNTAX     Integer32 (0..255)
    MAX-ACCESS read-write
    STATUS     current
    DESCRIPTION
            "-- empty --"
    ::= { lcsSetupMCastIgmpParameterEntry 2 }

-- {COLUMN} 1.3.6.1.4.1.2356.11.2.108.1.6.1.3
lcsSetupMCastIgmpParameterEntryUnsolicitedReportInterval OBJECT-TYPE
    SYNTAX     Integer32 (0..255)
    MAX-ACCESS read-write
    STATUS     current
    DESCRIPTION
            "-- empty --"
    ::= { lcsSetupMCastIgmpParameterEntry 3 }

-- {COLUMN} 1.3.6.1.4.1.2356.11.2.108.1.6.1.4
lcsSetupMCastIgmpParameterEntryQueryInterval OBJECT-TYPE
    SYNTAX     Integer32 (0..2147483647)
    MAX-ACCESS read-write
    STATUS     current
    DESCRIPTION
            "-- empty --"
    ::= { lcsSetupMCastIgmpParameterEntry 4 }

-- {COLUMN} 1.3.6.1.4.1.2356.11.2.108.1.6.1.5
lcsSetupMCastIgmpParameterEntryQueryResponseInterval OBJECT-TYPE
    SYNTAX     Integer32 (0..2147483647)
    MAX-ACCESS read-write
    STATUS     current
    DESCRIPTION
            "-- empty --"
    ::= { lcsSetupMCastIgmpParameterEntry 5 }

-- {COLUMN} 1.3.6.1.4.1.2356.11.2.108.1.6.1.6
lcsSetupMCastIgmpParameterEntryStartupQueryInterval OBJECT-TYPE
    SYNTAX     Integer32 (0..2147483647)
    MAX-ACCESS read-write
    STATUS     current
    DESCRIPTION
            "-- empty --"
    ::= { lcsSetupMCastIgmpParameterEntry 6 }

-- {COLUMN} 1.3.6.1.4.1.2356.11.2.108.1.6.1.7
lcsSetupMCastIgmpParameterEntryStartupQueryCount OBJECT-TYPE
    SYNTAX     Integer32 (0..255)
    MAX-ACCESS read-write
    STATUS     current
    DESCRIPTION
            "-- empty --"
    ::= { lcsSetupMCastIgmpParameterEntry 7 }

-- {COLUMN} 1.3.6.1.4.1.2356.11.2.108.1.6.1.8
lcsSetupMCastIgmpParameterEntryLastListenerQueryInterval OBJECT-TYPE
    SYNTAX     Integer32 (0..255)
    MAX-ACCESS read-write
    STATUS     current
    DESCRIPTION
            "-- empty --"
    ::= { lcsSetupMCastIgmpParameterEntry 8 }

-- {COLUMN} 1.3.6.1.4.1.2356.11.2.108.1.6.1.9
lcsSetupMCastIgmpParameterEntryLastListenerQueryCount OBJECT-TYPE
    SYNTAX     Integer32 (0..255)
    MAX-ACCESS read-write
    STATUS     current
    DESCRIPTION
            "-- empty --"
    ::= { lcsSetupMCastIgmpParameterEntry 9 }

-- {COLUMN} 1.3.6.1.4.1.2356.11.2.108.1.6.1.10
lcsSetupMCastIgmpParameterEntryIgmpCompatibilityMode OBJECT-TYPE
    SYNTAX     INTEGER {
                  eOff (0),
                  eV1 (1),
                  eV2 (2),
                  eV3 (3)
            }
    MAX-ACCESS read-write
    STATUS     current
    DESCRIPTION
            "-- empty --"
    ::= { lcsSetupMCastIgmpParameterEntry 10 }

-- {COLUMN} 1.3.6.1.4.1.2356.11.2.108.1.6.1.11
lcsSetupMCastIgmpParameterEntryQuickLeave OBJECT-TYPE
    SYNTAX     INTEGER {
                  eNo (0),
                  eYes (1)
            }
    MAX-ACCESS read-write
    STATUS     current
    DESCRIPTION
            "-- empty --"
    ::= { lcsSetupMCastIgmpParameterEntry 11 }

-- {SCALAR} 1.3.6.1.4.1.2356.11.2.108.1.7
lcsSetupMCastIgmpCheckRouterAlert OBJECT-TYPE
    SYNTAX     INTEGER {
                  eNo (0),
                  eYes (1)
            }
    MAX-ACCESS read-write
    STATUS     current
    DESCRIPTION
            "-- empty --"
    ::= { lcsSetupMCastIgmp 7 }

-- {SCALAR} 1.3.6.1.4.1.2356.11.2.108.1.8
lcsSetupMCastIgmpCollectStatistics OBJECT-TYPE
    SYNTAX     INTEGER {
                  eNo (0),
                  eYes (1)
            }
    MAX-ACCESS read-write
    STATUS     current
    DESCRIPTION
            "-- empty --"
    ::= { lcsSetupMCastIgmp 8 }

-- {TABLE} 1.3.6.1.4.1.2356.11.2.108.1.9
lcsSetupMCastIgmpStaticJoinTable OBJECT-TYPE
    SYNTAX     SEQUENCE OF LcsSetupMCastIgmpStaticJoinEntry
    MAX-ACCESS not-accessible
    STATUS     current
    DESCRIPTION
            "-- empty --"
    ::= { lcsSetupMCastIgmp 9 }

-- {ROW} 1.3.6.1.4.1.2356.11.2.108.1.9.1
lcsSetupMCastIgmpStaticJoinEntry OBJECT-TYPE
    SYNTAX     LcsSetupMCastIgmpStaticJoinEntry
    MAX-ACCESS not-accessible
    STATUS     current
    DESCRIPTION
            ""
    INDEX {
            lcsSetupMCastIgmpStaticJoinEntryInterface,
            lcsSetupMCastIgmpStaticJoinEntryGroup
          }
    ::= { lcsSetupMCastIgmpStaticJoinTable 1 }

LcsSetupMCastIgmpStaticJoinEntry ::= SEQUENCE {
            lcsSetupMCastIgmpStaticJoinEntryInterface DisplayString,
            lcsSetupMCastIgmpStaticJoinEntryGroup IpAddress,
            lcsSetupMCastIgmpStaticJoinEntryComment DisplayString
    }

-- {COLUMN} 1.3.6.1.4.1.2356.11.2.108.1.9.1.1
lcsSetupMCastIgmpStaticJoinEntryInterface OBJECT-TYPE
    SYNTAX     DisplayString (SIZE(0..16))
    MAX-ACCESS read-write
    STATUS     current
    DESCRIPTION
            "-- empty --"
    ::= { lcsSetupMCastIgmpStaticJoinEntry 1 }

-- {COLUMN} 1.3.6.1.4.1.2356.11.2.108.1.9.1.2
lcsSetupMCastIgmpStaticJoinEntryGroup OBJECT-TYPE
    SYNTAX     IpAddress
    MAX-ACCESS read-write
    STATUS     current
    DESCRIPTION
            "-- empty --"
    ::= { lcsSetupMCastIgmpStaticJoinEntry 2 }

-- {COLUMN} 1.3.6.1.4.1.2356.11.2.108.1.9.1.3
lcsSetupMCastIgmpStaticJoinEntryComment OBJECT-TYPE
    SYNTAX     DisplayString (SIZE(0..254))
    MAX-ACCESS read-write
    STATUS     current
    DESCRIPTION
            "-- empty --"
    ::= { lcsSetupMCastIgmpStaticJoinEntry 3 }

-- {NODE} 1.3.6.1.4.1.2356.11.2.108.2
lcsSetupMCastMld OBJECT IDENTIFIER ::= { lcsSetupMCast 2 }

-- {TABLE} 1.3.6.1.4.1.2356.11.2.108.2.1
lcsSetupMCastMldMldProxyTable OBJECT-TYPE
    SYNTAX     SEQUENCE OF LcsSetupMCastMldMldProxyEntry
    MAX-ACCESS not-accessible
    STATUS     current
    DESCRIPTION
            "-- empty --"
    ::= { lcsSetupMCastMld 1 }

-- {ROW} 1.3.6.1.4.1.2356.11.2.108.2.1.1
lcsSetupMCastMldMldProxyEntry OBJECT-TYPE
    SYNTAX     LcsSetupMCastMldMldProxyEntry
    MAX-ACCESS not-accessible
    STATUS     current
    DESCRIPTION
            ""
    INDEX {
            lcsSetupMCastMldMldProxyEntryDownstreamInterface,
            lcsSetupMCastMldMldProxyEntryUpstreamInterface
          }
    ::= { lcsSetupMCastMldMldProxyTable 1 }

LcsSetupMCastMldMldProxyEntry ::= SEQUENCE {
            lcsSetupMCastMldMldProxyEntryDownstreamInterface DisplayString,
            lcsSetupMCastMldMldProxyEntryUpstreamInterface DisplayString,
            lcsSetupMCastMldMldProxyEntryGroupFilter DisplayString
    }

-- {COLUMN} 1.3.6.1.4.1.2356.11.2.108.2.1.1.1
lcsSetupMCastMldMldProxyEntryDownstreamInterface OBJECT-TYPE
    SYNTAX     DisplayString (SIZE(0..16))
    MAX-ACCESS read-write
    STATUS     current
    DESCRIPTION
            "-- empty --"
    ::= { lcsSetupMCastMldMldProxyEntry 1 }

-- {COLUMN} 1.3.6.1.4.1.2356.11.2.108.2.1.1.2
lcsSetupMCastMldMldProxyEntryUpstreamInterface OBJECT-TYPE
    SYNTAX     DisplayString (SIZE(0..16))
    MAX-ACCESS read-write
    STATUS     current
    DESCRIPTION
            "-- empty --"
    ::= { lcsSetupMCastMldMldProxyEntry 2 }

-- {COLUMN} 1.3.6.1.4.1.2356.11.2.108.2.1.1.3
lcsSetupMCastMldMldProxyEntryGroupFilter OBJECT-TYPE
    SYNTAX     DisplayString (SIZE(0..16))
    MAX-ACCESS read-write
    STATUS     current
    DESCRIPTION
            "-- empty --"
    ::= { lcsSetupMCastMldMldProxyEntry 3 }

-- {TABLE} 1.3.6.1.4.1.2356.11.2.108.2.3
lcsSetupMCastMldSsmRangesTable OBJECT-TYPE
    SYNTAX     SEQUENCE OF LcsSetupMCastMldSsmRangesEntry
    MAX-ACCESS not-accessible
    STATUS     current
    DESCRIPTION
            "-- empty --"
    ::= { lcsSetupMCastMld 3 }

-- {ROW} 1.3.6.1.4.1.2356.11.2.108.2.3.1
lcsSetupMCastMldSsmRangesEntry OBJECT-TYPE
    SYNTAX     LcsSetupMCastMldSsmRangesEntry
    MAX-ACCESS not-accessible
    STATUS     current
    DESCRIPTION
            ""
    INDEX {
            lcsSetupMCastMldSsmRangesEntryPrefix
          }
    ::= { lcsSetupMCastMldSsmRangesTable 1 }

LcsSetupMCastMldSsmRangesEntry ::= SEQUENCE {
            lcsSetupMCastMldSsmRangesEntryPrefix DisplayString
    }

-- {COLUMN} 1.3.6.1.4.1.2356.11.2.108.2.3.1.1
lcsSetupMCastMldSsmRangesEntryPrefix OBJECT-TYPE
    SYNTAX     DisplayString (SIZE(0..43))
    MAX-ACCESS read-write
    STATUS     current
    DESCRIPTION
            "-- empty --"
    ::= { lcsSetupMCastMldSsmRangesEntry 1 }

-- {TABLE} 1.3.6.1.4.1.2356.11.2.108.2.4
lcsSetupMCastMldSsmSourceIpListTable OBJECT-TYPE
    SYNTAX     SEQUENCE OF LcsSetupMCastMldSsmSourceIpListEntry
    MAX-ACCESS not-accessible
    STATUS     current
    DESCRIPTION
            "-- empty --"
    ::= { lcsSetupMCastMld 4 }

-- {ROW} 1.3.6.1.4.1.2356.11.2.108.2.4.1
lcsSetupMCastMldSsmSourceIpListEntry OBJECT-TYPE
    SYNTAX     LcsSetupMCastMldSsmSourceIpListEntry
    MAX-ACCESS not-accessible
    STATUS     current
    DESCRIPTION
            ""
    INDEX {
            lcsSetupMCastMldSsmSourceIpListEntryName,
            lcsSetupMCastMldSsmSourceIpListEntryIpAddress
          }
    ::= { lcsSetupMCastMldSsmSourceIpListTable 1 }

LcsSetupMCastMldSsmSourceIpListEntry ::= SEQUENCE {
            lcsSetupMCastMldSsmSourceIpListEntryName DisplayString,
            lcsSetupMCastMldSsmSourceIpListEntryIpAddress IpAddress
    }

-- {COLUMN} 1.3.6.1.4.1.2356.11.2.108.2.4.1.1
lcsSetupMCastMldSsmSourceIpListEntryName OBJECT-TYPE
    SYNTAX     DisplayString (SIZE(0..16))
    MAX-ACCESS read-write
    STATUS     current
    DESCRIPTION
            "-- empty --"
    ::= { lcsSetupMCastMldSsmSourceIpListEntry 1 }

-- {COLUMN} 1.3.6.1.4.1.2356.11.2.108.2.4.1.2
lcsSetupMCastMldSsmSourceIpListEntryIpAddress OBJECT-TYPE
    SYNTAX     IpAddress
    MAX-ACCESS read-write
    STATUS     current
    DESCRIPTION
            "-- empty --"
    ::= { lcsSetupMCastMldSsmSourceIpListEntry 2 }

-- {TABLE} 1.3.6.1.4.1.2356.11.2.108.2.5
lcsSetupMCastMldStaticRoutesTable OBJECT-TYPE
    SYNTAX     SEQUENCE OF LcsSetupMCastMldStaticRoutesEntry
    MAX-ACCESS not-accessible
    STATUS     current
    DESCRIPTION
            "-- empty --"
    ::= { lcsSetupMCastMld 5 }

-- {ROW} 1.3.6.1.4.1.2356.11.2.108.2.5.1
lcsSetupMCastMldStaticRoutesEntry OBJECT-TYPE
    SYNTAX     LcsSetupMCastMldStaticRoutesEntry
    MAX-ACCESS not-accessible
    STATUS     current
    DESCRIPTION
            ""
    INDEX {
            lcsSetupMCastMldStaticRoutesEntryUpstreamInterface,
            lcsSetupMCastMldStaticRoutesEntryGroup,
            lcsSetupMCastMldStaticRoutesEntryDownstreamInterface
          }
    ::= { lcsSetupMCastMldStaticRoutesTable 1 }

LcsSetupMCastMldStaticRoutesEntry ::= SEQUENCE {
            lcsSetupMCastMldStaticRoutesEntryUpstreamInterface DisplayString,
            lcsSetupMCastMldStaticRoutesEntryGroup IpAddress,
            lcsSetupMCastMldStaticRoutesEntryDownstreamInterface DisplayString,
            lcsSetupMCastMldStaticRoutesEntryMode INTEGER,
            lcsSetupMCastMldStaticRoutesEntrySsmSourceIpList DisplayString
    }

-- {COLUMN} 1.3.6.1.4.1.2356.11.2.108.2.5.1.1
lcsSetupMCastMldStaticRoutesEntryUpstreamInterface OBJECT-TYPE
    SYNTAX     DisplayString (SIZE(0..16))
    MAX-ACCESS read-write
    STATUS     current
    DESCRIPTION
            "-- empty --"
    ::= { lcsSetupMCastMldStaticRoutesEntry 1 }

-- {COLUMN} 1.3.6.1.4.1.2356.11.2.108.2.5.1.2
lcsSetupMCastMldStaticRoutesEntryGroup OBJECT-TYPE
    SYNTAX     IpAddress
    MAX-ACCESS read-write
    STATUS     current
    DESCRIPTION
            "-- empty --"
    ::= { lcsSetupMCastMldStaticRoutesEntry 2 }

-- {COLUMN} 1.3.6.1.4.1.2356.11.2.108.2.5.1.3
lcsSetupMCastMldStaticRoutesEntryDownstreamInterface OBJECT-TYPE
    SYNTAX     DisplayString (SIZE(0..16))
    MAX-ACCESS read-write
    STATUS     current
    DESCRIPTION
            "-- empty --"
    ::= { lcsSetupMCastMldStaticRoutesEntry 3 }

-- {COLUMN} 1.3.6.1.4.1.2356.11.2.108.2.5.1.4
lcsSetupMCastMldStaticRoutesEntryMode OBJECT-TYPE
    SYNTAX     INTEGER {
                  eInclude (1),
                  eExclude (2)
            }
    MAX-ACCESS read-write
    STATUS     current
    DESCRIPTION
            "-- empty --"
    ::= { lcsSetupMCastMldStaticRoutesEntry 4 }

-- {COLUMN} 1.3.6.1.4.1.2356.11.2.108.2.5.1.5
lcsSetupMCastMldStaticRoutesEntrySsmSourceIpList OBJECT-TYPE
    SYNTAX     DisplayString (SIZE(0..16))
    MAX-ACCESS read-write
    STATUS     current
    DESCRIPTION
            "-- empty --"
    ::= { lcsSetupMCastMldStaticRoutesEntry 5 }

-- {TABLE} 1.3.6.1.4.1.2356.11.2.108.2.6
lcsSetupMCastMldParameterTable OBJECT-TYPE
    SYNTAX     SEQUENCE OF LcsSetupMCastMldParameterEntry
    MAX-ACCESS not-accessible
    STATUS     current
    DESCRIPTION
            "-- empty --"
    ::= { lcsSetupMCastMld 6 }

-- {ROW} 1.3.6.1.4.1.2356.11.2.108.2.6.1
lcsSetupMCastMldParameterEntry OBJECT-TYPE
    SYNTAX     LcsSetupMCastMldParameterEntry
    MAX-ACCESS not-accessible
    STATUS     current
    DESCRIPTION
            ""
    INDEX {
            lcsSetupMCastMldParameterEntryInterface
          }
    ::= { lcsSetupMCastMldParameterTable 1 }

LcsSetupMCastMldParameterEntry ::= SEQUENCE {
            lcsSetupMCastMldParameterEntryInterface DisplayString,
            lcsSetupMCastMldParameterEntryRobustnessVariable Integer32,
            lcsSetupMCastMldParameterEntryUnsolicitedReportInterval Integer32,
            lcsSetupMCastMldParameterEntryQueryInterval Integer32,
            lcsSetupMCastMldParameterEntryQueryResponseInterval Integer32,
            lcsSetupMCastMldParameterEntryStartupQueryInterval Integer32,
            lcsSetupMCastMldParameterEntryStartupQueryCount Integer32,
            lcsSetupMCastMldParameterEntryLastListenerQueryInterval Integer32,
            lcsSetupMCastMldParameterEntryLastListenerQueryCount Integer32,
            lcsSetupMCastMldParameterEntryMldCompatibilityMode INTEGER,
            lcsSetupMCastMldParameterEntryQuickLeave INTEGER
    }

-- {COLUMN} 1.3.6.1.4.1.2356.11.2.108.2.6.1.1
lcsSetupMCastMldParameterEntryInterface OBJECT-TYPE
    SYNTAX     DisplayString (SIZE(0..16))
    MAX-ACCESS read-write
    STATUS     current
    DESCRIPTION
            "-- empty --"
    ::= { lcsSetupMCastMldParameterEntry 1 }

-- {COLUMN} 1.3.6.1.4.1.2356.11.2.108.2.6.1.2
lcsSetupMCastMldParameterEntryRobustnessVariable OBJECT-TYPE
    SYNTAX     Integer32 (0..255)
    MAX-ACCESS read-write
    STATUS     current
    DESCRIPTION
            "-- empty --"
    ::= { lcsSetupMCastMldParameterEntry 2 }

-- {COLUMN} 1.3.6.1.4.1.2356.11.2.108.2.6.1.3
lcsSetupMCastMldParameterEntryUnsolicitedReportInterval OBJECT-TYPE
    SYNTAX     Integer32 (0..255)
    MAX-ACCESS read-write
    STATUS     current
    DESCRIPTION
            "-- empty --"
    ::= { lcsSetupMCastMldParameterEntry 3 }

-- {COLUMN} 1.3.6.1.4.1.2356.11.2.108.2.6.1.4
lcsSetupMCastMldParameterEntryQueryInterval OBJECT-TYPE
    SYNTAX     Integer32 (0..2147483647)
    MAX-ACCESS read-write
    STATUS     current
    DESCRIPTION
            "-- empty --"
    ::= { lcsSetupMCastMldParameterEntry 4 }

-- {COLUMN} 1.3.6.1.4.1.2356.11.2.108.2.6.1.5
lcsSetupMCastMldParameterEntryQueryResponseInterval OBJECT-TYPE
    SYNTAX     Integer32 (0..2147483647)
    MAX-ACCESS read-write
    STATUS     current
    DESCRIPTION
            "-- empty --"
    ::= { lcsSetupMCastMldParameterEntry 5 }

-- {COLUMN} 1.3.6.1.4.1.2356.11.2.108.2.6.1.6
lcsSetupMCastMldParameterEntryStartupQueryInterval OBJECT-TYPE
    SYNTAX     Integer32 (0..2147483647)
    MAX-ACCESS read-write
    STATUS     current
    DESCRIPTION
            "-- empty --"
    ::= { lcsSetupMCastMldParameterEntry 6 }

-- {COLUMN} 1.3.6.1.4.1.2356.11.2.108.2.6.1.7
lcsSetupMCastMldParameterEntryStartupQueryCount OBJECT-TYPE
    SYNTAX     Integer32 (0..255)
    MAX-ACCESS read-write
    STATUS     current
    DESCRIPTION
            "-- empty --"
    ::= { lcsSetupMCastMldParameterEntry 7 }

-- {COLUMN} 1.3.6.1.4.1.2356.11.2.108.2.6.1.8
lcsSetupMCastMldParameterEntryLastListenerQueryInterval OBJECT-TYPE
    SYNTAX     Integer32 (0..255)
    MAX-ACCESS read-write
    STATUS     current
    DESCRIPTION
            "-- empty --"
    ::= { lcsSetupMCastMldParameterEntry 8 }

-- {COLUMN} 1.3.6.1.4.1.2356.11.2.108.2.6.1.9
lcsSetupMCastMldParameterEntryLastListenerQueryCount OBJECT-TYPE
    SYNTAX     Integer32 (0..255)
    MAX-ACCESS read-write
    STATUS     current
    DESCRIPTION
            "-- empty --"
    ::= { lcsSetupMCastMldParameterEntry 9 }

-- {COLUMN} 1.3.6.1.4.1.2356.11.2.108.2.6.1.10
lcsSetupMCastMldParameterEntryMldCompatibilityMode OBJECT-TYPE
    SYNTAX     INTEGER {
                  eOff (0),
                  eV1 (1),
                  eV2 (2)
            }
    MAX-ACCESS read-write
    STATUS     current
    DESCRIPTION
            "-- empty --"
    ::= { lcsSetupMCastMldParameterEntry 10 }

-- {COLUMN} 1.3.6.1.4.1.2356.11.2.108.2.6.1.11
lcsSetupMCastMldParameterEntryQuickLeave OBJECT-TYPE
    SYNTAX     INTEGER {
                  eNo (0),
                  eYes (1)
            }
    MAX-ACCESS read-write
    STATUS     current
    DESCRIPTION
            "-- empty --"
    ::= { lcsSetupMCastMldParameterEntry 11 }

-- {SCALAR} 1.3.6.1.4.1.2356.11.2.108.2.8
lcsSetupMCastMldCollectStatistics OBJECT-TYPE
    SYNTAX     INTEGER {
                  eNo (0),
                  eYes (1)
            }
    MAX-ACCESS read-write
    STATUS     current
    DESCRIPTION
            "-- empty --"
    ::= { lcsSetupMCastMld 8 }

-- {TABLE} 1.3.6.1.4.1.2356.11.2.108.2.9
lcsSetupMCastMldStaticJoinTable OBJECT-TYPE
    SYNTAX     SEQUENCE OF LcsSetupMCastMldStaticJoinEntry
    MAX-ACCESS not-accessible
    STATUS     current
    DESCRIPTION
            "-- empty --"
    ::= { lcsSetupMCastMld 9 }

-- {ROW} 1.3.6.1.4.1.2356.11.2.108.2.9.1
lcsSetupMCastMldStaticJoinEntry OBJECT-TYPE
    SYNTAX     LcsSetupMCastMldStaticJoinEntry
    MAX-ACCESS not-accessible
    STATUS     current
    DESCRIPTION
            ""
    INDEX {
            lcsSetupMCastMldStaticJoinEntryInterface,
            lcsSetupMCastMldStaticJoinEntryGroup
          }
    ::= { lcsSetupMCastMldStaticJoinTable 1 }

LcsSetupMCastMldStaticJoinEntry ::= SEQUENCE {
            lcsSetupMCastMldStaticJoinEntryInterface DisplayString,
            lcsSetupMCastMldStaticJoinEntryGroup IpAddress,
            lcsSetupMCastMldStaticJoinEntryComment DisplayString
    }

-- {COLUMN} 1.3.6.1.4.1.2356.11.2.108.2.9.1.1
lcsSetupMCastMldStaticJoinEntryInterface OBJECT-TYPE
    SYNTAX     DisplayString (SIZE(0..16))
    MAX-ACCESS read-write
    STATUS     current
    DESCRIPTION
            "-- empty --"
    ::= { lcsSetupMCastMldStaticJoinEntry 1 }

-- {COLUMN} 1.3.6.1.4.1.2356.11.2.108.2.9.1.2
lcsSetupMCastMldStaticJoinEntryGroup OBJECT-TYPE
    SYNTAX     IpAddress
    MAX-ACCESS read-write
    STATUS     current
    DESCRIPTION
            "-- empty --"
    ::= { lcsSetupMCastMldStaticJoinEntry 2 }

-- {COLUMN} 1.3.6.1.4.1.2356.11.2.108.2.9.1.3
lcsSetupMCastMldStaticJoinEntryComment OBJECT-TYPE
    SYNTAX     DisplayString (SIZE(0..254))
    MAX-ACCESS read-write
    STATUS     current
    DESCRIPTION
            "-- empty --"
    ::= { lcsSetupMCastMldStaticJoinEntry 3 }

-- {SCALAR} 1.3.6.1.4.1.2356.11.2.108.2.127
lcsSetupMCastMldEnableLancomGroup OBJECT-TYPE
    SYNTAX     INTEGER {
                  eNo (0),
                  eYes (1)
            }
    MAX-ACCESS read-write
    STATUS     current
    DESCRIPTION
            "-- empty --"
    ::= { lcsSetupMCastMld 127 }

-- {NODE} 1.3.6.1.4.1.2356.11.2.108.4
lcsSetupMCastPim OBJECT IDENTIFIER ::= { lcsSetupMCast 4 }

-- {NODE} 1.3.6.1.4.1.2356.11.2.108.4.1
lcsSetupMCastPimIpv4 OBJECT IDENTIFIER ::= { lcsSetupMCastPim 1 }

-- {TABLE} 1.3.6.1.4.1.2356.11.2.108.4.1.1
lcsSetupMCastPimIpv4RpListTable OBJECT-TYPE
    SYNTAX     SEQUENCE OF LcsSetupMCastPimIpv4RpListEntry
    MAX-ACCESS not-accessible
    STATUS     current
    DESCRIPTION
            "-- empty --"
    ::= { lcsSetupMCastPimIpv4 1 }

-- {ROW} 1.3.6.1.4.1.2356.11.2.108.4.1.1.1
lcsSetupMCastPimIpv4RpListEntry OBJECT-TYPE
    SYNTAX     LcsSetupMCastPimIpv4RpListEntry
    MAX-ACCESS not-accessible
    STATUS     current
    DESCRIPTION
            ""
    INDEX {
            lcsSetupMCastPimIpv4RpListEntryGroupFilter,
            lcsSetupMCastPimIpv4RpListEntryRtgTag
          }
    ::= { lcsSetupMCastPimIpv4RpListTable 1 }

LcsSetupMCastPimIpv4RpListEntry ::= SEQUENCE {
            lcsSetupMCastPimIpv4RpListEntryGroupFilter DisplayString,
            lcsSetupMCastPimIpv4RpListEntryRtgTag Integer32,
            lcsSetupMCastPimIpv4RpListEntryRpAddress DisplayString,
            lcsSetupMCastPimIpv4RpListEntryRpName DisplayString,
            lcsSetupMCastPimIpv4RpListEntryComment DisplayString
    }

-- {COLUMN} 1.3.6.1.4.1.2356.11.2.108.4.1.1.1.1
lcsSetupMCastPimIpv4RpListEntryGroupFilter OBJECT-TYPE
    SYNTAX     DisplayString (SIZE(0..16))
    MAX-ACCESS read-write
    STATUS     current
    DESCRIPTION
            "-- empty --"
    ::= { lcsSetupMCastPimIpv4RpListEntry 1 }

-- {COLUMN} 1.3.6.1.4.1.2356.11.2.108.4.1.1.1.2
lcsSetupMCastPimIpv4RpListEntryRtgTag OBJECT-TYPE
    SYNTAX     Integer32 (0..65535)
    MAX-ACCESS read-write
    STATUS     current
    DESCRIPTION
            "-- empty --"
    ::= { lcsSetupMCastPimIpv4RpListEntry 2 }

-- {COLUMN} 1.3.6.1.4.1.2356.11.2.108.4.1.1.1.3
lcsSetupMCastPimIpv4RpListEntryRpAddress OBJECT-TYPE
    SYNTAX     DisplayString (SIZE(0..15))
    MAX-ACCESS read-write
    STATUS     current
    DESCRIPTION
            "-- empty --"
    ::= { lcsSetupMCastPimIpv4RpListEntry 3 }

-- {COLUMN} 1.3.6.1.4.1.2356.11.2.108.4.1.1.1.5
lcsSetupMCastPimIpv4RpListEntryRpName OBJECT-TYPE
    SYNTAX     DisplayString (SIZE(0..16))
    MAX-ACCESS read-write
    STATUS     current
    DESCRIPTION
            "-- empty --"
    ::= { lcsSetupMCastPimIpv4RpListEntry 5 }

-- {COLUMN} 1.3.6.1.4.1.2356.11.2.108.4.1.1.1.6
lcsSetupMCastPimIpv4RpListEntryComment OBJECT-TYPE
    SYNTAX     DisplayString (SIZE(0..254))
    MAX-ACCESS read-write
    STATUS     current
    DESCRIPTION
            "-- empty --"
    ::= { lcsSetupMCastPimIpv4RpListEntry 6 }

-- {TABLE} 1.3.6.1.4.1.2356.11.2.108.4.1.2
lcsSetupMCastPimIpv4SsmListTable OBJECT-TYPE
    SYNTAX     SEQUENCE OF LcsSetupMCastPimIpv4SsmListEntry
    MAX-ACCESS not-accessible
    STATUS     current
    DESCRIPTION
            "-- empty --"
    ::= { lcsSetupMCastPimIpv4 2 }

-- {ROW} 1.3.6.1.4.1.2356.11.2.108.4.1.2.1
lcsSetupMCastPimIpv4SsmListEntry OBJECT-TYPE
    SYNTAX     LcsSetupMCastPimIpv4SsmListEntry
    MAX-ACCESS not-accessible
    STATUS     current
    DESCRIPTION
            ""
    INDEX {
            lcsSetupMCastPimIpv4SsmListEntryGroupFilter,
            lcsSetupMCastPimIpv4SsmListEntryRtgTag,
            lcsSetupMCastPimIpv4SsmListEntrySsmSourceFilter
          }
    ::= { lcsSetupMCastPimIpv4SsmListTable 1 }

LcsSetupMCastPimIpv4SsmListEntry ::= SEQUENCE {
            lcsSetupMCastPimIpv4SsmListEntryGroupFilter DisplayString,
            lcsSetupMCastPimIpv4SsmListEntryRtgTag Integer32,
            lcsSetupMCastPimIpv4SsmListEntrySsmSourceFilter DisplayString,
            lcsSetupMCastPimIpv4SsmListEntrySsmName DisplayString,
            lcsSetupMCastPimIpv4SsmListEntryComment DisplayString
    }

-- {COLUMN} 1.3.6.1.4.1.2356.11.2.108.4.1.2.1.1
lcsSetupMCastPimIpv4SsmListEntryGroupFilter OBJECT-TYPE
    SYNTAX     DisplayString (SIZE(0..16))
    MAX-ACCESS read-write
    STATUS     current
    DESCRIPTION
            "-- empty --"
    ::= { lcsSetupMCastPimIpv4SsmListEntry 1 }

-- {COLUMN} 1.3.6.1.4.1.2356.11.2.108.4.1.2.1.2
lcsSetupMCastPimIpv4SsmListEntryRtgTag OBJECT-TYPE
    SYNTAX     Integer32 (0..65535)
    MAX-ACCESS read-write
    STATUS     current
    DESCRIPTION
            "-- empty --"
    ::= { lcsSetupMCastPimIpv4SsmListEntry 2 }

-- {COLUMN} 1.3.6.1.4.1.2356.11.2.108.4.1.2.1.3
lcsSetupMCastPimIpv4SsmListEntrySsmSourceFilter OBJECT-TYPE
    SYNTAX     DisplayString (SIZE(0..16))
    MAX-ACCESS read-write
    STATUS     current
    DESCRIPTION
            "-- empty --"
    ::= { lcsSetupMCastPimIpv4SsmListEntry 3 }

-- {COLUMN} 1.3.6.1.4.1.2356.11.2.108.4.1.2.1.5
lcsSetupMCastPimIpv4SsmListEntrySsmName OBJECT-TYPE
    SYNTAX     DisplayString (SIZE(0..16))
    MAX-ACCESS read-write
    STATUS     current
    DESCRIPTION
            "-- empty --"
    ::= { lcsSetupMCastPimIpv4SsmListEntry 5 }

-- {COLUMN} 1.3.6.1.4.1.2356.11.2.108.4.1.2.1.6
lcsSetupMCastPimIpv4SsmListEntryComment OBJECT-TYPE
    SYNTAX     DisplayString (SIZE(0..254))
    MAX-ACCESS read-write
    STATUS     current
    DESCRIPTION
            "-- empty --"
    ::= { lcsSetupMCastPimIpv4SsmListEntry 6 }

-- {TABLE} 1.3.6.1.4.1.2356.11.2.108.4.1.3
lcsSetupMCastPimIpv4SsmMappingTable OBJECT-TYPE
    SYNTAX     SEQUENCE OF LcsSetupMCastPimIpv4SsmMappingEntry
    MAX-ACCESS not-accessible
    STATUS     current
    DESCRIPTION
            "-- empty --"
    ::= { lcsSetupMCastPimIpv4 3 }

-- {ROW} 1.3.6.1.4.1.2356.11.2.108.4.1.3.1
lcsSetupMCastPimIpv4SsmMappingEntry OBJECT-TYPE
    SYNTAX     LcsSetupMCastPimIpv4SsmMappingEntry
    MAX-ACCESS not-accessible
    STATUS     current
    DESCRIPTION
            ""
    INDEX {
            lcsSetupMCastPimIpv4SsmMappingEntryGroupFilter,
            lcsSetupMCastPimIpv4SsmMappingEntryRtgTag
          }
    ::= { lcsSetupMCastPimIpv4SsmMappingTable 1 }

LcsSetupMCastPimIpv4SsmMappingEntry ::= SEQUENCE {
            lcsSetupMCastPimIpv4SsmMappingEntryGroupFilter DisplayString,
            lcsSetupMCastPimIpv4SsmMappingEntryRtgTag Integer32,
            lcsSetupMCastPimIpv4SsmMappingEntrySsmSourceIp DisplayString,
            lcsSetupMCastPimIpv4SsmMappingEntryComment DisplayString
    }

-- {COLUMN} 1.3.6.1.4.1.2356.11.2.108.4.1.3.1.1
lcsSetupMCastPimIpv4SsmMappingEntryGroupFilter OBJECT-TYPE
    SYNTAX     DisplayString (SIZE(0..16))
    MAX-ACCESS read-write
    STATUS     current
    DESCRIPTION
            "-- empty --"
    ::= { lcsSetupMCastPimIpv4SsmMappingEntry 1 }

-- {COLUMN} 1.3.6.1.4.1.2356.11.2.108.4.1.3.1.2
lcsSetupMCastPimIpv4SsmMappingEntryRtgTag OBJECT-TYPE
    SYNTAX     Integer32 (0..65535)
    MAX-ACCESS read-write
    STATUS     current
    DESCRIPTION
            "-- empty --"
    ::= { lcsSetupMCastPimIpv4SsmMappingEntry 2 }

-- {COLUMN} 1.3.6.1.4.1.2356.11.2.108.4.1.3.1.3
lcsSetupMCastPimIpv4SsmMappingEntrySsmSourceIp OBJECT-TYPE
    SYNTAX     DisplayString (SIZE(0..15))
    MAX-ACCESS read-write
    STATUS     current
    DESCRIPTION
            "-- empty --"
    ::= { lcsSetupMCastPimIpv4SsmMappingEntry 3 }

-- {COLUMN} 1.3.6.1.4.1.2356.11.2.108.4.1.3.1.4
lcsSetupMCastPimIpv4SsmMappingEntryComment OBJECT-TYPE
    SYNTAX     DisplayString (SIZE(0..254))
    MAX-ACCESS read-write
    STATUS     current
    DESCRIPTION
            "-- empty --"
    ::= { lcsSetupMCastPimIpv4SsmMappingEntry 4 }

-- {NODE} 1.3.6.1.4.1.2356.11.2.108.4.2
lcsSetupMCastPimIpv6 OBJECT IDENTIFIER ::= { lcsSetupMCastPim 2 }

-- {TABLE} 1.3.6.1.4.1.2356.11.2.108.4.2.1
lcsSetupMCastPimIpv6RpListTable OBJECT-TYPE
    SYNTAX     SEQUENCE OF LcsSetupMCastPimIpv6RpListEntry
    MAX-ACCESS not-accessible
    STATUS     current
    DESCRIPTION
            "-- empty --"
    ::= { lcsSetupMCastPimIpv6 1 }

-- {ROW} 1.3.6.1.4.1.2356.11.2.108.4.2.1.1
lcsSetupMCastPimIpv6RpListEntry OBJECT-TYPE
    SYNTAX     LcsSetupMCastPimIpv6RpListEntry
    MAX-ACCESS not-accessible
    STATUS     current
    DESCRIPTION
            ""
    INDEX {
            lcsSetupMCastPimIpv6RpListEntryGroupFilter,
            lcsSetupMCastPimIpv6RpListEntryRtgTag
          }
    ::= { lcsSetupMCastPimIpv6RpListTable 1 }

LcsSetupMCastPimIpv6RpListEntry ::= SEQUENCE {
            lcsSetupMCastPimIpv6RpListEntryGroupFilter DisplayString,
            lcsSetupMCastPimIpv6RpListEntryRtgTag Integer32,
            lcsSetupMCastPimIpv6RpListEntryRpAddress DisplayString,
            lcsSetupMCastPimIpv6RpListEntryRpName DisplayString,
            lcsSetupMCastPimIpv6RpListEntryComment DisplayString
    }

-- {COLUMN} 1.3.6.1.4.1.2356.11.2.108.4.2.1.1.1
lcsSetupMCastPimIpv6RpListEntryGroupFilter OBJECT-TYPE
    SYNTAX     DisplayString (SIZE(0..16))
    MAX-ACCESS read-write
    STATUS     current
    DESCRIPTION
            "-- empty --"
    ::= { lcsSetupMCastPimIpv6RpListEntry 1 }

-- {COLUMN} 1.3.6.1.4.1.2356.11.2.108.4.2.1.1.2
lcsSetupMCastPimIpv6RpListEntryRtgTag OBJECT-TYPE
    SYNTAX     Integer32 (0..65535)
    MAX-ACCESS read-write
    STATUS     current
    DESCRIPTION
            "-- empty --"
    ::= { lcsSetupMCastPimIpv6RpListEntry 2 }

-- {COLUMN} 1.3.6.1.4.1.2356.11.2.108.4.2.1.1.3
lcsSetupMCastPimIpv6RpListEntryRpAddress OBJECT-TYPE
    SYNTAX     DisplayString (SIZE(0..39))
    MAX-ACCESS read-write
    STATUS     current
    DESCRIPTION
            "-- empty --"
    ::= { lcsSetupMCastPimIpv6RpListEntry 3 }

-- {COLUMN} 1.3.6.1.4.1.2356.11.2.108.4.2.1.1.5
lcsSetupMCastPimIpv6RpListEntryRpName OBJECT-TYPE
    SYNTAX     DisplayString (SIZE(0..16))
    MAX-ACCESS read-write
    STATUS     current
    DESCRIPTION
            "-- empty --"
    ::= { lcsSetupMCastPimIpv6RpListEntry 5 }

-- {COLUMN} 1.3.6.1.4.1.2356.11.2.108.4.2.1.1.6
lcsSetupMCastPimIpv6RpListEntryComment OBJECT-TYPE
    SYNTAX     DisplayString (SIZE(0..254))
    MAX-ACCESS read-write
    STATUS     current
    DESCRIPTION
            "-- empty --"
    ::= { lcsSetupMCastPimIpv6RpListEntry 6 }

-- {TABLE} 1.3.6.1.4.1.2356.11.2.108.4.2.2
lcsSetupMCastPimIpv6SsmListTable OBJECT-TYPE
    SYNTAX     SEQUENCE OF LcsSetupMCastPimIpv6SsmListEntry
    MAX-ACCESS not-accessible
    STATUS     current
    DESCRIPTION
            "-- empty --"
    ::= { lcsSetupMCastPimIpv6 2 }

-- {ROW} 1.3.6.1.4.1.2356.11.2.108.4.2.2.1
lcsSetupMCastPimIpv6SsmListEntry OBJECT-TYPE
    SYNTAX     LcsSetupMCastPimIpv6SsmListEntry
    MAX-ACCESS not-accessible
    STATUS     current
    DESCRIPTION
            ""
    INDEX {
            lcsSetupMCastPimIpv6SsmListEntryGroupFilter,
            lcsSetupMCastPimIpv6SsmListEntryRtgTag,
            lcsSetupMCastPimIpv6SsmListEntrySsmSourceFilter
          }
    ::= { lcsSetupMCastPimIpv6SsmListTable 1 }

LcsSetupMCastPimIpv6SsmListEntry ::= SEQUENCE {
            lcsSetupMCastPimIpv6SsmListEntryGroupFilter DisplayString,
            lcsSetupMCastPimIpv6SsmListEntryRtgTag Integer32,
            lcsSetupMCastPimIpv6SsmListEntrySsmSourceFilter DisplayString,
            lcsSetupMCastPimIpv6SsmListEntrySsmName DisplayString,
            lcsSetupMCastPimIpv6SsmListEntryComment DisplayString
    }

-- {COLUMN} 1.3.6.1.4.1.2356.11.2.108.4.2.2.1.1
lcsSetupMCastPimIpv6SsmListEntryGroupFilter OBJECT-TYPE
    SYNTAX     DisplayString (SIZE(0..16))
    MAX-ACCESS read-write
    STATUS     current
    DESCRIPTION
            "-- empty --"
    ::= { lcsSetupMCastPimIpv6SsmListEntry 1 }

-- {COLUMN} 1.3.6.1.4.1.2356.11.2.108.4.2.2.1.2
lcsSetupMCastPimIpv6SsmListEntryRtgTag OBJECT-TYPE
    SYNTAX     Integer32 (0..65535)
    MAX-ACCESS read-write
    STATUS     current
    DESCRIPTION
            "-- empty --"
    ::= { lcsSetupMCastPimIpv6SsmListEntry 2 }

-- {COLUMN} 1.3.6.1.4.1.2356.11.2.108.4.2.2.1.3
lcsSetupMCastPimIpv6SsmListEntrySsmSourceFilter OBJECT-TYPE
    SYNTAX     DisplayString (SIZE(0..16))
    MAX-ACCESS read-write
    STATUS     current
    DESCRIPTION
            "-- empty --"
    ::= { lcsSetupMCastPimIpv6SsmListEntry 3 }

-- {COLUMN} 1.3.6.1.4.1.2356.11.2.108.4.2.2.1.5
lcsSetupMCastPimIpv6SsmListEntrySsmName OBJECT-TYPE
    SYNTAX     DisplayString (SIZE(0..16))
    MAX-ACCESS read-write
    STATUS     current
    DESCRIPTION
            "-- empty --"
    ::= { lcsSetupMCastPimIpv6SsmListEntry 5 }

-- {COLUMN} 1.3.6.1.4.1.2356.11.2.108.4.2.2.1.6
lcsSetupMCastPimIpv6SsmListEntryComment OBJECT-TYPE
    SYNTAX     DisplayString (SIZE(0..254))
    MAX-ACCESS read-write
    STATUS     current
    DESCRIPTION
            "-- empty --"
    ::= { lcsSetupMCastPimIpv6SsmListEntry 6 }

-- {TABLE} 1.3.6.1.4.1.2356.11.2.108.4.2.3
lcsSetupMCastPimIpv6SsmMappingTable OBJECT-TYPE
    SYNTAX     SEQUENCE OF LcsSetupMCastPimIpv6SsmMappingEntry
    MAX-ACCESS not-accessible
    STATUS     current
    DESCRIPTION
            "-- empty --"
    ::= { lcsSetupMCastPimIpv6 3 }

-- {ROW} 1.3.6.1.4.1.2356.11.2.108.4.2.3.1
lcsSetupMCastPimIpv6SsmMappingEntry OBJECT-TYPE
    SYNTAX     LcsSetupMCastPimIpv6SsmMappingEntry
    MAX-ACCESS not-accessible
    STATUS     current
    DESCRIPTION
            ""
    INDEX {
            lcsSetupMCastPimIpv6SsmMappingEntryGroupFilter,
            lcsSetupMCastPimIpv6SsmMappingEntryRtgTag
          }
    ::= { lcsSetupMCastPimIpv6SsmMappingTable 1 }

LcsSetupMCastPimIpv6SsmMappingEntry ::= SEQUENCE {
            lcsSetupMCastPimIpv6SsmMappingEntryGroupFilter DisplayString,
            lcsSetupMCastPimIpv6SsmMappingEntryRtgTag Integer32,
            lcsSetupMCastPimIpv6SsmMappingEntrySsmSourceIp DisplayString,
            lcsSetupMCastPimIpv6SsmMappingEntryComment DisplayString
    }

-- {COLUMN} 1.3.6.1.4.1.2356.11.2.108.4.2.3.1.1
lcsSetupMCastPimIpv6SsmMappingEntryGroupFilter OBJECT-TYPE
    SYNTAX     DisplayString (SIZE(0..16))
    MAX-ACCESS read-write
    STATUS     current
    DESCRIPTION
            "-- empty --"
    ::= { lcsSetupMCastPimIpv6SsmMappingEntry 1 }

-- {COLUMN} 1.3.6.1.4.1.2356.11.2.108.4.2.3.1.2
lcsSetupMCastPimIpv6SsmMappingEntryRtgTag OBJECT-TYPE
    SYNTAX     Integer32 (0..65535)
    MAX-ACCESS read-write
    STATUS     current
    DESCRIPTION
            "-- empty --"
    ::= { lcsSetupMCastPimIpv6SsmMappingEntry 2 }

-- {COLUMN} 1.3.6.1.4.1.2356.11.2.108.4.2.3.1.3
lcsSetupMCastPimIpv6SsmMappingEntrySsmSourceIp OBJECT-TYPE
    SYNTAX     DisplayString (SIZE(0..39))
    MAX-ACCESS read-write
    STATUS     current
    DESCRIPTION
            "-- empty --"
    ::= { lcsSetupMCastPimIpv6SsmMappingEntry 3 }

-- {COLUMN} 1.3.6.1.4.1.2356.11.2.108.4.2.3.1.4
lcsSetupMCastPimIpv6SsmMappingEntryComment OBJECT-TYPE
    SYNTAX     DisplayString (SIZE(0..254))
    MAX-ACCESS read-write
    STATUS     current
    DESCRIPTION
            "-- empty --"
    ::= { lcsSetupMCastPimIpv6SsmMappingEntry 4 }

-- {TABLE} 1.3.6.1.4.1.2356.11.2.108.4.3
lcsSetupMCastPimInterfacesTable OBJECT-TYPE
    SYNTAX     SEQUENCE OF LcsSetupMCastPimInterfacesEntry
    MAX-ACCESS not-accessible
    STATUS     current
    DESCRIPTION
            "-- empty --"
    ::= { lcsSetupMCastPim 3 }

-- {ROW} 1.3.6.1.4.1.2356.11.2.108.4.3.1
lcsSetupMCastPimInterfacesEntry OBJECT-TYPE
    SYNTAX     LcsSetupMCastPimInterfacesEntry
    MAX-ACCESS not-accessible
    STATUS     current
    DESCRIPTION
            ""
    INDEX {
            lcsSetupMCastPimInterfacesEntryInterface
          }
    ::= { lcsSetupMCastPimInterfacesTable 1 }

LcsSetupMCastPimInterfacesEntry ::= SEQUENCE {
            lcsSetupMCastPimInterfacesEntryInterface DisplayString,
            lcsSetupMCastPimInterfacesEntryPimActive INTEGER,
            lcsSetupMCastPimInterfacesEntryGmpActive INTEGER,
            lcsSetupMCastPimInterfacesEntryAddressType BITS,
            lcsSetupMCastPimInterfacesEntryHelloInterval Integer32,
            lcsSetupMCastPimInterfacesEntryDrPriority Integer32,
            lcsSetupMCastPimInterfacesEntryTrackingSupport INTEGER,
            lcsSetupMCastPimInterfacesEntryOverrideInterval Integer32,
            lcsSetupMCastPimInterfacesEntryPropagationDelay Integer32
    }

-- {COLUMN} 1.3.6.1.4.1.2356.11.2.108.4.3.1.1
lcsSetupMCastPimInterfacesEntryInterface OBJECT-TYPE
    SYNTAX     DisplayString (SIZE(0..16))
    MAX-ACCESS read-write
    STATUS     current
    DESCRIPTION
            "-- empty --"
    ::= { lcsSetupMCastPimInterfacesEntry 1 }

-- {COLUMN} 1.3.6.1.4.1.2356.11.2.108.4.3.1.2
lcsSetupMCastPimInterfacesEntryPimActive OBJECT-TYPE
    SYNTAX     INTEGER {
                  eNo (0),
                  eYes (1)
            }
    MAX-ACCESS read-write
    STATUS     current
    DESCRIPTION
            "-- empty --"
    ::= { lcsSetupMCastPimInterfacesEntry 2 }

-- {COLUMN} 1.3.6.1.4.1.2356.11.2.108.4.3.1.3
lcsSetupMCastPimInterfacesEntryGmpActive OBJECT-TYPE
    SYNTAX     INTEGER {
                  eNo (0),
                  eYes (1)
            }
    MAX-ACCESS read-write
    STATUS     current
    DESCRIPTION
            "-- empty --"
    ::= { lcsSetupMCastPimInterfacesEntry 3 }

-- {COLUMN} 1.3.6.1.4.1.2356.11.2.108.4.3.1.4
lcsSetupMCastPimInterfacesEntryAddressType OBJECT-TYPE
    SYNTAX     BITS {
                  eIpv6 (6),
                  eIpv4 (7)
            }
    MAX-ACCESS read-write
    STATUS     current
    DESCRIPTION
            "-- empty --"
    ::= { lcsSetupMCastPimInterfacesEntry 4 }

-- {COLUMN} 1.3.6.1.4.1.2356.11.2.108.4.3.1.5
lcsSetupMCastPimInterfacesEntryHelloInterval OBJECT-TYPE
    SYNTAX     Integer32 (0..65535)
    MAX-ACCESS read-write
    STATUS     current
    DESCRIPTION
            "-- empty --"
    ::= { lcsSetupMCastPimInterfacesEntry 5 }

-- {COLUMN} 1.3.6.1.4.1.2356.11.2.108.4.3.1.6
lcsSetupMCastPimInterfacesEntryDrPriority OBJECT-TYPE
    SYNTAX     Integer32 (0..2147483647)
    MAX-ACCESS read-write
    STATUS     current
    DESCRIPTION
            "-- empty --"
    ::= { lcsSetupMCastPimInterfacesEntry 6 }

-- {COLUMN} 1.3.6.1.4.1.2356.11.2.108.4.3.1.7
lcsSetupMCastPimInterfacesEntryTrackingSupport OBJECT-TYPE
    SYNTAX     INTEGER {
                  eNo (0),
                  eYes (1)
            }
    MAX-ACCESS read-write
    STATUS     current
    DESCRIPTION
            "-- empty --"
    ::= { lcsSetupMCastPimInterfacesEntry 7 }

-- {COLUMN} 1.3.6.1.4.1.2356.11.2.108.4.3.1.8
lcsSetupMCastPimInterfacesEntryOverrideInterval OBJECT-TYPE
    SYNTAX     Integer32 (0..65535)
    MAX-ACCESS read-write
    STATUS     current
    DESCRIPTION
            "-- empty --"
    ::= { lcsSetupMCastPimInterfacesEntry 8 }

-- {COLUMN} 1.3.6.1.4.1.2356.11.2.108.4.3.1.9
lcsSetupMCastPimInterfacesEntryPropagationDelay OBJECT-TYPE
    SYNTAX     Integer32 (0..65535)
    MAX-ACCESS read-write
    STATUS     current
    DESCRIPTION
            "-- empty --"
    ::= { lcsSetupMCastPimInterfacesEntry 9 }

-- {SCALAR} 1.3.6.1.4.1.2356.11.2.108.4.6
lcsSetupMCastPimOperating OBJECT-TYPE
    SYNTAX     INTEGER {
                  eNo (0),
                  eYes (1)
            }
    MAX-ACCESS read-write
    STATUS     current
    DESCRIPTION
            "-- empty --"
    ::= { lcsSetupMCastPim 6 }

-- {TABLE} 1.3.6.1.4.1.2356.11.2.108.5
lcsSetupMCastIpv4FilterTableTable OBJECT-TYPE
    SYNTAX     SEQUENCE OF LcsSetupMCastIpv4FilterTableEntry
    MAX-ACCESS not-accessible
    STATUS     current
    DESCRIPTION
            "-- empty --"
    ::= { lcsSetupMCast 5 }

-- {ROW} 1.3.6.1.4.1.2356.11.2.108.5.1
lcsSetupMCastIpv4FilterTableEntry OBJECT-TYPE
    SYNTAX     LcsSetupMCastIpv4FilterTableEntry
    MAX-ACCESS not-accessible
    STATUS     current
    DESCRIPTION
            ""
    INDEX {
            lcsSetupMCastIpv4FilterTableEntryName,
            lcsSetupMCastIpv4FilterTableEntryPrefix
          }
    ::= { lcsSetupMCastIpv4FilterTableTable 1 }

LcsSetupMCastIpv4FilterTableEntry ::= SEQUENCE {
            lcsSetupMCastIpv4FilterTableEntryName DisplayString,
            lcsSetupMCastIpv4FilterTableEntryPrefix DisplayString,
            lcsSetupMCastIpv4FilterTableEntryAction INTEGER,
            lcsSetupMCastIpv4FilterTableEntryComment DisplayString
    }

-- {COLUMN} 1.3.6.1.4.1.2356.11.2.108.5.1.1
lcsSetupMCastIpv4FilterTableEntryName OBJECT-TYPE
    SYNTAX     DisplayString (SIZE(0..16))
    MAX-ACCESS read-write
    STATUS     current
    DESCRIPTION
            "-- empty --"
    ::= { lcsSetupMCastIpv4FilterTableEntry 1 }

-- {COLUMN} 1.3.6.1.4.1.2356.11.2.108.5.1.2
lcsSetupMCastIpv4FilterTableEntryPrefix OBJECT-TYPE
    SYNTAX     DisplayString (SIZE(0..18))
    MAX-ACCESS read-write
    STATUS     current
    DESCRIPTION
            "-- empty --"
    ::= { lcsSetupMCastIpv4FilterTableEntry 2 }

-- {COLUMN} 1.3.6.1.4.1.2356.11.2.108.5.1.3
lcsSetupMCastIpv4FilterTableEntryAction OBJECT-TYPE
    SYNTAX     INTEGER {
                  eAllow (0),
                  eDeny (1)
            }
    MAX-ACCESS read-write
    STATUS     current
    DESCRIPTION
            "-- empty --"
    ::= { lcsSetupMCastIpv4FilterTableEntry 3 }

-- {COLUMN} 1.3.6.1.4.1.2356.11.2.108.5.1.4
lcsSetupMCastIpv4FilterTableEntryComment OBJECT-TYPE
    SYNTAX     DisplayString (SIZE(0..254))
    MAX-ACCESS read-write
    STATUS     current
    DESCRIPTION
            "-- empty --"
    ::= { lcsSetupMCastIpv4FilterTableEntry 4 }

-- {TABLE} 1.3.6.1.4.1.2356.11.2.108.6
lcsSetupMCastIpv6FilterTableTable OBJECT-TYPE
    SYNTAX     SEQUENCE OF LcsSetupMCastIpv6FilterTableEntry
    MAX-ACCESS not-accessible
    STATUS     current
    DESCRIPTION
            "-- empty --"
    ::= { lcsSetupMCast 6 }

-- {ROW} 1.3.6.1.4.1.2356.11.2.108.6.1
lcsSetupMCastIpv6FilterTableEntry OBJECT-TYPE
    SYNTAX     LcsSetupMCastIpv6FilterTableEntry
    MAX-ACCESS not-accessible
    STATUS     current
    DESCRIPTION
            ""
    INDEX {
            lcsSetupMCastIpv6FilterTableEntryName,
            lcsSetupMCastIpv6FilterTableEntryPrefix
          }
    ::= { lcsSetupMCastIpv6FilterTableTable 1 }

LcsSetupMCastIpv6FilterTableEntry ::= SEQUENCE {
            lcsSetupMCastIpv6FilterTableEntryName DisplayString,
            lcsSetupMCastIpv6FilterTableEntryPrefix DisplayString,
            lcsSetupMCastIpv6FilterTableEntryAction INTEGER,
            lcsSetupMCastIpv6FilterTableEntryComment DisplayString
    }

-- {COLUMN} 1.3.6.1.4.1.2356.11.2.108.6.1.1
lcsSetupMCastIpv6FilterTableEntryName OBJECT-TYPE
    SYNTAX     DisplayString (SIZE(0..16))
    MAX-ACCESS read-write
    STATUS     current
    DESCRIPTION
            "-- empty --"
    ::= { lcsSetupMCastIpv6FilterTableEntry 1 }

-- {COLUMN} 1.3.6.1.4.1.2356.11.2.108.6.1.2
lcsSetupMCastIpv6FilterTableEntryPrefix OBJECT-TYPE
    SYNTAX     DisplayString (SIZE(0..43))
    MAX-ACCESS read-write
    STATUS     current
    DESCRIPTION
            "-- empty --"
    ::= { lcsSetupMCastIpv6FilterTableEntry 2 }

-- {COLUMN} 1.3.6.1.4.1.2356.11.2.108.6.1.3
lcsSetupMCastIpv6FilterTableEntryAction OBJECT-TYPE
    SYNTAX     INTEGER {
                  eAllow (0),
                  eDeny (1)
            }
    MAX-ACCESS read-write
    STATUS     current
    DESCRIPTION
            "-- empty --"
    ::= { lcsSetupMCastIpv6FilterTableEntry 3 }

-- {COLUMN} 1.3.6.1.4.1.2356.11.2.108.6.1.4
lcsSetupMCastIpv6FilterTableEntryComment OBJECT-TYPE
    SYNTAX     DisplayString (SIZE(0..254))
    MAX-ACCESS read-write
    STATUS     current
    DESCRIPTION
            "-- empty --"
    ::= { lcsSetupMCastIpv6FilterTableEntry 4 }

-- {NODE} 1.3.6.1.4.1.2356.11.2.109
lcsSetupNetflow OBJECT IDENTIFIER ::= { lcsSetup 109 }

-- {TABLE} 1.3.6.1.4.1.2356.11.2.109.1
lcsSetupNetflowCollectorsTable OBJECT-TYPE
    SYNTAX     SEQUENCE OF LcsSetupNetflowCollectorsEntry
    MAX-ACCESS not-accessible
    STATUS     current
    DESCRIPTION
            "-- empty --"
    ::= { lcsSetupNetflow 1 }

-- {ROW} 1.3.6.1.4.1.2356.11.2.109.1.1
lcsSetupNetflowCollectorsEntry OBJECT-TYPE
    SYNTAX     LcsSetupNetflowCollectorsEntry
    MAX-ACCESS not-accessible
    STATUS     current
    DESCRIPTION
            ""
    INDEX {
            lcsSetupNetflowCollectorsEntryName
          }
    ::= { lcsSetupNetflowCollectorsTable 1 }

LcsSetupNetflowCollectorsEntry ::= SEQUENCE {
            lcsSetupNetflowCollectorsEntryName DisplayString,
            lcsSetupNetflowCollectorsEntryAddress DisplayString,
            lcsSetupNetflowCollectorsEntryPort Integer32,
            lcsSetupNetflowCollectorsEntryProtocol INTEGER,
            lcsSetupNetflowCollectorsEntryLoopbackAddr DisplayString,
            lcsSetupNetflowCollectorsEntryRtgTag Integer32,
            lcsSetupNetflowCollectorsEntryTemplateRefreshTime Integer32,
            lcsSetupNetflowCollectorsEntryTemplateRefreshPackets Integer32,
            lcsSetupNetflowCollectorsEntryComment DisplayString
    }

-- {COLUMN} 1.3.6.1.4.1.2356.11.2.109.1.1.1
lcsSetupNetflowCollectorsEntryName OBJECT-TYPE
    SYNTAX     DisplayString (SIZE(0..20))
    MAX-ACCESS read-write
    STATUS     current
    DESCRIPTION
            "-- empty --"
    ::= { lcsSetupNetflowCollectorsEntry 1 }

-- {COLUMN} 1.3.6.1.4.1.2356.11.2.109.1.1.2
lcsSetupNetflowCollectorsEntryAddress OBJECT-TYPE
    SYNTAX     DisplayString (SIZE(0..64))
    MAX-ACCESS read-write
    STATUS     current
    DESCRIPTION
            "-- empty --"
    ::= { lcsSetupNetflowCollectorsEntry 2 }

-- {COLUMN} 1.3.6.1.4.1.2356.11.2.109.1.1.3
lcsSetupNetflowCollectorsEntryPort OBJECT-TYPE
    SYNTAX     Integer32 (0..65535)
    MAX-ACCESS read-write
    STATUS     current
    DESCRIPTION
            "-- empty --"
    ::= { lcsSetupNetflowCollectorsEntry 3 }

-- {COLUMN} 1.3.6.1.4.1.2356.11.2.109.1.1.4
lcsSetupNetflowCollectorsEntryProtocol OBJECT-TYPE
    SYNTAX     INTEGER {
                  eIpfixUdp (0),
                  eNetflow9Udp (16)
            }
    MAX-ACCESS read-write
    STATUS     current
    DESCRIPTION
            "-- empty --"
    ::= { lcsSetupNetflowCollectorsEntry 4 }

-- {COLUMN} 1.3.6.1.4.1.2356.11.2.109.1.1.5
lcsSetupNetflowCollectorsEntryLoopbackAddr OBJECT-TYPE
    SYNTAX     DisplayString (SIZE(0..16))
    MAX-ACCESS read-write
    STATUS     current
    DESCRIPTION
            "-- empty --"
    ::= { lcsSetupNetflowCollectorsEntry 5 }

-- {COLUMN} 1.3.6.1.4.1.2356.11.2.109.1.1.6
lcsSetupNetflowCollectorsEntryRtgTag OBJECT-TYPE
    SYNTAX     Integer32 (0..65535)
    MAX-ACCESS read-write
    STATUS     current
    DESCRIPTION
            "-- empty --"
    ::= { lcsSetupNetflowCollectorsEntry 6 }

-- {COLUMN} 1.3.6.1.4.1.2356.11.2.109.1.1.7
lcsSetupNetflowCollectorsEntryTemplateRefreshTime OBJECT-TYPE
    SYNTAX     Integer32 (0..65535)
    MAX-ACCESS read-write
    STATUS     current
    DESCRIPTION
            "-- empty --"
    ::= { lcsSetupNetflowCollectorsEntry 7 }

-- {COLUMN} 1.3.6.1.4.1.2356.11.2.109.1.1.8
lcsSetupNetflowCollectorsEntryTemplateRefreshPackets OBJECT-TYPE
    SYNTAX     Integer32 (0..2147483647)
    MAX-ACCESS read-write
    STATUS     current
    DESCRIPTION
            "-- empty --"
    ::= { lcsSetupNetflowCollectorsEntry 8 }

-- {COLUMN} 1.3.6.1.4.1.2356.11.2.109.1.1.99
lcsSetupNetflowCollectorsEntryComment OBJECT-TYPE
    SYNTAX     DisplayString (SIZE(0..50))
    MAX-ACCESS read-write
    STATUS     current
    DESCRIPTION
            "-- empty --"
    ::= { lcsSetupNetflowCollectorsEntry 99 }

-- {TABLE} 1.3.6.1.4.1.2356.11.2.109.2
lcsSetupNetflowInterfacesTable OBJECT-TYPE
    SYNTAX     SEQUENCE OF LcsSetupNetflowInterfacesEntry
    MAX-ACCESS not-accessible
    STATUS     current
    DESCRIPTION
            "-- empty --"
    ::= { lcsSetupNetflow 2 }

-- {ROW} 1.3.6.1.4.1.2356.11.2.109.2.1
lcsSetupNetflowInterfacesEntry OBJECT-TYPE
    SYNTAX     LcsSetupNetflowInterfacesEntry
    MAX-ACCESS not-accessible
    STATUS     current
    DESCRIPTION
            ""
    INDEX {
            lcsSetupNetflowInterfacesEntryIfc,
            lcsSetupNetflowInterfacesEntryCollector
          }
    ::= { lcsSetupNetflowInterfacesTable 1 }

LcsSetupNetflowInterfacesEntry ::= SEQUENCE {
            lcsSetupNetflowInterfacesEntryIfc DisplayString,
            lcsSetupNetflowInterfacesEntryCollector DisplayString,
            lcsSetupNetflowInterfacesEntryActive INTEGER,
            lcsSetupNetflowInterfacesEntryMeteringProfile DisplayString,
            lcsSetupNetflowInterfacesEntryComment DisplayString
    }

-- {COLUMN} 1.3.6.1.4.1.2356.11.2.109.2.1.1
lcsSetupNetflowInterfacesEntryIfc OBJECT-TYPE
    SYNTAX     DisplayString (SIZE(0..16))
    MAX-ACCESS read-write
    STATUS     current
    DESCRIPTION
            "-- empty --"
    ::= { lcsSetupNetflowInterfacesEntry 1 }

-- {COLUMN} 1.3.6.1.4.1.2356.11.2.109.2.1.2
lcsSetupNetflowInterfacesEntryCollector OBJECT-TYPE
    SYNTAX     DisplayString (SIZE(0..20))
    MAX-ACCESS read-write
    STATUS     current
    DESCRIPTION
            "-- empty --"
    ::= { lcsSetupNetflowInterfacesEntry 2 }

-- {COLUMN} 1.3.6.1.4.1.2356.11.2.109.2.1.3
lcsSetupNetflowInterfacesEntryActive OBJECT-TYPE
    SYNTAX     INTEGER {
                  eNo (0),
                  eYes (1)
            }
    MAX-ACCESS read-write
    STATUS     current
    DESCRIPTION
            "-- empty --"
    ::= { lcsSetupNetflowInterfacesEntry 3 }

-- {COLUMN} 1.3.6.1.4.1.2356.11.2.109.2.1.4
lcsSetupNetflowInterfacesEntryMeteringProfile OBJECT-TYPE
    SYNTAX     DisplayString (SIZE(0..20))
    MAX-ACCESS read-write
    STATUS     current
    DESCRIPTION
            "-- empty --"
    ::= { lcsSetupNetflowInterfacesEntry 4 }

-- {COLUMN} 1.3.6.1.4.1.2356.11.2.109.2.1.99
lcsSetupNetflowInterfacesEntryComment OBJECT-TYPE
    SYNTAX     DisplayString (SIZE(0..50))
    MAX-ACCESS read-write
    STATUS     current
    DESCRIPTION
            "-- empty --"
    ::= { lcsSetupNetflowInterfacesEntry 99 }

-- {SCALAR} 1.3.6.1.4.1.2356.11.2.109.3
lcsSetupNetflowOperating OBJECT-TYPE
    SYNTAX     INTEGER {
                  eNo (0),
                  eYes (1)
            }
    MAX-ACCESS read-write
    STATUS     current
    DESCRIPTION
            "-- empty --"
    ::= { lcsSetupNetflow 3 }

-- {TABLE} 1.3.6.1.4.1.2356.11.2.109.4
lcsSetupNetflowMeteringProfilesTable OBJECT-TYPE
    SYNTAX     SEQUENCE OF LcsSetupNetflowMeteringProfilesEntry
    MAX-ACCESS not-accessible
    STATUS     current
    DESCRIPTION
            "-- empty --"
    ::= { lcsSetupNetflow 4 }

-- {ROW} 1.3.6.1.4.1.2356.11.2.109.4.1
lcsSetupNetflowMeteringProfilesEntry OBJECT-TYPE
    SYNTAX     LcsSetupNetflowMeteringProfilesEntry
    MAX-ACCESS not-accessible
    STATUS     current
    DESCRIPTION
            ""
    INDEX {
            lcsSetupNetflowMeteringProfilesEntryName
          }
    ::= { lcsSetupNetflowMeteringProfilesTable 1 }

LcsSetupNetflowMeteringProfilesEntry ::= SEQUENCE {
            lcsSetupNetflowMeteringProfilesEntryName DisplayString,
            lcsSetupNetflowMeteringProfilesEntryDirection BITS,
            lcsSetupNetflowMeteringProfilesEntryIpVersion BITS,
            lcsSetupNetflowMeteringProfilesEntryComment DisplayString
    }

-- {COLUMN} 1.3.6.1.4.1.2356.11.2.109.4.1.1
lcsSetupNetflowMeteringProfilesEntryName OBJECT-TYPE
    SYNTAX     DisplayString (SIZE(0..20))
    MAX-ACCESS read-write
    STATUS     current
    DESCRIPTION
            "-- empty --"
    ::= { lcsSetupNetflowMeteringProfilesEntry 1 }

-- {COLUMN} 1.3.6.1.4.1.2356.11.2.109.4.1.2
lcsSetupNetflowMeteringProfilesEntryDirection OBJECT-TYPE
    SYNTAX     BITS {
                  eEgress (6),
                  eIngress (7)
            }
    MAX-ACCESS read-write
    STATUS     current
    DESCRIPTION
            "-- empty --"
    ::= { lcsSetupNetflowMeteringProfilesEntry 2 }

-- {COLUMN} 1.3.6.1.4.1.2356.11.2.109.4.1.3
lcsSetupNetflowMeteringProfilesEntryIpVersion OBJECT-TYPE
    SYNTAX     BITS {
                  eIpv6 (6),
                  eIpv4 (7)
            }
    MAX-ACCESS read-write
    STATUS     current
    DESCRIPTION
            "-- empty --"
    ::= { lcsSetupNetflowMeteringProfilesEntry 3 }

-- {COLUMN} 1.3.6.1.4.1.2356.11.2.109.4.1.99
lcsSetupNetflowMeteringProfilesEntryComment OBJECT-TYPE
    SYNTAX     DisplayString (SIZE(0..50))
    MAX-ACCESS read-write
    STATUS     current
    DESCRIPTION
            "-- empty --"
    ::= { lcsSetupNetflowMeteringProfilesEntry 99 }

-- {NODE} 1.3.6.1.4.1.2356.11.2.110
lcsSetupFirewall OBJECT IDENTIFIER ::= { lcsSetup 110 }

-- {TABLE} 1.3.6.1.4.1.2356.11.2.110.1
lcsSetupFirewallDnsDestinationsTable OBJECT-TYPE
    SYNTAX     SEQUENCE OF LcsSetupFirewallDnsDestinationsEntry
    MAX-ACCESS not-accessible
    STATUS     current
    DESCRIPTION
            "-- empty --"
    ::= { lcsSetupFirewall 1 }

-- {ROW} 1.3.6.1.4.1.2356.11.2.110.1.1
lcsSetupFirewallDnsDestinationsEntry OBJECT-TYPE
    SYNTAX     LcsSetupFirewallDnsDestinationsEntry
    MAX-ACCESS not-accessible
    STATUS     current
    DESCRIPTION
            ""
    INDEX {
            lcsSetupFirewallDnsDestinationsEntryName
          }
    ::= { lcsSetupFirewallDnsDestinationsTable 1 }

LcsSetupFirewallDnsDestinationsEntry ::= SEQUENCE {
            lcsSetupFirewallDnsDestinationsEntryName DisplayString,
            lcsSetupFirewallDnsDestinationsEntryWildcardExpressions DisplayString
    }

-- {COLUMN} 1.3.6.1.4.1.2356.11.2.110.1.1.1
lcsSetupFirewallDnsDestinationsEntryName OBJECT-TYPE
    SYNTAX     DisplayString (SIZE(0..36))
    MAX-ACCESS read-write
    STATUS     current
    DESCRIPTION
            "-- empty --"
    ::= { lcsSetupFirewallDnsDestinationsEntry 1 }

-- {COLUMN} 1.3.6.1.4.1.2356.11.2.110.1.1.2
lcsSetupFirewallDnsDestinationsEntryWildcardExpressions OBJECT-TYPE
    SYNTAX     DisplayString (SIZE(0..252))
    MAX-ACCESS read-write
    STATUS     current
    DESCRIPTION
            "-- empty --"
    ::= { lcsSetupFirewallDnsDestinationsEntry 2 }

-- {TABLE} 1.3.6.1.4.1.2356.11.2.110.2
lcsSetupFirewallDnsDestinationListTable OBJECT-TYPE
    SYNTAX     SEQUENCE OF LcsSetupFirewallDnsDestinationListEntry
    MAX-ACCESS not-accessible
    STATUS     current
    DESCRIPTION
            "-- empty --"
    ::= { lcsSetupFirewall 2 }

-- {ROW} 1.3.6.1.4.1.2356.11.2.110.2.1
lcsSetupFirewallDnsDestinationListEntry OBJECT-TYPE
    SYNTAX     LcsSetupFirewallDnsDestinationListEntry
    MAX-ACCESS not-accessible
    STATUS     current
    DESCRIPTION
            ""
    INDEX {
            lcsSetupFirewallDnsDestinationListEntryName
          }
    ::= { lcsSetupFirewallDnsDestinationListTable 1 }

LcsSetupFirewallDnsDestinationListEntry ::= SEQUENCE {
            lcsSetupFirewallDnsDestinationListEntryName DisplayString,
            lcsSetupFirewallDnsDestinationListEntryDestinations DisplayString
    }

-- {COLUMN} 1.3.6.1.4.1.2356.11.2.110.2.1.1
lcsSetupFirewallDnsDestinationListEntryName OBJECT-TYPE
    SYNTAX     DisplayString (SIZE(0..36))
    MAX-ACCESS read-write
    STATUS     current
    DESCRIPTION
            "-- empty --"
    ::= { lcsSetupFirewallDnsDestinationListEntry 1 }

-- {COLUMN} 1.3.6.1.4.1.2356.11.2.110.2.1.2
lcsSetupFirewallDnsDestinationListEntryDestinations OBJECT-TYPE
    SYNTAX     DisplayString (SIZE(0..252))
    MAX-ACCESS read-write
    STATUS     current
    DESCRIPTION
            "-- empty --"
    ::= { lcsSetupFirewallDnsDestinationListEntry 2 }

-- {NODE} 1.3.6.1.4.1.2356.11.2.111
lcsSetupIot OBJECT IDENTIFIER ::= { lcsSetup 111 }

-- {NODE} 1.3.6.1.4.1.2356.11.2.111.88
lcsSetupIotWirelessEpaper OBJECT IDENTIFIER ::= { lcsSetupIot 88 }

-- {SCALAR} 1.3.6.1.4.1.2356.11.2.111.88.1
lcsSetupIotWirelessEpaperOperating OBJECT-TYPE
    SYNTAX     INTEGER {
                  eOff (0),
                  eManual (1),
                  eManaged (2)
            }
    MAX-ACCESS read-write
    STATUS     current
    DESCRIPTION
            "-- empty --"
    ::= { lcsSetupIotWirelessEpaper 1 }

-- {SCALAR} 1.3.6.1.4.1.2356.11.2.111.88.2
lcsSetupIotWirelessEpaperPort OBJECT-TYPE
    SYNTAX     Integer32 (0..65535)
    MAX-ACCESS read-write
    STATUS     current
    DESCRIPTION
            "-- empty --"
    ::= { lcsSetupIotWirelessEpaper 2 }

-- {SCALAR} 1.3.6.1.4.1.2356.11.2.111.88.3
lcsSetupIotWirelessEpaperChannel OBJECT-TYPE
    SYNTAX     INTEGER {
                  e2404mhz (0),
                  e2410mhz (1),
                  e2422mhz (2),
                  e2425mhz (3),
                  e2442mhz (4),
                  e2450mhz (5),
                  e2462mhz (6),
                  e2470mhz (7),
                  e2474mhz (8),
                  e2477mhz (9),
                  e2480mhz (10),
                  eAuto (255)
            }
    MAX-ACCESS read-write
    STATUS     current
    DESCRIPTION
            "-- empty --"
    ::= { lcsSetupIotWirelessEpaper 3 }

-- {NODE} 1.3.6.1.4.1.2356.11.2.111.90
lcsSetupIotBluetooth OBJECT IDENTIFIER ::= { lcsSetupIot 90 }

-- {TABLE} 1.3.6.1.4.1.2356.11.2.111.90.2
lcsSetupIotBluetoothOperationalTable OBJECT-TYPE
    SYNTAX     SEQUENCE OF LcsSetupIotBluetoothOperationalEntry
    MAX-ACCESS not-accessible
    STATUS     current
    DESCRIPTION
            "-- empty --"
    ::= { lcsSetupIotBluetooth 2 }

-- {ROW} 1.3.6.1.4.1.2356.11.2.111.90.2.1
lcsSetupIotBluetoothOperationalEntry OBJECT-TYPE
    SYNTAX     LcsSetupIotBluetoothOperationalEntry
    MAX-ACCESS not-accessible
    STATUS     current
    DESCRIPTION
            ""
    INDEX {
            lcsSetupIotBluetoothOperationalEntryIfc
          }
    ::= { lcsSetupIotBluetoothOperationalTable 1 }

LcsSetupIotBluetoothOperationalEntry ::= SEQUENCE {
            lcsSetupIotBluetoothOperationalEntryIfc INTEGER,
            lcsSetupIotBluetoothOperationalEntryOperating INTEGER,
            lcsSetupIotBluetoothOperationalEntryOperationMode INTEGER,
            lcsSetupIotBluetoothOperationalEntryScanMode INTEGER
    }

-- {COLUMN} 1.3.6.1.4.1.2356.11.2.111.90.2.1.1
lcsSetupIotBluetoothOperationalEntryIfc OBJECT-TYPE
    SYNTAX     INTEGER {
                  eBt1 (1)
            }
    MAX-ACCESS read-write
    STATUS     current
    DESCRIPTION
            "-- empty --"
    ::= { lcsSetupIotBluetoothOperationalEntry 1 }

-- {COLUMN} 1.3.6.1.4.1.2356.11.2.111.90.2.1.2
lcsSetupIotBluetoothOperationalEntryOperating OBJECT-TYPE
    SYNTAX     INTEGER {
                  eYes (1),
                  eNo (2)
            }
    MAX-ACCESS read-write
    STATUS     current
    DESCRIPTION
            "-- empty --"
    ::= { lcsSetupIotBluetoothOperationalEntry 2 }

-- {COLUMN} 1.3.6.1.4.1.2356.11.2.111.90.2.1.3
lcsSetupIotBluetoothOperationalEntryOperationMode OBJECT-TYPE
    SYNTAX     INTEGER {
                  eBleBeacon (0),
                  eScanner (1)
            }
    MAX-ACCESS read-write
    STATUS     current
    DESCRIPTION
            "-- empty --"
    ::= { lcsSetupIotBluetoothOperationalEntry 3 }

-- {COLUMN} 1.3.6.1.4.1.2356.11.2.111.90.2.1.4
lcsSetupIotBluetoothOperationalEntryScanMode OBJECT-TYPE
    SYNTAX     INTEGER {
                  ePassive (0),
                  eActive (1)
            }
    MAX-ACCESS read-write
    STATUS     current
    DESCRIPTION
            "-- empty --"
    ::= { lcsSetupIotBluetoothOperationalEntry 4 }

-- {TABLE} 1.3.6.1.4.1.2356.11.2.111.90.3
lcsSetupIotBluetoothBeaconSettingsTable OBJECT-TYPE
    SYNTAX     SEQUENCE OF LcsSetupIotBluetoothBeaconSettingsEntry
    MAX-ACCESS not-accessible
    STATUS     current
    DESCRIPTION
            "-- empty --"
    ::= { lcsSetupIotBluetooth 3 }

-- {ROW} 1.3.6.1.4.1.2356.11.2.111.90.3.1
lcsSetupIotBluetoothBeaconSettingsEntry OBJECT-TYPE
    SYNTAX     LcsSetupIotBluetoothBeaconSettingsEntry
    MAX-ACCESS not-accessible
    STATUS     current
    DESCRIPTION
            ""
    INDEX {
            lcsSetupIotBluetoothBeaconSettingsEntryIfc
          }
    ::= { lcsSetupIotBluetoothBeaconSettingsTable 1 }

LcsSetupIotBluetoothBeaconSettingsEntry ::= SEQUENCE {
            lcsSetupIotBluetoothBeaconSettingsEntryIfc INTEGER,
            lcsSetupIotBluetoothBeaconSettingsEntryBeaconProfiles DisplayString,
            lcsSetupIotBluetoothBeaconSettingsEntryChannels BITS,
            lcsSetupIotBluetoothBeaconSettingsEntryTransmitPower INTEGER
    }

-- {COLUMN} 1.3.6.1.4.1.2356.11.2.111.90.3.1.1
lcsSetupIotBluetoothBeaconSettingsEntryIfc OBJECT-TYPE
    SYNTAX     INTEGER {
                  eBt1 (1)
            }
    MAX-ACCESS read-write
    STATUS     current
    DESCRIPTION
            "-- empty --"
    ::= { lcsSetupIotBluetoothBeaconSettingsEntry 1 }

-- {COLUMN} 1.3.6.1.4.1.2356.11.2.111.90.3.1.2
lcsSetupIotBluetoothBeaconSettingsEntryBeaconProfiles OBJECT-TYPE
    SYNTAX     DisplayString (SIZE(0..17))
    MAX-ACCESS read-write
    STATUS     current
    DESCRIPTION
            "-- empty --"
    ::= { lcsSetupIotBluetoothBeaconSettingsEntry 2 }

-- {COLUMN} 1.3.6.1.4.1.2356.11.2.111.90.3.1.3
lcsSetupIotBluetoothBeaconSettingsEntryChannels OBJECT-TYPE
    SYNTAX     BITS {
                  e2480mhz (5),
                  e2426mhz (6),
                  e2402mhz (7)
            }
    MAX-ACCESS read-write
    STATUS     current
    DESCRIPTION
            "-- empty --"
    ::= { lcsSetupIotBluetoothBeaconSettingsEntry 3 }

-- {COLUMN} 1.3.6.1.4.1.2356.11.2.111.90.3.1.4
lcsSetupIotBluetoothBeaconSettingsEntryTransmitPower OBJECT-TYPE
    SYNTAX     INTEGER {
                  eLow (0),
                  eMedium (1),
                  eHigh (2)
            }
    MAX-ACCESS read-write
    STATUS     current
    DESCRIPTION
            "-- empty --"
    ::= { lcsSetupIotBluetoothBeaconSettingsEntry 4 }

-- {TABLE} 1.3.6.1.4.1.2356.11.2.111.90.4
lcsSetupIotBluetoothBeaconProfilesTable OBJECT-TYPE
    SYNTAX     SEQUENCE OF LcsSetupIotBluetoothBeaconProfilesEntry
    MAX-ACCESS not-accessible
    STATUS     current
    DESCRIPTION
            "-- empty --"
    ::= { lcsSetupIotBluetooth 4 }

-- {ROW} 1.3.6.1.4.1.2356.11.2.111.90.4.1
lcsSetupIotBluetoothBeaconProfilesEntry OBJECT-TYPE
    SYNTAX     LcsSetupIotBluetoothBeaconProfilesEntry
    MAX-ACCESS not-accessible
    STATUS     current
    DESCRIPTION
            ""
    INDEX {
            lcsSetupIotBluetoothBeaconProfilesEntryName
          }
    ::= { lcsSetupIotBluetoothBeaconProfilesTable 1 }

LcsSetupIotBluetoothBeaconProfilesEntry ::= SEQUENCE {
            lcsSetupIotBluetoothBeaconProfilesEntryName DisplayString,
            lcsSetupIotBluetoothBeaconProfilesEntryIbeaconUuid DisplayString,
            lcsSetupIotBluetoothBeaconProfilesEntryIbeaconMajor Integer32,
            lcsSetupIotBluetoothBeaconProfilesEntryIbeaconMinor Integer32,
            lcsSetupIotBluetoothBeaconProfilesEntryMeasuredPowerOffset Integer32
    }

-- {COLUMN} 1.3.6.1.4.1.2356.11.2.111.90.4.1.1
lcsSetupIotBluetoothBeaconProfilesEntryName OBJECT-TYPE
    SYNTAX     DisplayString (SIZE(0..16))
    MAX-ACCESS read-write
    STATUS     current
    DESCRIPTION
            "-- empty --"
    ::= { lcsSetupIotBluetoothBeaconProfilesEntry 1 }

-- {COLUMN} 1.3.6.1.4.1.2356.11.2.111.90.4.1.2
lcsSetupIotBluetoothBeaconProfilesEntryIbeaconUuid OBJECT-TYPE
    SYNTAX     DisplayString (SIZE(0..36))
    MAX-ACCESS read-write
    STATUS     current
    DESCRIPTION
            "-- empty --"
    ::= { lcsSetupIotBluetoothBeaconProfilesEntry 2 }

-- {COLUMN} 1.3.6.1.4.1.2356.11.2.111.90.4.1.3
lcsSetupIotBluetoothBeaconProfilesEntryIbeaconMajor OBJECT-TYPE
    SYNTAX     Integer32 (0..65535)
    MAX-ACCESS read-write
    STATUS     current
    DESCRIPTION
            "-- empty --"
    ::= { lcsSetupIotBluetoothBeaconProfilesEntry 3 }

-- {COLUMN} 1.3.6.1.4.1.2356.11.2.111.90.4.1.4
lcsSetupIotBluetoothBeaconProfilesEntryIbeaconMinor OBJECT-TYPE
    SYNTAX     Integer32 (0..65535)
    MAX-ACCESS read-write
    STATUS     current
    DESCRIPTION
            "-- empty --"
    ::= { lcsSetupIotBluetoothBeaconProfilesEntry 4 }

-- {COLUMN} 1.3.6.1.4.1.2356.11.2.111.90.4.1.5
lcsSetupIotBluetoothBeaconProfilesEntryMeasuredPowerOffset OBJECT-TYPE
    SYNTAX     Integer32 (-128..127)
    MAX-ACCESS read-write
    STATUS     current
    DESCRIPTION
            "-- empty --"
    ::= { lcsSetupIotBluetoothBeaconProfilesEntry 5 }

-- {NODE} 1.3.6.1.4.1.2356.11.2.200
lcsSetupSipAlg OBJECT IDENTIFIER ::= { lcsSetup 200 }

-- {SCALAR} 1.3.6.1.4.1.2356.11.2.200.1
lcsSetupSipAlgOperating OBJECT-TYPE
    SYNTAX     INTEGER {
                  eNo (0),
                  eYes (1)
            }
    MAX-ACCESS read-write
    STATUS     current
    DESCRIPTION
            "-- empty --"
    ::= { lcsSetupSipAlg 1 }

-- {SCALAR} 1.3.6.1.4.1.2356.11.2.200.2
lcsSetupSipAlgFirewallOverrule OBJECT-TYPE
    SYNTAX     INTEGER {
                  eNo (0),
                  eYes (1)
            }
    MAX-ACCESS read-write
    STATUS     current
    DESCRIPTION
            "-- empty --"
    ::= { lcsSetupSipAlg 2 }

-- {NODE} 1.3.6.1.4.1.2356.11.3
lcsFirmware OBJECT IDENTIFIER ::= { lcos 3 }

-- {TABLE} 1.3.6.1.4.1.2356.11.3.1
lcsFirmwareVersionTableTable OBJECT-TYPE
    SYNTAX     SEQUENCE OF LcsFirmwareVersionTableEntry
    MAX-ACCESS not-accessible
    STATUS     current
    DESCRIPTION
            ""
    ::= { lcsFirmware 1 }

-- {ROW} 1.3.6.1.4.1.2356.11.3.1.1
lcsFirmwareVersionTableEntry OBJECT-TYPE
    SYNTAX     LcsFirmwareVersionTableEntry
    MAX-ACCESS not-accessible
    STATUS     current
    DESCRIPTION
            ""
    INDEX {
            lcsFirmwareVersionTableEntryIfc
          }
    ::= { lcsFirmwareVersionTableTable 1 }

LcsFirmwareVersionTableEntry ::= SEQUENCE {
            lcsFirmwareVersionTableEntryIfc INTEGER,
            lcsFirmwareVersionTableEntryModule DisplayString,
            lcsFirmwareVersionTableEntryVersion DisplayString,
            lcsFirmwareVersionTableEntrySerialNumber DisplayString
    }

-- {COLUMN} 1.3.6.1.4.1.2356.11.3.1.1.1
lcsFirmwareVersionTableEntryIfc OBJECT-TYPE
    SYNTAX     INTEGER {
                  eIfc (1)
            }
    MAX-ACCESS read-only
    STATUS     current
    DESCRIPTION
            ""
    ::= { lcsFirmwareVersionTableEntry 1 }

-- {COLUMN} 1.3.6.1.4.1.2356.11.3.1.1.2
lcsFirmwareVersionTableEntryModule OBJECT-TYPE
    SYNTAX     DisplayString (SIZE(0..64))
    MAX-ACCESS read-only
    STATUS     current
    DESCRIPTION
            ""
    ::= { lcsFirmwareVersionTableEntry 2 }

-- {COLUMN} 1.3.6.1.4.1.2356.11.3.1.1.3
lcsFirmwareVersionTableEntryVersion OBJECT-TYPE
    SYNTAX     DisplayString (SIZE(0..30))
    MAX-ACCESS read-only
    STATUS     current
    DESCRIPTION
            ""
    ::= { lcsFirmwareVersionTableEntry 3 }

-- {COLUMN} 1.3.6.1.4.1.2356.11.3.1.1.4
lcsFirmwareVersionTableEntrySerialNumber OBJECT-TYPE
    SYNTAX     DisplayString (SIZE(0..19))
    MAX-ACCESS read-only
    STATUS     current
    DESCRIPTION
            ""
    ::= { lcsFirmwareVersionTableEntry 4 }

-- {TABLE} 1.3.6.1.4.1.2356.11.3.2
lcsFirmwareTableFirmsafeTable OBJECT-TYPE
    SYNTAX     SEQUENCE OF LcsFirmwareTableFirmsafeEntry
    MAX-ACCESS not-accessible
    STATUS     current
    DESCRIPTION
            ""
    ::= { lcsFirmware 2 }

-- {ROW} 1.3.6.1.4.1.2356.11.3.2.1
lcsFirmwareTableFirmsafeEntry OBJECT-TYPE
    SYNTAX     LcsFirmwareTableFirmsafeEntry
    MAX-ACCESS not-accessible
    STATUS     current
    DESCRIPTION
            ""
    INDEX {
            lcsFirmwareTableFirmsafeEntryPosition
          }
    ::= { lcsFirmwareTableFirmsafeTable 1 }

LcsFirmwareTableFirmsafeEntry ::= SEQUENCE {
            lcsFirmwareTableFirmsafeEntryPosition Integer32,
            lcsFirmwareTableFirmsafeEntryStatus INTEGER,
            lcsFirmwareTableFirmsafeEntryVersion DisplayString,
            lcsFirmwareTableFirmsafeEntryDate DisplayString,
            lcsFirmwareTableFirmsafeEntrySize Integer32,
            lcsFirmwareTableFirmsafeEntryIndex Integer32
    }

-- {COLUMN} 1.3.6.1.4.1.2356.11.3.2.1.1
lcsFirmwareTableFirmsafeEntryPosition OBJECT-TYPE
    SYNTAX     Integer32 (0..255)
    MAX-ACCESS read-only
    STATUS     current
    DESCRIPTION
            ""
    ::= { lcsFirmwareTableFirmsafeEntry 1 }

-- {COLUMN} 1.3.6.1.4.1.2356.11.3.2.1.2
lcsFirmwareTableFirmsafeEntryStatus OBJECT-TYPE
    SYNTAX     INTEGER {
                  eInactive (0),
                  eActive (1),
                  eLoader (2),
                  eMinimalPlusInactive (4),
                  eMinimalPlusActive (5)
            }
    MAX-ACCESS read-write
    STATUS     current
    DESCRIPTION
            ""
    ::= { lcsFirmwareTableFirmsafeEntry 2 }

-- {COLUMN} 1.3.6.1.4.1.2356.11.3.2.1.3
lcsFirmwareTableFirmsafeEntryVersion OBJECT-TYPE
    SYNTAX     DisplayString (SIZE(0..17))
    MAX-ACCESS read-only
    STATUS     current
    DESCRIPTION
            ""
    ::= { lcsFirmwareTableFirmsafeEntry 3 }

-- {COLUMN} 1.3.6.1.4.1.2356.11.3.2.1.4
lcsFirmwareTableFirmsafeEntryDate OBJECT-TYPE
    SYNTAX     DisplayString (SIZE(0..9))
    MAX-ACCESS read-only
    STATUS     current
    DESCRIPTION
            ""
    ::= { lcsFirmwareTableFirmsafeEntry 4 }

-- {COLUMN} 1.3.6.1.4.1.2356.11.3.2.1.5
lcsFirmwareTableFirmsafeEntrySize OBJECT-TYPE
    SYNTAX     Integer32 (0..2147483647)
    MAX-ACCESS read-only
    STATUS     current
    DESCRIPTION
            ""
    ::= { lcsFirmwareTableFirmsafeEntry 5 }

-- {COLUMN} 1.3.6.1.4.1.2356.11.3.2.1.6
lcsFirmwareTableFirmsafeEntryIndex OBJECT-TYPE
    SYNTAX     Integer32 (0..2147483647)
    MAX-ACCESS read-only
    STATUS     current
    DESCRIPTION
            ""
    ::= { lcsFirmwareTableFirmsafeEntry 6 }

-- {SCALAR} 1.3.6.1.4.1.2356.11.3.3
lcsFirmwareModeFirmsafe OBJECT-TYPE
    SYNTAX     INTEGER {
                  eImmediate (0),
                  eLogin (1),
                  eManual (2)
            }
    MAX-ACCESS read-write
    STATUS     current
    DESCRIPTION
            ""
    ::= { lcsFirmware 3 }

-- {SCALAR} 1.3.6.1.4.1.2356.11.3.4
lcsFirmwareTimeoutFirmsafe OBJECT-TYPE
    SYNTAX     Integer32 (0..65535)
    MAX-ACCESS read-write
    STATUS     current
    DESCRIPTION
            ""
    ::= { lcsFirmware 4 }

-- {NODE} 1.3.6.1.4.1.2356.11.3.5
lcsFirmwareSecureUpload OBJECT IDENTIFIER ::= { lcsFirmware 5 }

-- {SCALAR} 1.3.6.1.4.1.2356.11.3.5.3
lcsFirmwareSecureUploadEraseLtk OBJECT-TYPE
    SYNTAX     DisplayString
    MAX-ACCESS read-write
    STATUS     current
    DESCRIPTION
            "-- empty --"
    ::= { lcsFirmwareSecureUpload 3 }

-- {SCALAR} 1.3.6.1.4.1.2356.11.3.5.4
lcsFirmwareSecureUploadLtkHash OBJECT-TYPE
    SYNTAX     OCTET STRING
    MAX-ACCESS read-only
    STATUS     current
    DESCRIPTION
            "-- empty --"
    ::= { lcsFirmwareSecureUpload 4 }

-- {SCALAR} 1.3.6.1.4.1.2356.11.3.7
lcsFirmwareFeatureWord OBJECT-TYPE
    SYNTAX     DisplayString (SIZE(0..34))
    MAX-ACCESS read-only
    STATUS     current
    DESCRIPTION
            ""
    ::= { lcsFirmware 7 }

-- {SCALAR} 1.3.6.1.4.1.2356.11.3.8
lcsFirmwareSwitchFirmware OBJECT-TYPE
    SYNTAX     DisplayString
    MAX-ACCESS read-write
    STATUS     current
    DESCRIPTION
            "-- empty --"
    ::= { lcsFirmware 8 }

-- {SCALAR} 1.3.6.1.4.1.2356.11.3.9
lcsFirmwareBootCause OBJECT-TYPE
    SYNTAX     DisplayString (SIZE(0..25))
    MAX-ACCESS read-only
    STATUS     current
    DESCRIPTION
            "-- empty --"
    ::= { lcsFirmware 9 }

-- {NODE} 1.3.6.1.4.1.2356.11.4
lcsOther OBJECT IDENTIFIER ::= { lcos 4 }

-- {NODE} 1.3.6.1.4.1.2356.11.4.1
lcsOtherManualDialing OBJECT IDENTIFIER ::= { lcsOther 1 }

-- {SCALAR} 1.3.6.1.4.1.2356.11.4.1.1
lcsOtherManualDialingConnect OBJECT-TYPE
    SYNTAX     DisplayString
    MAX-ACCESS read-write
    STATUS     current
    DESCRIPTION
            ""
    ::= { lcsOtherManualDialing 1 }

-- {SCALAR} 1.3.6.1.4.1.2356.11.4.1.2
lcsOtherManualDialingDisconnect OBJECT-TYPE
    SYNTAX     DisplayString
    MAX-ACCESS read-write
    STATUS     current
    DESCRIPTION
            ""
    ::= { lcsOtherManualDialing 2 }

-- {SCALAR} 1.3.6.1.4.1.2356.11.4.1.4
lcsOtherManualDialingTestcall OBJECT-TYPE
    SYNTAX     DisplayString
    MAX-ACCESS read-write
    STATUS     current
    DESCRIPTION
            "-- empty --"
    ::= { lcsOtherManualDialing 4 }

-- {SCALAR} 1.3.6.1.4.1.2356.11.4.2
lcsOtherBootSystem OBJECT-TYPE
    SYNTAX     DisplayString
    MAX-ACCESS read-write
    STATUS     current
    DESCRIPTION
            ""
    ::= { lcsOther 2 }

-- {SCALAR} 1.3.6.1.4.1.2356.11.4.5
lcsOtherColdBoot OBJECT-TYPE
    SYNTAX     DisplayString
    MAX-ACCESS read-write
    STATUS     current
    DESCRIPTION
            ""
    ::= { lcsOther 5 }

-- {NODE} 1.3.6.1.4.1.2356.11.4.6
lcsOtherVcCllMngr OBJECT IDENTIFIER ::= { lcsOther 6 }

-- {NODE} 1.3.6.1.4.1.2356.11.4.6.1
lcsOtherVcCllMngrLines OBJECT IDENTIFIER ::= { lcsOtherVcCllMngr 1 }

-- {SCALAR} 1.3.6.1.4.1.2356.11.4.6.1.1
lcsOtherVcCllMngrLinesUnregister OBJECT-TYPE
    SYNTAX     DisplayString
    MAX-ACCESS read-write
    STATUS     current
    DESCRIPTION
            "-- empty --"
    ::= { lcsOtherVcCllMngrLines 1 }

-- {SCALAR} 1.3.6.1.4.1.2356.11.4.6.1.2
lcsOtherVcCllMngrLinesRegister OBJECT-TYPE
    SYNTAX     DisplayString
    MAX-ACCESS read-write
    STATUS     current
    DESCRIPTION
            "-- empty --"
    ::= { lcsOtherVcCllMngrLines 2 }

-- {NODE} 1.3.6.1.4.1.2356.11.4.6.2
lcsOtherVcCllMngrGroups OBJECT IDENTIFIER ::= { lcsOtherVcCllMngr 2 }

-- {SCALAR} 1.3.6.1.4.1.2356.11.4.6.2.1
lcsOtherVcCllMngrGroupsShow OBJECT-TYPE
    SYNTAX     DisplayString
    MAX-ACCESS read-write
    STATUS     current
    DESCRIPTION
            "-- empty --"
    ::= { lcsOtherVcCllMngrGroups 1 }

-- {SCALAR} 1.3.6.1.4.1.2356.11.4.7
lcsOtherFlashRestore OBJECT-TYPE
    SYNTAX     DisplayString
    MAX-ACCESS read-write
    STATUS     current
    DESCRIPTION
            "-- empty --"
    ::= { lcsOther 7 }

-- {SCALAR} 1.3.6.1.4.1.2356.11.4.9
lcsOtherShutdown OBJECT-TYPE
    SYNTAX     DisplayString
    MAX-ACCESS read-write
    STATUS     current
    DESCRIPTION
            "-- empty --"
    ::= { lcsOther 9 }

-- {NODE} 1.3.6.1.4.1.2356.11.8
lcsProducts OBJECT IDENTIFIER ::= { lcos 8 }

-- {NODE} 1.3.6.1.4.1.2356.11.8.101
lcsProductsL320agnWireless OBJECT IDENTIFIER ::= { lcsProducts 101 }

-- {NODE} 1.3.6.1.4.1.2356.11.8.102
lcsProductsL321agnWireless OBJECT IDENTIFIER ::= { lcsProducts 102 }

-- {NODE} 1.3.6.1.4.1.2356.11.8.103
lcsProductsL322agnDualWireless OBJECT IDENTIFIER ::= { lcsProducts 103 }

-- {NODE} 1.3.6.1.4.1.2356.11.8.105
lcsProductsL451agnWireless OBJECT IDENTIFIER ::= { lcsProducts 105 }

-- {NODE} 1.3.6.1.4.1.2356.11.8.106
lcsProductsL452agnDualWireless OBJECT IDENTIFIER ::= { lcsProducts 106 }

-- {NODE} 1.3.6.1.4.1.2356.11.8.107
lcsProductsL460agnDualWireless OBJECT IDENTIFIER ::= { lcsProducts 107 }

-- {NODE} 1.3.6.1.4.1.2356.11.8.108
lcsProductsL151gnWireless OBJECT IDENTIFIER ::= { lcsProducts 108 }

-- {NODE} 1.3.6.1.4.1.2356.11.8.109
lcsProductsL320R2agnWireless OBJECT IDENTIFIER ::= { lcsProducts 109 }

-- {NODE} 1.3.6.1.4.1.2356.11.8.110
lcsProductsL321R2agnWireless OBJECT IDENTIFIER ::= { lcsProducts 110 }

-- {NODE} 1.3.6.1.4.1.2356.11.8.111
lcsProductsL322R2agnDualWireless OBJECT IDENTIFIER ::= { lcsProducts 111 }

-- {NODE} 1.3.6.1.4.1.2356.11.8.112
lcsProductsL1302acnDualWireless OBJECT IDENTIFIER ::= { lcsProducts 112 }

-- {NODE} 1.3.6.1.4.1.2356.11.8.113
lcsProductsL1310acnDualWireless OBJECT IDENTIFIER ::= { lcsProducts 113 }

-- {NODE} 1.3.6.1.4.1.2356.11.8.114
lcsProductsL322EWireless OBJECT IDENTIFIER ::= { lcsProducts 114 }

-- {NODE} 1.3.6.1.4.1.2356.11.8.115
lcsProductsL151EWireless OBJECT IDENTIFIER ::= { lcsProducts 115 }

-- {NODE} 1.3.6.1.4.1.2356.11.8.116
lcsProductsL330agnDualWireless OBJECT IDENTIFIER ::= { lcsProducts 116 }

-- {NODE} 1.3.6.1.4.1.2356.11.8.117
lcsProductsL822acnDualWireless OBJECT IDENTIFIER ::= { lcsProducts 117 }

-- {NODE} 1.3.6.1.4.1.2356.11.8.118
lcsProductsLN830acnDualWireless OBJECT IDENTIFIER ::= { lcsProducts 118 }

-- {NODE} 1.3.6.1.4.1.2356.11.8.119
lcsProductsLN830EWireless OBJECT IDENTIFIER ::= { lcsProducts 119 }

-- {NODE} 1.3.6.1.4.1.2356.11.8.120
lcsProductsLN630Wireless OBJECT IDENTIFIER ::= { lcsProducts 120 }

-- {NODE} 1.3.6.1.4.1.2356.11.8.121
lcsProductsLN1702 OBJECT IDENTIFIER ::= { lcsProducts 121 }

-- {NODE} 1.3.6.1.4.1.2356.11.8.122
lcsProductsLN862 OBJECT IDENTIFIER ::= { lcsProducts 122 }

-- {NODE} 1.3.6.1.4.1.2356.11.8.123
lcsProductsLN860 OBJECT IDENTIFIER ::= { lcsProducts 123 }

-- {NODE} 1.3.6.1.4.1.2356.11.8.124
lcsProductsLN1700 OBJECT IDENTIFIER ::= { lcsProducts 124 }

-- {NODE} 1.3.6.1.4.1.2356.11.8.125
lcsProductsLN830EplusWireless OBJECT IDENTIFIER ::= { lcsProducts 125 }

-- {NODE} 1.3.6.1.4.1.2356.11.8.126
lcsProductsLN830U OBJECT IDENTIFIER ::= { lcsProducts 126 }

-- {NODE} 1.3.6.1.4.1.2356.11.8.127
lcsProductsLN1700B OBJECT IDENTIFIER ::= { lcsProducts 127 }

-- {NODE} 1.3.6.1.4.1.2356.11.8.128
lcsProductsLN1702B OBJECT IDENTIFIER ::= { lcsProducts 128 }

-- {NODE} 1.3.6.1.4.1.2356.11.8.129
lcsProductsLN1700UE OBJECT IDENTIFIER ::= { lcsProducts 129 }

-- {NODE} 1.3.6.1.4.1.2356.11.8.201
lcsProductsIAP321agnWireless OBJECT IDENTIFIER ::= { lcsProducts 201 }

-- {NODE} 1.3.6.1.4.1.2356.11.8.202
lcsProductsIAP322agnDualWireless OBJECT IDENTIFIER ::= { lcsProducts 202 }

-- {NODE} 1.3.6.1.4.1.2356.11.8.203
lcsProductsIAP3G OBJECT IDENTIFIER ::= { lcsProducts 203 }

-- {NODE} 1.3.6.1.4.1.2356.11.8.204
lcsProductsIAP3213G OBJECT IDENTIFIER ::= { lcsProducts 204 }

-- {NODE} 1.3.6.1.4.1.2356.11.8.205
lcsProductsIAP4G OBJECT IDENTIFIER ::= { lcsProducts 205 }

-- {NODE} 1.3.6.1.4.1.2356.11.8.206
lcsProductsIAP4Gplus OBJECT IDENTIFIER ::= { lcsProducts 206 }

-- {NODE} 1.3.6.1.4.1.2356.11.8.301
lcsProductsOAP321agnWireless OBJECT IDENTIFIER ::= { lcsProducts 301 }

-- {NODE} 1.3.6.1.4.1.2356.11.8.302
lcsProductsOAP322agnDualWireless OBJECT IDENTIFIER ::= { lcsProducts 302 }

-- {NODE} 1.3.6.1.4.1.2356.11.8.303
lcsProductsOAP3213G OBJECT IDENTIFIER ::= { lcsProducts 303 }

-- {NODE} 1.3.6.1.4.1.2356.11.8.304
lcsProductsOAP3G OBJECT IDENTIFIER ::= { lcsProducts 304 }

-- {NODE} 1.3.6.1.4.1.2356.11.8.305
lcsProductsOAP821 OBJECT IDENTIFIER ::= { lcsProducts 305 }

-- {NODE} 1.3.6.1.4.1.2356.11.8.306
lcsProductsOAP382 OBJECT IDENTIFIER ::= { lcsProducts 306 }

-- {NODE} 1.3.6.1.4.1.2356.11.8.307
lcsProductsOAP822 OBJECT IDENTIFIER ::= { lcsProducts 307 }

-- {NODE} 1.3.6.1.4.1.2356.11.8.308
lcsProductsOAP4G OBJECT IDENTIFIER ::= { lcsProducts 308 }

-- {NODE} 1.3.6.1.4.1.2356.11.8.309
lcsProductsOAP830 OBJECT IDENTIFIER ::= { lcsProducts 309 }

-- {NODE} 1.3.6.1.4.1.2356.11.8.310
lcsProductsIAP821 OBJECT IDENTIFIER ::= { lcsProducts 310 }

-- {NODE} 1.3.6.1.4.1.2356.11.8.311
lcsProductsIAP822 OBJECT IDENTIFIER ::= { lcsProducts 311 }

-- {NODE} 1.3.6.1.4.1.2356.11.8.312
lcsProductsOAP1702B OBJECT IDENTIFIER ::= { lcsProducts 312 }

-- {NODE} 1.3.6.1.4.1.2356.11.8.313
lcsProductsOAP1700B OBJECT IDENTIFIER ::= { lcsProducts 313 }

-- {NODE} 1.3.6.1.4.1.2356.11.8.501
lcsProductsLC1681E OBJECT IDENTIFIER ::= { lcsProducts 501 }

-- {NODE} 1.3.6.1.4.1.2356.11.8.502
lcsProductsLC1681A OBJECT IDENTIFIER ::= { lcsProducts 502 }

-- {NODE} 1.3.6.1.4.1.2356.11.8.503
lcsProductsLC1681V OBJECT IDENTIFIER ::= { lcsProducts 503 }

-- {NODE} 1.3.6.1.4.1.2356.11.8.504
lcsProductsLC1681V-3G OBJECT IDENTIFIER ::= { lcsProducts 504 }

-- {NODE} 1.3.6.1.4.1.2356.11.8.505
lcsProductsLC1681-4G OBJECT IDENTIFIER ::= { lcsProducts 505 }

-- {NODE} 1.3.6.1.4.1.2356.11.8.506
lcsProductsLC1631E OBJECT IDENTIFIER ::= { lcsProducts 506 }

-- {NODE} 1.3.6.1.4.1.2356.11.8.507
lcsProductsLC831A OBJECT IDENTIFIER ::= { lcsProducts 507 }

-- {NODE} 1.3.6.1.4.1.2356.11.8.508
lcsProductsBusinessLANR800A OBJECT IDENTIFIER ::= { lcsProducts 508 }

-- {NODE} 1.3.6.1.4.1.2356.11.8.509
lcsProductsBusinessLANR800V OBJECT IDENTIFIER ::= { lcsProducts 509 }

-- {NODE} 1.3.6.1.4.1.2356.11.8.510
lcsProductsLC730VA OBJECT IDENTIFIER ::= { lcsProducts 510 }

-- {NODE} 1.3.6.1.4.1.2356.11.8.511
lcsProductsLC730-4G OBJECT IDENTIFIER ::= { lcsProducts 511 }

-- {NODE} 1.3.6.1.4.1.2356.11.8.512
lcsProductsLC1640E OBJECT IDENTIFIER ::= { lcsProducts 512 }

-- {NODE} 1.3.6.1.4.1.2356.11.8.513
lcsProductsLC730-4Gplus OBJECT IDENTIFIER ::= { lcsProducts 513 }

-- {NODE} 1.3.6.1.4.1.2356.11.8.601
lcsProductsLC1780EW3G OBJECT IDENTIFIER ::= { lcsProducts 601 }

-- {NODE} 1.3.6.1.4.1.2356.11.8.602
lcsProductsLC1781A OBJECT IDENTIFIER ::= { lcsProducts 602 }

-- {NODE} 1.3.6.1.4.1.2356.11.8.603
lcsProductsLC1781A-3G OBJECT IDENTIFIER ::= { lcsProducts 603 }

-- {NODE} 1.3.6.1.4.1.2356.11.8.604
lcsProductsLC1781EF OBJECT IDENTIFIER ::= { lcsProducts 604 }

-- {NODE} 1.3.6.1.4.1.2356.11.8.606
lcsProductsLC1781EW OBJECT IDENTIFIER ::= { lcsProducts 606 }

-- {NODE} 1.3.6.1.4.1.2356.11.8.607
lcsProductsLC1781AW OBJECT IDENTIFIER ::= { lcsProducts 607 }

-- {NODE} 1.3.6.1.4.1.2356.11.8.608
lcsProductsLC1781-4G OBJECT IDENTIFIER ::= { lcsProducts 608 }

-- {NODE} 1.3.6.1.4.1.2356.11.8.609
lcsProductsLC1781VA OBJECT IDENTIFIER ::= { lcsProducts 609 }

-- {NODE} 1.3.6.1.4.1.2356.11.8.610
lcsProductsLC1781EFplus OBJECT IDENTIFIER ::= { lcsProducts 610 }

-- {NODE} 1.3.6.1.4.1.2356.11.8.611
lcsProductsLC1781VAW OBJECT IDENTIFIER ::= { lcsProducts 611 }

-- {NODE} 1.3.6.1.4.1.2356.11.8.612
lcsProductsLC1781VA-4G OBJECT IDENTIFIER ::= { lcsProducts 612 }

-- {NODE} 1.3.6.1.4.1.2356.11.8.613
lcsProductsLC1781A-4G OBJECT IDENTIFIER ::= { lcsProducts 613 }

-- {NODE} 1.3.6.1.4.1.2356.11.8.620
lcsProductsLC1780EW4G OBJECT IDENTIFIER ::= { lcsProducts 620 }

-- {NODE} 1.3.6.1.4.1.2356.11.8.621
lcsProductsLC1781EWplus OBJECT IDENTIFIER ::= { lcsProducts 621 }

-- {NODE} 1.3.6.1.4.1.2356.11.8.622
lcsProductsLC1783VA OBJECT IDENTIFIER ::= { lcsProducts 622 }

-- {NODE} 1.3.6.1.4.1.2356.11.8.623
lcsProductsLC1783VAW OBJECT IDENTIFIER ::= { lcsProducts 623 }

-- {NODE} 1.3.6.1.4.1.2356.11.8.624
lcsProductsLC1783VA-4G OBJECT IDENTIFIER ::= { lcsProducts 624 }

-- {NODE} 1.3.6.1.4.1.2356.11.8.625
lcsProductsLC1784VA OBJECT IDENTIFIER ::= { lcsProducts 625 }

-- {NODE} 1.3.6.1.4.1.2356.11.8.626
lcsProductsLC1784VAW OBJECT IDENTIFIER ::= { lcsProducts 626 }

-- {NODE} 1.3.6.1.4.1.2356.11.8.627
lcsProductsBusinessLANR883VA OBJECT IDENTIFIER ::= { lcsProducts 627 }

-- {NODE} 1.3.6.1.4.1.2356.11.8.628
lcsProductsBusinessLANR883VAW OBJECT IDENTIFIER ::= { lcsProducts 628 }

-- {NODE} 1.3.6.1.4.1.2356.11.8.629
lcsProductsBusinessLANR884VA OBJECT IDENTIFIER ::= { lcsProducts 629 }

-- {NODE} 1.3.6.1.4.1.2356.11.8.630
lcsProductsBusinessLANR884VAW OBJECT IDENTIFIER ::= { lcsProducts 630 }

-- {NODE} 1.3.6.1.4.1.2356.11.8.631
lcsProductsLC883VoIP OBJECT IDENTIFIER ::= { lcsProducts 631 }

-- {NODE} 1.3.6.1.4.1.2356.11.8.632
lcsProductsLC884VoIP OBJECT IDENTIFIER ::= { lcsProducts 632 }

-- {NODE} 1.3.6.1.4.1.2356.11.8.633
lcsProductsLC1780EW4Gplus OBJECT IDENTIFIER ::= { lcsProducts 633 }

-- {NODE} 1.3.6.1.4.1.2356.11.8.634
lcsProductsIAP1781VAW OBJECT IDENTIFIER ::= { lcsProducts 634 }

-- {NODE} 1.3.6.1.4.1.2356.11.8.635
lcsProductsR883plus OBJECT IDENTIFIER ::= { lcsProducts 635 }

-- {NODE} 1.3.6.1.4.1.2356.11.8.636
lcsProductsR883plus4G OBJECT IDENTIFIER ::= { lcsProducts 636 }

-- {NODE} 1.3.6.1.4.1.2356.11.8.637
lcsProductsLC1790VA OBJECT IDENTIFIER ::= { lcsProducts 637 }

-- {NODE} 1.3.6.1.4.1.2356.11.8.638
lcsProductsLC1790VA-4G OBJECT IDENTIFIER ::= { lcsProducts 638 }

-- {NODE} 1.3.6.1.4.1.2356.11.8.639
lcsProductsLC1793VA OBJECT IDENTIFIER ::= { lcsProducts 639 }

-- {NODE} 1.3.6.1.4.1.2356.11.8.640
lcsProductsLC1793VA-4G OBJECT IDENTIFIER ::= { lcsProducts 640 }

-- {NODE} 1.3.6.1.4.1.2356.11.8.641
lcsProductsLC1790-4G OBJECT IDENTIFIER ::= { lcsProducts 641 }

-- {NODE} 1.3.6.1.4.1.2356.11.8.642
lcsProductsLC1793VAW OBJECT IDENTIFIER ::= { lcsProducts 642 }

-- {NODE} 1.3.6.1.4.1.2356.11.8.643
lcsProductsLC1790VAW OBJECT IDENTIFIER ::= { lcsProducts 643 }

-- {NODE} 1.3.6.1.4.1.2356.11.8.644
lcsProductsLC1790EF OBJECT IDENTIFIER ::= { lcsProducts 644 }

-- {NODE} 1.3.6.1.4.1.2356.11.8.645
lcsProductsIAP1781VAWplus OBJECT IDENTIFIER ::= { lcsProducts 645 }

-- {NODE} 1.3.6.1.4.1.2356.11.8.646
lcsProductsLC883VoIPplus OBJECT IDENTIFIER ::= { lcsProducts 646 }

-- {NODE} 1.3.6.1.4.1.2356.11.8.647
lcsProductsLC1790VA-4Gplus OBJECT IDENTIFIER ::= { lcsProducts 647 }

-- {NODE} 1.3.6.1.4.1.2356.11.8.648
lcsProductsLC1793VA-4Gplus OBJECT IDENTIFIER ::= { lcsProducts 648 }

-- {NODE} 1.3.6.1.4.1.2356.11.8.649
lcsProductsLC1790-4Gplus OBJECT IDENTIFIER ::= { lcsProducts 649 }

-- {NODE} 1.3.6.1.4.1.2356.11.8.1001
lcsProductsLC1900VA OBJECT IDENTIFIER ::= { lcsProducts 1001 }

-- {NODE} 1.3.6.1.4.1.2356.11.8.1002
lcsProductsLC1900EF OBJECT IDENTIFIER ::= { lcsProducts 1002 }

-- {NODE} 1.3.6.1.4.1.2356.11.8.1003
lcsProductsLC1906VA OBJECT IDENTIFIER ::= { lcsProducts 1003 }

-- {NODE} 1.3.6.1.4.1.2356.11.8.1004
lcsProductsLC1906VA-4G OBJECT IDENTIFIER ::= { lcsProducts 1004 }

-- {NODE} 1.3.6.1.4.1.2356.11.8.1005
lcsProductsLC1916VG-4G OBJECT IDENTIFIER ::= { lcsProducts 1005 }

-- {NODE} 1.3.6.1.4.1.2356.11.8.1006
lcsProductsLC1916VG OBJECT IDENTIFIER ::= { lcsProducts 1006 }

-- {NODE} 1.3.6.1.4.1.2356.11.8.1007
lcsProductsLC1926VG-4G OBJECT IDENTIFIER ::= { lcsProducts 1007 }

-- {NODE} 1.3.6.1.4.1.2356.11.8.4001
lcsProductsWLC4006 OBJECT IDENTIFIER ::= { lcsProducts 4001 }

-- {NODE} 1.3.6.1.4.1.2356.11.8.4002
lcsProductsWLC4025 OBJECT IDENTIFIER ::= { lcsProducts 4002 }

-- {NODE} 1.3.6.1.4.1.2356.11.8.4003
lcsProductsWLC4025plus OBJECT IDENTIFIER ::= { lcsProducts 4003 }

-- {NODE} 1.3.6.1.4.1.2356.11.8.4004
lcsProductsWLC4100 OBJECT IDENTIFIER ::= { lcsProducts 4004 }

-- {NODE} 1.3.6.1.4.1.2356.11.8.4005
lcsProductsWLC4006plus OBJECT IDENTIFIER ::= { lcsProducts 4005 }

-- {NODE} 1.3.6.1.4.1.2356.11.8.4006
lcsProductsWLC1000 OBJECT IDENTIFIER ::= { lcsProducts 4006 }

-- {NODE} 1.3.6.1.4.1.2356.11.8.4007
lcsProductsvWLC OBJECT IDENTIFIER ::= { lcsProducts 4007 }

-- {NODE} 1.3.6.1.4.1.2356.11.8.7001
lcsProductsLC7100VPN OBJECT IDENTIFIER ::= { lcsProducts 7001 }

-- {NODE} 1.3.6.1.4.1.2356.11.8.9001
lcsProductsLC9100VPN OBJECT IDENTIFIER ::= { lcsProducts 9001 }

-- {NODE} 1.3.6.1.4.1.2356.11.8.9002
lcsProductsLC9100plusVPN OBJECT IDENTIFIER ::= { lcsProducts 9002 }

-- {NODE} 1.3.6.1.4.1.2356.11.8.9003
lcsProductsLC7100plusVPN OBJECT IDENTIFIER ::= { lcsProducts 9003 }

-- {NODE} 1.3.6.1.4.1.2356.11.8.9010
lcsProductsISG-1000 OBJECT IDENTIFIER ::= { lcsProducts 9010 }

-- {NODE} 1.3.6.1.4.1.2356.11.8.9011
lcsProductsISG-4000 OBJECT IDENTIFIER ::= { lcsProducts 9011 }

-- {NODE} 1.3.6.1.4.1.2356.11.8.9012
lcsProductsvRouter OBJECT IDENTIFIER ::= { lcsProducts 9012 }

-- {NODE} 1.3.6.1.4.1.2356.11.8.9013
lcsProductsISG-8000 OBJECT IDENTIFIER ::= { lcsProducts 9013 }

--
-- NOTIFICATIONS
--
-- {NOTIFICATION} 1.3.6.1.4.1.2356.11.0.0.1
lcsTrapsStatChan NOTIFICATION-TYPE
    OBJECTS {
            sysDescr,
            sysName,
            lcsStatusSnmpEventEntryCount,
            lcsStatusWanConnections,
            lcsStatusChannelEntryState,
            lcsStatusChannelEntryApp,
            lcsStatusChannelEntryConnector,
            lcsStatusChannelEntryCause,
            lcsStatusChannelEntryNumber,
            lcsStatusChannelEntrySubaddress,
            lcsStatusChannelEntryCharge,
            lcsStatusChannelEntryExtra,
            lcsStatusChannelEntryConnTime,
            lcsStatusChannelEntryConnStart,
            lcsStatusChannelEntryIsdnDisplay,
            lcsStatusChannelEntryPhChan,
            lcsStatusChannelEntryPptpConns,
            lcsStatusChannelEntryVpnConns
          }
    STATUS     current
    DESCRIPTION
            "WAN connection status"
    ::= { lcsTraps 1 }

-- {NOTIFICATION} 1.3.6.1.4.1.2356.11.0.0.4
lcsTrapsFwUplStart NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress
          }
    STATUS     current
    DESCRIPTION
            "Firmware upload was started"
    ::= { lcsTraps 4 }

-- {NOTIFICATION} 1.3.6.1.4.1.2356.11.0.0.5
lcsTrapsUplsucc NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress,
            lcsStatusConfigEventLogEntryInfo1,
            lcsStatusConfigEventLogEntryInfo2
          }
    STATUS     current
    DESCRIPTION
            "Firmware or configuration upload successful"
    ::= { lcsTraps 5 }

-- {NOTIFICATION} 1.3.6.1.4.1.2356.11.0.0.6
lcsTrapsUplfailto NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress,
            lcsStatusConfigEventLogEntryInfo1,
            lcsStatusConfigEventLogEntryInfo2
          }
    STATUS     current
    DESCRIPTION
            "The upload the firmware or configuration failed: maximum time was exceeded"
    ::= { lcsTraps 6 }

-- {NOTIFICATION} 1.3.6.1.4.1.2356.11.0.0.7
lcsTrapsUplfailincl NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress,
            lcsStatusConfigEventLogEntryInfo1,
            lcsStatusConfigEventLogEntryInfo2
          }
    STATUS     current
    DESCRIPTION
            "The upload the firmware or configuration failed: incomplete configuration"
    ::= { lcsTraps 7 }

-- {NOTIFICATION} 1.3.6.1.4.1.2356.11.0.0.8
lcsTrapsUplfailbaddev NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress,
            lcsStatusConfigEventLogEntryInfo1,
            lcsStatusConfigEventLogEntryInfo2
          }
    STATUS     current
    DESCRIPTION
            "The upload the firmware or configuration failed: wrong device"
    ::= { lcsTraps 8 }

-- {NOTIFICATION} 1.3.6.1.4.1.2356.11.0.0.9
lcsTrapsLogin NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress
          }
    STATUS     current
    DESCRIPTION
            "Login to configuration successful"
    ::= { lcsTraps 9 }

-- {NOTIFICATION} 1.3.6.1.4.1.2356.11.0.0.10
lcsTrapsLogout NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress
          }
    STATUS     current
    DESCRIPTION
            "Logout from configuration was successful"
    ::= { lcsTraps 10 }

-- {NOTIFICATION} 1.3.6.1.4.1.2356.11.0.0.11
lcsTrapsCnfuplstart NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress
          }
    STATUS     current
    DESCRIPTION
            "Configuration upload was started"
    ::= { lcsTraps 11 }

-- {NOTIFICATION} 1.3.6.1.4.1.2356.11.0.0.12
lcsTrapsCnfdnlstart NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress
          }
    STATUS     current
    DESCRIPTION
            "Configuration download was started"
    ::= { lcsTraps 12 }

-- {NOTIFICATION} 1.3.6.1.4.1.2356.11.0.0.13
lcsTrapsCnfdnlsucc NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress,
            lcsStatusConfigEventLogEntryInfo1,
            lcsStatusConfigEventLogEntryInfo2
          }
    STATUS     current
    DESCRIPTION
            "Configuration download successful"
    ::= { lcsTraps 13 }

-- {NOTIFICATION} 1.3.6.1.4.1.2356.11.0.0.14
lcsTrapsBssscan NOTIFICATION-TYPE
    OBJECTS {
            sysDescr,
            sysName,
            lcsStatusSnmpEventEntryCount,
            lcsStatusWlanIfcsEntryIfc
          }
    STATUS     current
    DESCRIPTION
            ""
    ::= { lcsTraps 14 }

-- {NOTIFICATION} 1.3.6.1.4.1.2356.11.0.0.15
lcsTrapsBssstart NOTIFICATION-TYPE
    OBJECTS {
            sysDescr,
            sysName,
            lcsStatusSnmpEventEntryCount,
            lcsStatusWlanWlanParameterEntryIfc,
            lcsStatusWlanNetworksEntryBssid
          }
    STATUS     current
    DESCRIPTION
            ""
    ::= { lcsTraps 15 }

-- {NOTIFICATION} 1.3.6.1.4.1.2356.11.0.0.16
lcsTrapsBssjoin NOTIFICATION-TYPE
    OBJECTS {
            sysDescr,
            sysName,
            lcsStatusSnmpEventEntryCount,
            lcsStatusWlanWlanParameterEntryIfc,
            lcsStatusWlanNetworksEntryBssid
          }
    STATUS     current
    DESCRIPTION
            ""
    ::= { lcsTraps 16 }

-- {NOTIFICATION} 1.3.6.1.4.1.2356.11.0.0.17
lcsTrapsAuthstation NOTIFICATION-TYPE
    OBJECTS {
            sysDescr,
            sysName,
            lcsStatusSnmpEventEntryCount,
            lcsStatusWlanStationTableEntryMacAddress,
            lcsStatusWlanStationTableEntryIdentification
          }
    STATUS     current
    DESCRIPTION
            ""
    ::= { lcsTraps 17 }

-- {NOTIFICATION} 1.3.6.1.4.1.2356.11.0.0.18
lcsTrapsDeauthstation NOTIFICATION-TYPE
    OBJECTS {
            sysDescr,
            sysName,
            lcsStatusSnmpEventEntryCount,
            lcsStatusWlanStationTableEntryMacAddress,
            lcsStatusWlanStationTableEntryIdentification
          }
    STATUS     current
    DESCRIPTION
            ""
    ::= { lcsTraps 18 }

-- {NOTIFICATION} 1.3.6.1.4.1.2356.11.0.0.19
lcsTrapsAssstation NOTIFICATION-TYPE
    OBJECTS {
            sysDescr,
            sysName,
            lcsStatusSnmpEventEntryCount,
            lcsStatusWlanStationTableEntryMacAddress,
            lcsStatusWlanStationTableEntryIdentification
          }
    STATUS     current
    DESCRIPTION
            ""
    ::= { lcsTraps 19 }

-- {NOTIFICATION} 1.3.6.1.4.1.2356.11.0.0.20
lcsTrapsReassstation NOTIFICATION-TYPE
    OBJECTS {
            sysDescr,
            sysName,
            lcsStatusSnmpEventEntryCount,
            lcsStatusWlanStationTableEntryMacAddress,
            lcsStatusWlanStationTableEntryIdentification
          }
    STATUS     current
    DESCRIPTION
            ""
    ::= { lcsTraps 20 }

-- {NOTIFICATION} 1.3.6.1.4.1.2356.11.0.0.21
lcsTrapsDisassstation NOTIFICATION-TYPE
    OBJECTS {
            sysDescr,
            sysName,
            lcsStatusSnmpEventEntryCount,
            lcsStatusWlanStationTableEntryMacAddress,
            lcsStatusWlanStationTableEntryIdentification
          }
    STATUS     current
    DESCRIPTION
            ""
    ::= { lcsTraps 21 }

-- {NOTIFICATION} 1.3.6.1.4.1.2356.11.0.0.22
lcsTrapsAssrej NOTIFICATION-TYPE
    OBJECTS {
            sysDescr,
            sysName,
            lcsStatusSnmpEventEntryCount,
            lcsStatusWlanLogTableEntryAddress
          }
    STATUS     current
    DESCRIPTION
            ""
    ::= { lcsTraps 22 }

-- {NOTIFICATION} 1.3.6.1.4.1.2356.11.0.0.25
lcsTrapsCardhung NOTIFICATION-TYPE
    OBJECTS {
            sysDescr,
            sysName,
            lcsStatusSnmpEventEntryCount,
            lcsStatusWlanIfcsEntryIfc
          }
    STATUS     current
    DESCRIPTION
            ""
    ::= { lcsTraps 25 }

-- {NOTIFICATION} 1.3.6.1.4.1.2356.11.0.0.26
lcsTrapsIpfwflt NOTIFICATION-TYPE
    OBJECTS {
            sysDescr,
            sysName,
            lcsStatusSnmpEventEntryCount,
            lcsStatusIpRouterLogTableEntrySystemTime,
            lcsStatusIpRouterLogTableEntrySrcAddress,
            lcsStatusIpRouterLogTableEntryDstAddress,
            lcsStatusIpRouterLogTableEntryProt,
            lcsStatusIpRouterLogTableEntrySrcPort,
            lcsStatusIpRouterLogTableEntryDstPort,
            lcsStatusIpRouterLogTableEntryFilterRule,
            lcsStatusIpRouterLogTableEntryLimit,
            lcsStatusIpRouterLogTableEntryThreshold,
            lcsStatusIpRouterLogTableEntryAction
          }
    STATUS     current
    DESCRIPTION
            "Information about a firewall event"
    ::= { lcsTraps 26 }

-- {NOTIFICATION} 1.3.6.1.4.1.2356.11.0.0.27
lcsTrapsVpnconn NOTIFICATION-TYPE
    OBJECTS {
            sysDescr,
            sysName,
            lcsStatusSnmpEventEntryCount,
            lcsStatusVpnTunnel,
            lcsStatusVpnConnectionsEntryPeer,
            lcsStatusVpnConnectionsEntryState,
            lcsStatusVpnConnectionsEntryLastError,
            lcsStatusVpnConnectionsEntryMode,
            lcsStatusVpnConnectionsEntryShTime,
            lcsStatusVpnConnectionsEntryPhysConn,
            lcsStatusVpnConnectionsEntryB1Dt,
            lcsStatusVpnConnectionsEntryRemoteGwNew,
            lcsStatusVpnConnectionsEntryRemoteGw,
            lcsStatusVpnConnectionsEntryNatDetection,
            lcsStatusVpnConnectionsEntrySslEncaps,
            lcsStatusVpnConnectionsEntryCryptAlg,
            lcsStatusVpnConnectionsEntryCryptLength,
            lcsStatusVpnConnectionsEntryHashAlg,
            lcsStatusVpnConnectionsEntryHashLength,
            lcsStatusVpnConnectionsEntryHmacAlg,
            lcsStatusVpnConnectionsEntryHmacLength,
            lcsStatusVpnConnectionsEntryComprAlg,
            lcsStatusVpnConnectionsEntryClientSn
          }
    STATUS     current
    DESCRIPTION
            "Status of VPN connection"
    ::= { lcsTraps 27 }

-- {NOTIFICATION} 1.3.6.1.4.1.2356.11.0.0.28
lcsTrapsPptpconn NOTIFICATION-TYPE
    OBJECTS {
            sysDescr,
            sysName,
            lcsStatusSnmpEventEntryCount,
            lcsStatusPptpTunnel,
            lcsStatusPptpConnectionsEntryChannel,
            lcsStatusPptpConnectionsEntryState,
            lcsStatusPptpConnectionsEntryMode,
            lcsStatusPptpConnectionsEntryShTime,
            lcsStatusPptpConnectionsEntryPhysConnection,
            lcsStatusPptpConnectionsEntryPeerAddress,
            lcsStatusPptpConnectionsEntryIpAddress,
            lcsStatusPptpConnectionsEntryDnsDefault,
            lcsStatusPptpConnectionsEntryNbnsDefault,
            lcsStatusPptpConnectionsEntryLastError,
            lcsStatusPptpConnectionsEntryDnsBackup,
            lcsStatusPptpConnectionsEntryNbnsBackup
          }
    STATUS     current
    DESCRIPTION
            "Status of PPTP connection"
    ::= { lcsTraps 28 }

-- {NOTIFICATION} 1.3.6.1.4.1.2356.11.0.0.29
lcsTrapsErrlogin NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress
          }
    STATUS     current
    DESCRIPTION
            "Error during login to configuration"
    ::= { lcsTraps 29 }

-- {NOTIFICATION} 1.3.6.1.4.1.2356.11.0.0.33
lcsTrapsKeyhandshakeTimeout NOTIFICATION-TYPE
    OBJECTS {
            sysDescr,
            sysName,
            lcsStatusSnmpEventEntryCount
          }
    STATUS     current
    DESCRIPTION
            ""
    ::= { lcsTraps 33 }

-- {NOTIFICATION} 1.3.6.1.4.1.2356.11.0.0.35
lcsTrapsSupervision NOTIFICATION-TYPE
    OBJECTS {
            sysDescr,
            sysName,
            lcsStatusSnmpEventEntryCount,
            lcsStatusWlanStationTableEntryMacAddress,
            lcsStatusWlanStationTableEntryIdentification
          }
    STATUS     current
    DESCRIPTION
            ""
    ::= { lcsTraps 35 }

-- {NOTIFICATION} 1.3.6.1.4.1.2356.11.0.0.38
lcsTrapsLdblconn NOTIFICATION-TYPE
    OBJECTS {
            sysDescr,
            sysName,
            lcsStatusSnmpEventEntryCount,
            lcsStatusIpRouterLoadBalancerConnectionsEntryPeer,
            lcsStatusIpRouterLoadBalancerConnectionsEntryBundlePeer,
            lcsStatusIpRouterLoadBalancerConnectionsEntryState
          }
    STATUS     current
    DESCRIPTION
            ""
    ::= { lcsTraps 38 }

-- {NOTIFICATION} 1.3.6.1.4.1.2356.11.0.0.39
lcsTrapsPppoesconn NOTIFICATION-TYPE
    OBJECTS {
            sysDescr,
            sysName,
            lcsStatusSnmpEventEntryCount,
            lcsStatusPppoeServerNumConnections,
            lcsStatusPppoeServerConnectionsEntryChannel,
            lcsStatusPppoeServerConnectionsEntryMacAddress,
            lcsStatusPppoeServerConnectionsEntryState,
            lcsStatusPppoeServerConnectionsEntryLastError,
            lcsStatusPppoeServerConnectionsEntryShTime,
            lcsStatusPppoeServerConnectionsEntryPeerAddress
          }
    STATUS     current
    DESCRIPTION
            ""
    ::= { lcsTraps 39 }

-- {NOTIFICATION} 1.3.6.1.4.1.2356.11.0.0.41
lcsTrapsVrrp NOTIFICATION-TYPE
    OBJECTS {
            sysDescr,
            sysName,
            lcsStatusSnmpEventEntryCount,
            lcsStatusIpRouterVrrpEventLogEntrySystemTime,
            lcsStatusIpRouterVrrpEventLogEntrySrcAddress,
            lcsStatusIpRouterVrrpEventLogEntryVrid,
            lcsStatusIpRouterVrrpEventLogEntryEvent,
            lcsStatusIpRouterVrrpEventLogEntryInfo
          }
    STATUS     current
    DESCRIPTION
            ""
    ::= { lcsTraps 41 }

-- {NOTIFICATION} 1.3.6.1.4.1.2356.11.0.0.42
lcsTrapsExceirp NOTIFICATION-TYPE
    OBJECTS {
            sysDescr,
            sysName,
            lcsStatusSnmpEventEntryCount,
            lcsStatusWlanWlanParameterEntryIfc,
            lcsStatusWlanWlanParameterEntryEirp
          }
    STATUS     current
    DESCRIPTION
            ""
    ::= { lcsTraps 42 }

-- {NOTIFICATION} 1.3.6.1.4.1.2356.11.0.0.43
lcsTrapsVcmCallStatChan NOTIFICATION-TYPE
    OBJECTS {
            sysDescr,
            sysName,
            lcsStatusSnmpEventEntryCount,
            lcsStatusVcCllMngrCallCounter,
            lcsStatusVcCllMngrCallsEntryIndex,
            lcsStatusVcCllMngrCallsEntryFromLine,
            lcsStatusVcCllMngrCallsEntryFromDisplayname,
            lcsStatusVcCllMngrCallsEntryFromNumberName,
            lcsStatusVcCllMngrCallsEntryFromDomain,
            lcsStatusVcCllMngrCallsEntryToDomain,
            lcsStatusVcCllMngrCallsEntryToNumberName,
            lcsStatusVcCllMngrCallsEntryDestLine,
            lcsStatusVcCllMngrCallsEntryDestNumberName,
            lcsStatusVcCllMngrCallsEntryStatus,
            lcsStatusVcCllMngrCallsEntryStart,
            lcsStatusVcCllMngrCallsEntryEnd,
            lcsStatusVcCllMngrCallsEntryDestDisplayname,
            lcsStatusVcCllMngrCallsEntryDestDomain,
            lcsStatusVcCllMngrCallsEntryFromtocodec,
            lcsStatusVcCllMngrCallsEntryTofromcodec,
            lcsStatusVcCllMngrCallsEntryConnect,
            lcsStatusVcCllMngrCallsEntryCfMethod,
            lcsStatusVcCllMngrCallsEntryFaxDetected,
            lcsStatusVcCllMngrCallsEntryFromSrtp,
            lcsStatusVcCllMngrCallsEntryDestSrtp
          }
    STATUS     current
    DESCRIPTION
            "Status of SIP calls"
    ::= { lcsTraps 43 }

-- {NOTIFICATION} 1.3.6.1.4.1.2356.11.0.0.44
lcsTrapsVcmUserStatChan NOTIFICATION-TYPE
    OBJECTS {
            sysDescr,
            sysName,
            lcsStatusSnmpEventEntryCount,
            lcsStatusVcCllMngrUserCounter,
            lcsStatusVcCllMngrUsersEntryIndex,
            lcsStatusVcCllMngrUsersEntryNumberName,
            lcsStatusVcCllMngrUsersEntryType,
            lcsStatusVcCllMngrUsersEntryDisplayName,
            lcsStatusVcCllMngrUsersEntryDomain,
            lcsStatusVcCllMngrUsersEntryLocalRegister,
            lcsStatusVcCllMngrUsersEntryRemoteRegister,
            lcsStatusVcCllMngrUsersEntryIfc,
            lcsStatusVcCllMngrUsersEntryStatus,
            lcsStatusVcCllMngrUsersEntryAddress,
            lcsStatusVcCllMngrUsersEntryCfuActive,
            lcsStatusVcCllMngrUsersEntryCfuTarget,
            lcsStatusVcCllMngrUsersEntryCfnrActive,
            lcsStatusVcCllMngrUsersEntryCfnrTarget,
            lcsStatusVcCllMngrUsersEntryCfnrTimeout,
            lcsStatusVcCllMngrUsersEntryCfbActive,
            lcsStatusVcCllMngrUsersEntryCfbTarget,
            lcsStatusVcCllMngrUsersEntryAccessFromWan
          }
    STATUS     current
    DESCRIPTION
            "Status of SIP users"
    ::= { lcsTraps 44 }

-- {NOTIFICATION} 1.3.6.1.4.1.2356.11.0.0.45
lcsTrapsVcmLineStatChan NOTIFICATION-TYPE
    OBJECTS {
            sysDescr,
            sysName,
            lcsStatusSnmpEventEntryCount,
            lcsStatusVcCllMngrLineCounter,
            lcsStatusVcCllMngrLinesEntryIndex,
            lcsStatusVcCllMngrLinesEntryName,
            lcsStatusVcCllMngrLinesEntryType,
            lcsStatusVcCllMngrLinesEntryRegStatus,
            lcsStatusVcCllMngrLinesEntryLineStatus,
            lcsStatusVcCllMngrLinesEntryQuality,
            lcsStatusVcCllMngrLinesEntryNumber,
            lcsStatusVcCllMngrLinesEntryDomain,
            lcsStatusVcCllMngrLinesEntryRegState
          }
    STATUS     current
    DESCRIPTION
            "Status of SIP lines"
    ::= { lcsTraps 45 }

-- {NOTIFICATION} 1.3.6.1.4.1.2356.11.0.0.46
lcsTrapsIdleTimeout NOTIFICATION-TYPE
    OBJECTS {
            sysDescr,
            sysName,
            lcsStatusSnmpEventEntryCount
          }
    STATUS     current
    DESCRIPTION
            ""
    ::= { lcsTraps 46 }

-- {NOTIFICATION} 1.3.6.1.4.1.2356.11.0.0.47
lcsTrapsAdminDeassoc NOTIFICATION-TYPE
    OBJECTS {
            sysDescr,
            sysName,
            lcsStatusSnmpEventEntryCount,
            lcsStatusWlanStationTableEntryMacAddress,
            lcsStatusWlanStationTableEntryIdentification
          }
    STATUS     current
    DESCRIPTION
            ""
    ::= { lcsTraps 47 }

-- {NOTIFICATION} 1.3.6.1.4.1.2356.11.0.0.48
lcsTrapsWlanovertemp NOTIFICATION-TYPE
    OBJECTS {
            sysDescr,
            sysName,
            lcsStatusSnmpEventEntryCount,
            lcsStatusHardwareInfoTemperatureDegrees
          }
    STATUS     current
    DESCRIPTION
            ""
    ::= { lcsTraps 48 }

-- {NOTIFICATION} 1.3.6.1.4.1.2356.11.0.0.49
lcsTrapsWlanovertempend NOTIFICATION-TYPE
    OBJECTS {
            sysDescr,
            sysName,
            lcsStatusSnmpEventEntryCount,
            lcsStatusHardwareInfoTemperatureDegrees
          }
    STATUS     current
    DESCRIPTION
            ""
    ::= { lcsTraps 49 }

-- {NOTIFICATION} 1.3.6.1.4.1.2356.11.0.0.50
lcsTrapsWlanundertemp NOTIFICATION-TYPE
    OBJECTS {
            sysDescr,
            sysName,
            lcsStatusSnmpEventEntryCount,
            lcsStatusHardwareInfoTemperatureDegrees
          }
    STATUS     current
    DESCRIPTION
            ""
    ::= { lcsTraps 50 }

-- {NOTIFICATION} 1.3.6.1.4.1.2356.11.0.0.51
lcsTrapsWlanundertempend NOTIFICATION-TYPE
    OBJECTS {
            sysDescr,
            sysName,
            lcsStatusSnmpEventEntryCount,
            lcsStatusHardwareInfoTemperatureDegrees
          }
    STATUS     current
    DESCRIPTION
            ""
    ::= { lcsTraps 51 }

-- {NOTIFICATION} 1.3.6.1.4.1.2356.11.0.0.52
lcsTrapsMacchkfail NOTIFICATION-TYPE
    OBJECTS {
            sysDescr,
            sysName,
            lcsStatusSnmpEventEntryCount,
            lcsStatusWlanStationTableEntryMacAddress,
            lcsStatusWlanStationTableEntryIdentification
          }
    STATUS     current
    DESCRIPTION
            ""
    ::= { lcsTraps 52 }

-- {NOTIFICATION} 1.3.6.1.4.1.2356.11.0.0.53
lcsTrapsRoamed NOTIFICATION-TYPE
    OBJECTS {
            sysDescr,
            sysName,
            lcsStatusSnmpEventEntryCount,
            lcsStatusWlanStationTableEntryMacAddress,
            lcsStatusWlanStationTableEntryIdentification
          }
    STATUS     current
    DESCRIPTION
            ""
    ::= { lcsTraps 53 }

-- {NOTIFICATION} 1.3.6.1.4.1.2356.11.0.0.54
lcsTrapsConnected NOTIFICATION-TYPE
    OBJECTS {
            sysDescr,
            sysName,
            lcsStatusSnmpEventEntryCount,
            lcsStatusWlanStationTableEntryMacAddress,
            lcsStatusWlanStationTableEntryIdentification
          }
    STATUS     current
    DESCRIPTION
            ""
    ::= { lcsTraps 54 }

-- {NOTIFICATION} 1.3.6.1.4.1.2356.11.0.0.55
lcsTrapsClLostconn NOTIFICATION-TYPE
    OBJECTS {
            sysDescr,
            sysName,
            lcsStatusSnmpEventEntryCount,
            lcsStatusWlanClientIfcsEntryIfc,
            lcsStatusWlanClientIfcsEntryState
          }
    STATUS     current
    DESCRIPTION
            ""
    ::= { lcsTraps 55 }

-- {NOTIFICATION} 1.3.6.1.4.1.2356.11.0.0.56
lcsTrapsClAuthfail NOTIFICATION-TYPE
    OBJECTS {
            sysDescr,
            sysName,
            lcsStatusSnmpEventEntryCount,
            lcsStatusWlanClientIfcsEntryIfc,
            lcsStatusWlanClientIfcsEntryState
          }
    STATUS     current
    DESCRIPTION
            ""
    ::= { lcsTraps 56 }

-- {NOTIFICATION} 1.3.6.1.4.1.2356.11.0.0.57
lcsTrapsClAssocfail NOTIFICATION-TYPE
    OBJECTS {
            sysDescr,
            sysName,
            lcsStatusSnmpEventEntryCount,
            lcsStatusWlanClientIfcsEntryIfc,
            lcsStatusWlanClientIfcsEntryState
          }
    STATUS     current
    DESCRIPTION
            ""
    ::= { lcsTraps 57 }

-- {NOTIFICATION} 1.3.6.1.4.1.2356.11.0.0.58
lcsTrapsClConnected NOTIFICATION-TYPE
    OBJECTS {
            sysDescr,
            sysName,
            lcsStatusSnmpEventEntryCount,
            lcsStatusWlanClientIfcsEntryIfc,
            lcsStatusWlanClientIfcsEntryState
          }
    STATUS     current
    DESCRIPTION
            ""
    ::= { lcsTraps 58 }

-- {NOTIFICATION} 1.3.6.1.4.1.2356.11.0.0.59
lcsTrapsCl8021xFail NOTIFICATION-TYPE
    OBJECTS {
            sysDescr,
            sysName,
            lcsStatusSnmpEventEntryCount,
            lcsStatusWlanClientIfcsEntryIfc,
            lcsStatusWlanClientIfcsEntryState
          }
    STATUS     current
    DESCRIPTION
            ""
    ::= { lcsTraps 59 }

-- {NOTIFICATION} 1.3.6.1.4.1.2356.11.0.0.60
lcsTrapsAdslstate NOTIFICATION-TYPE
    OBJECTS {
            sysDescr,
            sysName,
            lcsStatusSnmpEventEntryCount,
            lcsStatusAdslLineState
          }
    STATUS     current
    DESCRIPTION
            "-- empty --"
    ::= { lcsTraps 60 }

-- {NOTIFICATION} 1.3.6.1.4.1.2356.11.0.0.61
lcsTrapsCastatchg NOTIFICATION-TYPE
    OBJECTS {
            sysDescr,
            sysName,
            lcsStatusSnmpEventEntryCount,
            lcsStatusCertsScepCaCaStatusCaStatus,
            lcsStatusCertsScepCaCaStatusError
          }
    STATUS     current
    DESCRIPTION
            ""
    ::= { lcsTraps 61 }

-- {NOTIFICATION} 1.3.6.1.4.1.2356.11.0.0.62
lcsTrapsNewpendreq NOTIFICATION-TYPE
    OBJECTS {
            sysDescr,
            sysName,
            lcsStatusSnmpEventEntryCount,
            lcsStatusCertsScepCaRequestsPendReqEntryIndex,
            lcsStatusCertsScepCaRequestsPendReqEntryMacAddress,
            lcsStatusCertsScepCaRequestsPendReqEntryIpAddress,
            lcsStatusCertsScepCaRequestsPendReqEntryReason,
            lcsStatusCertsScepCaRequestsPendReqEntryDn,
            lcsStatusCertsScepCaRequestsPendReqEntryReceiveDate
          }
    STATUS     current
    DESCRIPTION
            ""
    ::= { lcsTraps 62 }

-- {NOTIFICATION} 1.3.6.1.4.1.2356.11.0.0.63
lcsTrapsMissingAp NOTIFICATION-TYPE
    OBJECTS {
            sysDescr,
            sysName,
            lcsStatusSnmpEventEntryCount,
            lcsStatusWlanMngmtConnectedExpectedAp,
            lcsStatusWlanMngmtNextdoorAp,
            lcsStatusWlanMngmtExpectedAp,
            lcsStatusWlanMngmtApStatusMissingApEntryApLanMac,
            lcsStatusWlanMngmtApStatusMissingApEntryIpAddress,
            lcsStatusWlanMngmtApStatusMissingApEntryName,
            lcsStatusWlanMngmtApStatusMissingApEntryLocation,
            lcsStatusWlanMngmtApStatusMissingApEntryValid,
            lcsStatusWlanMngmtApStatusMissingApEntryModule
          }
    STATUS     current
    DESCRIPTION
            ""
    ::= { lcsTraps 63 }

-- {NOTIFICATION} 1.3.6.1.4.1.2356.11.0.0.64
lcsTrapsActiveAp NOTIFICATION-TYPE
    OBJECTS {
            sysDescr,
            sysName,
            lcsStatusSnmpEventEntryCount,
            lcsStatusWlanMngmtConnectedManagedAp,
            lcsStatusWlanMngmtNextdoorAp,
            lcsStatusWlanMngmtApStatusActiveRadiosEntryApLanMac,
            lcsStatusWlanMngmtApStatusActiveRadiosEntryIfc,
            lcsStatusWlanMngmtApStatusActiveRadiosEntryIpAddress,
            lcsStatusWlanMngmtApStatusActiveRadiosEntryName,
            lcsStatusWlanMngmtApStatusActiveRadiosEntryLocation,
            lcsStatusWlanMngmtApStatusActiveRadiosEntryValid,
            lcsStatusWlanMngmtApStatusActiveRadiosEntryApWlanMac,
            lcsStatusWlanMngmtApStatusActiveRadiosEntryRadioBand,
            lcsStatusWlanMngmtApStatusActiveRadiosEntryRadioChannel,
            lcsStatusWlanMngmtApStatusActiveRadiosEntryClientCount,
            lcsStatusWlanMngmtApStatusActiveRadiosEntryBackgroundScan,
            lcsStatusWlanMngmtApStatusActiveRadiosEntryCardId,
            lcsStatusWlanMngmtApStatusActiveRadiosEntryCardFirmwareVersion,
            lcsStatusWlanMngmtApStatusActiveRadiosEntryCardSerialNumber,
            lcsStatusWlanMngmtApStatusActiveRadiosEntryOperating,
            lcsStatusWlanMngmtApStatusActiveRadiosEntryTransmitPower,
            lcsStatusWlanMngmtApStatusActiveRadiosEntryEirp,
            lcsStatusWlanMngmtApStatusActiveRadiosEntryExcEirp,
            lcsStatusWlanMngmtApStatusActiveRadiosEntryInternal,
            lcsStatusWlanMngmtApStatusActiveRadiosEntryRadios,
            lcsStatusWlanMngmtApStatusActiveRadiosEntryModule,
            lcsStatusWlanMngmtApStatusActiveRadiosEntrySerialNumber,
            lcsStatusWlanMngmtApStatusActiveRadiosEntryVersion,
            lcsStatusWlanMngmtApStatusActiveRadiosEntryCardState,
            lcsStatusWlanMngmtApStatusActiveRadiosEntryRadioFldOpt,
            lcsStatusWlanMngmtApStatusActiveRadiosEntryMinimalModemLoad,
            lcsStatusWlanMngmtApStatusActiveRadiosEntryMaximalModemLoad,
            lcsStatusWlanMngmtApStatusActiveRadiosEntryAverageModemLoad,
            lcsStatusWlanMngmtApStatusActiveRadiosEntryApConnection
          }
    STATUS     current
    DESCRIPTION
            ""
    ::= { lcsTraps 64 }

-- {NOTIFICATION} 1.3.6.1.4.1.2356.11.0.0.65
lcsTrapsNewAp NOTIFICATION-TYPE
    OBJECTS {
            sysDescr,
            sysName,
            lcsStatusSnmpEventEntryCount,
            lcsStatusWlanMngmtConnectedNewAp,
            lcsStatusWlanMngmtApStatusNewApEntryApLanMac,
            lcsStatusWlanMngmtApStatusNewApEntryIpAddress,
            lcsStatusWlanMngmtApStatusNewApEntryName,
            lcsStatusWlanMngmtApStatusNewApEntryLocation,
            lcsStatusWlanMngmtApStatusNewApEntryValid,
            lcsStatusWlanMngmtApStatusNewApEntryConfiguration,
            lcsStatusWlanMngmtApStatusNewApEntryAutowdsIntegration
          }
    STATUS     current
    DESCRIPTION
            ""
    ::= { lcsTraps 65 }

-- {NOTIFICATION} 1.3.6.1.4.1.2356.11.0.0.66
lcsTrapsStations NOTIFICATION-TYPE
    OBJECTS {
            sysDescr,
            sysName,
            lcsStatusSnmpEventEntryCount,
            lcsStatusWlanMngmtStationTableEntryClientMac,
            lcsStatusWlanMngmtStationTableEntryApWlanMac,
            lcsStatusWlanMngmtStationTableEntryIdentification,
            lcsStatusWlanMngmtStationTableEntryTrap,
            lcsStatusWlanMngmtStationTableEntryPhySignal,
            lcsStatusWlanMngmtStationTableEntryTxRate,
            lcsStatusWlanMngmtStationTableEntryRxRate,
            lcsStatusWlanMngmtStationTableEntryNetworkName,
            lcsStatusWlanMngmtStationTableEntryKeyType,
            lcsStatusWlanMngmtStationTableEntryWpaVersion,
            lcsStatusWlanMngmtStationTableEntryState,
            lcsStatusWlanMngmtStationTableEntryLastError,
            lcsStatusWlanMngmtStationTableEntryIpAddress,
            lcsStatusWlanMngmtStationTableEntryInterface,
            lcsStatusWlanMngmtStationTableEntryThroughput,
            lcsStatusWlanMngmtStationTableEntryCompression,
            lcsStatusWlanMngmtStationTableEntryApLanMac,
            lcsStatusWlanMngmtStationTableEntryApName,
            lcsStatusWlanMngmtStationTableEntryValid,
            lcsStatusWlanMngmtStationTableEntryEffTxRate,
            lcsStatusWlanMngmtStationTableEntryEffRxRate,
            lcsStatusWlanMngmtStationTableEntryBssid,
            lcsStatusWlanMngmtStationTableEntryClientSteering,
            lcsStatusWlanMngmtStationTableEntryOperationMode,
            lcsStatusWlanMngmtStationTableEntryFastRoaming,
            lcsStatusWlanMngmtStationTableEntryUserName,
            lcsStatusWlanMngmtStationTableEntryRadioBand,
            lcsStatusWlanMngmtStationTableEntryRadioChannel,
            lcsStatusWlanMngmtNetCountEntryNumStations,
            lcsStatusWlanMngmtStationTableEntry11acBeamforming,
            lcsStatusWlanMngmtStationTableEntryDhcpHostname
          }
    STATUS     current
    DESCRIPTION
            ""
    ::= { lcsTraps 66 }

-- {NOTIFICATION} 1.3.6.1.4.1.2356.11.0.0.67
lcsTrapsNetworks NOTIFICATION-TYPE
    OBJECTS {
            sysDescr,
            sysName,
            lcsStatusSnmpEventEntryCount,
            lcsStatusWlanMngmtNetworksEntryBssid,
            lcsStatusWlanMngmtNetworksEntryApWlanMac,
            lcsStatusWlanMngmtNetworksEntryNetNumber,
            lcsStatusWlanMngmtNetworksEntryName,
            lcsStatusWlanMngmtNetworksEntryClientCount,
            lcsStatusWlanMngmtNetworksEntryValid
          }
    STATUS     current
    DESCRIPTION
            ""
    ::= { lcsTraps 67 }

-- {NOTIFICATION} 1.3.6.1.4.1.2356.11.0.0.68
lcsTrapsNetworkcounts NOTIFICATION-TYPE
    OBJECTS {
            sysDescr,
            sysName,
            lcsStatusSnmpEventEntryCount,
            lcsStatusWlanMngmtNetCountEntryName,
            lcsStatusWlanMngmtNetCountEntryNumRadios,
            lcsStatusWlanMngmtNetCountEntryNumStations,
            lcsStatusWlanMngmtNetCountEntrySsid,
            lcsStatusWlanMngmtNetCountEntryBridgeInterface
          }
    STATUS     current
    DESCRIPTION
            ""
    ::= { lcsTraps 68 }

-- {NOTIFICATION} 1.3.6.1.4.1.2356.11.0.0.69
lcsTrapsApCounter NOTIFICATION-TYPE
    OBJECTS {
            sysDescr,
            sysName,
            lcsStatusSnmpEventEntryCount,
            lcsStatusWlanMngmtConnectedExpectedAp,
            lcsStatusWlanMngmtConnectedManagedAp,
            lcsStatusWlanMngmtConnectedNewAp,
            lcsStatusWlanMngmtNextdoorAp
          }
    STATUS     current
    DESCRIPTION
            ""
    ::= { lcsTraps 69 }

-- {NOTIFICATION} 1.3.6.1.4.1.2356.11.0.0.72
lcsTrapsUtmcontentfilter NOTIFICATION-TYPE
    OBJECTS {
            sysDescr,
            sysName,
            lcsStatusSnmpEventEntryCount,
            lcsStatusUtmCfLogEntrySystemTime,
            lcsStatusUtmCfLogEntryCause,
            lcsStatusUtmCfLogEntryUserProfile,
            lcsStatusUtmCfLogEntryCategoryError,
            lcsStatusUtmCfLogEntryUrl
          }
    STATUS     current
    DESCRIPTION
            ""
    ::= { lcsTraps 72 }

-- {NOTIFICATION} 1.3.6.1.4.1.2356.11.0.0.73
lcsTrapsCerttabmod NOTIFICATION-TYPE
    OBJECTS {
            sysDescr,
            sysName,
            lcsStatusSnmpEventEntryCount,
            lcsStatusCertsScepCaCertsCertsStatusTabEntryIndex,
            lcsStatusCertsScepCaCertsCertsStatusTabEntrySerialnumber,
            lcsStatusCertsScepCaCertsCertsStatusTabEntryStatus,
            lcsStatusCertsScepCaCertsCertsStatusTabEntryCreationDate,
            lcsStatusCertsScepCaCertsCertsStatusTabEntryEndTime,
            lcsStatusCertsScepCaCertsCertsStatusTabEntryRevTime,
            lcsStatusCertsScepCaCertsCertsStatusTabEntryRevReas,
            lcsStatusCertsScepCaCertsCertsStatusTabEntryMacAddress,
            lcsStatusCertsScepCaCertsCertsStatusTabEntryDn
          }
    STATUS     current
    DESCRIPTION
            ""
    ::= { lcsTraps 73 }

-- {NOTIFICATION} 1.3.6.1.4.1.2356.11.0.0.74
lcsTrapsPendlistmod NOTIFICATION-TYPE
    OBJECTS {
            sysDescr,
            sysName,
            lcsStatusSnmpEventEntryCount
          }
    STATUS     current
    DESCRIPTION
            ""
    ::= { lcsTraps 74 }

-- {NOTIFICATION} 1.3.6.1.4.1.2356.11.0.0.75
lcsTrapsNextdoorAp NOTIFICATION-TYPE
    OBJECTS {
            sysDescr,
            sysName,
            lcsStatusSnmpEventEntryCount,
            lcsStatusWlanMngmtNextdoorAp,
            lcsStatusWlanMngmtApStatusNextdoorApEntryApLanMac,
            lcsStatusWlanMngmtApStatusNextdoorApEntryIpAddress,
            lcsStatusWlanMngmtApStatusNextdoorApEntryName,
            lcsStatusWlanMngmtApStatusNextdoorApEntryLocation,
            lcsStatusWlanMngmtApStatusNextdoorApEntryValid,
            lcsStatusWlanMngmtApStatusNextdoorApEntryWlcName
          }
    STATUS     current
    DESCRIPTION
            ""
    ::= { lcsTraps 75 }

-- {NOTIFICATION} 1.3.6.1.4.1.2356.11.0.0.76
lcsTrapsWlcTunnels NOTIFICATION-TYPE
    OBJECTS {
            sysDescr,
            sysName,
            lcsStatusSnmpEventEntryCount,
            lcsStatusWlanMngmtWlcTunnelsNumberOfWlcConn,
            lcsStatusWlanMngmtWlcTunnelsActiveConnections,
            lcsStatusWlanMngmtWlcTunnelsWlcConnectionsEntryIpAddress,
            lcsStatusWlanMngmtWlcTunnelsWlcConnectionsEntryPort,
            lcsStatusWlanMngmtWlcTunnelsWlcConnectionsEntryResult,
            lcsStatusWlanMngmtWlcTunnelsWlcConnectionsEntryName,
            lcsStatusWlanMngmtWlcTunnelsWlcConnectionsEntryState,
            lcsStatusWlanMngmtWlcTunnelsWlcConnectionsEntryValid
          }
    STATUS     current
    DESCRIPTION
            ""
    ::= { lcsTraps 76 }

-- {NOTIFICATION} 1.3.6.1.4.1.2356.11.0.0.77
lcsTrapsLicensemgtexpire NOTIFICATION-TYPE
    OBJECTS {
            sysDescr,
            sysName,
            lcsStatusSnmpEventEntryCount,
            lcsStatusConfigFeaturesEntryFeature,
            lcsStatusConfigFeaturesEntryExpires,
            lcsStatusConfigFeaturesEntryExpire,
            lcsStatusConfigFeaturesEntryState,
            lcsStatusConfigFeaturesEntryIndex,
            lcsStatusConfigFeaturesEntryCount
          }
    STATUS     current
    DESCRIPTION
            ""
    ::= { lcsTraps 77 }

-- {NOTIFICATION} 1.3.6.1.4.1.2356.11.0.0.78
lcsTrapsVdslstate NOTIFICATION-TYPE
    OBJECTS {
            sysDescr,
            sysName,
            lcsStatusSnmpEventEntryCount,
            lcsStatusVdslLineState
          }
    STATUS     current
    DESCRIPTION
            ""
    ::= { lcsTraps 78 }

-- {NOTIFICATION} 1.3.6.1.4.1.2356.11.0.0.79
lcsTrapsScrptuplstart NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress
          }
    STATUS     current
    DESCRIPTION
            ""
    ::= { lcsTraps 79 }

-- {NOTIFICATION} 1.3.6.1.4.1.2356.11.0.0.80
lcsTrapsScrptdnlstart NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress
          }
    STATUS     current
    DESCRIPTION
            ""
    ::= { lcsTraps 80 }

-- {NOTIFICATION} 1.3.6.1.4.1.2356.11.0.0.81
lcsTrapsIpv6fwflt NOTIFICATION-TYPE
    OBJECTS {
            sysDescr,
            sysName,
            lcsStatusSnmpEventEntryCount,
            lcsStatusIpv6FirewallLogTableEntrySystemTime,
            lcsStatusIpv6FirewallLogTableEntrySrcAddress,
            lcsStatusIpv6FirewallLogTableEntryDstAddress,
            lcsStatusIpv6FirewallLogTableEntryProt,
            lcsStatusIpv6FirewallLogTableEntrySrcPort,
            lcsStatusIpv6FirewallLogTableEntryDstPort,
            lcsStatusIpv6FirewallLogTableEntryFilterRule,
            lcsStatusIpv6FirewallLogTableEntryLimit,
            lcsStatusIpv6FirewallLogTableEntryThreshold,
            lcsStatusIpv6FirewallLogTableEntryAction
          }
    STATUS     current
    DESCRIPTION
            "-- empty --"
    ::= { lcsTraps 81 }

-- {NOTIFICATION} 1.3.6.1.4.1.2356.11.0.0.82
lcsTrapsWwanStates NOTIFICATION-TYPE
    OBJECTS {
            sysDescr,
            sysName,
            lcsStatusSnmpEventEntryCount,
            lcsStatusModemMobileState,
            lcsStatusModemMobileRegistration
          }
    STATUS     current
    DESCRIPTION
            "-- empty --"
    ::= { lcsTraps 82 }

-- {NOTIFICATION} 1.3.6.1.4.1.2356.11.0.0.83
lcsTrapsDS-Lite NOTIFICATION-TYPE
    OBJECTS {
            sysDescr,
            sysName,
            lcsStatusSnmpEventEntryCount,
            lcsStatusDsLiteConnectionsEntryPeer,
            lcsStatusDsLiteConnectionsEntryState,
            lcsStatusDsLiteConnectionsEntryLastError,
            lcsStatusDsLiteConnectionsEntryIpv4Address,
            lcsStatusDsLiteConnectionsEntryPhysConn,
            lcsStatusDsLiteConnectionsEntryAftrName,
            lcsStatusDsLiteConnectionsEntryAftrIpv6Address,
            lcsStatusDsLiteConnectionsEntryConnTime
          }
    STATUS     current
    DESCRIPTION
            "DS-LITE connection status"
    ::= { lcsTraps 83 }

-- {NOTIFICATION} 1.3.6.1.4.1.2356.11.0.0.84
lcsTrapsVolumebudget NOTIFICATION-TYPE
    OBJECTS {
            sysDescr,
            sysName,
            lcsStatusSnmpEventEntryCount,
            lcsStatusChargingVolumeBudgetsEntryPeer,
            lcsStatusChargingVolumeBudgetsEntryDataMb,
            lcsStatusChargingVolumeBudgetsEntryDataKb,
            lcsStatusChargingVolumeBudgetsEntryLimitMb,
            lcsStatusChargingVolumeBudgetsEntryPercent,
            lcsStatusChargingVolumeBudgetsEntryFlags,
            lcsStatusChargingVolumeBudgetsEntryMonth,
            lcsStatusChargingVolumeBudgetsEntryYear
          }
    STATUS     current
    DESCRIPTION
            "-- empty --"
    ::= { lcsTraps 84 }

-- {NOTIFICATION} 1.3.6.1.4.1.2356.11.0.0.85
lcsTrapsL2TP-Endpoints NOTIFICATION-TYPE
    OBJECTS {
            sysDescr,
            sysName,
            lcsStatusSnmpEventEntryCount,
            lcsStatusL2tpNumEndpoints,
            lcsStatusL2tpEndpointsEntryL2tpEndpoint,
            lcsStatusL2tpEndpointsEntryState,
            lcsStatusL2tpEndpointsEntryLastError,
            lcsStatusL2tpEndpointsEntryMode,
            lcsStatusL2tpEndpointsEntryPhysConnection,
            lcsStatusL2tpEndpointsEntryGateway,
            lcsStatusL2tpEndpointsEntrySessions,
            lcsStatusL2tpEndpointsEntryConnTime,
            lcsStatusL2tpEndpointsEntryEmbeddedErrorMessage
          }
    STATUS     current
    DESCRIPTION
            "L2TP tunnel end point status"
    ::= { lcsTraps 85 }

-- {NOTIFICATION} 1.3.6.1.4.1.2356.11.0.0.86
lcsTrapsL2TP-Connections NOTIFICATION-TYPE
    OBJECTS {
            sysDescr,
            sysName,
            lcsStatusSnmpEventEntryCount,
            lcsStatusL2tpNumConnections,
            lcsStatusL2tpConnectionsEntryPeer,
            lcsStatusL2tpConnectionsEntryState,
            lcsStatusL2tpConnectionsEntryLastError,
            lcsStatusL2tpConnectionsEntryMode,
            lcsStatusL2tpConnectionsEntryShTime,
            lcsStatusL2tpConnectionsEntryL2tpEndpoint,
            lcsStatusL2tpConnectionsEntryPeerAddress,
            lcsStatusL2tpConnectionsEntryIpAddress,
            lcsStatusL2tpConnectionsEntryDnsDefault,
            lcsStatusL2tpConnectionsEntryDnsBackup,
            lcsStatusL2tpConnectionsEntryNbnsDefault,
            lcsStatusL2tpConnectionsEntryNbnsBackup,
            lcsStatusL2tpConnectionsEntryConnTime
          }
    STATUS     current
    DESCRIPTION
            "L2TP connection status"
    ::= { lcsTraps 86 }

-- {NOTIFICATION} 1.3.6.1.4.1.2356.11.0.0.87
lcsTrapsLoginBlocked NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew
          }
    STATUS     current
    DESCRIPTION
            "Login is temporarily blocked"
    ::= { lcsTraps 87 }

-- {NOTIFICATION} 1.3.6.1.4.1.2356.11.0.0.88
lcsTrapsWidsAlarm NOTIFICATION-TYPE
    OBJECTS {
            sysDescr,
            sysName,
            lcsStatusSnmpEventEntryCount,
            lcsStatusWlanMngmtWIdsAlarmsEntryMacAddress,
            lcsStatusWlanMngmtWIdsAlarmsEntryIfc,
            lcsStatusWlanMngmtWIdsAlarmsEntrySignature,
            lcsStatusWlanMngmtWIdsAlarmsEntryName,
            lcsStatusWlanMngmtWIdsAlarmsEntryCounter,
            lcsStatusWlanMngmtWIdsAlarmsEntryAlarmState
          }
    STATUS     current
    DESCRIPTION
            "-- empty --"
    ::= { lcsTraps 88 }

-- {NOTIFICATION} 1.3.6.1.4.1.2356.11.0.0.89
lcsTrapsVdslstate2 NOTIFICATION-TYPE
    OBJECTS {
            sysDescr,
            sysName,
            lcsStatusSnmpEventEntryCount,
            lcsStatusXdslVdsl1LineState,
            lcsStatusXdslVdsl2LineState
          }
    STATUS     current
    DESCRIPTION
            "-- empty --"
    ::= { lcsTraps 89 }

-- {NOTIFICATION} 1.3.6.1.4.1.2356.11.0.0.102
lcsTrapsL2TP-Ethernet NOTIFICATION-TYPE
    OBJECTS {
            sysDescr,
            sysName,
            lcsStatusSnmpEventEntryCount,
            lcsStatusL2tpNumEthernet,
            lcsStatusL2tpEthernetEntryRemoteEnd,
            lcsStatusL2tpEthernetEntryL2tpEndpoint,
            lcsStatusL2tpEthernetEntryState,
            lcsStatusL2tpEthernetEntryMode,
            lcsStatusL2tpEthernetEntryInterface,
            lcsStatusL2tpEthernetEntryBrgAddr,
            lcsStatusL2tpEthernetEntryConnTime
          }
    STATUS     current
    DESCRIPTION
            "L2TP Ethernet pseudowire status"
    ::= { lcsTraps 102 }

-- {NOTIFICATION} 1.3.6.1.4.1.2356.11.0.0.1000
lcsTrapsSpgtreePortstatchg NOTIFICATION-TYPE
    OBJECTS {
            sysDescr,
            sysName,
            lcsStatusSnmpEventEntryCount,
            lcsStatusLanBridgeSpanningTreePortTableEntryDescription,
            lcsStatusLanBridgeSpanningTreePortTableEntryState,
            lcsStatusLanBridgeSpanningTreePortTableEntryPathCost
          }
    STATUS     current
    DESCRIPTION
            ""
    ::= { lcsTraps 1000 }

-- {NOTIFICATION} 1.3.6.1.4.1.2356.11.0.0.1001
lcsTrapsSpgtreeRstpstatchg NOTIFICATION-TYPE
    OBJECTS {
            sysDescr,
            sysName,
            lcsStatusSnmpEventEntryCount,
            lcsStatusLanBridgeSpanningTreeRstpPortTableEntryDescription,
            lcsStatusLanBridgeSpanningTreeRstpPortTableEntryRole,
            lcsStatusLanBridgeSpanningTreeRstpPortTableEntryLearning,
            lcsStatusLanBridgeSpanningTreeRstpPortTableEntryForwarding,
            lcsStatusLanBridgeSpanningTreeRstpPortTableEntryEdgePort,
            lcsStatusLanBridgeSpanningTreeRstpPortTableEntryProtocolVersion,
            lcsStatusLanBridgeSpanningTreeRstpPortTableEntryPathCost
          }
    STATUS     current
    DESCRIPTION
            ""
    ::= { lcsTraps 1001 }

-- {NOTIFICATION} 1.3.6.1.4.1.2356.11.0.0.1002
lcsTrapsSpgtreeRootportchg NOTIFICATION-TYPE
    OBJECTS {
            sysDescr,
            sysName,
            lcsStatusSnmpEventEntryCount,
            lcsStatusLanBridgeSpanningTreeRootBridge,
            lcsStatusLanBridgeSpanningTreeRootPort,
            lcsStatusLanBridgeSpanningTreeRootPathCost
          }
    STATUS     current
    DESCRIPTION
            ""
    ::= { lcsTraps 1002 }

-- {NOTIFICATION} 1.3.6.1.4.1.2356.11.0.0.2000
lcsTrapsHttpTunnelOpen NOTIFICATION-TYPE
    OBJECTS {
            sysDescr,
            sysName,
            lcsStatusSnmpEventEntryCount,
            lcsStatusTcpIpHttpActiveTunnelsEntryIndex,
            lcsStatusTcpIpHttpActiveTunnelsEntryRemoteAddress,
            lcsStatusTcpIpHttpActiveTunnelsEntryRemotePort,
            lcsStatusTcpIpHttpActiveTunnelsEntryLocalHost,
            lcsStatusTcpIpHttpActiveTunnelsEntryLocalPort,
            lcsStatusTcpIpHttpActiveTunnelsEntryIdleTime,
            lcsStatusTcpIpHttpActiveTunnelsEntryLocalRtgTag
          }
    STATUS     current
    DESCRIPTION
            "HTTP tunnel opened successful"
    ::= { lcsTraps 2000 }

-- {NOTIFICATION} 1.3.6.1.4.1.2356.11.0.0.2001
lcsTrapsHttpTunnelClose NOTIFICATION-TYPE
    OBJECTS {
            sysDescr,
            sysName,
            lcsStatusSnmpEventEntryCount,
            lcsStatusTcpIpHttpActiveTunnelsEntryIndex
          }
    STATUS     current
    DESCRIPTION
            "HTTP tunnel closed successful"
    ::= { lcsTraps 2001 }

-- {NOTIFICATION} 1.3.6.1.4.1.2356.11.0.0.3000
lcsTrapsLanauthuseradd NOTIFICATION-TYPE
    OBJECTS {
            sysDescr,
            sysName,
            lcsStatusSnmpEventEntryCount,
            lcsSetupPublicSpotModuleUserTableEntryName,
            lcsSetupPublicSpotModuleUserTableEntryComment
          }
    STATUS     current
    DESCRIPTION
            ""
    ::= { lcsTraps 3000 }

-- {NOTIFICATION} 1.3.6.1.4.1.2356.11.0.0.3001
lcsTrapsLanauthuserdel NOTIFICATION-TYPE
    OBJECTS {
            sysDescr,
            sysName,
            lcsStatusSnmpEventEntryCount,
            lcsSetupPublicSpotModuleUserTableEntryName,
            lcsSetupPublicSpotModuleUserTableEntryComment
          }
    STATUS     current
    DESCRIPTION
            ""
    ::= { lcsTraps 3001 }

-- {NOTIFICATION} 1.3.6.1.4.1.2356.11.0.0.3002
lcsTrapsLanauthsessionstart NOTIFICATION-TYPE
    OBJECTS {
            sysDescr,
            sysName,
            lcsStatusSnmpEventEntryCount,
            lcsStatusPublicSpotStationTableEntryMacAddress,
            lcsStatusPublicSpotStationTableEntryName,
            lcsStatusPublicSpotStationTableEntrySessionId
          }
    STATUS     current
    DESCRIPTION
            ""
    ::= { lcsTraps 3002 }

-- {NOTIFICATION} 1.3.6.1.4.1.2356.11.0.0.3003
lcsTrapsLanauthsessionend NOTIFICATION-TYPE
    OBJECTS {
            sysDescr,
            sysName,
            lcsStatusSnmpEventEntryCount,
            lcsStatusPublicSpotStationTableEntryMacAddress,
            lcsStatusPublicSpotStationTableEntryName,
            lcsStatusPublicSpotStationTableEntrySessionId,
            lcsStatusPublicSpotStationTableEntryTxBytesNew,
            lcsStatusPublicSpotStationTableEntryTxBytes,
            lcsStatusPublicSpotStationTableEntryRxBytesNew,
            lcsStatusPublicSpotStationTableEntryRxBytes,
            lcsStatusPublicSpotStationTableEntryTxPackets,
            lcsStatusPublicSpotStationTableEntryRxPackets,
            lcsStatusPublicSpotStationTableEntryLoginTime
          }
    STATUS     current
    DESCRIPTION
            ""
    ::= { lcsTraps 3003 }

-- {NOTIFICATION} 1.3.6.1.4.1.2356.11.0.0.4000
lcsTrapsTempmonovertemp NOTIFICATION-TYPE
    OBJECTS {
            sysDescr,
            sysName,
            lcsStatusSnmpEventEntryCount,
            lcsStatusHardwareInfoTemperatureDegrees
          }
    STATUS     current
    DESCRIPTION
            "Device temperature exceeds the upper tempreature limit"
    ::= { lcsTraps 4000 }

-- {NOTIFICATION} 1.3.6.1.4.1.2356.11.0.0.4001
lcsTrapsTempmonnoovertemp NOTIFICATION-TYPE
    OBJECTS {
            sysDescr,
            sysName,
            lcsStatusSnmpEventEntryCount,
            lcsStatusHardwareInfoTemperatureDegrees
          }
    STATUS     current
    DESCRIPTION
            "Device temperature falls below the upper temperature limit and is in the normal operating range again"
    ::= { lcsTraps 4001 }

-- {NOTIFICATION} 1.3.6.1.4.1.2356.11.0.0.4002
lcsTrapsTempmonundertemp NOTIFICATION-TYPE
    OBJECTS {
            sysDescr,
            sysName,
            lcsStatusSnmpEventEntryCount,
            lcsStatusHardwareInfoTemperatureDegrees
          }
    STATUS     current
    DESCRIPTION
            "Device temperature under-runs the lower temperature limit"
    ::= { lcsTraps 4002 }

-- {NOTIFICATION} 1.3.6.1.4.1.2356.11.0.0.4003
lcsTrapsTempmonnoundertemp NOTIFICATION-TYPE
    OBJECTS {
            sysDescr,
            sysName,
            lcsStatusSnmpEventEntryCount,
            lcsStatusHardwareInfoTemperatureDegrees
          }
    STATUS     current
    DESCRIPTION
            "Device temperature rises above the lower temperature limit and is in the normal operating range again"
    ::= { lcsTraps 4003 }

-- {NOTIFICATION} 1.3.6.1.4.1.2356.11.0.0.4500
lcsTrapsVoltmonovervolt NOTIFICATION-TYPE
    OBJECTS {
            sysDescr,
            sysName,
            lcsStatusSnmpEventEntryCount,
            lcsStatusHardwareInfoWideRangePowerSupplyMv
          }
    STATUS     current
    DESCRIPTION
            "-- empty --"
    ::= { lcsTraps 4500 }

-- {NOTIFICATION} 1.3.6.1.4.1.2356.11.0.0.4501
lcsTrapsVoltmonnoovervolt NOTIFICATION-TYPE
    OBJECTS {
            sysDescr,
            sysName,
            lcsStatusSnmpEventEntryCount,
            lcsStatusHardwareInfoWideRangePowerSupplyMv
          }
    STATUS     current
    DESCRIPTION
            "-- empty --"
    ::= { lcsTraps 4501 }

-- {NOTIFICATION} 1.3.6.1.4.1.2356.11.0.0.4502
lcsTrapsVoltmonundervolt NOTIFICATION-TYPE
    OBJECTS {
            sysDescr,
            sysName,
            lcsStatusSnmpEventEntryCount,
            lcsStatusHardwareInfoWideRangePowerSupplyMv
          }
    STATUS     current
    DESCRIPTION
            "-- empty --"
    ::= { lcsTraps 4502 }

-- {NOTIFICATION} 1.3.6.1.4.1.2356.11.0.0.4503
lcsTrapsVoltmonnoundervolt NOTIFICATION-TYPE
    OBJECTS {
            sysDescr,
            sysName,
            lcsStatusSnmpEventEntryCount,
            lcsStatusHardwareInfoWideRangePowerSupplyMv
          }
    STATUS     current
    DESCRIPTION
            "-- empty --"
    ::= { lcsTraps 4503 }

-- {NOTIFICATION} 1.3.6.1.4.1.2356.11.0.0.5001
lcsTrapsLanDownshift NOTIFICATION-TYPE
    OBJECTS {
            sysDescr,
            sysName,
            lcsStatusSnmpEventEntryCount,
            lcsStatusLanInterfacesEntryIfc,
            lcsStatusLanInterfacesEntryConnector,
            lcsStatusLanInterfacesEntryDownshift
          }
    STATUS     current
    DESCRIPTION
            "LAN interface downshifts its speed to 100 Mbit"
    ::= { lcsTraps 5001 }

-- {NOTIFICATION} 1.3.6.1.4.1.2356.11.0.0.5002
lcsTrapsLanOvertempThrottle NOTIFICATION-TYPE
    OBJECTS {
            sysDescr,
            sysName,
            lcsStatusSnmpEventEntryCount
          }
    STATUS     current
    DESCRIPTION
            "Throttling of LAN Speed due to temperature exceedance active"
    ::= { lcsTraps 5002 }

-- {NOTIFICATION} 1.3.6.1.4.1.2356.11.0.0.5003
lcsTrapsLanOvertempThrottleEnd NOTIFICATION-TYPE
    OBJECTS {
            sysDescr,
            sysName,
            lcsStatusSnmpEventEntryCount
          }
    STATUS     current
    DESCRIPTION
            "Throttling of LAN Speed due to temperature exceedance stopped"
    ::= { lcsTraps 5003 }

-- {NOTIFICATION} 1.3.6.1.4.1.2356.11.0.0.5004
lcsTrapsLanOvertempThrottleRecommend NOTIFICATION-TYPE
    OBJECTS {
            sysDescr,
            sysName,
            lcsStatusSnmpEventEntryCount
          }
    STATUS     current
    DESCRIPTION
            "Throttling of LAN Speed due to temperature exceedance recommended"
    ::= { lcsTraps 5004 }

-- {NOTIFICATION} 1.3.6.1.4.1.2356.11.0.0.5101
lcsTrapsEthPortDownshift NOTIFICATION-TYPE
    OBJECTS {
            sysDescr,
            sysName,
            lcsStatusSnmpEventEntryCount,
            lcsStatusEthernetPortsPortsEntryPort,
            lcsStatusEthernetPortsPortsEntryAssignment,
            lcsStatusEthernetPortsPortsEntryDownshift
          }
    STATUS     current
    DESCRIPTION
            "Ethernet interface downshifts its speed to 100 Mbit"
    ::= { lcsTraps 5101 }

-- {NOTIFICATION} 1.3.6.1.4.1.2356.11.0.0.6100
lcsTrapsWlanConfadaptRadiochannel NOTIFICATION-TYPE
    OBJECTS {
            sysDescr,
            sysName,
            lcsStatusSnmpEventEntryCount
          }
    STATUS     current
    DESCRIPTION
            ""
    ::= { lcsTraps 6100 }

-- {NOTIFICATION} 1.3.6.1.4.1.2356.11.0.0.6101
lcsTrapsWlanConfadaptRadiomode NOTIFICATION-TYPE
    OBJECTS {
            sysDescr,
            sysName,
            lcsStatusSnmpEventEntryCount,
            lcsStatusWlanNetworksEntryRadioMode
          }
    STATUS     current
    DESCRIPTION
            ""
    ::= { lcsTraps 6101 }

-- {NOTIFICATION} 1.3.6.1.4.1.2356.11.0.0.6102
lcsTrapsWlanConfadaptBasicRate NOTIFICATION-TYPE
    OBJECTS {
            sysDescr,
            sysName,
            lcsStatusSnmpEventEntryCount
          }
    STATUS     current
    DESCRIPTION
            ""
    ::= { lcsTraps 6102 }

-- {NOTIFICATION} 1.3.6.1.4.1.2356.11.0.0.6103
lcsTrapsWlanConfadaptEapolRate NOTIFICATION-TYPE
    OBJECTS {
            sysDescr,
            sysName,
            lcsStatusSnmpEventEntryCount
          }
    STATUS     current
    DESCRIPTION
            ""
    ::= { lcsTraps 6103 }

-- {NOTIFICATION} 1.3.6.1.4.1.2356.11.0.0.6104
lcsTrapsWlanConfadaptEncryption NOTIFICATION-TYPE
    OBJECTS {
            sysDescr,
            sysName,
            lcsStatusSnmpEventEntryCount
          }
    STATUS     current
    DESCRIPTION
            "-- empty --"
    ::= { lcsTraps 6104 }

-- {NOTIFICATION} 1.3.6.1.4.1.2356.11.0.0.6200
lcsTrapsWlanAlarmP2pSignal NOTIFICATION-TYPE
    OBJECTS {
            sysDescr,
            sysName,
            lcsStatusSnmpEventEntryCount,
            lcsStatusWlanInterpointsAccesspointListEntryAlarmState,
            lcsStatusWlanInterpointsAccesspointListEntryRxPhySignal,
            lcsStatusWlanInterpointsAccesspointListEntryLinkPhySignal
          }
    STATUS     current
    DESCRIPTION
            ""
    ::= { lcsTraps 6200 }

-- {NOTIFICATION} 1.3.6.1.4.1.2356.11.0.0.6201
lcsTrapsWlanAlarmP2pTxtotretries NOTIFICATION-TYPE
    OBJECTS {
            sysDescr,
            sysName,
            lcsStatusSnmpEventEntryCount,
            lcsStatusWlanInterpointsAccesspointListEntryAlarmState,
            lcsStatusWlanInterpointsAccesspointListEntryTxPackets,
            lcsStatusWlanInterpointsAccesspointListEntryTotalRetries
          }
    STATUS     current
    DESCRIPTION
            ""
    ::= { lcsTraps 6201 }

-- {NOTIFICATION} 1.3.6.1.4.1.2356.11.0.0.6202
lcsTrapsWlanAlarmP2pTxerrors NOTIFICATION-TYPE
    OBJECTS {
            sysDescr,
            sysName,
            lcsStatusSnmpEventEntryCount,
            lcsStatusWlanInterpointsAccesspointListEntryAlarmState,
            lcsStatusWlanInterpointsAccesspointListEntryTxPackets,
            lcsStatusWlanInterpointsAccesspointListEntryTxErrors
          }
    STATUS     current
    DESCRIPTION
            ""
    ::= { lcsTraps 6202 }

-- {NOTIFICATION} 1.3.6.1.4.1.2356.11.0.0.6203
lcsTrapsWlanAlarmNetwSignal NOTIFICATION-TYPE
    OBJECTS {
            sysDescr,
            sysName,
            lcsStatusSnmpEventEntryCount,
            lcsStatusWlanNetworksEntryAlarmState
          }
    STATUS     current
    DESCRIPTION
            ""
    ::= { lcsTraps 6203 }

-- {NOTIFICATION} 1.3.6.1.4.1.2356.11.0.0.6204
lcsTrapsWlanAlarmNetwTxtotretries NOTIFICATION-TYPE
    OBJECTS {
            sysDescr,
            sysName,
            lcsStatusSnmpEventEntryCount,
            lcsStatusWlanNetworksEntryAlarmState
          }
    STATUS     current
    DESCRIPTION
            ""
    ::= { lcsTraps 6204 }

-- {NOTIFICATION} 1.3.6.1.4.1.2356.11.0.0.6205
lcsTrapsWlanAlarmNetwTxerrors NOTIFICATION-TYPE
    OBJECTS {
            sysDescr,
            sysName,
            lcsStatusSnmpEventEntryCount,
            lcsStatusWlanNetworksEntryAlarmState
          }
    STATUS     current
    DESCRIPTION
            ""
    ::= { lcsTraps 6205 }

-- {NOTIFICATION} 1.3.6.1.4.1.2356.11.0.0.6206
lcsTrapsWlanAlarmClientSignal NOTIFICATION-TYPE
    OBJECTS {
            sysDescr,
            sysName,
            lcsStatusSnmpEventEntryCount,
            lcsStatusWlanClientIfcsEntryAlarmState,
            lcsStatusWlanClientIfcsEntryPhySignal,
            lcsStatusWlanClientIfcsEntryLinkPhySignal
          }
    STATUS     current
    DESCRIPTION
            ""
    ::= { lcsTraps 6206 }

-- {NOTIFICATION} 1.3.6.1.4.1.2356.11.0.0.6207
lcsTrapsWlanAlarmClientTxtotretries NOTIFICATION-TYPE
    OBJECTS {
            sysDescr,
            sysName,
            lcsStatusSnmpEventEntryCount,
            lcsStatusWlanClientIfcsEntryAlarmState,
            lcsStatusWlanClientIfcsEntryTxPackets,
            lcsStatusWlanClientIfcsEntryTotalRetries
          }
    STATUS     current
    DESCRIPTION
            ""
    ::= { lcsTraps 6207 }

-- {NOTIFICATION} 1.3.6.1.4.1.2356.11.0.0.6208
lcsTrapsWlanAlarmClientTxerrors NOTIFICATION-TYPE
    OBJECTS {
            sysDescr,
            sysName,
            lcsStatusSnmpEventEntryCount,
            lcsStatusWlanClientIfcsEntryAlarmState,
            lcsStatusWlanClientIfcsEntryTxPackets,
            lcsStatusWlanClientIfcsEntryTotalRetries
          }
    STATUS     current
    DESCRIPTION
            ""
    ::= { lcsTraps 6208 }

-- {NOTIFICATION} 1.3.6.1.4.1.2356.11.0.0.6300
lcsTrapsWlanDfsAllblocked NOTIFICATION-TYPE
    OBJECTS {
            sysDescr,
            sysName,
            lcsStatusSnmpEventEntryCount
          }
    STATUS     current
    DESCRIPTION
            "-- empty --"
    ::= { lcsTraps 6300 }

-- {NOTIFICATION} 1.3.6.1.4.1.2356.11.0.0.7000
lcsTrapsUplinvversion NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress,
            lcsStatusConfigEventLogEntryInfo1,
            lcsStatusConfigEventLogEntryInfo2
          }
    STATUS     current
    DESCRIPTION
            ""
    ::= { lcsTraps 7000 }

-- {NOTIFICATION} 1.3.6.1.4.1.2356.11.0.0.7001
lcsTrapsUplfileexists NOTIFICATION-TYPE
    OBJECTS {
            sysDescr,
            sysName,
            lcsStatusSnmpEventEntryCount,
            lcsStatusConfigEventLogEntrySystemTime,
            lcsStatusConfigEventLogEntryEvent,
            lcsStatusConfigEventLogEntryAccess,
            lcsStatusConfigEventLogEntryIpAddressNew,
            lcsStatusConfigEventLogEntryIpAddress,
            lcsStatusConfigEventLogEntryInfo1,
            lcsStatusConfigEventLogEntryInfo2
          }
    STATUS     current
    DESCRIPTION
            ""
    ::= { lcsTraps 7001 }

-- {NOTIFICATION} 1.3.6.1.4.1.2356.11.0.0.8000
lcsTrapsSmsinboxmsgchanged NOTIFICATION-TYPE
    OBJECTS {
            sysDescr,
            sysName,
            lcsStatusSnmpEventEntryCount,
            lcsStatusSmsInboxEntryRowstatus
          }
    STATUS     current
    DESCRIPTION
            "-- empty --"
    ::= { lcsTraps 8000 }

-- {NOTIFICATION} 1.3.6.1.4.1.2356.11.0.0.8001
lcsTrapsSmsoutboxmsgchanged NOTIFICATION-TYPE
    OBJECTS {
            sysDescr,
            sysName,
            lcsStatusSnmpEventEntryCount,
            lcsStatusSmsOutboxEntryRowstatus
          }
    STATUS     current
    DESCRIPTION
            "-- empty --"
    ::= { lcsTraps 8001 }

-- {NOTIFICATION} 1.3.6.1.4.1.2356.11.0.0.8002
lcsTrapsSmsoutboxcleared NOTIFICATION-TYPE
    OBJECTS {
            sysDescr,
            sysName,
            lcsStatusSnmpEventEntryCount
          }
    STATUS     current
    DESCRIPTION
            "-- empty --"
    ::= { lcsTraps 8002 }

-- {NOTIFICATION} 1.3.6.1.4.1.2356.11.0.0.8003
lcsTrapsSmsinboxcleared NOTIFICATION-TYPE
    OBJECTS {
            sysDescr,
            sysName,
            lcsStatusSnmpEventEntryCount
          }
    STATUS     current
    DESCRIPTION
            "-- empty --"
    ::= { lcsTraps 8003 }

-- {NOTIFICATION} 1.3.6.1.4.1.2356.11.0.0.8100
lcsTrapsSimstatuschanged NOTIFICATION-TYPE
    OBJECTS {
            sysDescr,
            sysName,
            lcsStatusSnmpEventEntryCount,
            lcsStatusModemMobileSimstatusEntrySimstatus,
            lcsStatusModemMobileSimstatusEntrySimIdIccid,
            lcsStatusModemMobileSimstatusEntryProvidername,
            lcsStatusModemMobileSimstatusEntryImsi,
            lcsStatusModemMobileSimstatusEntryPhoneNumber
          }
    STATUS     current
    DESCRIPTION
            "-- empty --"
    ::= { lcsTraps 8100 }

-- {NOTIFICATION} 1.3.6.1.4.1.2356.11.0.0.9700
lcsTrapsUpsConnectionStart NOTIFICATION-TYPE
    OBJECTS {
            sysDescr,
            sysName,
            lcsStatusSnmpEventEntryCount,
            lcsStatusBatteryPackConnected
          }
    STATUS     current
    DESCRIPTION
            "UPS connection established"
    ::= { lcsTraps 9700 }

-- {NOTIFICATION} 1.3.6.1.4.1.2356.11.0.0.9701
lcsTrapsUpsConnectionStop NOTIFICATION-TYPE
    OBJECTS {
            sysDescr,
            sysName,
            lcsStatusSnmpEventEntryCount,
            lcsStatusBatteryPackConnected
          }
    STATUS     current
    DESCRIPTION
            "UPS connection lost"
    ::= { lcsTraps 9701 }

-- {NOTIFICATION} 1.3.6.1.4.1.2356.11.0.0.9702
lcsTrapsUpsPowerFailure NOTIFICATION-TYPE
    OBJECTS {
            sysDescr,
            sysName,
            lcsStatusSnmpEventEntryCount,
            lcsStatusBatteryPackMainsAvailable,
            lcsStatusBatteryPackChargerState
          }
    STATUS     current
    DESCRIPTION
            "Start of power outage"
    ::= { lcsTraps 9702 }

-- {NOTIFICATION} 1.3.6.1.4.1.2356.11.0.0.9703
lcsTrapsUpsPowerAvailable NOTIFICATION-TYPE
    OBJECTS {
            sysDescr,
            sysName,
            lcsStatusSnmpEventEntryCount,
            lcsStatusBatteryPackMainsAvailable,
            lcsStatusBatteryPackChargerState
          }
    STATUS     current
    DESCRIPTION
            "End of power outage"
    ::= { lcsTraps 9703 }

-- {NOTIFICATION} 1.3.6.1.4.1.2356.11.0.0.9704
lcsTrapsUpsBatteryLow NOTIFICATION-TYPE
    OBJECTS {
            sysDescr,
            sysName,
            lcsStatusSnmpEventEntryCount,
            lcsStatusBatteryPackChargeCycles,
            lcsStatusBatteryPackChargeConditionPercent,
            lcsStatusBatteryPackRemainingEnergyWs,
            lcsStatusBatteryPackRemainingTime
          }
    STATUS     current
    DESCRIPTION
            "Battery low"
    ::= { lcsTraps 9704 }

-- {NOTIFICATION} 1.3.6.1.4.1.2356.11.0.0.9705
lcsTrapsUpsBatteryDefect NOTIFICATION-TYPE
    OBJECTS {
            sysDescr,
            sysName,
            lcsStatusSnmpEventEntryCount,
            lcsStatusBatteryPackChargerState,
            lcsStatusBatteryPackChargeCycles,
            lcsStatusBatteryPackBatteryChangeDate
          }
    STATUS     current
    DESCRIPTION
            "Battery defect"
    ::= { lcsTraps 9705 }

-- {NOTIFICATION} 1.3.6.1.4.1.2356.11.0.0.9706
lcsTrapsUpsTempHigh NOTIFICATION-TYPE
    OBJECTS {
            sysDescr,
            sysName,
            lcsStatusSnmpEventEntryCount,
            lcsStatusBatteryPackTemperatureDegrees
          }
    STATUS     current
    DESCRIPTION
            "UPS temperature high"
    ::= { lcsTraps 9706 }

-- {NOTIFICATION} 1.3.6.1.4.1.2356.11.0.0.9707
lcsTrapsUpsTempDown NOTIFICATION-TYPE
    OBJECTS {
            sysDescr,
            sysName,
            lcsStatusSnmpEventEntryCount,
            lcsStatusBatteryPackTemperatureDegrees
          }
    STATUS     current
    DESCRIPTION
            "UPS temperature normal"
    ::= { lcsTraps 9707 }

-- {NOTIFICATION} 1.3.6.1.4.1.2356.11.0.0.9708
lcsTrapsUpsService NOTIFICATION-TYPE
    OBJECTS {
            sysDescr,
            sysName,
            lcsStatusSnmpEventEntryCount,
            lcsStatusBatteryPackServiceRequest,
            lcsStatusBatteryPackServiceDate,
            lcsStatusBatteryPackServiceOperatingTime,
            lcsStatusBatteryPackServiceChargeCycles
          }
    STATUS     current
    DESCRIPTION
            "UPS service request"
    ::= { lcsTraps 9708 }

-- {NOTIFICATION} 1.3.6.1.4.1.2356.11.0.0.9800
lcsTrapsL7DetectionStatus NOTIFICATION-TYPE
    OBJECTS {
            sysDescr,
            sysName,
            lcsStatusSnmpEventEntryCount,
            lcsStatusLay7AppDetTotTrafperAppEntryAppname,
            lcsStatusLay7AppDetTotTrafperAppEntryTxKbytes,
            lcsStatusLay7AppDetTotTrafperAppEntryRxKbytes,
            lcsStatusLay7AppDetTotTrafperAppEntryTxKbytesCurrDay,
            lcsStatusLay7AppDetTotTrafperAppEntryRxKbytesCurrDay,
            lcsStatusLay7AppDetTotTrafperUserEntryUserMac,
            lcsStatusLay7AppDetTotTrafperUserEntryUserName,
            lcsStatusLay7AppDetTotTrafperUserEntryPspotUserName,
            lcsStatusLay7AppDetTotTrafperUserEntryTxKbytes,
            lcsStatusLay7AppDetTotTrafperUserEntryRxKbytes,
            lcsStatusLay7AppDetTotTrafperUserEntryTxKbytesCurrDay,
            lcsStatusLay7AppDetTotTrafperUserEntryRxKbytesCurrDay
          }
    STATUS     current
    DESCRIPTION
            "-- empty --"
    ::= { lcsTraps 9800 }

-- {NOTIFICATION} 1.3.6.1.4.1.2356.11.0.0.10000
lcsTrapsIdsTrapEvent NOTIFICATION-TYPE
    OBJECTS {
            sysDescr,
            sysName,
            lcsStatusSnmpEventEntryCount,
            lcsStatusWlanWIdsEventTableEntryEventType
          }
    STATUS     current
    DESCRIPTION
            "-- empty --"
    ::= { lcsTraps 10000 }
END

-- statistics ---------------------------------------------
-- module-ids     1
-- nodes          699
-- scalars        3325
-- tables         1021
-- rows           1021
-- columns        8605
-- notifications  132
-----------------------------------------------------------
