LCOS-LX-MIB DEFINITIONS ::= BEGIN

IMPORTS
    DisplayString, MacAddress
        FROM SNMPv2-TC
    OBJECT-TYPE, MODULE-IDENTITY, NOTIFICATION-TYPE, enterprises,
    Integer32, Unsigned32, Counter64, IpAddress
        FROM SNMPv2-SMI;


lcosLX MODULE-IDENTITY
    LAST-UPDATED "202607301950Z" -- July 30, 2026
    ORGANIZATION
            "LANCOM Systems GmbH"
    CONTACT-INFO
            "
            Adenauerstrasse 20 / B2
            52146 Wuerselen
            Germany

            Phone:  +49 (0)2405 49 93 6 0
            Fax:    +49 (0)2405 49 93 6 99
            E-Mail: info@lancom.eu"
    DESCRIPTION
        "LANCOM Systems GmbH LCOS-LX MIB"
    REVISION "202607301950Z" -- July 30, 2026
    DESCRIPTION
        "Version 7.14"
    ::= { enterprises lancom-systems(2356) 13 }

-- {OID} 13.0
lcosLXTrapsGrp OBJECT IDENTIFIER ::= { lcosLX 0 }


-- {OID} 13.0.0
lcosLXWifiTraps OBJECT IDENTIFIER ::= { lcosLXTrapsGrp 0 }


-- {OID} 13.1
lcosLXStatus OBJECT IDENTIFIER ::= { lcosLX 1 }

-- {SCALAR} 13.1.2
lcosLXStatusOperatingTime OBJECT-TYPE
    SYNTAX     Unsigned32 (0..4294967295)
    MAX-ACCESS read-only
    STATUS     current
    DESCRIPTION
        ""
    ::= { lcosLXStatus 2 }

-- {OID} 13.1.3
lcosLXStatusWLAN OBJECT IDENTIFIER ::= { lcosLXStatus 3 }

-- {SCALAR} 13.1.3.1
lcosLXStatusWLANEnvironmentScanStatus OBJECT-TYPE
    SYNTAX     OCTET STRING (SIZE(0..17))
    MAX-ACCESS read-only
    STATUS     current
    DESCRIPTION
        ""
    ::= { lcosLXStatusWLAN 1 }

-- {SCALAR} 13.1.3.3
lcosLXStatusWLANEnvironmentScanStatusShort OBJECT-TYPE
    SYNTAX     INTEGER {
                  eNever(0),
                  eScanning(1),
                  eScanned(2)
               }
    MAX-ACCESS read-only
    STATUS     current
    DESCRIPTION
        ""
    ::= { lcosLXStatusWLAN 3 }

-- {OID} 13.1.3.4
lcosLXStatusWLANClientManagement OBJECT IDENTIFIER ::= { lcosLXStatusWLAN 4 }

-- {TABLE} 13.1.3.4.1
lcosLXStatusWLANClientManagementStationTable OBJECT-TYPE
    SYNTAX     SEQUENCE OF LcosLXStatusWLANClientManagementStationEntry
    MAX-ACCESS not-accessible
    STATUS     current
    DESCRIPTION
        ""
    ::= { lcosLXStatusWLANClientManagement 1 }

-- {INDEX} 13.1.3.4.1
lcosLXStatusWLANClientManagementStationEntry OBJECT-TYPE
    SYNTAX     LcosLXStatusWLANClientManagementStationEntry
    MAX-ACCESS not-accessible
    STATUS     current
    DESCRIPTION
        ""
    INDEX {
        lcosLXStatusWLANClientManagementStationEntryMACAddress
    }
    ::= { lcosLXStatusWLANClientManagementStationTable 1 }

-- {SEQUENCE} 13.1.3.4.1
LcosLXStatusWLANClientManagementStationEntry ::= SEQUENCE {
    lcosLXStatusWLANClientManagementStationEntryMACAddress MacAddress,
    lcosLXStatusWLANClientManagementStationEntryChannel Unsigned32,
    lcosLXStatusWLANClientManagementStationEntryActive INTEGER,
    lcosLXStatusWLANClientManagementStationEntryDualBand INTEGER,
    lcosLXStatusWLANClientManagementStationEntryBTMSupport INTEGER,
    lcosLXStatusWLANClientManagementStationEntryRRMSupport INTEGER,
    lcosLXStatusWLANClientManagementStationEntryBTMUnfriendly INTEGER,
    lcosLXStatusWLANClientManagementStationEntryBTMCompliance INTEGER,
    lcosLXStatusWLANClientManagementStationEntrySteeringUnfriendly INTEGER,
    lcosLXStatusWLANClientManagementStationEntrySteeringProhibited INTEGER
}

-- {COLUMN} 13.1.3.4.1.1.1
lcosLXStatusWLANClientManagementStationEntryMACAddress OBJECT-TYPE
    SYNTAX     MacAddress
    MAX-ACCESS not-accessible
    STATUS     current
    DESCRIPTION
        ""
    ::= { lcosLXStatusWLANClientManagementStationEntry 1 }

-- {COLUMN} 13.1.3.4.1.1.2
lcosLXStatusWLANClientManagementStationEntryChannel OBJECT-TYPE
    SYNTAX     Unsigned32 (0..255)
    MAX-ACCESS read-only
    STATUS     current
    DESCRIPTION
        ""
    ::= { lcosLXStatusWLANClientManagementStationEntry 2 }

-- {COLUMN} 13.1.3.4.1.1.3
lcosLXStatusWLANClientManagementStationEntryActive OBJECT-TYPE
    SYNTAX     INTEGER {
                  eNo(0),
                  eYes(1)
               }
    MAX-ACCESS read-only
    STATUS     current
    DESCRIPTION
        ""
    ::= { lcosLXStatusWLANClientManagementStationEntry 3 }

-- {COLUMN} 13.1.3.4.1.1.4
lcosLXStatusWLANClientManagementStationEntryDualBand OBJECT-TYPE
    SYNTAX     INTEGER {
                  eNo(0),
                  eYes(1)
               }
    MAX-ACCESS read-only
    STATUS     current
    DESCRIPTION
        ""
    ::= { lcosLXStatusWLANClientManagementStationEntry 4 }

-- {COLUMN} 13.1.3.4.1.1.5
lcosLXStatusWLANClientManagementStationEntryBTMSupport OBJECT-TYPE
    SYNTAX     INTEGER {
                  eNo(0),
                  eYes(1)
               }
    MAX-ACCESS read-only
    STATUS     current
    DESCRIPTION
        ""
    ::= { lcosLXStatusWLANClientManagementStationEntry 5 }

-- {COLUMN} 13.1.3.4.1.1.6
lcosLXStatusWLANClientManagementStationEntryRRMSupport OBJECT-TYPE
    SYNTAX     INTEGER {
                  eNo(0),
                  eYes(1)
               }
    MAX-ACCESS read-only
    STATUS     current
    DESCRIPTION
        ""
    ::= { lcosLXStatusWLANClientManagementStationEntry 6 }

-- {COLUMN} 13.1.3.4.1.1.7
lcosLXStatusWLANClientManagementStationEntryBTMUnfriendly OBJECT-TYPE
    SYNTAX     INTEGER {
                  eNo(0),
                  eYes(1)
               }
    MAX-ACCESS read-only
    STATUS     current
    DESCRIPTION
        ""
    ::= { lcosLXStatusWLANClientManagementStationEntry 7 }

-- {COLUMN} 13.1.3.4.1.1.8
lcosLXStatusWLANClientManagementStationEntryBTMCompliance OBJECT-TYPE
    SYNTAX     INTEGER {
                  eUnknown(0),
                  eIdle(1),
                  eActiveUnfriendly(2),
                  eActive(3)
               }
    MAX-ACCESS read-only
    STATUS     current
    DESCRIPTION
        ""
    ::= { lcosLXStatusWLANClientManagementStationEntry 8 }

-- {COLUMN} 13.1.3.4.1.1.9
lcosLXStatusWLANClientManagementStationEntrySteeringUnfriendly OBJECT-TYPE
    SYNTAX     INTEGER {
                  eNo(0),
                  eYes(1)
               }
    MAX-ACCESS read-only
    STATUS     current
    DESCRIPTION
        ""
    ::= { lcosLXStatusWLANClientManagementStationEntry 9 }

-- {COLUMN} 13.1.3.4.1.1.10
lcosLXStatusWLANClientManagementStationEntrySteeringProhibited OBJECT-TYPE
    SYNTAX     INTEGER {
                  eNo(0),
                  eYes(1)
               }
    MAX-ACCESS read-only
    STATUS     current
    DESCRIPTION
        ""
    ::= { lcosLXStatusWLANClientManagementStationEntry 10 }

-- {TABLE} 13.1.3.4.2
lcosLXStatusWLANClientManagementChannelTable OBJECT-TYPE
    SYNTAX     SEQUENCE OF LcosLXStatusWLANClientManagementChannelEntry
    MAX-ACCESS not-accessible
    STATUS     current
    DESCRIPTION
        ""
    ::= { lcosLXStatusWLANClientManagement 2 }

-- {INDEX} 13.1.3.4.2
lcosLXStatusWLANClientManagementChannelEntry OBJECT-TYPE
    SYNTAX     LcosLXStatusWLANClientManagementChannelEntry
    MAX-ACCESS not-accessible
    STATUS     current
    DESCRIPTION
        ""
    INDEX {
        lcosLXStatusWLANClientManagementChannelEntryChannel
    }
    ::= { lcosLXStatusWLANClientManagementChannelTable 1 }

-- {SEQUENCE} 13.1.3.4.2
LcosLXStatusWLANClientManagementChannelEntry ::= SEQUENCE {
    lcosLXStatusWLANClientManagementChannelEntryChannel Unsigned32,
    lcosLXStatusWLANClientManagementChannelEntryUtilization Unsigned32,
    lcosLXStatusWLANClientManagementChannelEntryOverload INTEGER
}

-- {COLUMN} 13.1.3.4.2.1.1
lcosLXStatusWLANClientManagementChannelEntryChannel OBJECT-TYPE
    SYNTAX     Unsigned32 (0..255)
    MAX-ACCESS not-accessible
    STATUS     current
    DESCRIPTION
        ""
    ::= { lcosLXStatusWLANClientManagementChannelEntry 1 }

-- {COLUMN} 13.1.3.4.2.1.2
lcosLXStatusWLANClientManagementChannelEntryUtilization OBJECT-TYPE
    SYNTAX     Unsigned32 (0..255)
    MAX-ACCESS read-only
    STATUS     current
    DESCRIPTION
        ""
    ::= { lcosLXStatusWLANClientManagementChannelEntry 2 }

-- {COLUMN} 13.1.3.4.2.1.3
lcosLXStatusWLANClientManagementChannelEntryOverload OBJECT-TYPE
    SYNTAX     INTEGER {
                  eNo(0),
                  eYes(1)
               }
    MAX-ACCESS read-only
    STATUS     current
    DESCRIPTION
        ""
    ::= { lcosLXStatusWLANClientManagementChannelEntry 3 }

-- {TABLE} 13.1.3.4.3
lcosLXStatusWLANClientManagementSteeringLog OBJECT-TYPE
    SYNTAX     SEQUENCE OF LcosLXStatusWLANClientManagementSteeringLogEntry
    MAX-ACCESS not-accessible
    STATUS     current
    DESCRIPTION
        ""
    ::= { lcosLXStatusWLANClientManagement 3 }

-- {INDEX} 13.1.3.4.3
lcosLXStatusWLANClientManagementSteeringLogEntry OBJECT-TYPE
    SYNTAX     LcosLXStatusWLANClientManagementSteeringLogEntry
    MAX-ACCESS not-accessible
    STATUS     current
    DESCRIPTION
        ""
    INDEX {
        lcosLXStatusWLANClientManagementSteeringLogEntryID
    }
    ::= { lcosLXStatusWLANClientManagementSteeringLog 1 }

-- {SEQUENCE} 13.1.3.4.3
LcosLXStatusWLANClientManagementSteeringLogEntry ::= SEQUENCE {
    lcosLXStatusWLANClientManagementSteeringLogEntryID Unsigned32,
    lcosLXStatusWLANClientManagementSteeringLogEntryTimestampEpoch Unsigned32,
    lcosLXStatusWLANClientManagementSteeringLogEntryTimestamp OCTET STRING,
    lcosLXStatusWLANClientManagementSteeringLogEntryMACAddress MacAddress,
    lcosLXStatusWLANClientManagementSteeringLogEntryReason INTEGER,
    lcosLXStatusWLANClientManagementSteeringLogEntryChannel Unsigned32,
    lcosLXStatusWLANClientManagementSteeringLogEntryCandidates OCTET STRING,
    lcosLXStatusWLANClientManagementSteeringLogEntryType INTEGER,
    lcosLXStatusWLANClientManagementSteeringLogEntryState INTEGER
}

-- {COLUMN} 13.1.3.4.3.1.1
lcosLXStatusWLANClientManagementSteeringLogEntryID OBJECT-TYPE
    SYNTAX     Unsigned32 (0..255)
    MAX-ACCESS not-accessible
    STATUS     current
    DESCRIPTION
        ""
    ::= { lcosLXStatusWLANClientManagementSteeringLogEntry 1 }

-- {COLUMN} 13.1.3.4.3.1.2
lcosLXStatusWLANClientManagementSteeringLogEntryTimestampEpoch OBJECT-TYPE
    SYNTAX     Unsigned32 (0..4294967295)
    MAX-ACCESS read-only
    STATUS     current
    DESCRIPTION
        ""
    ::= { lcosLXStatusWLANClientManagementSteeringLogEntry 2 }

-- {COLUMN} 13.1.3.4.3.1.3
lcosLXStatusWLANClientManagementSteeringLogEntryTimestamp OBJECT-TYPE
    SYNTAX     OCTET STRING (SIZE(0..20))
    MAX-ACCESS read-only
    STATUS     current
    DESCRIPTION
        ""
    ::= { lcosLXStatusWLANClientManagementSteeringLogEntry 3 }

-- {COLUMN} 13.1.3.4.3.1.4
lcosLXStatusWLANClientManagementSteeringLogEntryMACAddress OBJECT-TYPE
    SYNTAX     MacAddress
    MAX-ACCESS read-only
    STATUS     current
    DESCRIPTION
        ""
    ::= { lcosLXStatusWLANClientManagementSteeringLogEntry 4 }

-- {COLUMN} 13.1.3.4.3.1.5
lcosLXStatusWLANClientManagementSteeringLogEntryReason OBJECT-TYPE
    SYNTAX     INTEGER {
                  eUnknown(0),
                  eActiveUpgrade(1),
                  eActiveDowngradeRate(2),
                  eActiveDowngradeRSSI(3),
                  eIdleUpgrade(4),
                  eIdleDowngrade(5),
                  eActiveOffload(6),
                  eIdleOffload(7),
                  eInterferenceAvoidance(8)
               }
    MAX-ACCESS read-only
    STATUS     current
    DESCRIPTION
        ""
    ::= { lcosLXStatusWLANClientManagementSteeringLogEntry 5 }

-- {COLUMN} 13.1.3.4.3.1.6
lcosLXStatusWLANClientManagementSteeringLogEntryChannel OBJECT-TYPE
    SYNTAX     Unsigned32 (0..255)
    MAX-ACCESS read-only
    STATUS     current
    DESCRIPTION
        ""
    ::= { lcosLXStatusWLANClientManagementSteeringLogEntry 6 }

-- {COLUMN} 13.1.3.4.3.1.7
lcosLXStatusWLANClientManagementSteeringLogEntryCandidates OBJECT-TYPE
    SYNTAX     OCTET STRING (SIZE(0..64))
    MAX-ACCESS read-only
    STATUS     current
    DESCRIPTION
        ""
    ::= { lcosLXStatusWLANClientManagementSteeringLogEntry 7 }

-- {COLUMN} 13.1.3.4.3.1.8
lcosLXStatusWLANClientManagementSteeringLogEntryType OBJECT-TYPE
    SYNTAX     INTEGER {
                  eUnknown(0),
                  eNone(1),
                  eLegacy(2),
                  eBTMAndBlacklist(3),
                  eBTM(4),
                  eBTMAndBlacklistActive(5),
                  eBTMActive(6),
                  ePreassociation(7),
                  eBTMBE(8),
                  eBTMBEActive(9),
                  eBTMBlacklistBE(10),
                  eBTMBlacklistBEActive(11),
                  eLegacyBE(12),
                  eBTMBEActiveForce(13)
               }
    MAX-ACCESS read-only
    STATUS     current
    DESCRIPTION
        ""
    ::= { lcosLXStatusWLANClientManagementSteeringLogEntry 8 }

-- {COLUMN} 13.1.3.4.3.1.9
lcosLXStatusWLANClientManagementSteeringLogEntryState OBJECT-TYPE
    SYNTAX     INTEGER {
                  eUnknown(0),
                  eRunning(1),
                  eSuccess(2),
                  eAbortAuthReject(3),
                  eAbortLowRSSI(4),
                  eAbortChangeTarget(5),
                  eBTMReject(6),
                  eBTMResponseTimeout(7),
                  eAssocTimeout(8),
                  eChannelChange(9),
                  ePrepareFail(10),
                  eUnexpectedBSS(11)
               }
    MAX-ACCESS read-only
    STATUS     current
    DESCRIPTION
        ""
    ::= { lcosLXStatusWLANClientManagementSteeringLogEntry 9 }

-- {SCALAR} 13.1.3.6
lcosLXStatusWLANAutomaticEnvironmentScanTime OBJECT-TYPE
    SYNTAX     OCTET STRING (SIZE(0..5))
    MAX-ACCESS read-only
    STATUS     current
    DESCRIPTION
        ""
    ::= { lcosLXStatusWLAN 6 }

-- {OID} 13.1.3.12
lcosLXStatusWLANHotspots OBJECT IDENTIFIER ::= { lcosLXStatusWLAN 12 }

-- {TABLE} 13.1.3.12.1
lcosLXStatusWLANHotspotsHotspots OBJECT-TYPE
    SYNTAX     SEQUENCE OF LcosLXStatusWLANHotspotsHotspotsEntry
    MAX-ACCESS not-accessible
    STATUS     current
    DESCRIPTION
        ""
    ::= { lcosLXStatusWLANHotspots 1 }

-- {INDEX} 13.1.3.12.1
lcosLXStatusWLANHotspotsHotspotsEntry OBJECT-TYPE
    SYNTAX     LcosLXStatusWLANHotspotsHotspotsEntry
    MAX-ACCESS not-accessible
    STATUS     current
    DESCRIPTION
        ""
    INDEX {
        lcosLXStatusWLANHotspotsHotspotsEntryHotspot,
        lcosLXStatusWLANHotspotsHotspotsEntryMACAddress
    }
    ::= { lcosLXStatusWLANHotspotsHotspots 1 }

-- {SEQUENCE} 13.1.3.12.1
LcosLXStatusWLANHotspotsHotspotsEntry ::= SEQUENCE {
    lcosLXStatusWLANHotspotsHotspotsEntryHotspot OCTET STRING,
    lcosLXStatusWLANHotspotsHotspotsEntryMACAddress MacAddress,
    lcosLXStatusWLANHotspotsHotspotsEntryLastLoggedIn Unsigned32,
    lcosLXStatusWLANHotspotsHotspotsEntryValidUntil Unsigned32
}

-- {COLUMN} 13.1.3.12.1.1.1
lcosLXStatusWLANHotspotsHotspotsEntryHotspot OBJECT-TYPE
    SYNTAX     OCTET STRING (SIZE(0..32))
    MAX-ACCESS not-accessible
    STATUS     current
    DESCRIPTION
        ""
    ::= { lcosLXStatusWLANHotspotsHotspotsEntry 1 }

-- {COLUMN} 13.1.3.12.1.1.2
lcosLXStatusWLANHotspotsHotspotsEntryMACAddress OBJECT-TYPE
    SYNTAX     MacAddress
    MAX-ACCESS not-accessible
    STATUS     current
    DESCRIPTION
        ""
    ::= { lcosLXStatusWLANHotspotsHotspotsEntry 2 }

-- {COLUMN} 13.1.3.12.1.1.3
lcosLXStatusWLANHotspotsHotspotsEntryLastLoggedIn OBJECT-TYPE
    SYNTAX     Unsigned32 (0..4294967295)
    MAX-ACCESS read-only
    STATUS     current
    DESCRIPTION
        ""
    ::= { lcosLXStatusWLANHotspotsHotspotsEntry 3 }

-- {COLUMN} 13.1.3.12.1.1.4
lcosLXStatusWLANHotspotsHotspotsEntryValidUntil OBJECT-TYPE
    SYNTAX     Unsigned32 (0..4294967295)
    MAX-ACCESS read-only
    STATUS     current
    DESCRIPTION
        ""
    ::= { lcosLXStatusWLANHotspotsHotspotsEntry 4 }

-- {SCALAR} 13.1.3.14
lcosLXStatusWLANUUID OBJECT-TYPE
    SYNTAX     OCTET STRING (SIZE(0..36))
    MAX-ACCESS read-only
    STATUS     current
    DESCRIPTION
        ""
    ::= { lcosLXStatusWLAN 14 }

-- {TABLE} 13.1.3.32
lcosLXStatusWLANStationTable OBJECT-TYPE
    SYNTAX     SEQUENCE OF LcosLXStatusWLANStationEntry
    MAX-ACCESS not-accessible
    STATUS     current
    DESCRIPTION
        ""
    ::= { lcosLXStatusWLAN 32 }

-- {INDEX} 13.1.3.32
lcosLXStatusWLANStationEntry OBJECT-TYPE
    SYNTAX     LcosLXStatusWLANStationEntry
    MAX-ACCESS not-accessible
    STATUS     current
    DESCRIPTION
        ""
    INDEX {
        lcosLXStatusWLANStationEntryMACAddress
    }
    ::= { lcosLXStatusWLANStationTable 1 }

-- {SEQUENCE} 13.1.3.32
LcosLXStatusWLANStationEntry ::= SEQUENCE {
    lcosLXStatusWLANStationEntryRadioBand INTEGER,
    lcosLXStatusWLANStationEntryIfc OCTET STRING,
    lcosLXStatusWLANStationEntryMACAddress MacAddress,
    lcosLXStatusWLANStationEntryTxBytes Counter64,
    lcosLXStatusWLANStationEntryRxBytes Counter64,
    lcosLXStatusWLANStationEntryIdentification OCTET STRING,
    lcosLXStatusWLANStationEntryState INTEGER,
    lcosLXStatusWLANStationEntryInterface OCTET STRING,
    lcosLXStatusWLANStationEntryConnectTime Counter64,
    lcosLXStatusWLANStationEntryThroughput Unsigned32,
    lcosLXStatusWLANStationEntryPhySignal Unsigned32,
    lcosLXStatusWLANStationEntryIPv4Address IpAddress,
    lcosLXStatusWLANStationEntryIPv6Address OCTET STRING,
    lcosLXStatusWLANStationEntryWPAVersion INTEGER,
    lcosLXStatusWLANStationEntryVLANId Unsigned32,
    lcosLXStatusWLANStationEntryUserName OCTET STRING,
    lcosLXStatusWLANStationEntryPairwiseCipher OCTET STRING,
    lcosLXStatusWLANStationEntryNetworkID OCTET STRING,
    lcosLXStatusWLANStationEntryMLDAddress MacAddress,
    lcosLXStatusWLANStationEntryIdleTimeout Unsigned32,
    lcosLXStatusWLANStationEntryMLOMode BITS,
    lcosLXStatusWLANStationEntryEffTxRate Unsigned32,
    lcosLXStatusWLANStationEntryEffRxRate Unsigned32,
    lcosLXStatusWLANStationEntryFastRoaming INTEGER,
    lcosLXStatusWLANStationEntryWPA2KeyManagement INTEGER,
    lcosLXStatusWLANStationEntryChannelBandwidths OCTET STRING,
    lcosLXStatusWLANStationEntryOperationMode INTEGER,
    lcosLXStatusWLANStationEntryDHCPHostname OCTET STRING,
    lcosLXStatusWLANStationEntryMaxSpatialStreams Unsigned32,
    lcosLXStatusWLANStationEntryPhySignaldBm Integer32,
    lcosLXStatusWLANStationEntryNetworkName OCTET STRING,
    lcosLXStatusWLANStationEntrySSID OCTET STRING
}

-- {COLUMN} 13.1.3.32.1.2
lcosLXStatusWLANStationEntryRadioBand OBJECT-TYPE
    SYNTAX     INTEGER {
                  e24GHz(1),
                  e5GHz(2),
                  e6GHz(3)
               }
    MAX-ACCESS read-only
    STATUS     current
    DESCRIPTION
        ""
    ::= { lcosLXStatusWLANStationEntry 2 }

-- {COLUMN} 13.1.3.32.1.3
lcosLXStatusWLANStationEntryIfc OBJECT-TYPE
    SYNTAX     OCTET STRING (SIZE(0..10))
    MAX-ACCESS read-only
    STATUS     current
    DESCRIPTION
        ""
    ::= { lcosLXStatusWLANStationEntry 3 }

-- {COLUMN} 13.1.3.32.1.4
lcosLXStatusWLANStationEntryMACAddress OBJECT-TYPE
    SYNTAX     MacAddress
    MAX-ACCESS not-accessible
    STATUS     current
    DESCRIPTION
        ""
    ::= { lcosLXStatusWLANStationEntry 4 }

-- {COLUMN} 13.1.3.32.1.6
lcosLXStatusWLANStationEntryTxBytes OBJECT-TYPE
    SYNTAX     Counter64
    MAX-ACCESS read-only
    STATUS     current
    DESCRIPTION
        ""
    ::= { lcosLXStatusWLANStationEntry 6 }

-- {COLUMN} 13.1.3.32.1.7
lcosLXStatusWLANStationEntryRxBytes OBJECT-TYPE
    SYNTAX     Counter64
    MAX-ACCESS read-only
    STATUS     current
    DESCRIPTION
        ""
    ::= { lcosLXStatusWLANStationEntry 7 }

-- {COLUMN} 13.1.3.32.1.9
lcosLXStatusWLANStationEntryIdentification OBJECT-TYPE
    SYNTAX     OCTET STRING (SIZE(0..18))
    MAX-ACCESS read-only
    STATUS     current
    DESCRIPTION
        ""
    ::= { lcosLXStatusWLANStationEntry 9 }

-- {COLUMN} 13.1.3.32.1.10
lcosLXStatusWLANStationEntryState OBJECT-TYPE
    SYNTAX     INTEGER {
                  eNone(0),
                  eAuthenticated(2),
                  eConnected(3),
                  eAssociated(9),
                  e1XNegotiation(10),
                  eKeyHandshake(8)
               }
    MAX-ACCESS read-only
    STATUS     current
    DESCRIPTION
        ""
    ::= { lcosLXStatusWLANStationEntry 10 }

-- {COLUMN} 13.1.3.32.1.15
lcosLXStatusWLANStationEntryInterface OBJECT-TYPE
    SYNTAX     OCTET STRING (SIZE(0..64))
    MAX-ACCESS read-only
    STATUS     current
    DESCRIPTION
        ""
    ::= { lcosLXStatusWLANStationEntry 15 }

-- {COLUMN} 13.1.3.32.1.18
lcosLXStatusWLANStationEntryConnectTime OBJECT-TYPE
    SYNTAX     Counter64
    MAX-ACCESS read-only
    STATUS     current
    DESCRIPTION
        ""
    ::= { lcosLXStatusWLANStationEntry 18 }

-- {COLUMN} 13.1.3.32.1.20
lcosLXStatusWLANStationEntryThroughput OBJECT-TYPE
    SYNTAX     Unsigned32 (0..4294967295)
    MAX-ACCESS read-only
    STATUS     current
    DESCRIPTION
        ""
    ::= { lcosLXStatusWLANStationEntry 20 }

-- {COLUMN} 13.1.3.32.1.26
lcosLXStatusWLANStationEntryPhySignal OBJECT-TYPE
    SYNTAX     Unsigned32 (0..255)
    MAX-ACCESS read-only
    STATUS     current
    DESCRIPTION
        ""
    ::= { lcosLXStatusWLANStationEntry 26 }

-- {COLUMN} 13.1.3.32.1.27
lcosLXStatusWLANStationEntryIPv4Address OBJECT-TYPE
    SYNTAX     IpAddress
    MAX-ACCESS read-only
    STATUS     current
    DESCRIPTION
        ""
    ::= { lcosLXStatusWLANStationEntry 27 }

-- {COLUMN} 13.1.3.32.1.28
lcosLXStatusWLANStationEntryIPv6Address OBJECT-TYPE
    SYNTAX     OCTET STRING (SIZE(0..44))
    MAX-ACCESS read-only
    STATUS     current
    DESCRIPTION
        ""
    ::= { lcosLXStatusWLANStationEntry 28 }

-- {COLUMN} 13.1.3.32.1.33
lcosLXStatusWLANStationEntryWPAVersion OBJECT-TYPE
    SYNTAX     INTEGER {
                  eNone(0),
                  eWPA1(1),
                  eWPA2(2),
                  eWPA3(3)
               }
    MAX-ACCESS read-only
    STATUS     current
    DESCRIPTION
        ""
    ::= { lcosLXStatusWLANStationEntry 33 }

-- {COLUMN} 13.1.3.32.1.38
lcosLXStatusWLANStationEntryVLANId OBJECT-TYPE
    SYNTAX     Unsigned32 (0..65535)
    MAX-ACCESS read-only
    STATUS     current
    DESCRIPTION
        ""
    ::= { lcosLXStatusWLANStationEntry 38 }

-- {COLUMN} 13.1.3.32.1.39
lcosLXStatusWLANStationEntryUserName OBJECT-TYPE
    SYNTAX     OCTET STRING (SIZE(0..64))
    MAX-ACCESS read-only
    STATUS     current
    DESCRIPTION
        ""
    ::= { lcosLXStatusWLANStationEntry 39 }

-- {COLUMN} 13.1.3.32.1.40
lcosLXStatusWLANStationEntryPairwiseCipher OBJECT-TYPE
    SYNTAX     OCTET STRING (SIZE(0..32))
    MAX-ACCESS read-only
    STATUS     current
    DESCRIPTION
        ""
    ::= { lcosLXStatusWLANStationEntry 40 }

-- {COLUMN} 13.1.3.32.1.41
lcosLXStatusWLANStationEntryNetworkID OBJECT-TYPE
    SYNTAX     OCTET STRING (SIZE(0..36))
    MAX-ACCESS read-only
    STATUS     current
    DESCRIPTION
        ""
    ::= { lcosLXStatusWLANStationEntry 41 }

-- {COLUMN} 13.1.3.32.1.42
lcosLXStatusWLANStationEntryMLDAddress OBJECT-TYPE
    SYNTAX     MacAddress
    MAX-ACCESS read-only
    STATUS     current
    DESCRIPTION
        ""
    ::= { lcosLXStatusWLANStationEntry 42 }

-- {COLUMN} 13.1.3.32.1.43
lcosLXStatusWLANStationEntryIdleTimeout OBJECT-TYPE
    SYNTAX     Unsigned32 (0..65535)
    MAX-ACCESS read-only
    STATUS     current
    DESCRIPTION
        ""
    ::= { lcosLXStatusWLANStationEntry 43 }

-- {COLUMN} 13.1.3.32.1.44
lcosLXStatusWLANStationEntryMLOMode OBJECT-TYPE
    SYNTAX     BITS {
                  eeMLSR(0),
                  eeMLMR(1),
                  eSTR(2)
               }
    MAX-ACCESS read-only
    STATUS     current
    DESCRIPTION
        ""
    ::= { lcosLXStatusWLANStationEntry 44 }

-- {COLUMN} 13.1.3.32.1.50
lcosLXStatusWLANStationEntryEffTxRate OBJECT-TYPE
    SYNTAX     Unsigned32 (0..65535)
    MAX-ACCESS read-only
    STATUS     current
    DESCRIPTION
        ""
    ::= { lcosLXStatusWLANStationEntry 50 }

-- {COLUMN} 13.1.3.32.1.51
lcosLXStatusWLANStationEntryEffRxRate OBJECT-TYPE
    SYNTAX     Unsigned32 (0..65535)
    MAX-ACCESS read-only
    STATUS     current
    DESCRIPTION
        ""
    ::= { lcosLXStatusWLANStationEntry 51 }

-- {COLUMN} 13.1.3.32.1.63
lcosLXStatusWLANStationEntryFastRoaming OBJECT-TYPE
    SYNTAX     INTEGER {
                  eNo(0),
                  eYes(1)
               }
    MAX-ACCESS read-only
    STATUS     current
    DESCRIPTION
        ""
    ::= { lcosLXStatusWLANStationEntry 63 }

-- {COLUMN} 13.1.3.32.1.64
lcosLXStatusWLANStationEntryWPA2KeyManagement OBJECT-TYPE
    SYNTAX     INTEGER {
                  eNone(0),
                  eStandard(1),
                  eFastRoaming(2),
                  eSHA256(3),
                  eSHA384(4),
                  eFastRoamingSHA384(5),
                  eSHA512(6)
               }
    MAX-ACCESS read-only
    STATUS     current
    DESCRIPTION
        ""
    ::= { lcosLXStatusWLANStationEntry 64 }

-- {COLUMN} 13.1.3.32.1.66
lcosLXStatusWLANStationEntryChannelBandwidths OBJECT-TYPE
    SYNTAX     OCTET STRING (SIZE(0..7))
    MAX-ACCESS read-only
    STATUS     current
    DESCRIPTION
        ""
    ::= { lcosLXStatusWLANStationEntry 66 }

-- {COLUMN} 13.1.3.32.1.71
lcosLXStatusWLANStationEntryOperationMode OBJECT-TYPE
    SYNTAX     INTEGER {
                  eunknown(0),
                  e11b(1),
                  e11g(2),
                  e11a(3),
                  e11n(4),
                  e11ac(5),
                  e11ax(6),
                  e11be(7)
               }
    MAX-ACCESS read-only
    STATUS     current
    DESCRIPTION
        ""
    ::= { lcosLXStatusWLANStationEntry 71 }

-- {COLUMN} 13.1.3.32.1.80
lcosLXStatusWLANStationEntryDHCPHostname OBJECT-TYPE
    SYNTAX     OCTET STRING (SIZE(0..64))
    MAX-ACCESS read-only
    STATUS     current
    DESCRIPTION
        ""
    ::= { lcosLXStatusWLANStationEntry 80 }

-- {COLUMN} 13.1.3.32.1.83
lcosLXStatusWLANStationEntryMaxSpatialStreams OBJECT-TYPE
    SYNTAX     Unsigned32 (0..255)
    MAX-ACCESS read-only
    STATUS     current
    DESCRIPTION
        ""
    ::= { lcosLXStatusWLANStationEntry 83 }

-- {COLUMN} 13.1.3.32.1.97
lcosLXStatusWLANStationEntryPhySignaldBm OBJECT-TYPE
    SYNTAX     Integer32 (-128..127)
    MAX-ACCESS read-only
    STATUS     current
    DESCRIPTION
        ""
    ::= { lcosLXStatusWLANStationEntry 97 }

-- {COLUMN} 13.1.3.32.1.98
lcosLXStatusWLANStationEntryNetworkName OBJECT-TYPE
    SYNTAX     OCTET STRING (SIZE(0..64))
    MAX-ACCESS read-only
    STATUS     current
    DESCRIPTION
        ""
    ::= { lcosLXStatusWLANStationEntry 98 }

-- {COLUMN} 13.1.3.32.1.99
lcosLXStatusWLANStationEntrySSID OBJECT-TYPE
    SYNTAX     OCTET STRING (SIZE(0..32))
    MAX-ACCESS read-only
    STATUS     current
    DESCRIPTION
        ""
    ::= { lcosLXStatusWLANStationEntry 99 }

-- {TABLE} 13.1.3.38
lcosLXStatusWLANIAPPTable OBJECT-TYPE
    SYNTAX     SEQUENCE OF LcosLXStatusWLANIAPPEntry
    MAX-ACCESS not-accessible
    STATUS     current
    DESCRIPTION
        ""
    ::= { lcosLXStatusWLAN 38 }

-- {INDEX} 13.1.3.38
lcosLXStatusWLANIAPPEntry OBJECT-TYPE
    SYNTAX     LcosLXStatusWLANIAPPEntry
    MAX-ACCESS not-accessible
    STATUS     current
    DESCRIPTION
        ""
    INDEX {
        lcosLXStatusWLANIAPPEntryIPAddress,
        lcosLXStatusWLANIAPPEntryBSSID
    }
    ::= { lcosLXStatusWLANIAPPTable 1 }

-- {SEQUENCE} 13.1.3.38
LcosLXStatusWLANIAPPEntry ::= SEQUENCE {
    lcosLXStatusWLANIAPPEntryIPAddress IpAddress,
    lcosLXStatusWLANIAPPEntryBSSID OCTET STRING,
    lcosLXStatusWLANIAPPEntrySSID OCTET STRING,
    lcosLXStatusWLANIAPPEntryRadioChannel Unsigned32,
    lcosLXStatusWLANIAPPEntryDomainID OCTET STRING,
    lcosLXStatusWLANIAPPEntryLoad OCTET STRING
}

-- {COLUMN} 13.1.3.38.1.1
lcosLXStatusWLANIAPPEntryIPAddress OBJECT-TYPE
    SYNTAX     IpAddress
    MAX-ACCESS not-accessible
    STATUS     current
    DESCRIPTION
        ""
    ::= { lcosLXStatusWLANIAPPEntry 1 }

-- {COLUMN} 13.1.3.38.1.2
lcosLXStatusWLANIAPPEntryBSSID OBJECT-TYPE
    SYNTAX     OCTET STRING (SIZE(0..18))
    MAX-ACCESS not-accessible
    STATUS     current
    DESCRIPTION
        ""
    ::= { lcosLXStatusWLANIAPPEntry 2 }

-- {COLUMN} 13.1.3.38.1.7
lcosLXStatusWLANIAPPEntrySSID OBJECT-TYPE
    SYNTAX     OCTET STRING (SIZE(0..32))
    MAX-ACCESS read-only
    STATUS     current
    DESCRIPTION
        ""
    ::= { lcosLXStatusWLANIAPPEntry 7 }

-- {COLUMN} 13.1.3.38.1.8
lcosLXStatusWLANIAPPEntryRadioChannel OBJECT-TYPE
    SYNTAX     Unsigned32 (0..255)
    MAX-ACCESS read-only
    STATUS     current
    DESCRIPTION
        ""
    ::= { lcosLXStatusWLANIAPPEntry 8 }

-- {COLUMN} 13.1.3.38.1.9
lcosLXStatusWLANIAPPEntryDomainID OBJECT-TYPE
    SYNTAX     OCTET STRING (SIZE(0..64))
    MAX-ACCESS read-only
    STATUS     current
    DESCRIPTION
        ""
    ::= { lcosLXStatusWLANIAPPEntry 9 }

-- {COLUMN} 13.1.3.38.1.10
lcosLXStatusWLANIAPPEntryLoad OBJECT-TYPE
    SYNTAX     OCTET STRING (SIZE(0..7))
    MAX-ACCESS read-only
    STATUS     current
    DESCRIPTION
        ""
    ::= { lcosLXStatusWLANIAPPEntry 10 }

-- {TABLE} 13.1.3.42
lcosLXStatusWLANChannelScanResults OBJECT-TYPE
    SYNTAX     SEQUENCE OF LcosLXStatusWLANChannelScanResultsEntry
    MAX-ACCESS not-accessible
    STATUS     current
    DESCRIPTION
        ""
    ::= { lcosLXStatusWLAN 42 }

-- {INDEX} 13.1.3.42
lcosLXStatusWLANChannelScanResultsEntry OBJECT-TYPE
    SYNTAX     LcosLXStatusWLANChannelScanResultsEntry
    MAX-ACCESS not-accessible
    STATUS     current
    DESCRIPTION
        ""
    INDEX {
        lcosLXStatusWLANChannelScanResultsEntryRadioChannel,
        lcosLXStatusWLANChannelScanResultsEntryInterface,
        lcosLXStatusWLANChannelScanResultsEntryRadioBand
    }
    ::= { lcosLXStatusWLANChannelScanResults 1 }

-- {SEQUENCE} 13.1.3.42
LcosLXStatusWLANChannelScanResultsEntry ::= SEQUENCE {
    lcosLXStatusWLANChannelScanResultsEntryRadioChannel Unsigned32,
    lcosLXStatusWLANChannelScanResultsEntryInterface OCTET STRING,
    lcosLXStatusWLANChannelScanResultsEntryRadioBand INTEGER,
    lcosLXStatusWLANChannelScanResultsEntryDFSState INTEGER,
    lcosLXStatusWLANChannelScanResultsEntryDFSScanAge Unsigned32,
    lcosLXStatusWLANChannelScanResultsEntryChannelBandwidth INTEGER
}

-- {COLUMN} 13.1.3.42.1.1
lcosLXStatusWLANChannelScanResultsEntryRadioChannel OBJECT-TYPE
    SYNTAX     Unsigned32 (0..255)
    MAX-ACCESS not-accessible
    STATUS     current
    DESCRIPTION
        ""
    ::= { lcosLXStatusWLANChannelScanResultsEntry 1 }

-- {COLUMN} 13.1.3.42.1.2
lcosLXStatusWLANChannelScanResultsEntryInterface OBJECT-TYPE
    SYNTAX     OCTET STRING (SIZE(0..16))
    MAX-ACCESS not-accessible
    STATUS     current
    DESCRIPTION
        ""
    ::= { lcosLXStatusWLANChannelScanResultsEntry 2 }

-- {COLUMN} 13.1.3.42.1.9
lcosLXStatusWLANChannelScanResultsEntryRadioBand OBJECT-TYPE
    SYNTAX     INTEGER {
                  e24GHz(1),
                  e5GHz(2),
                  e6GHz(3)
               }
    MAX-ACCESS not-accessible
    STATUS     current
    DESCRIPTION
        ""
    ::= { lcosLXStatusWLANChannelScanResultsEntry 9 }

-- {COLUMN} 13.1.3.42.1.12
lcosLXStatusWLANChannelScanResultsEntryDFSState OBJECT-TYPE
    SYNTAX     INTEGER {
                  eunknown(0),
                  eclear(1),
                  eblocked(2)
               }
    MAX-ACCESS read-only
    STATUS     current
    DESCRIPTION
        ""
    ::= { lcosLXStatusWLANChannelScanResultsEntry 12 }

-- {COLUMN} 13.1.3.42.1.13
lcosLXStatusWLANChannelScanResultsEntryDFSScanAge OBJECT-TYPE
    SYNTAX     Unsigned32 (0..4294967295)
    MAX-ACCESS read-only
    STATUS     current
    DESCRIPTION
        ""
    ::= { lcosLXStatusWLANChannelScanResultsEntry 13 }

-- {COLUMN} 13.1.3.42.1.23
lcosLXStatusWLANChannelScanResultsEntryChannelBandwidth OBJECT-TYPE
    SYNTAX     INTEGER {
                  e20MHz(0),
                  e40MHz(1),
                  e80MHz(2),
                  e160MHz(3),
                  e320MHz(4),
                  eAuto(255)
               }
    MAX-ACCESS read-only
    STATUS     current
    DESCRIPTION
        ""
    ::= { lcosLXStatusWLANChannelScanResultsEntry 23 }

-- {TABLE} 13.1.3.51
lcosLXStatusWLANInterfaces OBJECT-TYPE
    SYNTAX     SEQUENCE OF LcosLXStatusWLANInterfacesEntry
    MAX-ACCESS not-accessible
    STATUS     current
    DESCRIPTION
        ""
    ::= { lcosLXStatusWLAN 51 }

-- {INDEX} 13.1.3.51
lcosLXStatusWLANInterfacesEntry OBJECT-TYPE
    SYNTAX     LcosLXStatusWLANInterfacesEntry
    MAX-ACCESS not-accessible
    STATUS     current
    DESCRIPTION
        ""
    INDEX {
        lcosLXStatusWLANInterfacesEntryNetworkName,
        lcosLXStatusWLANInterfacesEntryRadioBand
    }
    ::= { lcosLXStatusWLANInterfaces 1 }

-- {SEQUENCE} 13.1.3.51
LcosLXStatusWLANInterfacesEntry ::= SEQUENCE {
    lcosLXStatusWLANInterfacesEntryNetworkName OCTET STRING,
    lcosLXStatusWLANInterfacesEntrySSID OCTET STRING,
    lcosLXStatusWLANInterfacesEntryRadioBand INTEGER,
    lcosLXStatusWLANInterfacesEntryWPAPSKNumSuccess Unsigned32,
    lcosLXStatusWLANInterfacesEntryWPAPSKNumFailures Unsigned32,
    lcosLXStatusWLANInterfacesEntryWPAPSKNumWrongPassphrase Unsigned32,
    lcosLXStatusWLANInterfacesEntryIfc OCTET STRING,
    lcosLXStatusWLANInterfacesEntryBroadcastRate INTEGER,
    lcosLXStatusWLANInterfacesEntryMulticastRate INTEGER,
    lcosLXStatusWLANInterfacesEntryBSSID MacAddress,
    lcosLXStatusWLANInterfacesEntryBasicRates BITS,
    lcosLXStatusWLANInterfacesEntrySupportedRates BITS,
    lcosLXStatusWLANInterfacesEntryBeaconRate INTEGER,
    lcosLXStatusWLANInterfacesEntryNetworkID OCTET STRING,
    lcosLXStatusWLANInterfacesEntryMLDAddress MacAddress
}

-- {COLUMN} 13.1.3.51.1.1
lcosLXStatusWLANInterfacesEntryNetworkName OBJECT-TYPE
    SYNTAX     OCTET STRING (SIZE(0..64))
    MAX-ACCESS not-accessible
    STATUS     current
    DESCRIPTION
        ""
    ::= { lcosLXStatusWLANInterfacesEntry 1 }

-- {COLUMN} 13.1.3.51.1.2
lcosLXStatusWLANInterfacesEntrySSID OBJECT-TYPE
    SYNTAX     OCTET STRING (SIZE(0..32))
    MAX-ACCESS read-only
    STATUS     current
    DESCRIPTION
        ""
    ::= { lcosLXStatusWLANInterfacesEntry 2 }

-- {COLUMN} 13.1.3.51.1.3
lcosLXStatusWLANInterfacesEntryRadioBand OBJECT-TYPE
    SYNTAX     INTEGER {
                  e24GHz(1),
                  e5GHz(2),
                  e6GHz(3)
               }
    MAX-ACCESS not-accessible
    STATUS     current
    DESCRIPTION
        ""
    ::= { lcosLXStatusWLANInterfacesEntry 3 }

-- {COLUMN} 13.1.3.51.1.4
lcosLXStatusWLANInterfacesEntryWPAPSKNumSuccess OBJECT-TYPE
    SYNTAX     Unsigned32 (0..4294967295)
    MAX-ACCESS read-only
    STATUS     current
    DESCRIPTION
        ""
    ::= { lcosLXStatusWLANInterfacesEntry 4 }

-- {COLUMN} 13.1.3.51.1.5
lcosLXStatusWLANInterfacesEntryWPAPSKNumFailures OBJECT-TYPE
    SYNTAX     Unsigned32 (0..4294967295)
    MAX-ACCESS read-only
    STATUS     current
    DESCRIPTION
        ""
    ::= { lcosLXStatusWLANInterfacesEntry 5 }

-- {COLUMN} 13.1.3.51.1.6
lcosLXStatusWLANInterfacesEntryWPAPSKNumWrongPassphrase OBJECT-TYPE
    SYNTAX     Unsigned32 (0..4294967295)
    MAX-ACCESS read-only
    STATUS     current
    DESCRIPTION
        ""
    ::= { lcosLXStatusWLANInterfacesEntry 6 }

-- {COLUMN} 13.1.3.51.1.7
lcosLXStatusWLANInterfacesEntryIfc OBJECT-TYPE
    SYNTAX     OCTET STRING (SIZE(0..10))
    MAX-ACCESS read-only
    STATUS     current
    DESCRIPTION
        ""
    ::= { lcosLXStatusWLANInterfacesEntry 7 }

-- {COLUMN} 13.1.3.51.1.8
lcosLXStatusWLANInterfacesEntryBroadcastRate OBJECT-TYPE
    SYNTAX     INTEGER {
                  edefault(0),
                  e1Mbps(1000),
                  e2Mbps(2000),
                  e55Mbps(5500),
                  e11Mbps(11000),
                  e6Mbps(6000),
                  e9Mbps(9000),
                  e12Mbps(12000),
                  e18Mbps(18000),
                  e24Mbps(24000),
                  e36Mbps(36000),
                  e48Mbps(48000),
                  e54Mbps(54000)
               }
    MAX-ACCESS read-only
    STATUS     current
    DESCRIPTION
        ""
    ::= { lcosLXStatusWLANInterfacesEntry 8 }

-- {COLUMN} 13.1.3.51.1.9
lcosLXStatusWLANInterfacesEntryMulticastRate OBJECT-TYPE
    SYNTAX     INTEGER {
                  edefault(0),
                  e1Mbps(1000),
                  e2Mbps(2000),
                  e55Mbps(5500),
                  e11Mbps(11000),
                  e6Mbps(6000),
                  e9Mbps(9000),
                  e12Mbps(12000),
                  e18Mbps(18000),
                  e24Mbps(24000),
                  e36Mbps(36000),
                  e48Mbps(48000),
                  e54Mbps(54000)
               }
    MAX-ACCESS read-only
    STATUS     current
    DESCRIPTION
        ""
    ::= { lcosLXStatusWLANInterfacesEntry 9 }

-- {COLUMN} 13.1.3.51.1.10
lcosLXStatusWLANInterfacesEntryBSSID OBJECT-TYPE
    SYNTAX     MacAddress
    MAX-ACCESS read-only
    STATUS     current
    DESCRIPTION
        ""
    ::= { lcosLXStatusWLANInterfacesEntry 10 }

-- {COLUMN} 13.1.3.51.1.11
lcosLXStatusWLANInterfacesEntryBasicRates OBJECT-TYPE
    SYNTAX     BITS {
                  e1Mbps(0),
                  e2Mbps(1),
                  e55Mbps(2),
                  e11Mbps(3),
                  e6Mbps(4),
                  e9Mbps(5),
                  e12Mbps(6),
                  e18Mbps(7),
                  e24Mbps(8),
                  e36Mbps(9),
                  e48Mbps(10),
                  e54Mbps(11)
               }
    MAX-ACCESS read-only
    STATUS     current
    DESCRIPTION
        ""
    ::= { lcosLXStatusWLANInterfacesEntry 11 }

-- {COLUMN} 13.1.3.51.1.12
lcosLXStatusWLANInterfacesEntrySupportedRates OBJECT-TYPE
    SYNTAX     BITS {
                  e1Mbps(0),
                  e2Mbps(1),
                  e55Mbps(2),
                  e11Mbps(3),
                  e6Mbps(4),
                  e9Mbps(5),
                  e12Mbps(6),
                  e18Mbps(7),
                  e24Mbps(8),
                  e36Mbps(9),
                  e48Mbps(10),
                  e54Mbps(11)
               }
    MAX-ACCESS read-only
    STATUS     current
    DESCRIPTION
        ""
    ::= { lcosLXStatusWLANInterfacesEntry 12 }

-- {COLUMN} 13.1.3.51.1.13
lcosLXStatusWLANInterfacesEntryBeaconRate OBJECT-TYPE
    SYNTAX     INTEGER {
                  edefault(0),
                  e1Mbps(1000),
                  e2Mbps(2000),
                  e55Mbps(5500),
                  e11Mbps(11000),
                  e6Mbps(6000),
                  e9Mbps(9000),
                  e12Mbps(12000),
                  e18Mbps(18000),
                  e24Mbps(24000),
                  e36Mbps(36000),
                  e48Mbps(48000),
                  e54Mbps(54000)
               }
    MAX-ACCESS read-only
    STATUS     current
    DESCRIPTION
        ""
    ::= { lcosLXStatusWLANInterfacesEntry 13 }

-- {COLUMN} 13.1.3.51.1.41
lcosLXStatusWLANInterfacesEntryNetworkID OBJECT-TYPE
    SYNTAX     OCTET STRING (SIZE(0..36))
    MAX-ACCESS read-only
    STATUS     current
    DESCRIPTION
        ""
    ::= { lcosLXStatusWLANInterfacesEntry 41 }

-- {COLUMN} 13.1.3.51.1.42
lcosLXStatusWLANInterfacesEntryMLDAddress OBJECT-TYPE
    SYNTAX     MacAddress
    MAX-ACCESS read-only
    STATUS     current
    DESCRIPTION
        ""
    ::= { lcosLXStatusWLANInterfacesEntry 42 }

-- {TABLE} 13.1.3.57
lcosLXStatusWLANRadios OBJECT-TYPE
    SYNTAX     SEQUENCE OF LcosLXStatusWLANRadiosEntry
    MAX-ACCESS not-accessible
    STATUS     current
    DESCRIPTION
        ""
    ::= { lcosLXStatusWLAN 57 }

-- {INDEX} 13.1.3.57
lcosLXStatusWLANRadiosEntry OBJECT-TYPE
    SYNTAX     LcosLXStatusWLANRadiosEntry
    MAX-ACCESS not-accessible
    STATUS     current
    DESCRIPTION
        ""
    INDEX {
        lcosLXStatusWLANRadiosEntryIfc
    }
    ::= { lcosLXStatusWLANRadios 1 }

-- {SEQUENCE} 13.1.3.57
LcosLXStatusWLANRadiosEntry ::= SEQUENCE {
    lcosLXStatusWLANRadiosEntryIfc OCTET STRING,
    lcosLXStatusWLANRadiosEntryRadioBand INTEGER,
    lcosLXStatusWLANRadiosEntryRadioChannel Unsigned32,
    lcosLXStatusWLANRadiosEntryNoiseFloor Integer32,
    lcosLXStatusWLANRadiosEntryNoiseLevel Integer32,
    lcosLXStatusWLANRadiosEntryModemLoad Unsigned32,
    lcosLXStatusWLANRadiosEntryTransmitPower Integer32,
    lcosLXStatusWLANRadiosEntryEIRP Integer32,
    lcosLXStatusWLANRadiosEntryNumStations Unsigned32,
    lcosLXStatusWLANRadiosEntryMode INTEGER,
    lcosLXStatusWLANRadiosEntryChannelBandwidth INTEGER,
    lcosLXStatusWLANRadiosEntryRxErrorRatio Unsigned32,
    lcosLXStatusWLANRadiosEntryTxErrorRatio Unsigned32,
    lcosLXStatusWLANRadiosEntryRxBytes Counter64,
    lcosLXStatusWLANRadiosEntryTxBytes Counter64,
    lcosLXStatusWLANRadiosEntryModemLoadMin Unsigned32,
    lcosLXStatusWLANRadiosEntryModemLoadMax Unsigned32,
    lcosLXStatusWLANRadiosEntryModemLoadAverage Unsigned32,
    lcosLXStatusWLANRadiosEntryTemperatureDegrees Unsigned32,
    lcosLXStatusWLANRadiosEntryAllChannelsBlocked INTEGER
}

-- {COLUMN} 13.1.3.57.1.1
lcosLXStatusWLANRadiosEntryIfc OBJECT-TYPE
    SYNTAX     OCTET STRING (SIZE(0..10))
    MAX-ACCESS not-accessible
    STATUS     current
    DESCRIPTION
        ""
    ::= { lcosLXStatusWLANRadiosEntry 1 }

-- {COLUMN} 13.1.3.57.1.2
lcosLXStatusWLANRadiosEntryRadioBand OBJECT-TYPE
    SYNTAX     INTEGER {
                  e24GHz(1),
                  e5GHz(2),
                  e6GHz(3)
               }
    MAX-ACCESS read-only
    STATUS     current
    DESCRIPTION
        ""
    ::= { lcosLXStatusWLANRadiosEntry 2 }

-- {COLUMN} 13.1.3.57.1.3
lcosLXStatusWLANRadiosEntryRadioChannel OBJECT-TYPE
    SYNTAX     Unsigned32 (0..255)
    MAX-ACCESS read-only
    STATUS     current
    DESCRIPTION
        ""
    ::= { lcosLXStatusWLANRadiosEntry 3 }

-- {COLUMN} 13.1.3.57.1.4
lcosLXStatusWLANRadiosEntryNoiseFloor OBJECT-TYPE
    SYNTAX     Integer32 (-128..127)
    MAX-ACCESS read-only
    STATUS     current
    DESCRIPTION
        ""
    ::= { lcosLXStatusWLANRadiosEntry 4 }

-- {COLUMN} 13.1.3.57.1.5
lcosLXStatusWLANRadiosEntryNoiseLevel OBJECT-TYPE
    SYNTAX     Integer32 (-128..127)
    MAX-ACCESS read-only
    STATUS     current
    DESCRIPTION
        ""
    ::= { lcosLXStatusWLANRadiosEntry 5 }

-- {COLUMN} 13.1.3.57.1.6
lcosLXStatusWLANRadiosEntryModemLoad OBJECT-TYPE
    SYNTAX     Unsigned32 (0..255)
    MAX-ACCESS read-only
    STATUS     current
    DESCRIPTION
        ""
    ::= { lcosLXStatusWLANRadiosEntry 6 }

-- {COLUMN} 13.1.3.57.1.7
lcosLXStatusWLANRadiosEntryTransmitPower OBJECT-TYPE
    SYNTAX     Integer32 (-32768..32767)
    MAX-ACCESS read-only
    STATUS     current
    DESCRIPTION
        ""
    ::= { lcosLXStatusWLANRadiosEntry 7 }

-- {COLUMN} 13.1.3.57.1.8
lcosLXStatusWLANRadiosEntryEIRP OBJECT-TYPE
    SYNTAX     Integer32 (-128..127)
    MAX-ACCESS read-only
    STATUS     current
    DESCRIPTION
        ""
    ::= { lcosLXStatusWLANRadiosEntry 8 }

-- {COLUMN} 13.1.3.57.1.9
lcosLXStatusWLANRadiosEntryNumStations OBJECT-TYPE
    SYNTAX     Unsigned32 (0..65535)
    MAX-ACCESS read-only
    STATUS     current
    DESCRIPTION
        ""
    ::= { lcosLXStatusWLANRadiosEntry 9 }

-- {COLUMN} 13.1.3.57.1.14
lcosLXStatusWLANRadiosEntryMode OBJECT-TYPE
    SYNTAX     INTEGER {
                  e11bgmixed(0),
                  e11gonly(1),
                  e11bonly(2),
                  e11bgnmixed(5),
                  e11gnmixed(7),
                  e11nonly(8),
                  e11bgnaxmixed(9),
                  e11gnaxmixed(10),
                  e11bgnaxbemixed(11),
                  e11gnaxbemixed(12),
                  eoff(255),
                  e11aonly(256),
                  e11anmixed(259),
                  e11anacmixed(263),
                  e11nacmixed(264),
                  e11aconly(265),
                  e11anacaxmixed(266),
                  e11anacaxbemixed(267),
                  e11ax(268),
                  e11axbemixed(269)
               }
    MAX-ACCESS read-only
    STATUS     current
    DESCRIPTION
        ""
    ::= { lcosLXStatusWLANRadiosEntry 14 }

-- {COLUMN} 13.1.3.57.1.19
lcosLXStatusWLANRadiosEntryChannelBandwidth OBJECT-TYPE
    SYNTAX     INTEGER {
                  e20MHz(0),
                  e40MHz(1),
                  e80MHz(2),
                  e160MHz(3),
                  e320MHz(4),
                  eAuto(255)
               }
    MAX-ACCESS read-only
    STATUS     current
    DESCRIPTION
        ""
    ::= { lcosLXStatusWLANRadiosEntry 19 }

-- {COLUMN} 13.1.3.57.1.20
lcosLXStatusWLANRadiosEntryRxErrorRatio OBJECT-TYPE
    SYNTAX     Unsigned32 (0..65535)
    MAX-ACCESS read-only
    STATUS     current
    DESCRIPTION
        ""
    ::= { lcosLXStatusWLANRadiosEntry 20 }

-- {COLUMN} 13.1.3.57.1.21
lcosLXStatusWLANRadiosEntryTxErrorRatio OBJECT-TYPE
    SYNTAX     Unsigned32 (0..65535)
    MAX-ACCESS read-only
    STATUS     current
    DESCRIPTION
        ""
    ::= { lcosLXStatusWLANRadiosEntry 21 }

-- {COLUMN} 13.1.3.57.1.22
lcosLXStatusWLANRadiosEntryRxBytes OBJECT-TYPE
    SYNTAX     Counter64
    MAX-ACCESS read-only
    STATUS     current
    DESCRIPTION
        ""
    ::= { lcosLXStatusWLANRadiosEntry 22 }

-- {COLUMN} 13.1.3.57.1.23
lcosLXStatusWLANRadiosEntryTxBytes OBJECT-TYPE
    SYNTAX     Counter64
    MAX-ACCESS read-only
    STATUS     current
    DESCRIPTION
        ""
    ::= { lcosLXStatusWLANRadiosEntry 23 }

-- {COLUMN} 13.1.3.57.1.40
lcosLXStatusWLANRadiosEntryModemLoadMin OBJECT-TYPE
    SYNTAX     Unsigned32 (0..255)
    MAX-ACCESS read-only
    STATUS     current
    DESCRIPTION
        ""
    ::= { lcosLXStatusWLANRadiosEntry 40 }

-- {COLUMN} 13.1.3.57.1.41
lcosLXStatusWLANRadiosEntryModemLoadMax OBJECT-TYPE
    SYNTAX     Unsigned32 (0..255)
    MAX-ACCESS read-only
    STATUS     current
    DESCRIPTION
        ""
    ::= { lcosLXStatusWLANRadiosEntry 41 }

-- {COLUMN} 13.1.3.57.1.42
lcosLXStatusWLANRadiosEntryModemLoadAverage OBJECT-TYPE
    SYNTAX     Unsigned32 (0..255)
    MAX-ACCESS read-only
    STATUS     current
    DESCRIPTION
        ""
    ::= { lcosLXStatusWLANRadiosEntry 42 }

-- {COLUMN} 13.1.3.57.1.50
lcosLXStatusWLANRadiosEntryTemperatureDegrees OBJECT-TYPE
    SYNTAX     Unsigned32 (0..65535)
    MAX-ACCESS read-only
    STATUS     current
    DESCRIPTION
        ""
    ::= { lcosLXStatusWLANRadiosEntry 50 }

-- {COLUMN} 13.1.3.57.1.51
lcosLXStatusWLANRadiosEntryAllChannelsBlocked OBJECT-TYPE
    SYNTAX     INTEGER {
                  eNo(0),
                  eYes(1)
               }
    MAX-ACCESS read-only
    STATUS     current
    DESCRIPTION
        ""
    ::= { lcosLXStatusWLANRadiosEntry 51 }

-- {TABLE} 13.1.3.69
lcosLXStatusWLANEnvironmentScanResults OBJECT-TYPE
    SYNTAX     SEQUENCE OF LcosLXStatusWLANEnvironmentScanResultsEntry
    MAX-ACCESS not-accessible
    STATUS     current
    DESCRIPTION
        ""
    ::= { lcosLXStatusWLAN 69 }

-- {INDEX} 13.1.3.69
lcosLXStatusWLANEnvironmentScanResultsEntry OBJECT-TYPE
    SYNTAX     LcosLXStatusWLANEnvironmentScanResultsEntry
    MAX-ACCESS not-accessible
    STATUS     current
    DESCRIPTION
        ""
    INDEX {
        lcosLXStatusWLANEnvironmentScanResultsEntryBSSID
    }
    ::= { lcosLXStatusWLANEnvironmentScanResults 1 }

-- {SEQUENCE} 13.1.3.69
LcosLXStatusWLANEnvironmentScanResultsEntry ::= SEQUENCE {
    lcosLXStatusWLANEnvironmentScanResultsEntryBSSID OCTET STRING,
    lcosLXStatusWLANEnvironmentScanResultsEntrySSID OCTET STRING,
    lcosLXStatusWLANEnvironmentScanResultsEntryIfc OCTET STRING,
    lcosLXStatusWLANEnvironmentScanResultsEntryRadioChannel Unsigned32,
    lcosLXStatusWLANEnvironmentScanResultsEntryRadioBand INTEGER,
    lcosLXStatusWLANEnvironmentScanResultsEntrySignalLevel Integer32,
    lcosLXStatusWLANEnvironmentScanResultsEntrySignalLevelPercent Unsigned32,
    lcosLXStatusWLANEnvironmentScanResultsEntryChannelBandwidth Unsigned32,
    lcosLXStatusWLANEnvironmentScanResultsEntryUUID OCTET STRING,
    lcosLXStatusWLANEnvironmentScanResultsEntryDevicename OCTET STRING
}

-- {COLUMN} 13.1.3.69.1.1
lcosLXStatusWLANEnvironmentScanResultsEntryBSSID OBJECT-TYPE
    SYNTAX     OCTET STRING (SIZE(0..18))
    MAX-ACCESS not-accessible
    STATUS     current
    DESCRIPTION
        ""
    ::= { lcosLXStatusWLANEnvironmentScanResultsEntry 1 }

-- {COLUMN} 13.1.3.69.1.2
lcosLXStatusWLANEnvironmentScanResultsEntrySSID OBJECT-TYPE
    SYNTAX     OCTET STRING (SIZE(0..32))
    MAX-ACCESS read-only
    STATUS     current
    DESCRIPTION
        ""
    ::= { lcosLXStatusWLANEnvironmentScanResultsEntry 2 }

-- {COLUMN} 13.1.3.69.1.3
lcosLXStatusWLANEnvironmentScanResultsEntryIfc OBJECT-TYPE
    SYNTAX     OCTET STRING (SIZE(0..10))
    MAX-ACCESS read-only
    STATUS     current
    DESCRIPTION
        ""
    ::= { lcosLXStatusWLANEnvironmentScanResultsEntry 3 }

-- {COLUMN} 13.1.3.69.1.8
lcosLXStatusWLANEnvironmentScanResultsEntryRadioChannel OBJECT-TYPE
    SYNTAX     Unsigned32 (0..255)
    MAX-ACCESS read-only
    STATUS     current
    DESCRIPTION
        ""
    ::= { lcosLXStatusWLANEnvironmentScanResultsEntry 8 }

-- {COLUMN} 13.1.3.69.1.16
lcosLXStatusWLANEnvironmentScanResultsEntryRadioBand OBJECT-TYPE
    SYNTAX     INTEGER {
                  e24GHz(1),
                  e5GHz(2),
                  e6GHz(3)
               }
    MAX-ACCESS read-only
    STATUS     current
    DESCRIPTION
        ""
    ::= { lcosLXStatusWLANEnvironmentScanResultsEntry 16 }

-- {COLUMN} 13.1.3.69.1.26
lcosLXStatusWLANEnvironmentScanResultsEntrySignalLevel OBJECT-TYPE
    SYNTAX     Integer32 (-128..127)
    MAX-ACCESS read-only
    STATUS     current
    DESCRIPTION
        ""
    ::= { lcosLXStatusWLANEnvironmentScanResultsEntry 26 }

-- {COLUMN} 13.1.3.69.1.27
lcosLXStatusWLANEnvironmentScanResultsEntrySignalLevelPercent OBJECT-TYPE
    SYNTAX     Unsigned32 (0..255)
    MAX-ACCESS read-only
    STATUS     current
    DESCRIPTION
        ""
    ::= { lcosLXStatusWLANEnvironmentScanResultsEntry 27 }

-- {COLUMN} 13.1.3.69.1.45
lcosLXStatusWLANEnvironmentScanResultsEntryChannelBandwidth OBJECT-TYPE
    SYNTAX     Unsigned32 (0..255)
    MAX-ACCESS read-only
    STATUS     current
    DESCRIPTION
        ""
    ::= { lcosLXStatusWLANEnvironmentScanResultsEntry 45 }

-- {COLUMN} 13.1.3.69.1.80
lcosLXStatusWLANEnvironmentScanResultsEntryUUID OBJECT-TYPE
    SYNTAX     OCTET STRING (SIZE(0..36))
    MAX-ACCESS read-only
    STATUS     current
    DESCRIPTION
        ""
    ::= { lcosLXStatusWLANEnvironmentScanResultsEntry 80 }

-- {COLUMN} 13.1.3.69.1.81
lcosLXStatusWLANEnvironmentScanResultsEntryDevicename OBJECT-TYPE
    SYNTAX     OCTET STRING (SIZE(0..64))
    MAX-ACCESS read-only
    STATUS     current
    DESCRIPTION
        ""
    ::= { lcosLXStatusWLANEnvironmentScanResultsEntry 81 }

-- {TABLE} 13.1.3.70
lcosLXStatusWLANCompetingNetworks OBJECT-TYPE
    SYNTAX     SEQUENCE OF LcosLXStatusWLANCompetingNetworksEntry
    MAX-ACCESS not-accessible
    STATUS     current
    DESCRIPTION
        ""
    ::= { lcosLXStatusWLAN 70 }

-- {INDEX} 13.1.3.70
lcosLXStatusWLANCompetingNetworksEntry OBJECT-TYPE
    SYNTAX     LcosLXStatusWLANCompetingNetworksEntry
    MAX-ACCESS not-accessible
    STATUS     current
    DESCRIPTION
        ""
    INDEX {
        lcosLXStatusWLANCompetingNetworksEntryBSSID
    }
    ::= { lcosLXStatusWLANCompetingNetworks 1 }

-- {SEQUENCE} 13.1.3.70
LcosLXStatusWLANCompetingNetworksEntry ::= SEQUENCE {
    lcosLXStatusWLANCompetingNetworksEntryBSSID OCTET STRING,
    lcosLXStatusWLANCompetingNetworksEntrySSID OCTET STRING,
    lcosLXStatusWLANCompetingNetworksEntryIfc OCTET STRING,
    lcosLXStatusWLANCompetingNetworksEntryRadioChannel Unsigned32,
    lcosLXStatusWLANCompetingNetworksEntryRadioBand INTEGER,
    lcosLXStatusWLANCompetingNetworksEntrySignalLevel Integer32,
    lcosLXStatusWLANCompetingNetworksEntrySignalLevelPercent Unsigned32,
    lcosLXStatusWLANCompetingNetworksEntryChannelBandwidth Unsigned32,
    lcosLXStatusWLANCompetingNetworksEntryUUID OCTET STRING,
    lcosLXStatusWLANCompetingNetworksEntryDevicename OCTET STRING
}

-- {COLUMN} 13.1.3.70.1.1
lcosLXStatusWLANCompetingNetworksEntryBSSID OBJECT-TYPE
    SYNTAX     OCTET STRING (SIZE(0..18))
    MAX-ACCESS not-accessible
    STATUS     current
    DESCRIPTION
        ""
    ::= { lcosLXStatusWLANCompetingNetworksEntry 1 }

-- {COLUMN} 13.1.3.70.1.2
lcosLXStatusWLANCompetingNetworksEntrySSID OBJECT-TYPE
    SYNTAX     OCTET STRING (SIZE(0..32))
    MAX-ACCESS read-only
    STATUS     current
    DESCRIPTION
        ""
    ::= { lcosLXStatusWLANCompetingNetworksEntry 2 }

-- {COLUMN} 13.1.3.70.1.3
lcosLXStatusWLANCompetingNetworksEntryIfc OBJECT-TYPE
    SYNTAX     OCTET STRING (SIZE(0..10))
    MAX-ACCESS read-only
    STATUS     current
    DESCRIPTION
        ""
    ::= { lcosLXStatusWLANCompetingNetworksEntry 3 }

-- {COLUMN} 13.1.3.70.1.8
lcosLXStatusWLANCompetingNetworksEntryRadioChannel OBJECT-TYPE
    SYNTAX     Unsigned32 (0..255)
    MAX-ACCESS read-only
    STATUS     current
    DESCRIPTION
        ""
    ::= { lcosLXStatusWLANCompetingNetworksEntry 8 }

-- {COLUMN} 13.1.3.70.1.16
lcosLXStatusWLANCompetingNetworksEntryRadioBand OBJECT-TYPE
    SYNTAX     INTEGER {
                  e24GHz(1),
                  e5GHz(2),
                  e6GHz(3)
               }
    MAX-ACCESS read-only
    STATUS     current
    DESCRIPTION
        ""
    ::= { lcosLXStatusWLANCompetingNetworksEntry 16 }

-- {COLUMN} 13.1.3.70.1.26
lcosLXStatusWLANCompetingNetworksEntrySignalLevel OBJECT-TYPE
    SYNTAX     Integer32 (-128..127)
    MAX-ACCESS read-only
    STATUS     current
    DESCRIPTION
        ""
    ::= { lcosLXStatusWLANCompetingNetworksEntry 26 }

-- {COLUMN} 13.1.3.70.1.27
lcosLXStatusWLANCompetingNetworksEntrySignalLevelPercent OBJECT-TYPE
    SYNTAX     Unsigned32 (0..255)
    MAX-ACCESS read-only
    STATUS     current
    DESCRIPTION
        ""
    ::= { lcosLXStatusWLANCompetingNetworksEntry 27 }

-- {COLUMN} 13.1.3.70.1.45
lcosLXStatusWLANCompetingNetworksEntryChannelBandwidth OBJECT-TYPE
    SYNTAX     Unsigned32 (0..255)
    MAX-ACCESS read-only
    STATUS     current
    DESCRIPTION
        ""
    ::= { lcosLXStatusWLANCompetingNetworksEntry 45 }

-- {COLUMN} 13.1.3.70.1.80
lcosLXStatusWLANCompetingNetworksEntryUUID OBJECT-TYPE
    SYNTAX     OCTET STRING (SIZE(0..36))
    MAX-ACCESS read-only
    STATUS     current
    DESCRIPTION
        ""
    ::= { lcosLXStatusWLANCompetingNetworksEntry 80 }

-- {COLUMN} 13.1.3.70.1.81
lcosLXStatusWLANCompetingNetworksEntryDevicename OBJECT-TYPE
    SYNTAX     OCTET STRING (SIZE(0..64))
    MAX-ACCESS read-only
    STATUS     current
    DESCRIPTION
        ""
    ::= { lcosLXStatusWLANCompetingNetworksEntry 81 }

-- {TABLE} 13.1.3.100
lcosLXStatusWLANChannelsAllowedByRegulatory OBJECT-TYPE
    SYNTAX     SEQUENCE OF LcosLXStatusWLANChannelsAllowedByRegulatoryEntry
    MAX-ACCESS not-accessible
    STATUS     current
    DESCRIPTION
        ""
    ::= { lcosLXStatusWLAN 100 }

-- {INDEX} 13.1.3.100
lcosLXStatusWLANChannelsAllowedByRegulatoryEntry OBJECT-TYPE
    SYNTAX     LcosLXStatusWLANChannelsAllowedByRegulatoryEntry
    MAX-ACCESS not-accessible
    STATUS     current
    DESCRIPTION
        ""
    INDEX {
        lcosLXStatusWLANChannelsAllowedByRegulatoryEntryChannel,
        lcosLXStatusWLANChannelsAllowedByRegulatoryEntryRadioBand
    }
    ::= { lcosLXStatusWLANChannelsAllowedByRegulatory 1 }

-- {SEQUENCE} 13.1.3.100
LcosLXStatusWLANChannelsAllowedByRegulatoryEntry ::= SEQUENCE {
    lcosLXStatusWLANChannelsAllowedByRegulatoryEntryChannel Unsigned32,
    lcosLXStatusWLANChannelsAllowedByRegulatoryEntryOutdoor INTEGER,
    lcosLXStatusWLANChannelsAllowedByRegulatoryEntryDFS INTEGER,
    lcosLXStatusWLANChannelsAllowedByRegulatoryEntryWeatherRadarChan INTEGER,
    lcosLXStatusWLANChannelsAllowedByRegulatoryEntryRadioBand INTEGER
}

-- {COLUMN} 13.1.3.100.1.1
lcosLXStatusWLANChannelsAllowedByRegulatoryEntryChannel OBJECT-TYPE
    SYNTAX     Unsigned32 (0..65535)
    MAX-ACCESS not-accessible
    STATUS     current
    DESCRIPTION
        ""
    ::= { lcosLXStatusWLANChannelsAllowedByRegulatoryEntry 1 }

-- {COLUMN} 13.1.3.100.1.2
lcosLXStatusWLANChannelsAllowedByRegulatoryEntryOutdoor OBJECT-TYPE
    SYNTAX     INTEGER {
                  eNo(0),
                  eYes(1)
               }
    MAX-ACCESS read-only
    STATUS     current
    DESCRIPTION
        ""
    ::= { lcosLXStatusWLANChannelsAllowedByRegulatoryEntry 2 }

-- {COLUMN} 13.1.3.100.1.3
lcosLXStatusWLANChannelsAllowedByRegulatoryEntryDFS OBJECT-TYPE
    SYNTAX     INTEGER {
                  eNo(0),
                  eYes(1)
               }
    MAX-ACCESS read-only
    STATUS     current
    DESCRIPTION
        ""
    ::= { lcosLXStatusWLANChannelsAllowedByRegulatoryEntry 3 }

-- {COLUMN} 13.1.3.100.1.4
lcosLXStatusWLANChannelsAllowedByRegulatoryEntryWeatherRadarChan OBJECT-TYPE
    SYNTAX     INTEGER {
                  eNo(0),
                  eYes(1)
               }
    MAX-ACCESS read-only
    STATUS     current
    DESCRIPTION
        ""
    ::= { lcosLXStatusWLANChannelsAllowedByRegulatoryEntry 4 }

-- {COLUMN} 13.1.3.100.1.5
lcosLXStatusWLANChannelsAllowedByRegulatoryEntryRadioBand OBJECT-TYPE
    SYNTAX     INTEGER {
                  e24GHz(1),
                  e5GHz(2),
                  e6GHz(3)
               }
    MAX-ACCESS not-accessible
    STATUS     current
    DESCRIPTION
        ""
    ::= { lcosLXStatusWLANChannelsAllowedByRegulatoryEntry 5 }

-- {OID} 13.1.3.101
lcosLXStatusWLANWDS OBJECT IDENTIFIER ::= { lcosLXStatusWLAN 101 }

-- {TABLE} 13.1.3.101.1
lcosLXStatusWLANWDSLinks OBJECT-TYPE
    SYNTAX     SEQUENCE OF LcosLXStatusWLANWDSLinksEntry
    MAX-ACCESS not-accessible
    STATUS     current
    DESCRIPTION
        ""
    ::= { lcosLXStatusWLANWDS 1 }

-- {INDEX} 13.1.3.101.1
lcosLXStatusWLANWDSLinksEntry OBJECT-TYPE
    SYNTAX     LcosLXStatusWLANWDSLinksEntry
    MAX-ACCESS not-accessible
    STATUS     current
    DESCRIPTION
        ""
    INDEX {
        lcosLXStatusWLANWDSLinksEntryLinkName,
        lcosLXStatusWLANWDSLinksEntryMACAddress
    }
    ::= { lcosLXStatusWLANWDSLinks 1 }

-- {SEQUENCE} 13.1.3.101.1
LcosLXStatusWLANWDSLinksEntry ::= SEQUENCE {
    lcosLXStatusWLANWDSLinksEntryLinkName OCTET STRING,
    lcosLXStatusWLANWDSLinksEntryMACAddress OCTET STRING,
    lcosLXStatusWLANWDSLinksEntryConnected INTEGER,
    lcosLXStatusWLANWDSLinksEntryRadio INTEGER,
    lcosLXStatusWLANWDSLinksEntryRxPhySignal Unsigned32,
    lcosLXStatusWLANWDSLinksEntryRemoteMode INTEGER,
    lcosLXStatusWLANWDSLinksEntryEffTxRate Unsigned32,
    lcosLXStatusWLANWDSLinksEntryEffRxRate Unsigned32,
    lcosLXStatusWLANWDSLinksEntryTxPackets Counter64,
    lcosLXStatusWLANWDSLinksEntryTxBytes Counter64,
    lcosLXStatusWLANWDSLinksEntryRxPackets Counter64,
    lcosLXStatusWLANWDSLinksEntryRxBytes Counter64,
    lcosLXStatusWLANWDSLinksEntryWPAVersion INTEGER
}

-- {COLUMN} 13.1.3.101.1.1.1
lcosLXStatusWLANWDSLinksEntryLinkName OBJECT-TYPE
    SYNTAX     OCTET STRING (SIZE(0..64))
    MAX-ACCESS not-accessible
    STATUS     current
    DESCRIPTION
        ""
    ::= { lcosLXStatusWLANWDSLinksEntry 1 }

-- {COLUMN} 13.1.3.101.1.1.2
lcosLXStatusWLANWDSLinksEntryMACAddress OBJECT-TYPE
    SYNTAX     OCTET STRING (SIZE(0..17))
    MAX-ACCESS not-accessible
    STATUS     current
    DESCRIPTION
        ""
    ::= { lcosLXStatusWLANWDSLinksEntry 2 }

-- {COLUMN} 13.1.3.101.1.1.3
lcosLXStatusWLANWDSLinksEntryConnected OBJECT-TYPE
    SYNTAX     INTEGER {
                  eNo(0),
                  eYes(1)
               }
    MAX-ACCESS read-only
    STATUS     current
    DESCRIPTION
        ""
    ::= { lcosLXStatusWLANWDSLinksEntry 3 }

-- {COLUMN} 13.1.3.101.1.1.4
lcosLXStatusWLANWDSLinksEntryRadio OBJECT-TYPE
    SYNTAX     INTEGER {
                  e24GHz(1),
                  e5GHz(2),
                  e6GHz(3)
               }
    MAX-ACCESS read-only
    STATUS     current
    DESCRIPTION
        ""
    ::= { lcosLXStatusWLANWDSLinksEntry 4 }

-- {COLUMN} 13.1.3.101.1.1.5
lcosLXStatusWLANWDSLinksEntryRxPhySignal OBJECT-TYPE
    SYNTAX     Unsigned32 (0..255)
    MAX-ACCESS read-only
    STATUS     current
    DESCRIPTION
        ""
    ::= { lcosLXStatusWLANWDSLinksEntry 5 }

-- {COLUMN} 13.1.3.101.1.1.6
lcosLXStatusWLANWDSLinksEntryRemoteMode OBJECT-TYPE
    SYNTAX     INTEGER {
                  eAccessPoint(0),
                  eStation(1),
                  eLegacyStation(2)
               }
    MAX-ACCESS read-only
    STATUS     current
    DESCRIPTION
        ""
    ::= { lcosLXStatusWLANWDSLinksEntry 6 }

-- {COLUMN} 13.1.3.101.1.1.7
lcosLXStatusWLANWDSLinksEntryEffTxRate OBJECT-TYPE
    SYNTAX     Unsigned32 (0..4294967295)
    MAX-ACCESS read-only
    STATUS     current
    DESCRIPTION
        ""
    ::= { lcosLXStatusWLANWDSLinksEntry 7 }

-- {COLUMN} 13.1.3.101.1.1.8
lcosLXStatusWLANWDSLinksEntryEffRxRate OBJECT-TYPE
    SYNTAX     Unsigned32 (0..4294967295)
    MAX-ACCESS read-only
    STATUS     current
    DESCRIPTION
        ""
    ::= { lcosLXStatusWLANWDSLinksEntry 8 }

-- {COLUMN} 13.1.3.101.1.1.9
lcosLXStatusWLANWDSLinksEntryTxPackets OBJECT-TYPE
    SYNTAX     Counter64
    MAX-ACCESS read-only
    STATUS     current
    DESCRIPTION
        ""
    ::= { lcosLXStatusWLANWDSLinksEntry 9 }

-- {COLUMN} 13.1.3.101.1.1.10
lcosLXStatusWLANWDSLinksEntryTxBytes OBJECT-TYPE
    SYNTAX     Counter64
    MAX-ACCESS read-only
    STATUS     current
    DESCRIPTION
        ""
    ::= { lcosLXStatusWLANWDSLinksEntry 10 }

-- {COLUMN} 13.1.3.101.1.1.11
lcosLXStatusWLANWDSLinksEntryRxPackets OBJECT-TYPE
    SYNTAX     Counter64
    MAX-ACCESS read-only
    STATUS     current
    DESCRIPTION
        ""
    ::= { lcosLXStatusWLANWDSLinksEntry 11 }

-- {COLUMN} 13.1.3.101.1.1.12
lcosLXStatusWLANWDSLinksEntryRxBytes OBJECT-TYPE
    SYNTAX     Counter64
    MAX-ACCESS read-only
    STATUS     current
    DESCRIPTION
        ""
    ::= { lcosLXStatusWLANWDSLinksEntry 12 }

-- {COLUMN} 13.1.3.101.1.1.13
lcosLXStatusWLANWDSLinksEntryWPAVersion OBJECT-TYPE
    SYNTAX     INTEGER {
                  eNone(0),
                  eWPA1(1),
                  eWPA2(2),
                  eWPA3(3)
               }
    MAX-ACCESS read-only
    STATUS     current
    DESCRIPTION
        ""
    ::= { lcosLXStatusWLANWDSLinksEntry 13 }

-- {SCALAR} 13.1.3.101.3
lcosLXStatusWLANWDSContinuousProbeRequestsRunning OBJECT-TYPE
    SYNTAX     INTEGER {
                  eNo(0),
                  eYes(1)
               }
    MAX-ACCESS read-only
    STATUS     current
    DESCRIPTION
        ""
    ::= { lcosLXStatusWLANWDS 3 }

-- {OID} 13.1.5
lcosLXStatusLAN OBJECT IDENTIFIER ::= { lcosLXStatus 5 }

-- {OID} 13.1.5.1
lcosLXStatusLANSpanningTree OBJECT IDENTIFIER ::= { lcosLXStatusLAN 1 }

-- {SCALAR} 13.1.5.1.1
lcosLXStatusLANSpanningTreeOperating OBJECT-TYPE
    SYNTAX     INTEGER {
                  eNo(0),
                  eYes(1)
               }
    MAX-ACCESS read-only
    STATUS     current
    DESCRIPTION
        ""
    ::= { lcosLXStatusLANSpanningTree 1 }

-- {SCALAR} 13.1.5.1.2
lcosLXStatusLANSpanningTreeBridgeID OBJECT-TYPE
    SYNTAX     OCTET STRING (SIZE(0..64))
    MAX-ACCESS read-only
    STATUS     current
    DESCRIPTION
        ""
    ::= { lcosLXStatusLANSpanningTree 2 }

-- {SCALAR} 13.1.5.1.3
lcosLXStatusLANSpanningTreeBridgePriority OBJECT-TYPE
    SYNTAX     INTEGER {
                  e0(0),
                  e4096(1),
                  e8192(2),
                  e12288(3),
                  e16384(4),
                  e20480(5),
                  e24576(6),
                  e28672(7),
                  e32768(8),
                  e36864(9),
                  e40960(10),
                  e45056(11),
                  e49152(12),
                  e53248(13),
                  e57344(14),
                  e61440(15)
               }
    MAX-ACCESS read-only
    STATUS     current
    DESCRIPTION
        ""
    ::= { lcosLXStatusLANSpanningTree 3 }

-- {SCALAR} 13.1.5.1.4
lcosLXStatusLANSpanningTreeRootBridge OBJECT-TYPE
    SYNTAX     OCTET STRING (SIZE(0..64))
    MAX-ACCESS read-only
    STATUS     current
    DESCRIPTION
        ""
    ::= { lcosLXStatusLANSpanningTree 4 }

-- {SCALAR} 13.1.5.1.5
lcosLXStatusLANSpanningTreeRootPort OBJECT-TYPE
    SYNTAX     OCTET STRING (SIZE(0..64))
    MAX-ACCESS read-only
    STATUS     current
    DESCRIPTION
        ""
    ::= { lcosLXStatusLANSpanningTree 5 }

-- {SCALAR} 13.1.5.1.6
lcosLXStatusLANSpanningTreeRootPathCost OBJECT-TYPE
    SYNTAX     Unsigned32 (0..4294967295)
    MAX-ACCESS read-only
    STATUS     current
    DESCRIPTION
        ""
    ::= { lcosLXStatusLANSpanningTree 6 }

-- {SCALAR} 13.1.5.1.7
lcosLXStatusLANSpanningTreeProtocolVersion OBJECT-TYPE
    SYNTAX     INTEGER {
                  eClassic(0),
                  eRapid(1)
               }
    MAX-ACCESS read-only
    STATUS     current
    DESCRIPTION
        ""
    ::= { lcosLXStatusLANSpanningTree 7 }

-- {TABLE} 13.1.5.1.8
lcosLXStatusLANSpanningTreePortTable OBJECT-TYPE
    SYNTAX     SEQUENCE OF LcosLXStatusLANSpanningTreePortEntry
    MAX-ACCESS not-accessible
    STATUS     current
    DESCRIPTION
        ""
    ::= { lcosLXStatusLANSpanningTree 8 }

-- {INDEX} 13.1.5.1.8
lcosLXStatusLANSpanningTreePortEntry OBJECT-TYPE
    SYNTAX     LcosLXStatusLANSpanningTreePortEntry
    MAX-ACCESS not-accessible
    STATUS     current
    DESCRIPTION
        ""
    INDEX {
        lcosLXStatusLANSpanningTreePortEntryPort
    }
    ::= { lcosLXStatusLANSpanningTreePortTable 1 }

-- {SEQUENCE} 13.1.5.1.8
LcosLXStatusLANSpanningTreePortEntry ::= SEQUENCE {
    lcosLXStatusLANSpanningTreePortEntryPort OCTET STRING,
    lcosLXStatusLANSpanningTreePortEntryPriority INTEGER,
    lcosLXStatusLANSpanningTreePortEntryState OCTET STRING,
    lcosLXStatusLANSpanningTreePortEntryRoot OCTET STRING,
    lcosLXStatusLANSpanningTreePortEntryBridge OCTET STRING,
    lcosLXStatusLANSpanningTreePortEntryPathCost Unsigned32,
    lcosLXStatusLANSpanningTreePortEntryRole OCTET STRING,
    lcosLXStatusLANSpanningTreePortEntryEdgePort INTEGER
}

-- {COLUMN} 13.1.5.1.8.1.1
lcosLXStatusLANSpanningTreePortEntryPort OBJECT-TYPE
    SYNTAX     OCTET STRING (SIZE(0..64))
    MAX-ACCESS not-accessible
    STATUS     current
    DESCRIPTION
        ""
    ::= { lcosLXStatusLANSpanningTreePortEntry 1 }

-- {COLUMN} 13.1.5.1.8.1.2
lcosLXStatusLANSpanningTreePortEntryPriority OBJECT-TYPE
    SYNTAX     INTEGER {
                  e0(0),
                  e16(1),
                  e32(2),
                  e48(3),
                  e64(4),
                  e80(5),
                  e96(6),
                  e112(7),
                  e128(8),
                  e144(9),
                  e160(10),
                  e176(11),
                  e192(12),
                  e208(13),
                  e224(14),
                  e240(15)
               }
    MAX-ACCESS read-only
    STATUS     current
    DESCRIPTION
        ""
    ::= { lcosLXStatusLANSpanningTreePortEntry 2 }

-- {COLUMN} 13.1.5.1.8.1.3
lcosLXStatusLANSpanningTreePortEntryState OBJECT-TYPE
    SYNTAX     OCTET STRING (SIZE(0..64))
    MAX-ACCESS read-only
    STATUS     current
    DESCRIPTION
        ""
    ::= { lcosLXStatusLANSpanningTreePortEntry 3 }

-- {COLUMN} 13.1.5.1.8.1.4
lcosLXStatusLANSpanningTreePortEntryRoot OBJECT-TYPE
    SYNTAX     OCTET STRING (SIZE(0..64))
    MAX-ACCESS read-only
    STATUS     current
    DESCRIPTION
        ""
    ::= { lcosLXStatusLANSpanningTreePortEntry 4 }

-- {COLUMN} 13.1.5.1.8.1.5
lcosLXStatusLANSpanningTreePortEntryBridge OBJECT-TYPE
    SYNTAX     OCTET STRING (SIZE(0..64))
    MAX-ACCESS read-only
    STATUS     current
    DESCRIPTION
        ""
    ::= { lcosLXStatusLANSpanningTreePortEntry 5 }

-- {COLUMN} 13.1.5.1.8.1.6
lcosLXStatusLANSpanningTreePortEntryPathCost OBJECT-TYPE
    SYNTAX     Unsigned32 (0..4294967295)
    MAX-ACCESS read-only
    STATUS     current
    DESCRIPTION
        ""
    ::= { lcosLXStatusLANSpanningTreePortEntry 6 }

-- {COLUMN} 13.1.5.1.8.1.7
lcosLXStatusLANSpanningTreePortEntryRole OBJECT-TYPE
    SYNTAX     OCTET STRING (SIZE(0..64))
    MAX-ACCESS read-only
    STATUS     current
    DESCRIPTION
        ""
    ::= { lcosLXStatusLANSpanningTreePortEntry 7 }

-- {COLUMN} 13.1.5.1.8.1.8
lcosLXStatusLANSpanningTreePortEntryEdgePort OBJECT-TYPE
    SYNTAX     INTEGER {
                  eNo(0),
                  eYes(1)
               }
    MAX-ACCESS read-only
    STATUS     current
    DESCRIPTION
        ""
    ::= { lcosLXStatusLANSpanningTreePortEntry 8 }

-- {TABLE} 13.1.5.44
lcosLXStatusLANLACP OBJECT-TYPE
    SYNTAX     SEQUENCE OF LcosLXStatusLANLACPEntry
    MAX-ACCESS not-accessible
    STATUS     current
    DESCRIPTION
        ""
    ::= { lcosLXStatusLAN 44 }

-- {INDEX} 13.1.5.44
lcosLXStatusLANLACPEntry OBJECT-TYPE
    SYNTAX     LcosLXStatusLANLACPEntry
    MAX-ACCESS not-accessible
    STATUS     current
    DESCRIPTION
        ""
    INDEX {
        lcosLXStatusLANLACPEntryBondName
    }
    ::= { lcosLXStatusLANLACP 1 }

-- {SEQUENCE} 13.1.5.44
LcosLXStatusLANLACPEntry ::= SEQUENCE {
    lcosLXStatusLANLACPEntryBondName OCTET STRING,
    lcosLXStatusLANLACPEntryStatus OCTET STRING,
    lcosLXStatusLANLACPEntryTimeout OCTET STRING,
    lcosLXStatusLANLACPEntryPriority Unsigned32,
    lcosLXStatusLANLACPEntryAggrID Unsigned32,
    lcosLXStatusLANLACPEntryLocalID OCTET STRING,
    lcosLXStatusLANLACPEntryLocalKey Unsigned32,
    lcosLXStatusLANLACPEntryPartnerID OCTET STRING,
    lcosLXStatusLANLACPEntryPartnerKey Unsigned32,
    lcosLXStatusLANLACPEntryLocalPorts OCTET STRING,
    lcosLXStatusLANLACPEntryBundleState OCTET STRING
}

-- {COLUMN} 13.1.5.44.1.1
lcosLXStatusLANLACPEntryBondName OBJECT-TYPE
    SYNTAX     OCTET STRING (SIZE(0..10))
    MAX-ACCESS not-accessible
    STATUS     current
    DESCRIPTION
        ""
    ::= { lcosLXStatusLANLACPEntry 1 }

-- {COLUMN} 13.1.5.44.1.2
lcosLXStatusLANLACPEntryStatus OBJECT-TYPE
    SYNTAX     OCTET STRING (SIZE(0..5))
    MAX-ACCESS read-only
    STATUS     current
    DESCRIPTION
        ""
    ::= { lcosLXStatusLANLACPEntry 2 }

-- {COLUMN} 13.1.5.44.1.3
lcosLXStatusLANLACPEntryTimeout OBJECT-TYPE
    SYNTAX     OCTET STRING (SIZE(0..8))
    MAX-ACCESS read-only
    STATUS     current
    DESCRIPTION
        ""
    ::= { lcosLXStatusLANLACPEntry 3 }

-- {COLUMN} 13.1.5.44.1.4
lcosLXStatusLANLACPEntryPriority OBJECT-TYPE
    SYNTAX     Unsigned32 (0..65535)
    MAX-ACCESS read-only
    STATUS     current
    DESCRIPTION
        ""
    ::= { lcosLXStatusLANLACPEntry 4 }

-- {COLUMN} 13.1.5.44.1.5
lcosLXStatusLANLACPEntryAggrID OBJECT-TYPE
    SYNTAX     Unsigned32 (0..65535)
    MAX-ACCESS read-only
    STATUS     current
    DESCRIPTION
        ""
    ::= { lcosLXStatusLANLACPEntry 5 }

-- {COLUMN} 13.1.5.44.1.6
lcosLXStatusLANLACPEntryLocalID OBJECT-TYPE
    SYNTAX     OCTET STRING (SIZE(0..24))
    MAX-ACCESS read-only
    STATUS     current
    DESCRIPTION
        ""
    ::= { lcosLXStatusLANLACPEntry 6 }

-- {COLUMN} 13.1.5.44.1.7
lcosLXStatusLANLACPEntryLocalKey OBJECT-TYPE
    SYNTAX     Unsigned32 (0..65535)
    MAX-ACCESS read-only
    STATUS     current
    DESCRIPTION
        ""
    ::= { lcosLXStatusLANLACPEntry 7 }

-- {COLUMN} 13.1.5.44.1.8
lcosLXStatusLANLACPEntryPartnerID OBJECT-TYPE
    SYNTAX     OCTET STRING (SIZE(0..24))
    MAX-ACCESS read-only
    STATUS     current
    DESCRIPTION
        ""
    ::= { lcosLXStatusLANLACPEntry 8 }

-- {COLUMN} 13.1.5.44.1.9
lcosLXStatusLANLACPEntryPartnerKey OBJECT-TYPE
    SYNTAX     Unsigned32 (0..65535)
    MAX-ACCESS read-only
    STATUS     current
    DESCRIPTION
        ""
    ::= { lcosLXStatusLANLACPEntry 9 }

-- {COLUMN} 13.1.5.44.1.10
lcosLXStatusLANLACPEntryLocalPorts OBJECT-TYPE
    SYNTAX     OCTET STRING (SIZE(0..32))
    MAX-ACCESS read-only
    STATUS     current
    DESCRIPTION
        ""
    ::= { lcosLXStatusLANLACPEntry 10 }

-- {COLUMN} 13.1.5.44.1.11
lcosLXStatusLANLACPEntryBundleState OBJECT-TYPE
    SYNTAX     OCTET STRING (SIZE(0..32))
    MAX-ACCESS read-only
    STATUS     current
    DESCRIPTION
        ""
    ::= { lcosLXStatusLANLACPEntry 11 }

-- {TABLE} 13.1.5.52
lcosLXStatusLANByteTransport OBJECT-TYPE
    SYNTAX     SEQUENCE OF LcosLXStatusLANByteTransportEntry
    MAX-ACCESS not-accessible
    STATUS     current
    DESCRIPTION
        ""
    ::= { lcosLXStatusLAN 52 }

-- {INDEX} 13.1.5.52
lcosLXStatusLANByteTransportEntry OBJECT-TYPE
    SYNTAX     LcosLXStatusLANByteTransportEntry
    MAX-ACCESS not-accessible
    STATUS     current
    DESCRIPTION
        ""
    INDEX {
        lcosLXStatusLANByteTransportEntryPort
    }
    ::= { lcosLXStatusLANByteTransport 1 }

-- {SEQUENCE} 13.1.5.52
LcosLXStatusLANByteTransportEntry ::= SEQUENCE {
    lcosLXStatusLANByteTransportEntryPort OCTET STRING,
    lcosLXStatusLANByteTransportEntryTxBytes Counter64,
    lcosLXStatusLANByteTransportEntryRxBytes Counter64,
    lcosLXStatusLANByteTransportEntryRxCRCErrors Counter64
}

-- {COLUMN} 13.1.5.52.1.1
lcosLXStatusLANByteTransportEntryPort OBJECT-TYPE
    SYNTAX     OCTET STRING (SIZE(0..5))
    MAX-ACCESS not-accessible
    STATUS     current
    DESCRIPTION
        ""
    ::= { lcosLXStatusLANByteTransportEntry 1 }

-- {COLUMN} 13.1.5.52.1.2
lcosLXStatusLANByteTransportEntryTxBytes OBJECT-TYPE
    SYNTAX     Counter64
    MAX-ACCESS read-only
    STATUS     current
    DESCRIPTION
        ""
    ::= { lcosLXStatusLANByteTransportEntry 2 }

-- {COLUMN} 13.1.5.52.1.3
lcosLXStatusLANByteTransportEntryRxBytes OBJECT-TYPE
    SYNTAX     Counter64
    MAX-ACCESS read-only
    STATUS     current
    DESCRIPTION
        ""
    ::= { lcosLXStatusLANByteTransportEntry 3 }

-- {COLUMN} 13.1.5.52.1.4
lcosLXStatusLANByteTransportEntryRxCRCErrors OBJECT-TYPE
    SYNTAX     Counter64
    MAX-ACCESS read-only
    STATUS     current
    DESCRIPTION
        ""
    ::= { lcosLXStatusLANByteTransportEntry 4 }

-- {TABLE} 13.1.5.99
lcosLXStatusLANPorts OBJECT-TYPE
    SYNTAX     SEQUENCE OF LcosLXStatusLANPortsEntry
    MAX-ACCESS not-accessible
    STATUS     current
    DESCRIPTION
        ""
    ::= { lcosLXStatusLAN 99 }

-- {INDEX} 13.1.5.99
lcosLXStatusLANPortsEntry OBJECT-TYPE
    SYNTAX     LcosLXStatusLANPortsEntry
    MAX-ACCESS not-accessible
    STATUS     current
    DESCRIPTION
        ""
    INDEX {
        lcosLXStatusLANPortsEntryPort
    }
    ::= { lcosLXStatusLANPorts 1 }

-- {SEQUENCE} 13.1.5.99
LcosLXStatusLANPortsEntry ::= SEQUENCE {
    lcosLXStatusLANPortsEntryPort OCTET STRING,
    lcosLXStatusLANPortsEntryLinkActive INTEGER,
    lcosLXStatusLANPortsEntryConnector INTEGER,
    lcosLXStatusLANPortsEntryMACAddress MacAddress
}

-- {COLUMN} 13.1.5.99.1.1
lcosLXStatusLANPortsEntryPort OBJECT-TYPE
    SYNTAX     OCTET STRING (SIZE(0..5))
    MAX-ACCESS not-accessible
    STATUS     current
    DESCRIPTION
        ""
    ::= { lcosLXStatusLANPortsEntry 1 }

-- {COLUMN} 13.1.5.99.1.2
lcosLXStatusLANPortsEntryLinkActive OBJECT-TYPE
    SYNTAX     INTEGER {
                  eNo(0),
                  eYes(1)
               }
    MAX-ACCESS read-only
    STATUS     current
    DESCRIPTION
        ""
    ::= { lcosLXStatusLANPortsEntry 2 }

-- {COLUMN} 13.1.5.99.1.3
lcosLXStatusLANPortsEntryConnector OBJECT-TYPE
    SYNTAX     INTEGER {
                  eNone(0),
                  e10BT(1),
                  eFD10BTX(2),
                  e100BTX(3),
                  eFD100BTX(4),
                  eFD1000BTX(6),
                  eFD2500BTX(9),
                  eFD5000BTX(10),
                  eFD10GBTX(11),
                  ePowerDown(255)
               }
    MAX-ACCESS read-only
    STATUS     current
    DESCRIPTION
        ""
    ::= { lcosLXStatusLANPortsEntry 3 }

-- {COLUMN} 13.1.5.99.1.4
lcosLXStatusLANPortsEntryMACAddress OBJECT-TYPE
    SYNTAX     MacAddress
    MAX-ACCESS read-only
    STATUS     current
    DESCRIPTION
        ""
    ::= { lcosLXStatusLANPortsEntry 4 }

-- {OID} 13.1.11
lcosLXStatusConfig OBJECT IDENTIFIER ::= { lcosLXStatus 11 }

-- {TABLE} 13.1.11.71
lcosLXStatusConfigServices OBJECT-TYPE
    SYNTAX     SEQUENCE OF LcosLXStatusConfigServicesEntry
    MAX-ACCESS not-accessible
    STATUS     current
    DESCRIPTION
        ""
    ::= { lcosLXStatusConfig 71 }

-- {INDEX} 13.1.11.71
lcosLXStatusConfigServicesEntry OBJECT-TYPE
    SYNTAX     LcosLXStatusConfigServicesEntry
    MAX-ACCESS not-accessible
    STATUS     current
    DESCRIPTION
        ""
    INDEX {
        lcosLXStatusConfigServicesEntryService
    }
    ::= { lcosLXStatusConfigServices 1 }

-- {SEQUENCE} 13.1.11.71
LcosLXStatusConfigServicesEntry ::= SEQUENCE {
    lcosLXStatusConfigServicesEntryService OCTET STRING,
    lcosLXStatusConfigServicesEntryPort Unsigned32,
    lcosLXStatusConfigServicesEntryProtocol OCTET STRING,
    lcosLXStatusConfigServicesEntryActive INTEGER,
    lcosLXStatusConfigServicesEntryLAN INTEGER,
    lcosLXStatusConfigServicesEntryWLAN INTEGER
}

-- {COLUMN} 13.1.11.71.1.1
lcosLXStatusConfigServicesEntryService OBJECT-TYPE
    SYNTAX     OCTET STRING (SIZE(0..10))
    MAX-ACCESS not-accessible
    STATUS     current
    DESCRIPTION
        ""
    ::= { lcosLXStatusConfigServicesEntry 1 }

-- {COLUMN} 13.1.11.71.1.2
lcosLXStatusConfigServicesEntryPort OBJECT-TYPE
    SYNTAX     Unsigned32 (0..65535)
    MAX-ACCESS read-only
    STATUS     current
    DESCRIPTION
        ""
    ::= { lcosLXStatusConfigServicesEntry 2 }

-- {COLUMN} 13.1.11.71.1.3
lcosLXStatusConfigServicesEntryProtocol OBJECT-TYPE
    SYNTAX     OCTET STRING (SIZE(0..5))
    MAX-ACCESS read-only
    STATUS     current
    DESCRIPTION
        ""
    ::= { lcosLXStatusConfigServicesEntry 3 }

-- {COLUMN} 13.1.11.71.1.4
lcosLXStatusConfigServicesEntryActive OBJECT-TYPE
    SYNTAX     INTEGER {
                  eNo(0),
                  eYes(1)
               }
    MAX-ACCESS read-only
    STATUS     current
    DESCRIPTION
        ""
    ::= { lcosLXStatusConfigServicesEntry 4 }

-- {COLUMN} 13.1.11.71.1.5
lcosLXStatusConfigServicesEntryLAN OBJECT-TYPE
    SYNTAX     INTEGER {
                  eNo(0),
                  eYes(1)
               }
    MAX-ACCESS read-only
    STATUS     current
    DESCRIPTION
        ""
    ::= { lcosLXStatusConfigServicesEntry 5 }

-- {COLUMN} 13.1.11.71.1.8
lcosLXStatusConfigServicesEntryWLAN OBJECT-TYPE
    SYNTAX     INTEGER {
                  eNo(0),
                  eYes(1)
               }
    MAX-ACCESS read-only
    STATUS     current
    DESCRIPTION
        ""
    ::= { lcosLXStatusConfigServicesEntry 8 }

-- {SCALAR} 13.1.18
lcosLXStatusCurrentTime OBJECT-TYPE
    SYNTAX     OCTET STRING (SIZE(0..20))
    MAX-ACCESS read-only
    STATUS     current
    DESCRIPTION
        ""
    ::= { lcosLXStatus 18 }

-- {SCALAR} 13.1.19
lcosLXStatusCurrentTimeEpoch OBJECT-TYPE
    SYNTAX     Unsigned32 (0..4294967295)
    MAX-ACCESS read-only
    STATUS     current
    DESCRIPTION
        ""
    ::= { lcosLXStatus 19 }

-- {SCALAR} 13.1.20
lcosLXStatusCurrentTimeOffset OBJECT-TYPE
    SYNTAX     Integer32 (-2147483648..2147483647)
    MAX-ACCESS read-only
    STATUS     current
    DESCRIPTION
        ""
    ::= { lcosLXStatus 20 }

-- {OID} 13.1.32
lcosLXStatusDHCPClient OBJECT IDENTIFIER ::= { lcosLXStatus 32 }

-- {SCALAR} 13.1.32.5
lcosLXStatusDHCPClientLMCDomain OBJECT-TYPE
    SYNTAX     OCTET STRING (SIZE(0..255))
    MAX-ACCESS read-only
    STATUS     current
    DESCRIPTION
        ""
    ::= { lcosLXStatusDHCPClient 5 }

-- {SCALAR} 13.1.32.6
lcosLXStatusDHCPClientRolloutProjectID OBJECT-TYPE
    SYNTAX     OCTET STRING (SIZE(0..36))
    MAX-ACCESS read-only
    STATUS     current
    DESCRIPTION
        ""
    ::= { lcosLXStatusDHCPClient 6 }

-- {SCALAR} 13.1.32.7
lcosLXStatusDHCPClientRolloutLocationID OBJECT-TYPE
    SYNTAX     OCTET STRING (SIZE(0..36))
    MAX-ACCESS read-only
    STATUS     current
    DESCRIPTION
        ""
    ::= { lcosLXStatusDHCPClient 7 }

-- {OID} 13.1.35
lcosLXStatusSNMP OBJECT IDENTIFIER ::= { lcosLXStatus 35 }

-- {TABLE} 13.1.35.1
lcosLXStatusSNMPEvent OBJECT-TYPE
    SYNTAX     SEQUENCE OF LcosLXStatusSNMPEventEntry
    MAX-ACCESS not-accessible
    STATUS     current
    DESCRIPTION
        ""
    ::= { lcosLXStatusSNMP 1 }

-- {INDEX} 13.1.35.1
lcosLXStatusSNMPEventEntry OBJECT-TYPE
    SYNTAX     LcosLXStatusSNMPEventEntry
    MAX-ACCESS not-accessible
    STATUS     current
    DESCRIPTION
        ""
    INDEX {
        lcosLXStatusSNMPEventEntryTrapID
    }
    ::= { lcosLXStatusSNMPEvent 1 }

-- {SEQUENCE} 13.1.35.1
LcosLXStatusSNMPEventEntry ::= SEQUENCE {
    lcosLXStatusSNMPEventEntryTrapID OBJECT IDENTIFIER,
    lcosLXStatusSNMPEventEntryGroup OCTET STRING,
    lcosLXStatusSNMPEventEntryName OCTET STRING,
    lcosLXStatusSNMPEventEntryCount Unsigned32
}

-- {COLUMN} 13.1.35.1.1.1
lcosLXStatusSNMPEventEntryTrapID OBJECT-TYPE
    SYNTAX     OBJECT IDENTIFIER
    MAX-ACCESS not-accessible
    STATUS     current
    DESCRIPTION
        ""
    ::= { lcosLXStatusSNMPEventEntry 1 }

-- {COLUMN} 13.1.35.1.1.2
lcosLXStatusSNMPEventEntryGroup OBJECT-TYPE
    SYNTAX     OCTET STRING (SIZE(0..32))
    MAX-ACCESS read-only
    STATUS     current
    DESCRIPTION
        ""
    ::= { lcosLXStatusSNMPEventEntry 2 }

-- {COLUMN} 13.1.35.1.1.3
lcosLXStatusSNMPEventEntryName OBJECT-TYPE
    SYNTAX     OCTET STRING (SIZE(0..32))
    MAX-ACCESS read-only
    STATUS     current
    DESCRIPTION
        ""
    ::= { lcosLXStatusSNMPEventEntry 3 }

-- {COLUMN} 13.1.35.1.1.4
lcosLXStatusSNMPEventEntryCount OBJECT-TYPE
    SYNTAX     Unsigned32 (0..4294967295)
    MAX-ACCESS read-only
    STATUS     current
    DESCRIPTION
        ""
    ::= { lcosLXStatusSNMPEventEntry 4 }

-- {OID} 13.1.40
lcosLXStatusMulticastSnooping OBJECT IDENTIFIER ::= { lcosLXStatus 40 }

-- {OID} 13.1.45
lcosLXStatusBridge OBJECT IDENTIFIER ::= { lcosLXStatus 45 }

-- {TABLE} 13.1.45.1
lcosLXStatusBridgeBridgesList OBJECT-TYPE
    SYNTAX     SEQUENCE OF LcosLXStatusBridgeBridgesListEntry
    MAX-ACCESS not-accessible
    STATUS     current
    DESCRIPTION
        ""
    ::= { lcosLXStatusBridge 1 }

-- {INDEX} 13.1.45.1
lcosLXStatusBridgeBridgesListEntry OBJECT-TYPE
    SYNTAX     LcosLXStatusBridgeBridgesListEntry
    MAX-ACCESS not-accessible
    STATUS     current
    DESCRIPTION
        ""
    INDEX {
        lcosLXStatusBridgeBridgesListEntryBridgeName
    }
    ::= { lcosLXStatusBridgeBridgesList 1 }

-- {SEQUENCE} 13.1.45.1
LcosLXStatusBridgeBridgesListEntry ::= SEQUENCE {
    lcosLXStatusBridgeBridgesListEntryBridgeName OCTET STRING,
    lcosLXStatusBridgeBridgesListEntryBridgeId OCTET STRING,
    lcosLXStatusBridgeBridgesListEntrySTPState INTEGER,
    lcosLXStatusBridgeBridgesListEntryInterfaces OCTET STRING
}

-- {COLUMN} 13.1.45.1.1.1
lcosLXStatusBridgeBridgesListEntryBridgeName OBJECT-TYPE
    SYNTAX     OCTET STRING (SIZE(0..64))
    MAX-ACCESS not-accessible
    STATUS     current
    DESCRIPTION
        ""
    ::= { lcosLXStatusBridgeBridgesListEntry 1 }

-- {COLUMN} 13.1.45.1.1.2
lcosLXStatusBridgeBridgesListEntryBridgeId OBJECT-TYPE
    SYNTAX     OCTET STRING (SIZE(0..64))
    MAX-ACCESS read-only
    STATUS     current
    DESCRIPTION
        ""
    ::= { lcosLXStatusBridgeBridgesListEntry 2 }

-- {COLUMN} 13.1.45.1.1.3
lcosLXStatusBridgeBridgesListEntrySTPState OBJECT-TYPE
    SYNTAX     INTEGER {
                  edisabled(0),
                  eenabled(1),
                  eusermanaged(2)
               }
    MAX-ACCESS read-only
    STATUS     current
    DESCRIPTION
        ""
    ::= { lcosLXStatusBridgeBridgesListEntry 3 }

-- {COLUMN} 13.1.45.1.1.4
lcosLXStatusBridgeBridgesListEntryInterfaces OBJECT-TYPE
    SYNTAX     OCTET STRING (SIZE(0..64))
    MAX-ACCESS read-only
    STATUS     current
    DESCRIPTION
        ""
    ::= { lcosLXStatusBridgeBridgesListEntry 4 }

-- {TABLE} 13.1.45.2
lcosLXStatusBridgeForwardingTable OBJECT-TYPE
    SYNTAX     SEQUENCE OF LcosLXStatusBridgeForwardingEntry
    MAX-ACCESS not-accessible
    STATUS     current
    DESCRIPTION
        ""
    ::= { lcosLXStatusBridge 2 }

-- {INDEX} 13.1.45.2
lcosLXStatusBridgeForwardingEntry OBJECT-TYPE
    SYNTAX     LcosLXStatusBridgeForwardingEntry
    MAX-ACCESS not-accessible
    STATUS     current
    DESCRIPTION
        ""
    INDEX {
        lcosLXStatusBridgeForwardingEntryMACAddress,
        lcosLXStatusBridgeForwardingEntryInterfaceName,
        lcosLXStatusBridgeForwardingEntryVLAN
    }
    ::= { lcosLXStatusBridgeForwardingTable 1 }

-- {SEQUENCE} 13.1.45.2
LcosLXStatusBridgeForwardingEntry ::= SEQUENCE {
    lcosLXStatusBridgeForwardingEntryMACAddress OCTET STRING,
    lcosLXStatusBridgeForwardingEntryInterfaceName OCTET STRING,
    lcosLXStatusBridgeForwardingEntryVLAN Unsigned32,
    lcosLXStatusBridgeForwardingEntryDst OCTET STRING,
    lcosLXStatusBridgeForwardingEntryPort Unsigned32,
    lcosLXStatusBridgeForwardingEntryVNI Unsigned32,
    lcosLXStatusBridgeForwardingEntrySrcVni Unsigned32,
    lcosLXStatusBridgeForwardingEntryViaIfindex Unsigned32,
    lcosLXStatusBridgeForwardingEntryViaIf OCTET STRING,
    lcosLXStatusBridgeForwardingEntryLinkNetnsid Unsigned32,
    lcosLXStatusBridgeForwardingEntryFlags OCTET STRING,
    lcosLXStatusBridgeForwardingEntryMaster OCTET STRING,
    lcosLXStatusBridgeForwardingEntryState INTEGER
}

-- {COLUMN} 13.1.45.2.1.1
lcosLXStatusBridgeForwardingEntryMACAddress OBJECT-TYPE
    SYNTAX     OCTET STRING (SIZE(0..18))
    MAX-ACCESS not-accessible
    STATUS     current
    DESCRIPTION
        ""
    ::= { lcosLXStatusBridgeForwardingEntry 1 }

-- {COLUMN} 13.1.45.2.1.2
lcosLXStatusBridgeForwardingEntryInterfaceName OBJECT-TYPE
    SYNTAX     OCTET STRING (SIZE(0..64))
    MAX-ACCESS not-accessible
    STATUS     current
    DESCRIPTION
        ""
    ::= { lcosLXStatusBridgeForwardingEntry 2 }

-- {COLUMN} 13.1.45.2.1.3
lcosLXStatusBridgeForwardingEntryVLAN OBJECT-TYPE
    SYNTAX     Unsigned32 (0..65535)
    MAX-ACCESS not-accessible
    STATUS     current
    DESCRIPTION
        ""
    ::= { lcosLXStatusBridgeForwardingEntry 3 }

-- {COLUMN} 13.1.45.2.1.4
lcosLXStatusBridgeForwardingEntryDst OBJECT-TYPE
    SYNTAX     OCTET STRING (SIZE(0..64))
    MAX-ACCESS read-only
    STATUS     current
    DESCRIPTION
        ""
    ::= { lcosLXStatusBridgeForwardingEntry 4 }

-- {COLUMN} 13.1.45.2.1.5
lcosLXStatusBridgeForwardingEntryPort OBJECT-TYPE
    SYNTAX     Unsigned32 (0..65535)
    MAX-ACCESS read-only
    STATUS     current
    DESCRIPTION
        ""
    ::= { lcosLXStatusBridgeForwardingEntry 5 }

-- {COLUMN} 13.1.45.2.1.6
lcosLXStatusBridgeForwardingEntryVNI OBJECT-TYPE
    SYNTAX     Unsigned32 (0..255)
    MAX-ACCESS read-only
    STATUS     current
    DESCRIPTION
        ""
    ::= { lcosLXStatusBridgeForwardingEntry 6 }

-- {COLUMN} 13.1.45.2.1.7
lcosLXStatusBridgeForwardingEntrySrcVni OBJECT-TYPE
    SYNTAX     Unsigned32 (0..255)
    MAX-ACCESS read-only
    STATUS     current
    DESCRIPTION
        ""
    ::= { lcosLXStatusBridgeForwardingEntry 7 }

-- {COLUMN} 13.1.45.2.1.8
lcosLXStatusBridgeForwardingEntryViaIfindex OBJECT-TYPE
    SYNTAX     Unsigned32 (0..255)
    MAX-ACCESS read-only
    STATUS     current
    DESCRIPTION
        ""
    ::= { lcosLXStatusBridgeForwardingEntry 8 }

-- {COLUMN} 13.1.45.2.1.9
lcosLXStatusBridgeForwardingEntryViaIf OBJECT-TYPE
    SYNTAX     OCTET STRING (SIZE(0..64))
    MAX-ACCESS read-only
    STATUS     current
    DESCRIPTION
        ""
    ::= { lcosLXStatusBridgeForwardingEntry 9 }

-- {COLUMN} 13.1.45.2.1.10
lcosLXStatusBridgeForwardingEntryLinkNetnsid OBJECT-TYPE
    SYNTAX     Unsigned32 (0..255)
    MAX-ACCESS read-only
    STATUS     current
    DESCRIPTION
        ""
    ::= { lcosLXStatusBridgeForwardingEntry 10 }

-- {COLUMN} 13.1.45.2.1.11
lcosLXStatusBridgeForwardingEntryFlags OBJECT-TYPE
    SYNTAX     OCTET STRING (SIZE(0..64))
    MAX-ACCESS read-only
    STATUS     current
    DESCRIPTION
        ""
    ::= { lcosLXStatusBridgeForwardingEntry 11 }

-- {COLUMN} 13.1.45.2.1.12
lcosLXStatusBridgeForwardingEntryMaster OBJECT-TYPE
    SYNTAX     OCTET STRING (SIZE(0..64))
    MAX-ACCESS read-only
    STATUS     current
    DESCRIPTION
        ""
    ::= { lcosLXStatusBridgeForwardingEntry 12 }

-- {COLUMN} 13.1.45.2.1.13
lcosLXStatusBridgeForwardingEntryState OBJECT-TYPE
    SYNTAX     INTEGER {
                  edynamic(0),
                  epermanent(1),
                  estatic(2),
                  estale(3)
               }
    MAX-ACCESS read-only
    STATUS     current
    DESCRIPTION
        ""
    ::= { lcosLXStatusBridgeForwardingEntry 13 }

-- {TABLE} 13.1.45.3
lcosLXStatusBridgeVLANTable OBJECT-TYPE
    SYNTAX     SEQUENCE OF LcosLXStatusBridgeVLANEntry
    MAX-ACCESS not-accessible
    STATUS     current
    DESCRIPTION
        ""
    ::= { lcosLXStatusBridge 3 }

-- {INDEX} 13.1.45.3
lcosLXStatusBridgeVLANEntry OBJECT-TYPE
    SYNTAX     LcosLXStatusBridgeVLANEntry
    MAX-ACCESS not-accessible
    STATUS     current
    DESCRIPTION
        ""
    INDEX {
        lcosLXStatusBridgeVLANEntryInterfaceName,
        lcosLXStatusBridgeVLANEntryVLANId
    }
    ::= { lcosLXStatusBridgeVLANTable 1 }

-- {SEQUENCE} 13.1.45.3
LcosLXStatusBridgeVLANEntry ::= SEQUENCE {
    lcosLXStatusBridgeVLANEntryInterfaceName OCTET STRING,
    lcosLXStatusBridgeVLANEntryVLANId Unsigned32,
    lcosLXStatusBridgeVLANEntryFlags OCTET STRING
}

-- {COLUMN} 13.1.45.3.1.1
lcosLXStatusBridgeVLANEntryInterfaceName OBJECT-TYPE
    SYNTAX     OCTET STRING (SIZE(0..64))
    MAX-ACCESS not-accessible
    STATUS     current
    DESCRIPTION
        ""
    ::= { lcosLXStatusBridgeVLANEntry 1 }

-- {COLUMN} 13.1.45.3.1.2
lcosLXStatusBridgeVLANEntryVLANId OBJECT-TYPE
    SYNTAX     Unsigned32 (0..65535)
    MAX-ACCESS not-accessible
    STATUS     current
    DESCRIPTION
        ""
    ::= { lcosLXStatusBridgeVLANEntry 2 }

-- {COLUMN} 13.1.45.3.1.3
lcosLXStatusBridgeVLANEntryFlags OBJECT-TYPE
    SYNTAX     OCTET STRING (SIZE(0..64))
    MAX-ACCESS read-only
    STATUS     current
    DESCRIPTION
        ""
    ::= { lcosLXStatusBridgeVLANEntry 3 }

-- {OID} 13.1.47
lcosLXStatusHardwareInfo OBJECT IDENTIFIER ::= { lcosLXStatus 47 }

-- {SCALAR} 13.1.47.4
lcosLXStatusHardwareInfoTotalMemoryKbytes OBJECT-TYPE
    SYNTAX     Unsigned32 (0..4294967295)
    MAX-ACCESS read-only
    STATUS     current
    DESCRIPTION
        ""
    ::= { lcosLXStatusHardwareInfo 4 }

-- {SCALAR} 13.1.47.5
lcosLXStatusHardwareInfoFreeMemoryKbytes OBJECT-TYPE
    SYNTAX     Unsigned32 (0..4294967295)
    MAX-ACCESS read-only
    STATUS     current
    DESCRIPTION
        ""
    ::= { lcosLXStatusHardwareInfo 5 }

-- {SCALAR} 13.1.47.7
lcosLXStatusHardwareInfoSerialNumber OBJECT-TYPE
    SYNTAX     OCTET STRING (SIZE(0..16))
    MAX-ACCESS read-only
    STATUS     current
    DESCRIPTION
        ""
    ::= { lcosLXStatusHardwareInfo 7 }

-- {SCALAR} 13.1.47.8
lcosLXStatusHardwareInfoBoardRevision OBJECT-TYPE
    SYNTAX     OCTET STRING (SIZE(0..16))
    MAX-ACCESS read-only
    STATUS     current
    DESCRIPTION
        ""
    ::= { lcosLXStatusHardwareInfo 8 }

-- {SCALAR} 13.1.47.9
lcosLXStatusHardwareInfoSWVersion OBJECT-TYPE
    SYNTAX     OCTET STRING (SIZE(0..32))
    MAX-ACCESS read-only
    STATUS     current
    DESCRIPTION
        ""
    ::= { lcosLXStatusHardwareInfo 9 }

-- {SCALAR} 13.1.47.11
lcosLXStatusHardwareInfoMountingType OBJECT-TYPE
    SYNTAX     INTEGER {
                  eUnknown(0),
                  eCeiling(1),
                  eWall(2),
                  eFloor(3)
               }
    MAX-ACCESS read-only
    STATUS     current
    DESCRIPTION
        ""
    ::= { lcosLXStatusHardwareInfo 11 }

-- {SCALAR} 13.1.47.12
lcosLXStatusHardwareInfoMountingAngle OBJECT-TYPE
    SYNTAX     Integer32 (-2147483648..2147483647)
    MAX-ACCESS read-only
    STATUS     current
    DESCRIPTION
        ""
    ::= { lcosLXStatusHardwareInfo 12 }

-- {SCALAR} 13.1.47.13
lcosLXStatusHardwareInfoTemperatureDegrees OBJECT-TYPE
    SYNTAX     Integer32 (-2147483648..2147483647)
    MAX-ACCESS read-only
    STATUS     current
    DESCRIPTION
        ""
    ::= { lcosLXStatusHardwareInfo 13 }

-- {SCALAR} 13.1.47.14
lcosLXStatusHardwareInfoCPULoad60sPercent OBJECT-TYPE
    SYNTAX     Unsigned32 (0..65535)
    MAX-ACCESS read-only
    STATUS     current
    DESCRIPTION
        ""
    ::= { lcosLXStatusHardwareInfo 14 }

-- {SCALAR} 13.1.47.41
lcosLXStatusHardwareInfoProductiondate OBJECT-TYPE
    SYNTAX     OCTET STRING (SIZE(0..16))
    MAX-ACCESS read-only
    STATUS     current
    DESCRIPTION
        ""
    ::= { lcosLXStatusHardwareInfo 41 }

-- {OID} 13.1.47.42
lcosLXStatusHardwareInfoPower OBJECT IDENTIFIER ::= { lcosLXStatusHardwareInfo 42 }

-- {SCALAR} 13.1.47.42.1
lcosLXStatusHardwareInfoPowerPoEType OBJECT-TYPE
    SYNTAX     OCTET STRING (SIZE(0..70))
    MAX-ACCESS read-only
    STATUS     current
    DESCRIPTION
        ""
    ::= { lcosLXStatusHardwareInfoPower 1 }

-- {TABLE} 13.1.47.42.6
lcosLXStatusHardwareInfoPowerPorts OBJECT-TYPE
    SYNTAX     SEQUENCE OF LcosLXStatusHardwareInfoPowerPortsEntry
    MAX-ACCESS not-accessible
    STATUS     current
    DESCRIPTION
        ""
    ::= { lcosLXStatusHardwareInfoPower 6 }

-- {INDEX} 13.1.47.42.6
lcosLXStatusHardwareInfoPowerPortsEntry OBJECT-TYPE
    SYNTAX     LcosLXStatusHardwareInfoPowerPortsEntry
    MAX-ACCESS not-accessible
    STATUS     current
    DESCRIPTION
        ""
    INDEX {
        lcosLXStatusHardwareInfoPowerPortsEntryPort
    }
    ::= { lcosLXStatusHardwareInfoPowerPorts 1 }

-- {SEQUENCE} 13.1.47.42.6
LcosLXStatusHardwareInfoPowerPortsEntry ::= SEQUENCE {
    lcosLXStatusHardwareInfoPowerPortsEntryPort OCTET STRING,
    lcosLXStatusHardwareInfoPowerPortsEntryPoEinType INTEGER,
    lcosLXStatusHardwareInfoPowerPortsEntryPoEinClass INTEGER,
    lcosLXStatusHardwareInfoPowerPortsEntryLLDPPowerNegotiation INTEGER,
    lcosLXStatusHardwareInfoPowerPortsEntryPoEPowerAllocatedmW OCTET STRING,
    lcosLXStatusHardwareInfoPowerPortsEntryPoEPowerAvg1smW OCTET STRING,
    lcosLXStatusHardwareInfoPowerPortsEntryPoEPowerAvg1minmW OCTET STRING,
    lcosLXStatusHardwareInfoPowerPortsEntryPoEPowerAvg1hmW OCTET STRING,
    lcosLXStatusHardwareInfoPowerPortsEntryPoEPowerAvg24hmW OCTET STRING
}

-- {COLUMN} 13.1.47.42.6.1.1
lcosLXStatusHardwareInfoPowerPortsEntryPort OBJECT-TYPE
    SYNTAX     OCTET STRING (SIZE(0..5))
    MAX-ACCESS not-accessible
    STATUS     current
    DESCRIPTION
        ""
    ::= { lcosLXStatusHardwareInfoPowerPortsEntry 1 }

-- {COLUMN} 13.1.47.42.6.1.2
lcosLXStatusHardwareInfoPowerPortsEntryPoEinType OBJECT-TYPE
    SYNTAX     INTEGER {
                  e8023afType1or8023atType2(0),
                  eunknown(255),
                  enoPoE(254),
                  e8023btType3(1),
                  e8023afType1(2),
                  e8023atType2(3)
               }
    MAX-ACCESS read-only
    STATUS     current
    DESCRIPTION
        ""
    ::= { lcosLXStatusHardwareInfoPowerPortsEntry 2 }

-- {COLUMN} 13.1.47.42.6.1.3
lcosLXStatusHardwareInfoPowerPortsEntryPoEinClass OBJECT-TYPE
    SYNTAX     INTEGER {
                  eunknown(255),
                  eNone(254),
                  eClass0(0),
                  eClass1(1),
                  eClass2(2),
                  eClass3(3),
                  eClass4(4),
                  eClass5(5),
                  eClass6(6),
                  eClass7(7),
                  eClass8(8)
               }
    MAX-ACCESS read-only
    STATUS     current
    DESCRIPTION
        ""
    ::= { lcosLXStatusHardwareInfoPowerPortsEntry 3 }

-- {COLUMN} 13.1.47.42.6.1.4
lcosLXStatusHardwareInfoPowerPortsEntryLLDPPowerNegotiation OBJECT-TYPE
    SYNTAX     INTEGER {
                  eNo(0),
                  eYes(1)
               }
    MAX-ACCESS read-only
    STATUS     current
    DESCRIPTION
        ""
    ::= { lcosLXStatusHardwareInfoPowerPortsEntry 4 }

-- {COLUMN} 13.1.47.42.6.1.5
lcosLXStatusHardwareInfoPowerPortsEntryPoEPowerAllocatedmW OBJECT-TYPE
    SYNTAX     OCTET STRING (SIZE(0..16))
    MAX-ACCESS read-only
    STATUS     current
    DESCRIPTION
        ""
    ::= { lcosLXStatusHardwareInfoPowerPortsEntry 5 }

-- {COLUMN} 13.1.47.42.6.1.6
lcosLXStatusHardwareInfoPowerPortsEntryPoEPowerAvg1smW OBJECT-TYPE
    SYNTAX     OCTET STRING (SIZE(0..16))
    MAX-ACCESS read-only
    STATUS     current
    DESCRIPTION
        ""
    ::= { lcosLXStatusHardwareInfoPowerPortsEntry 6 }

-- {COLUMN} 13.1.47.42.6.1.7
lcosLXStatusHardwareInfoPowerPortsEntryPoEPowerAvg1minmW OBJECT-TYPE
    SYNTAX     OCTET STRING (SIZE(0..16))
    MAX-ACCESS read-only
    STATUS     current
    DESCRIPTION
        ""
    ::= { lcosLXStatusHardwareInfoPowerPortsEntry 7 }

-- {COLUMN} 13.1.47.42.6.1.8
lcosLXStatusHardwareInfoPowerPortsEntryPoEPowerAvg1hmW OBJECT-TYPE
    SYNTAX     OCTET STRING (SIZE(0..16))
    MAX-ACCESS read-only
    STATUS     current
    DESCRIPTION
        ""
    ::= { lcosLXStatusHardwareInfoPowerPortsEntry 8 }

-- {COLUMN} 13.1.47.42.6.1.9
lcosLXStatusHardwareInfoPowerPortsEntryPoEPowerAvg24hmW OBJECT-TYPE
    SYNTAX     OCTET STRING (SIZE(0..16))
    MAX-ACCESS read-only
    STATUS     current
    DESCRIPTION
        ""
    ::= { lcosLXStatusHardwareInfoPowerPortsEntry 9 }

-- {OID} 13.1.47.42.7
lcosLXStatusHardwareInfoPowerDeviceFunctions OBJECT IDENTIFIER ::= { lcosLXStatusHardwareInfoPower 7 }

-- {SCALAR} 13.1.47.42.7.1
lcosLXStatusHardwareInfoPowerDeviceFunctionsWLANStreams24GHz OBJECT-TYPE
    SYNTAX     INTEGER {
                  eOff(0),
                  eOne(1),
                  eTwo(2),
                  eThree(3),
                  eFour(4)
               }
    MAX-ACCESS read-only
    STATUS     current
    DESCRIPTION
        ""
    ::= { lcosLXStatusHardwareInfoPowerDeviceFunctions 1 }

-- {SCALAR} 13.1.47.42.7.2
lcosLXStatusHardwareInfoPowerDeviceFunctionsWLANStreams5GHz OBJECT-TYPE
    SYNTAX     INTEGER {
                  eOff(0),
                  eOne(1),
                  eTwo(2),
                  eThree(3),
                  eFour(4)
               }
    MAX-ACCESS read-only
    STATUS     current
    DESCRIPTION
        ""
    ::= { lcosLXStatusHardwareInfoPowerDeviceFunctions 2 }

-- {SCALAR} 13.1.47.42.7.3
lcosLXStatusHardwareInfoPowerDeviceFunctionsWLANStreams6GHz OBJECT-TYPE
    SYNTAX     INTEGER {
                  eOff(0),
                  eOne(1),
                  eTwo(2),
                  eThree(3),
                  eFour(4)
               }
    MAX-ACCESS read-only
    STATUS     current
    DESCRIPTION
        ""
    ::= { lcosLXStatusHardwareInfoPowerDeviceFunctions 3 }

-- {SCALAR} 13.1.47.42.7.4
lcosLXStatusHardwareInfoPowerDeviceFunctionsWLANScanRadio OBJECT-TYPE
    SYNTAX     INTEGER {
                  eOff(0),
                  eOn(1)
               }
    MAX-ACCESS read-only
    STATUS     current
    DESCRIPTION
        ""
    ::= { lcosLXStatusHardwareInfoPowerDeviceFunctions 4 }

-- {SCALAR} 13.1.47.42.7.5
lcosLXStatusHardwareInfoPowerDeviceFunctionsUSBPort OBJECT-TYPE
    SYNTAX     INTEGER {
                  eOff(0),
                  eOn(1)
               }
    MAX-ACCESS read-only
    STATUS     current
    DESCRIPTION
        ""
    ::= { lcosLXStatusHardwareInfoPowerDeviceFunctions 5 }

-- {SCALAR} 13.1.47.42.10
lcosLXStatusHardwareInfoPowerFailoverStatus OBJECT-TYPE
    SYNTAX     INTEGER {
                  eDisabled(0),
                  eReady(1),
                  eEngaged(2)
               }
    MAX-ACCESS read-only
    STATUS     current
    DESCRIPTION
        ""
    ::= { lcosLXStatusHardwareInfoPower 10 }

-- {SCALAR} 13.1.47.42.11
lcosLXStatusHardwareInfoPowerPowerStatus OBJECT-TYPE
    SYNTAX     INTEGER {
                  eFullyoperational(0),
                  eReducedfunctionset(1)
               }
    MAX-ACCESS read-only
    STATUS     current
    DESCRIPTION
        ""
    ::= { lcosLXStatusHardwareInfoPower 11 }

-- {SCALAR} 13.1.47.42.12
lcosLXStatusHardwareInfoPowerDualPoEMode OBJECT-TYPE
    SYNTAX     INTEGER {
                  eHitlessFailover(0),
                  eLoadBalancing(1)
               }
    MAX-ACCESS read-only
    STATUS     current
    DESCRIPTION
        ""
    ::= { lcosLXStatusHardwareInfoPower 12 }

-- {OID} 13.1.59
lcosLXStatusWLANManagement OBJECT IDENTIFIER ::= { lcosLXStatus 59 }

-- {TABLE} 13.1.59.1
lcosLXStatusWLANManagementAPConnections OBJECT-TYPE
    SYNTAX     SEQUENCE OF LcosLXStatusWLANManagementAPConnectionsEntry
    MAX-ACCESS not-accessible
    STATUS     current
    DESCRIPTION
        ""
    ::= { lcosLXStatusWLANManagement 1 }

-- {INDEX} 13.1.59.1
lcosLXStatusWLANManagementAPConnectionsEntry OBJECT-TYPE
    SYNTAX     LcosLXStatusWLANManagementAPConnectionsEntry
    MAX-ACCESS not-accessible
    STATUS     current
    DESCRIPTION
        ""
    INDEX {
        lcosLXStatusWLANManagementAPConnectionsEntryIPAddress
    }
    ::= { lcosLXStatusWLANManagementAPConnections 1 }

-- {SEQUENCE} 13.1.59.1
LcosLXStatusWLANManagementAPConnectionsEntry ::= SEQUENCE {
    lcosLXStatusWLANManagementAPConnectionsEntryIPAddress OCTET STRING,
    lcosLXStatusWLANManagementAPConnectionsEntryPort Unsigned32,
    lcosLXStatusWLANManagementAPConnectionsEntryRespTime Unsigned32,
    lcosLXStatusWLANManagementAPConnectionsEntryName OCTET STRING,
    lcosLXStatusWLANManagementAPConnectionsEntryState INTEGER,
    lcosLXStatusWLANManagementAPConnectionsEntryResult INTEGER,
    lcosLXStatusWLANManagementAPConnectionsEntryUtilisation OCTET STRING,
    lcosLXStatusWLANManagementAPConnectionsEntryFirmwareVersion OCTET STRING,
    lcosLXStatusWLANManagementAPConnectionsEntryPMTU Unsigned32,
    lcosLXStatusWLANManagementAPConnectionsEntryPreference Unsigned32,
    lcosLXStatusWLANManagementAPConnectionsEntryCPULoad300sPercent OCTET STRING,
    lcosLXStatusWLANManagementAPConnectionsEntryRetransmissions Unsigned32
}

-- {COLUMN} 13.1.59.1.1.2
lcosLXStatusWLANManagementAPConnectionsEntryIPAddress OBJECT-TYPE
    SYNTAX     OCTET STRING (SIZE(0..44))
    MAX-ACCESS not-accessible
    STATUS     current
    DESCRIPTION
        ""
    ::= { lcosLXStatusWLANManagementAPConnectionsEntry 2 }

-- {COLUMN} 13.1.59.1.1.3
lcosLXStatusWLANManagementAPConnectionsEntryPort OBJECT-TYPE
    SYNTAX     Unsigned32 (0..65535)
    MAX-ACCESS read-only
    STATUS     current
    DESCRIPTION
        ""
    ::= { lcosLXStatusWLANManagementAPConnectionsEntry 3 }

-- {COLUMN} 13.1.59.1.1.4
lcosLXStatusWLANManagementAPConnectionsEntryRespTime OBJECT-TYPE
    SYNTAX     Unsigned32 (0..4294967295)
    MAX-ACCESS read-only
    STATUS     current
    DESCRIPTION
        ""
    ::= { lcosLXStatusWLANManagementAPConnectionsEntry 4 }

-- {COLUMN} 13.1.59.1.1.5
lcosLXStatusWLANManagementAPConnectionsEntryName OBJECT-TYPE
    SYNTAX     OCTET STRING (SIZE(0..32))
    MAX-ACCESS read-only
    STATUS     current
    DESCRIPTION
        ""
    ::= { lcosLXStatusWLANManagementAPConnectionsEntry 5 }

-- {COLUMN} 13.1.59.1.1.6
lcosLXStatusWLANManagementAPConnectionsEntryState OBJECT-TYPE
    SYNTAX     INTEGER {
                  eUnknown(0),
                  eIdle(5),
                  eDiscovery(10),
                  eDTLSSetup(15),
                  eJoin(20),
                  eConfigure(25),
                  eImageData(30),
                  eReset(35),
                  eDTLSTeardown(40),
                  eSulking(45),
                  eRun(100),
                  eOff(255)
               }
    MAX-ACCESS read-only
    STATUS     current
    DESCRIPTION
        ""
    ::= { lcosLXStatusWLANManagementAPConnectionsEntry 6 }

-- {COLUMN} 13.1.59.1.1.7
lcosLXStatusWLANManagementAPConnectionsEntryResult OBJECT-TYPE
    SYNTAX     INTEGER {
                  eSuccess(0),
                  eFailure(1),
                  eSuccessNAT(2),
                  eJoinFailunspecified(3),
                  eJoinFailResourceDepletion(4),
                  eJoinFailUnknwnSrc(5),
                  eJoinFailIncorrectData(6),
                  eJoinFailSessionIDinuse(7),
                  eJoinFailWTPnotsupported(8),
                  eJoinFailBindingnotsupp(9),
                  eResetFailUnabletoReset(10),
                  eResetFailFirmwWriteErr(11),
                  eFailMissingMandMsgElem(12),
                  eFailUnrecognizedMsgElem(13),
                  eUnsupportedLoaderVersion(14),
                  eUnsupportedFirmwareVersion(15),
                  e(16),
                  eConfigurationErrorServprovanyhow(17),
                  eConfigurationErrorServnotprov(18),
                  eImageDataErrorChecksum(19),
                  eImageDataErrorLength(20),
                  eImageDataErrorOther(21),
                  eImageDataErrorAlrpresent(300),
                  eMessageUnexpectedinvalid(301),
                  eMessageUnexpectedunrecognized(302),
                  eJoinFailAlreadyConnected(303)
               }
    MAX-ACCESS read-only
    STATUS     current
    DESCRIPTION
        ""
    ::= { lcosLXStatusWLANManagementAPConnectionsEntry 7 }

-- {COLUMN} 13.1.59.1.1.9
lcosLXStatusWLANManagementAPConnectionsEntryUtilisation OBJECT-TYPE
    SYNTAX     OCTET STRING (SIZE(0..32))
    MAX-ACCESS read-only
    STATUS     current
    DESCRIPTION
        ""
    ::= { lcosLXStatusWLANManagementAPConnectionsEntry 9 }

-- {COLUMN} 13.1.59.1.1.10
lcosLXStatusWLANManagementAPConnectionsEntryFirmwareVersion OBJECT-TYPE
    SYNTAX     OCTET STRING (SIZE(0..32))
    MAX-ACCESS read-only
    STATUS     current
    DESCRIPTION
        ""
    ::= { lcosLXStatusWLANManagementAPConnectionsEntry 10 }

-- {COLUMN} 13.1.59.1.1.11
lcosLXStatusWLANManagementAPConnectionsEntryPMTU OBJECT-TYPE
    SYNTAX     Unsigned32 (0..4294967295)
    MAX-ACCESS read-only
    STATUS     current
    DESCRIPTION
        ""
    ::= { lcosLXStatusWLANManagementAPConnectionsEntry 11 }

-- {COLUMN} 13.1.59.1.1.14
lcosLXStatusWLANManagementAPConnectionsEntryPreference OBJECT-TYPE
    SYNTAX     Unsigned32 (0..255)
    MAX-ACCESS read-only
    STATUS     current
    DESCRIPTION
        ""
    ::= { lcosLXStatusWLANManagementAPConnectionsEntry 14 }

-- {COLUMN} 13.1.59.1.1.15
lcosLXStatusWLANManagementAPConnectionsEntryCPULoad300sPercent OBJECT-TYPE
    SYNTAX     OCTET STRING (SIZE(0..32))
    MAX-ACCESS read-only
    STATUS     current
    DESCRIPTION
        ""
    ::= { lcosLXStatusWLANManagementAPConnectionsEntry 15 }

-- {COLUMN} 13.1.59.1.1.16
lcosLXStatusWLANManagementAPConnectionsEntryRetransmissions OBJECT-TYPE
    SYNTAX     Unsigned32 (0..4294967295)
    MAX-ACCESS read-only
    STATUS     current
    DESCRIPTION
        ""
    ::= { lcosLXStatusWLANManagementAPConnectionsEntry 16 }

-- {SCALAR} 13.1.59.2
lcosLXStatusWLANManagementState OBJECT-TYPE
    SYNTAX     INTEGER {
                  eUnknown(0),
                  eIdle(5),
                  eDiscovery(10),
                  eDTLSSetup(15),
                  eJoin(20),
                  eConfigure(25),
                  eImageData(30),
                  eReset(35),
                  eDTLSTeardown(40),
                  eSulking(45),
                  eRun(100),
                  eOff(255)
               }
    MAX-ACCESS read-only
    STATUS     current
    DESCRIPTION
        ""
    ::= { lcosLXStatusWLANManagement 2 }

-- {SCALAR} 13.1.59.3
lcosLXStatusWLANManagementStarted OBJECT-TYPE
    SYNTAX     OCTET STRING (SIZE(0..20))
    MAX-ACCESS read-only
    STATUS     current
    DESCRIPTION
        ""
    ::= { lcosLXStatusWLANManagement 3 }

-- {SCALAR} 13.1.59.4
lcosLXStatusWLANManagementDNSSuffix OBJECT-TYPE
    SYNTAX     OCTET STRING (SIZE(0..32))
    MAX-ACCESS read-only
    STATUS     current
    DESCRIPTION
        ""
    ::= { lcosLXStatusWLANManagement 4 }

-- {TABLE} 13.1.59.101
lcosLXStatusWLANManagementRadioprofiles OBJECT-TYPE
    SYNTAX     SEQUENCE OF LcosLXStatusWLANManagementRadioprofilesEntry
    MAX-ACCESS not-accessible
    STATUS     current
    DESCRIPTION
        ""
    ::= { lcosLXStatusWLANManagement 101 }

-- {INDEX} 13.1.59.101
lcosLXStatusWLANManagementRadioprofilesEntry OBJECT-TYPE
    SYNTAX     LcosLXStatusWLANManagementRadioprofilesEntry
    MAX-ACCESS not-accessible
    STATUS     current
    DESCRIPTION
        ""
    INDEX {
        lcosLXStatusWLANManagementRadioprofilesEntryName
    }
    ::= { lcosLXStatusWLANManagementRadioprofiles 1 }

-- {SEQUENCE} 13.1.59.101
LcosLXStatusWLANManagementRadioprofilesEntry ::= SEQUENCE {
    lcosLXStatusWLANManagementRadioprofilesEntryName OCTET STRING,
    lcosLXStatusWLANManagementRadioprofilesEntryCountry INTEGER,
    lcosLXStatusWLANManagementRadioprofilesEntry24GHzMode INTEGER,
    lcosLXStatusWLANManagementRadioprofilesEntry5GHzMode INTEGER,
    lcosLXStatusWLANManagementRadioprofilesEntry5GHzSubbands INTEGER,
    lcosLXStatusWLANManagementRadioprofilesEntryQoS INTEGER,
    lcosLXStatusWLANManagementRadioprofilesEntryDTIMPeriod Unsigned32,
    lcosLXStatusWLANManagementRadioprofilesEntryBackgroundScan Unsigned32,
    lcosLXStatusWLANManagementRadioprofilesEntryAntennaGain Integer32,
    lcosLXStatusWLANManagementRadioprofilesEntryTxPowerReduction Unsigned32,
    lcosLXStatusWLANManagementRadioprofilesEntryIndoorOnlyOperation INTEGER,
    lcosLXStatusWLANManagementRadioprofilesEntryReportSeenClients INTEGER,
    lcosLXStatusWLANManagementRadioprofilesEntryRxSensReduction Unsigned32,
    lcosLXStatusWLANManagementRadioprofilesEntry6GHzMode INTEGER,
    lcosLXStatusWLANManagementRadioprofilesEntry6GHzSubbands INTEGER
}

-- {COLUMN} 13.1.59.101.1.1
lcosLXStatusWLANManagementRadioprofilesEntryName OBJECT-TYPE
    SYNTAX     OCTET STRING (SIZE(0..32))
    MAX-ACCESS not-accessible
    STATUS     current
    DESCRIPTION
        ""
    ::= { lcosLXStatusWLANManagementRadioprofilesEntry 1 }

-- {COLUMN} 13.1.59.101.1.4
lcosLXStatusWLANManagementRadioprofilesEntryCountry OBJECT-TYPE
    SYNTAX     INTEGER {
                  eAustralia(36),
                  eAustria(40),
                  eBelgium(56),
                  eBosniaHerzegovina(70),
                  eBulgaria(100),
                  eCanada(124),
                  eCroatia(191),
                  eCyprus(196),
                  eCzechRepublic(203),
                  eDenmark(208),
                  eEstonia(233),
                  eFinland(246),
                  eFrance(250),
                  eGermany(276),
                  eGreece(300),
                  eHungary(348),
                  eIreland(372),
                  eItaly(380),
                  eLatvia(428),
                  eLiechtenstein(438),
                  eLithuania(440),
                  eLuxembourg(442),
                  eMalta(470),
                  eMorocco(504),
                  eNetherlands(528),
                  eNewZealand(554),
                  eNorway(578),
                  ePoland(616),
                  ePortugal(620),
                  eRomania(642),
                  eRwanda(646),
                  eSenegal(686),
                  eSerbia(688),
                  eSingapore(702),
                  eSlovakia(703),
                  eSlovenia(705),
                  eSouthAfrica(710),
                  eSpain(724),
                  eSweden(752),
                  eSwitzerland(756),
                  eTurkey(792),
                  eUkraine(804),
                  eUnitedKingdom(826),
                  eUnitedStates(840),
                  eEurope(998)
               }
    MAX-ACCESS read-only
    STATUS     current
    DESCRIPTION
        ""
    ::= { lcosLXStatusWLANManagementRadioprofilesEntry 4 }

-- {COLUMN} 13.1.59.101.1.6
lcosLXStatusWLANManagementRadioprofilesEntry24GHzMode OBJECT-TYPE
    SYNTAX     INTEGER {
                  e11bgmixed(0),
                  e11gonly(1),
                  e11bonly(2),
                  e108Mbps(3),
                  e11bgnmixed(4),
                  e11gnmixed(5),
                  eGreenfield(6),
                  e11bgnaxmixed(7),
                  e11gnaxmixed(8),
                  eAuto(255)
               }
    MAX-ACCESS read-only
    STATUS     current
    DESCRIPTION
        ""
    ::= { lcosLXStatusWLANManagementRadioprofilesEntry 6 }

-- {COLUMN} 13.1.59.101.1.7
lcosLXStatusWLANManagementRadioprofilesEntry5GHzMode OBJECT-TYPE
    SYNTAX     INTEGER {
                  eNormal(0),
                  e108Mbps(3),
                  e11anmixed(4),
                  eGreenfield(5),
                  e11anacmixed(6),
                  e11nacmixed(7),
                  e11aconly(8),
                  e11anacaxmixed(9),
                  e11anacaxbemixed(10),
                  eAuto(255)
               }
    MAX-ACCESS read-only
    STATUS     current
    DESCRIPTION
        ""
    ::= { lcosLXStatusWLANManagementRadioprofilesEntry 7 }

-- {COLUMN} 13.1.59.101.1.8
lcosLXStatusWLANManagementRadioprofilesEntry5GHzSubbands OBJECT-TYPE
    SYNTAX     INTEGER {
                  eBand123(0),
                  eBand1(1),
                  eBand2(2),
                  eBand3(3),
                  eBand12(4),
                  eBand13(5),
                  eBand23(6)
               }
    MAX-ACCESS read-only
    STATUS     current
    DESCRIPTION
        ""
    ::= { lcosLXStatusWLANManagementRadioprofilesEntry 8 }

-- {COLUMN} 13.1.59.101.1.9
lcosLXStatusWLANManagementRadioprofilesEntryQoS OBJECT-TYPE
    SYNTAX     INTEGER {
                  eNo(0),
                  eYes(1)
               }
    MAX-ACCESS read-only
    STATUS     current
    DESCRIPTION
        ""
    ::= { lcosLXStatusWLANManagementRadioprofilesEntry 9 }

-- {COLUMN} 13.1.59.101.1.10
lcosLXStatusWLANManagementRadioprofilesEntryDTIMPeriod OBJECT-TYPE
    SYNTAX     Unsigned32 (0..255)
    MAX-ACCESS read-only
    STATUS     current
    DESCRIPTION
        ""
    ::= { lcosLXStatusWLANManagementRadioprofilesEntry 10 }

-- {COLUMN} 13.1.59.101.1.11
lcosLXStatusWLANManagementRadioprofilesEntryBackgroundScan OBJECT-TYPE
    SYNTAX     Unsigned32 (0..4294967295)
    MAX-ACCESS read-only
    STATUS     current
    DESCRIPTION
        ""
    ::= { lcosLXStatusWLANManagementRadioprofilesEntry 11 }

-- {COLUMN} 13.1.59.101.1.12
lcosLXStatusWLANManagementRadioprofilesEntryAntennaGain OBJECT-TYPE
    SYNTAX     Integer32 (-128..127)
    MAX-ACCESS read-only
    STATUS     current
    DESCRIPTION
        ""
    ::= { lcosLXStatusWLANManagementRadioprofilesEntry 12 }

-- {COLUMN} 13.1.59.101.1.13
lcosLXStatusWLANManagementRadioprofilesEntryTxPowerReduction OBJECT-TYPE
    SYNTAX     Unsigned32 (0..255)
    MAX-ACCESS read-only
    STATUS     current
    DESCRIPTION
        ""
    ::= { lcosLXStatusWLANManagementRadioprofilesEntry 13 }

-- {COLUMN} 13.1.59.101.1.16
lcosLXStatusWLANManagementRadioprofilesEntryIndoorOnlyOperation OBJECT-TYPE
    SYNTAX     INTEGER {
                  eNo(0),
                  eYes(1)
               }
    MAX-ACCESS read-only
    STATUS     current
    DESCRIPTION
        ""
    ::= { lcosLXStatusWLANManagementRadioprofilesEntry 16 }

-- {COLUMN} 13.1.59.101.1.20
lcosLXStatusWLANManagementRadioprofilesEntryReportSeenClients OBJECT-TYPE
    SYNTAX     INTEGER {
                  eNo(0),
                  eYes(1)
               }
    MAX-ACCESS read-only
    STATUS     current
    DESCRIPTION
        ""
    ::= { lcosLXStatusWLANManagementRadioprofilesEntry 20 }

-- {COLUMN} 13.1.59.101.1.25
lcosLXStatusWLANManagementRadioprofilesEntryRxSensReduction OBJECT-TYPE
    SYNTAX     Unsigned32 (0..255)
    MAX-ACCESS read-only
    STATUS     current
    DESCRIPTION
        ""
    ::= { lcosLXStatusWLANManagementRadioprofilesEntry 25 }

-- {COLUMN} 13.1.59.101.1.26
lcosLXStatusWLANManagementRadioprofilesEntry6GHzMode OBJECT-TYPE
    SYNTAX     INTEGER {
                  eAuto(255),
                  e11ax(0),
                  e11axbemixed(1)
               }
    MAX-ACCESS read-only
    STATUS     current
    DESCRIPTION
        ""
    ::= { lcosLXStatusWLANManagementRadioprofilesEntry 26 }

-- {COLUMN} 13.1.59.101.1.27
lcosLXStatusWLANManagementRadioprofilesEntry6GHzSubbands OBJECT-TYPE
    SYNTAX     INTEGER {
                  eBand57(0),
                  eBand5(1),
                  eBand7(2)
               }
    MAX-ACCESS read-only
    STATUS     current
    DESCRIPTION
        ""
    ::= { lcosLXStatusWLANManagementRadioprofilesEntry 27 }

-- {TABLE} 13.1.59.103
lcosLXStatusWLANManagementNetworkprofiles OBJECT-TYPE
    SYNTAX     SEQUENCE OF LcosLXStatusWLANManagementNetworkprofilesEntry
    MAX-ACCESS not-accessible
    STATUS     current
    DESCRIPTION
        ""
    ::= { lcosLXStatusWLANManagement 103 }

-- {INDEX} 13.1.59.103
lcosLXStatusWLANManagementNetworkprofilesEntry OBJECT-TYPE
    SYNTAX     LcosLXStatusWLANManagementNetworkprofilesEntry
    MAX-ACCESS not-accessible
    STATUS     current
    DESCRIPTION
        ""
    INDEX {
        lcosLXStatusWLANManagementNetworkprofilesEntryName
    }
    ::= { lcosLXStatusWLANManagementNetworkprofiles 1 }

-- {SEQUENCE} 13.1.59.103
LcosLXStatusWLANManagementNetworkprofilesEntry ::= SEQUENCE {
    lcosLXStatusWLANManagementNetworkprofilesEntryName OCTET STRING,
    lcosLXStatusWLANManagementNetworkprofilesEntryOperating INTEGER,
    lcosLXStatusWLANManagementNetworkprofilesEntryEncryption INTEGER,
    lcosLXStatusWLANManagementNetworkprofilesEntryWPA1SessKeytypes INTEGER,
    lcosLXStatusWLANManagementNetworkprofilesEntryWPAVersion INTEGER,
    lcosLXStatusWLANManagementNetworkprofilesEntryKey OCTET STRING,
    lcosLXStatusWLANManagementNetworkprofilesEntryRadioBand INTEGER,
    lcosLXStatusWLANManagementNetworkprofilesEntryContinuationTime Unsigned32,
    lcosLXStatusWLANManagementNetworkprofilesEntryMinTxRate INTEGER,
    lcosLXStatusWLANManagementNetworkprofilesEntryMaxTxRate INTEGER,
    lcosLXStatusWLANManagementNetworkprofilesEntryBasicRate INTEGER,
    lcosLXStatusWLANManagementNetworkprofilesEntryPreamble INTEGER,
    lcosLXStatusWLANManagementNetworkprofilesEntryMACFilter INTEGER,
    lcosLXStatusWLANManagementNetworkprofilesEntryClBrgSupport INTEGER,
    lcosLXStatusWLANManagementNetworkprofilesEntryMaxStations Unsigned32,
    lcosLXStatusWLANManagementNetworkprofilesEntryClosedNetwork INTEGER,
    lcosLXStatusWLANManagementNetworkprofilesEntrySSID OCTET STRING,
    lcosLXStatusWLANManagementNetworkprofilesEntryMinHTMCS INTEGER,
    lcosLXStatusWLANManagementNetworkprofilesEntryMaxHTMCS INTEGER,
    lcosLXStatusWLANManagementNetworkprofilesEntryShortGuardInterval INTEGER,
    lcosLXStatusWLANManagementNetworkprofilesEntryMaxSpatialStreams INTEGER,
    lcosLXStatusWLANManagementNetworkprofilesEntrySendAggregates INTEGER,
    lcosLXStatusWLANManagementNetworkprofilesEntryRADIUSAccounting INTEGER,
    lcosLXStatusWLANManagementNetworkprofilesEntryVLANMode INTEGER,
    lcosLXStatusWLANManagementNetworkprofilesEntryConnectSSIDto INTEGER,
    lcosLXStatusWLANManagementNetworkprofilesEntryVLANId Unsigned32,
    lcosLXStatusWLANManagementNetworkprofilesEntryRADIUSProfile OCTET STRING,
    lcosLXStatusWLANManagementNetworkprofilesEntryMinClientStrength Unsigned32,
    lcosLXStatusWLANManagementNetworkprofilesEntryIEEE80211uNetProf OCTET STRING,
    lcosLXStatusWLANManagementNetworkprofilesEntryOKC INTEGER,
    lcosLXStatusWLANManagementNetworkprofilesEntryWPA2KeyManagement INTEGER,
    lcosLXStatusWLANManagementNetworkprofilesEntryAPSD INTEGER,
    lcosLXStatusWLANManagementNetworkprofilesEntryProtMgmtFrames INTEGER,
    lcosLXStatusWLANManagementNetworkprofilesEntryTxLimit Unsigned32,
    lcosLXStatusWLANManagementNetworkprofilesEntryRxLimit Unsigned32,
    lcosLXStatusWLANManagementNetworkprofilesEntryLBSTracking INTEGER,
    lcosLXStatusWLANManagementNetworkprofilesEntryLBSTrackingList OCTET STRING,
    lcosLXStatusWLANManagementNetworkprofilesEntryConverttoUnicast BITS,
    lcosLXStatusWLANManagementNetworkprofilesEntryTransonlyUnicast INTEGER,
    lcosLXStatusWLANManagementNetworkprofilesEntryWPA23SessKeytypes BITS,
    lcosLXStatusWLANManagementNetworkprofilesEntryWPA8021XSecLev INTEGER,
    lcosLXStatusWLANManagementNetworkprofilesEntryPerClientTxLimit Unsigned32,
    lcosLXStatusWLANManagementNetworkprofilesEntryPerClientRxLimit Unsigned32,
    lcosLXStatusWLANManagementNetworkprofilesEntryProtBeacons INTEGER
}

-- {COLUMN} 13.1.59.103.1.1
lcosLXStatusWLANManagementNetworkprofilesEntryName OBJECT-TYPE
    SYNTAX     OCTET STRING (SIZE(0..64))
    MAX-ACCESS not-accessible
    STATUS     current
    DESCRIPTION
        ""
    ::= { lcosLXStatusWLANManagementNetworkprofilesEntry 1 }

-- {COLUMN} 13.1.59.103.1.4
lcosLXStatusWLANManagementNetworkprofilesEntryOperating OBJECT-TYPE
    SYNTAX     INTEGER {
                  eNo(0),
                  eYes(1)
               }
    MAX-ACCESS read-only
    STATUS     current
    DESCRIPTION
        ""
    ::= { lcosLXStatusWLANManagementNetworkprofilesEntry 4 }

-- {COLUMN} 13.1.59.103.1.6
lcosLXStatusWLANManagementNetworkprofilesEntryEncryption OBJECT-TYPE
    SYNTAX     INTEGER {
                  e80211iWPAPSK(0),
                  e80211iWPA8021X(1),
                  eWEP104Bits(2),
                  eWEP40Bits(3),
                  eWEP104Bits8021X(4),
                  eWEP40Bits8021X(5),
                  eNone(6),
                  eEnhancedOpen(7),
                  eEnhancedOpenTransitional(8)
               }
    MAX-ACCESS read-only
    STATUS     current
    DESCRIPTION
        ""
    ::= { lcosLXStatusWLANManagementNetworkprofilesEntry 6 }

-- {COLUMN} 13.1.59.103.1.7
lcosLXStatusWLANManagementNetworkprofilesEntryWPA1SessKeytypes OBJECT-TYPE
    SYNTAX     INTEGER {
                  eTKIP(1),
                  eAES(2),
                  eTKIPAES(3)
               }
    MAX-ACCESS read-only
    STATUS     current
    DESCRIPTION
        ""
    ::= { lcosLXStatusWLANManagementNetworkprofilesEntry 7 }

-- {COLUMN} 13.1.59.103.1.8
lcosLXStatusWLANManagementNetworkprofilesEntryWPAVersion OBJECT-TYPE
    SYNTAX     INTEGER {
                  eWPA12(0),
                  eWPA1(1),
                  eWPA2(2),
                  eWPA3(3),
                  eWPA23(4),
                  eWPA123(5)
               }
    MAX-ACCESS read-only
    STATUS     current
    DESCRIPTION
        ""
    ::= { lcosLXStatusWLANManagementNetworkprofilesEntry 8 }

-- {COLUMN} 13.1.59.103.1.9
lcosLXStatusWLANManagementNetworkprofilesEntryKey OBJECT-TYPE
    SYNTAX     OCTET STRING (SIZE(0..64))
    MAX-ACCESS read-only
    STATUS     current
    DESCRIPTION
        ""
    ::= { lcosLXStatusWLANManagementNetworkprofilesEntry 9 }

-- {COLUMN} 13.1.59.103.1.10
lcosLXStatusWLANManagementNetworkprofilesEntryRadioBand OBJECT-TYPE
    SYNTAX     INTEGER {
                  eAll(0),
                  e24GHz(1),
                  e5GHz(2),
                  e6GHz(3)
               }
    MAX-ACCESS read-only
    STATUS     current
    DESCRIPTION
        ""
    ::= { lcosLXStatusWLANManagementNetworkprofilesEntry 10 }

-- {COLUMN} 13.1.59.103.1.11
lcosLXStatusWLANManagementNetworkprofilesEntryContinuationTime OBJECT-TYPE
    SYNTAX     Unsigned32 (0..65535)
    MAX-ACCESS read-only
    STATUS     current
    DESCRIPTION
        ""
    ::= { lcosLXStatusWLANManagementNetworkprofilesEntry 11 }

-- {COLUMN} 13.1.59.103.1.12
lcosLXStatusWLANManagementNetworkprofilesEntryMinTxRate OBJECT-TYPE
    SYNTAX     INTEGER {
                  eAuto(0),
                  e1M(1),
                  e2M(2),
                  e55M(3),
                  e11M(4),
                  e6M(5),
                  e9M(6),
                  e12M(7),
                  e18M(8),
                  e24M(9),
                  e36M(10),
                  e48M(11),
                  e54M(12),
                  eT72M(13),
                  eT96M(14),
                  eT108M(15)
               }
    MAX-ACCESS read-only
    STATUS     current
    DESCRIPTION
        ""
    ::= { lcosLXStatusWLANManagementNetworkprofilesEntry 12 }

-- {COLUMN} 13.1.59.103.1.13
lcosLXStatusWLANManagementNetworkprofilesEntryMaxTxRate OBJECT-TYPE
    SYNTAX     INTEGER {
                  eAuto(0),
                  e1M(1),
                  e2M(2),
                  e55M(3),
                  e11M(4),
                  e6M(5),
                  e9M(6),
                  e12M(7),
                  e18M(8),
                  e24M(9),
                  e36M(10),
                  e48M(11),
                  e54M(12),
                  eT72M(13),
                  eT96M(14),
                  eT108M(15)
               }
    MAX-ACCESS read-only
    STATUS     current
    DESCRIPTION
        ""
    ::= { lcosLXStatusWLANManagementNetworkprofilesEntry 13 }

-- {COLUMN} 13.1.59.103.1.14
lcosLXStatusWLANManagementNetworkprofilesEntryBasicRate OBJECT-TYPE
    SYNTAX     INTEGER {
                  e2M(0),
                  e1M(1),
                  eAuto(2),
                  e55M(3),
                  e11M(4),
                  e6M(5),
                  e9M(6),
                  e12M(7),
                  e18M(8),
                  e24M(9),
                  e36M(10),
                  e48M(11),
                  e54M(12),
                  eT72M(13),
                  eT96M(14),
                  eT108M(15)
               }
    MAX-ACCESS read-only
    STATUS     current
    DESCRIPTION
        ""
    ::= { lcosLXStatusWLANManagementNetworkprofilesEntry 14 }

-- {COLUMN} 13.1.59.103.1.15
lcosLXStatusWLANManagementNetworkprofilesEntryPreamble OBJECT-TYPE
    SYNTAX     INTEGER {
                  eAuto(0),
                  eLang(1)
               }
    MAX-ACCESS read-only
    STATUS     current
    DESCRIPTION
        ""
    ::= { lcosLXStatusWLANManagementNetworkprofilesEntry 15 }

-- {COLUMN} 13.1.59.103.1.16
lcosLXStatusWLANManagementNetworkprofilesEntryMACFilter OBJECT-TYPE
    SYNTAX     INTEGER {
                  eNo(0),
                  eYes(1)
               }
    MAX-ACCESS read-only
    STATUS     current
    DESCRIPTION
        ""
    ::= { lcosLXStatusWLANManagementNetworkprofilesEntry 16 }

-- {COLUMN} 13.1.59.103.1.17
lcosLXStatusWLANManagementNetworkprofilesEntryClBrgSupport OBJECT-TYPE
    SYNTAX     INTEGER {
                  eNo(0),
                  eYes(1),
                  eExclusive(2)
               }
    MAX-ACCESS read-only
    STATUS     current
    DESCRIPTION
        ""
    ::= { lcosLXStatusWLANManagementNetworkprofilesEntry 17 }

-- {COLUMN} 13.1.59.103.1.18
lcosLXStatusWLANManagementNetworkprofilesEntryMaxStations OBJECT-TYPE
    SYNTAX     Unsigned32 (0..65535)
    MAX-ACCESS read-only
    STATUS     current
    DESCRIPTION
        ""
    ::= { lcosLXStatusWLANManagementNetworkprofilesEntry 18 }

-- {COLUMN} 13.1.59.103.1.19
lcosLXStatusWLANManagementNetworkprofilesEntryClosedNetwork OBJECT-TYPE
    SYNTAX     INTEGER {
                  eNo(0),
                  eYes(1),
                  eTightened(2)
               }
    MAX-ACCESS read-only
    STATUS     current
    DESCRIPTION
        ""
    ::= { lcosLXStatusWLANManagementNetworkprofilesEntry 19 }

-- {COLUMN} 13.1.59.103.1.21
lcosLXStatusWLANManagementNetworkprofilesEntrySSID OBJECT-TYPE
    SYNTAX     OCTET STRING (SIZE(0..64))
    MAX-ACCESS read-only
    STATUS     current
    DESCRIPTION
        ""
    ::= { lcosLXStatusWLANManagementNetworkprofilesEntry 21 }

-- {COLUMN} 13.1.59.103.1.22
lcosLXStatusWLANManagementNetworkprofilesEntryMinHTMCS OBJECT-TYPE
    SYNTAX     INTEGER {
                  eAuto(0),
                  eMCS08(1),
                  eMCS19(2),
                  eMCS210(3),
                  eMCS311(4),
                  eMCS412(5),
                  eMCS513(6),
                  eMCS614(7),
                  eMCS715(8)
               }
    MAX-ACCESS read-only
    STATUS     current
    DESCRIPTION
        ""
    ::= { lcosLXStatusWLANManagementNetworkprofilesEntry 22 }

-- {COLUMN} 13.1.59.103.1.23
lcosLXStatusWLANManagementNetworkprofilesEntryMaxHTMCS OBJECT-TYPE
    SYNTAX     INTEGER {
                  eAuto(0),
                  eMCS08(1),
                  eMCS19(2),
                  eMCS210(3),
                  eMCS311(4),
                  eMCS412(5),
                  eMCS513(6),
                  eMCS614(7),
                  eMCS715(8)
               }
    MAX-ACCESS read-only
    STATUS     current
    DESCRIPTION
        ""
    ::= { lcosLXStatusWLANManagementNetworkprofilesEntry 23 }

-- {COLUMN} 13.1.59.103.1.24
lcosLXStatusWLANManagementNetworkprofilesEntryShortGuardInterval OBJECT-TYPE
    SYNTAX     INTEGER {
                  eAuto(0),
                  eNo(1)
               }
    MAX-ACCESS read-only
    STATUS     current
    DESCRIPTION
        ""
    ::= { lcosLXStatusWLANManagementNetworkprofilesEntry 24 }

-- {COLUMN} 13.1.59.103.1.25
lcosLXStatusWLANManagementNetworkprofilesEntryMaxSpatialStreams OBJECT-TYPE
    SYNTAX     INTEGER {
                  eAuto(0),
                  eOne(1),
                  eTwo(2),
                  eThree(3),
                  eFour(4)
               }
    MAX-ACCESS read-only
    STATUS     current
    DESCRIPTION
        ""
    ::= { lcosLXStatusWLANManagementNetworkprofilesEntry 25 }

-- {COLUMN} 13.1.59.103.1.26
lcosLXStatusWLANManagementNetworkprofilesEntrySendAggregates OBJECT-TYPE
    SYNTAX     INTEGER {
                  eNo(0),
                  eYes(1)
               }
    MAX-ACCESS read-only
    STATUS     current
    DESCRIPTION
        ""
    ::= { lcosLXStatusWLANManagementNetworkprofilesEntry 26 }

-- {COLUMN} 13.1.59.103.1.28
lcosLXStatusWLANManagementNetworkprofilesEntryRADIUSAccounting OBJECT-TYPE
    SYNTAX     INTEGER {
                  eNo(0),
                  eYes(1)
               }
    MAX-ACCESS read-only
    STATUS     current
    DESCRIPTION
        ""
    ::= { lcosLXStatusWLANManagementNetworkprofilesEntry 28 }

-- {COLUMN} 13.1.59.103.1.30
lcosLXStatusWLANManagementNetworkprofilesEntryVLANMode OBJECT-TYPE
    SYNTAX     INTEGER {
                  eUntagged(0),
                  eTagged(1)
               }
    MAX-ACCESS read-only
    STATUS     current
    DESCRIPTION
        ""
    ::= { lcosLXStatusWLANManagementNetworkprofilesEntry 30 }

-- {COLUMN} 13.1.59.103.1.32
lcosLXStatusWLANManagementNetworkprofilesEntryConnectSSIDto OBJECT-TYPE
    SYNTAX     INTEGER {
                  ebrlan(0),
                  eWLCTunnel1(1),
                  eWLCTunnel2(2),
                  eWLCTunnel3(3),
                  eWLCTunnel4(4),
                  eWLCTunnel5(5),
                  eWLCTunnel6(6),
                  eWLCTunnel7(7),
                  eWLCTunnel8(8),
                  eWLCTunnel9(9),
                  eWLCTunnel10(10),
                  eWLCTunnel11(11),
                  eWLCTunnel12(12),
                  eWLCTunnel13(13),
                  eWLCTunnel14(14),
                  eWLCTunnel15(15),
                  eWLCTunnel16(16),
                  eWLCTunnel17(17),
                  eWLCTunnel18(18),
                  eWLCTunnel19(19),
                  eWLCTunnel20(20),
                  eWLCTunnel21(21),
                  eWLCTunnel22(22),
                  eWLCTunnel23(23),
                  eWLCTunnel24(24),
                  eWLCTunnel25(25),
                  eWLCTunnel26(26),
                  eWLCTunnel27(27),
                  eWLCTunnel28(28),
                  eWLCTunnel29(29),
                  eWLCTunnel30(30),
                  eWLCTunnel31(31),
                  eWLCTunnel32(32),
                  eL2TPTunnel1(34),
                  eL2TPTunnel2(35),
                  eL2TPTunnel3(36),
                  eL2TPTunnel4(37),
                  eL2TPTunnel5(38),
                  eL2TPTunnel6(39),
                  eL2TPTunnel7(40),
                  eL2TPTunnel8(41),
                  eL2TPTunnel9(42),
                  eL2TPTunnel10(43),
                  eL2TPTunnel11(44),
                  eL2TPTunnel12(45),
                  eL2TPTunnel13(46),
                  eL2TPTunnel14(47),
                  eL2TPTunnel15(48),
                  eL2TPTunnel16(49)
               }
    MAX-ACCESS read-only
    STATUS     current
    DESCRIPTION
        ""
    ::= { lcosLXStatusWLANManagementNetworkprofilesEntry 32 }

-- {COLUMN} 13.1.59.103.1.34
lcosLXStatusWLANManagementNetworkprofilesEntryVLANId OBJECT-TYPE
    SYNTAX     Unsigned32 (0..65535)
    MAX-ACCESS read-only
    STATUS     current
    DESCRIPTION
        ""
    ::= { lcosLXStatusWLANManagementNetworkprofilesEntry 34 }

-- {COLUMN} 13.1.59.103.1.35
lcosLXStatusWLANManagementNetworkprofilesEntryRADIUSProfile OBJECT-TYPE
    SYNTAX     OCTET STRING (SIZE(0..32))
    MAX-ACCESS read-only
    STATUS     current
    DESCRIPTION
        ""
    ::= { lcosLXStatusWLANManagementNetworkprofilesEntry 35 }

-- {COLUMN} 13.1.59.103.1.38
lcosLXStatusWLANManagementNetworkprofilesEntryMinClientStrength OBJECT-TYPE
    SYNTAX     Unsigned32 (0..65535)
    MAX-ACCESS read-only
    STATUS     current
    DESCRIPTION
        ""
    ::= { lcosLXStatusWLANManagementNetworkprofilesEntry 38 }

-- {COLUMN} 13.1.59.103.1.39
lcosLXStatusWLANManagementNetworkprofilesEntryIEEE80211uNetProf OBJECT-TYPE
    SYNTAX     OCTET STRING (SIZE(0..64))
    MAX-ACCESS read-only
    STATUS     current
    DESCRIPTION
        ""
    ::= { lcosLXStatusWLANManagementNetworkprofilesEntry 39 }

-- {COLUMN} 13.1.59.103.1.40
lcosLXStatusWLANManagementNetworkprofilesEntryOKC OBJECT-TYPE
    SYNTAX     INTEGER {
                  eNo(0),
                  eYes(1)
               }
    MAX-ACCESS read-only
    STATUS     current
    DESCRIPTION
        ""
    ::= { lcosLXStatusWLANManagementNetworkprofilesEntry 40 }

-- {COLUMN} 13.1.59.103.1.41
lcosLXStatusWLANManagementNetworkprofilesEntryWPA2KeyManagement OBJECT-TYPE
    SYNTAX     INTEGER {
                  eStandard(0),
                  eFastRoaming(1),
                  eStandardFastRoaming(2)
               }
    MAX-ACCESS read-only
    STATUS     current
    DESCRIPTION
        ""
    ::= { lcosLXStatusWLANManagementNetworkprofilesEntry 41 }

-- {COLUMN} 13.1.59.103.1.42
lcosLXStatusWLANManagementNetworkprofilesEntryAPSD OBJECT-TYPE
    SYNTAX     INTEGER {
                  eNo(0),
                  eYes(1)
               }
    MAX-ACCESS read-only
    STATUS     current
    DESCRIPTION
        ""
    ::= { lcosLXStatusWLANManagementNetworkprofilesEntry 42 }

-- {COLUMN} 13.1.59.103.1.43
lcosLXStatusWLANManagementNetworkprofilesEntryProtMgmtFrames OBJECT-TYPE
    SYNTAX     INTEGER {
                  eNo(0),
                  eoptional(1),
                  emandatory(2)
               }
    MAX-ACCESS read-only
    STATUS     current
    DESCRIPTION
        ""
    ::= { lcosLXStatusWLANManagementNetworkprofilesEntry 43 }

-- {COLUMN} 13.1.59.103.1.44
lcosLXStatusWLANManagementNetworkprofilesEntryTxLimit OBJECT-TYPE
    SYNTAX     Unsigned32 (0..4294967295)
    MAX-ACCESS read-only
    STATUS     current
    DESCRIPTION
        ""
    ::= { lcosLXStatusWLANManagementNetworkprofilesEntry 44 }

-- {COLUMN} 13.1.59.103.1.45
lcosLXStatusWLANManagementNetworkprofilesEntryRxLimit OBJECT-TYPE
    SYNTAX     Unsigned32 (0..4294967295)
    MAX-ACCESS read-only
    STATUS     current
    DESCRIPTION
        ""
    ::= { lcosLXStatusWLANManagementNetworkprofilesEntry 45 }

-- {COLUMN} 13.1.59.103.1.46
lcosLXStatusWLANManagementNetworkprofilesEntryLBSTracking OBJECT-TYPE
    SYNTAX     INTEGER {
                  eNo(0),
                  eYes(1)
               }
    MAX-ACCESS read-only
    STATUS     current
    DESCRIPTION
        ""
    ::= { lcosLXStatusWLANManagementNetworkprofilesEntry 46 }

-- {COLUMN} 13.1.59.103.1.47
lcosLXStatusWLANManagementNetworkprofilesEntryLBSTrackingList OBJECT-TYPE
    SYNTAX     OCTET STRING (SIZE(0..64))
    MAX-ACCESS read-only
    STATUS     current
    DESCRIPTION
        ""
    ::= { lcosLXStatusWLANManagementNetworkprofilesEntry 47 }

-- {COLUMN} 13.1.59.103.1.50
lcosLXStatusWLANManagementNetworkprofilesEntryConverttoUnicast OBJECT-TYPE
    SYNTAX     BITS {
                  eDHCP(0),
                  eMulticast(1)
               }
    MAX-ACCESS read-only
    STATUS     current
    DESCRIPTION
        ""
    ::= { lcosLXStatusWLANManagementNetworkprofilesEntry 50 }

-- {COLUMN} 13.1.59.103.1.51
lcosLXStatusWLANManagementNetworkprofilesEntryTransonlyUnicast OBJECT-TYPE
    SYNTAX     INTEGER {
                  eNo(0),
                  eYes(1)
               }
    MAX-ACCESS read-only
    STATUS     current
    DESCRIPTION
        ""
    ::= { lcosLXStatusWLANManagementNetworkprofilesEntry 51 }

-- {COLUMN} 13.1.59.103.1.53
lcosLXStatusWLANManagementNetworkprofilesEntryWPA23SessKeytypes OBJECT-TYPE
    SYNTAX     BITS {
                  eTKIP(0),
                  eAESCCMP128(1),
                  eAESCCMP256(2),
                  eAESGCMP128(3),
                  eAESGCMP256(4)
               }
    MAX-ACCESS read-only
    STATUS     current
    DESCRIPTION
        ""
    ::= { lcosLXStatusWLANManagementNetworkprofilesEntry 53 }

-- {COLUMN} 13.1.59.103.1.54
lcosLXStatusWLANManagementNetworkprofilesEntryWPA8021XSecLev OBJECT-TYPE
    SYNTAX     INTEGER {
                  eStandard(0),
                  eSuiteB128Bits(1),
                  eSuiteB192Bits(2)
               }
    MAX-ACCESS read-only
    STATUS     current
    DESCRIPTION
        ""
    ::= { lcosLXStatusWLANManagementNetworkprofilesEntry 54 }

-- {COLUMN} 13.1.59.103.1.55
lcosLXStatusWLANManagementNetworkprofilesEntryPerClientTxLimit OBJECT-TYPE
    SYNTAX     Unsigned32 (0..4294967295)
    MAX-ACCESS read-only
    STATUS     current
    DESCRIPTION
        ""
    ::= { lcosLXStatusWLANManagementNetworkprofilesEntry 55 }

-- {COLUMN} 13.1.59.103.1.56
lcosLXStatusWLANManagementNetworkprofilesEntryPerClientRxLimit OBJECT-TYPE
    SYNTAX     Unsigned32 (0..4294967295)
    MAX-ACCESS read-only
    STATUS     current
    DESCRIPTION
        ""
    ::= { lcosLXStatusWLANManagementNetworkprofilesEntry 56 }

-- {COLUMN} 13.1.59.103.1.60
lcosLXStatusWLANManagementNetworkprofilesEntryProtBeacons OBJECT-TYPE
    SYNTAX     INTEGER {
                  eNo(0),
                  eYes(1),
                  eAuto(255)
               }
    MAX-ACCESS read-only
    STATUS     current
    DESCRIPTION
        ""
    ::= { lcosLXStatusWLANManagementNetworkprofilesEntry 60 }

-- {TABLE} 13.1.59.105
lcosLXStatusWLANManagementRADIUSProfiles OBJECT-TYPE
    SYNTAX     SEQUENCE OF LcosLXStatusWLANManagementRADIUSProfilesEntry
    MAX-ACCESS not-accessible
    STATUS     current
    DESCRIPTION
        ""
    ::= { lcosLXStatusWLANManagement 105 }

-- {INDEX} 13.1.59.105
lcosLXStatusWLANManagementRADIUSProfilesEntry OBJECT-TYPE
    SYNTAX     LcosLXStatusWLANManagementRADIUSProfilesEntry
    MAX-ACCESS not-accessible
    STATUS     current
    DESCRIPTION
        ""
    INDEX {
        lcosLXStatusWLANManagementRADIUSProfilesEntryName
    }
    ::= { lcosLXStatusWLANManagementRADIUSProfiles 1 }

-- {SEQUENCE} 13.1.59.105
LcosLXStatusWLANManagementRADIUSProfilesEntry ::= SEQUENCE {
    lcosLXStatusWLANManagementRADIUSProfilesEntryName OCTET STRING,
    lcosLXStatusWLANManagementRADIUSProfilesEntryAccountIP OCTET STRING,
    lcosLXStatusWLANManagementRADIUSProfilesEntryAccountPort Unsigned32,
    lcosLXStatusWLANManagementRADIUSProfilesEntryAccountSecret OCTET STRING,
    lcosLXStatusWLANManagementRADIUSProfilesEntryAccountLoopback OCTET STRING,
    lcosLXStatusWLANManagementRADIUSProfilesEntryAccountProtocol INTEGER,
    lcosLXStatusWLANManagementRADIUSProfilesEntryAccessIP OCTET STRING,
    lcosLXStatusWLANManagementRADIUSProfilesEntryAccessPort Unsigned32,
    lcosLXStatusWLANManagementRADIUSProfilesEntryAccessSecret OCTET STRING,
    lcosLXStatusWLANManagementRADIUSProfilesEntryAccessLoopback OCTET STRING,
    lcosLXStatusWLANManagementRADIUSProfilesEntryAccessProtocol INTEGER,
    lcosLXStatusWLANManagementRADIUSProfilesEntryBackup OCTET STRING
}

-- {COLUMN} 13.1.59.105.1.1
lcosLXStatusWLANManagementRADIUSProfilesEntryName OBJECT-TYPE
    SYNTAX     OCTET STRING (SIZE(0..64))
    MAX-ACCESS not-accessible
    STATUS     current
    DESCRIPTION
        ""
    ::= { lcosLXStatusWLANManagementRADIUSProfilesEntry 1 }

-- {COLUMN} 13.1.59.105.1.2
lcosLXStatusWLANManagementRADIUSProfilesEntryAccountIP OBJECT-TYPE
    SYNTAX     OCTET STRING (SIZE(0..44))
    MAX-ACCESS read-only
    STATUS     current
    DESCRIPTION
        ""
    ::= { lcosLXStatusWLANManagementRADIUSProfilesEntry 2 }

-- {COLUMN} 13.1.59.105.1.3
lcosLXStatusWLANManagementRADIUSProfilesEntryAccountPort OBJECT-TYPE
    SYNTAX     Unsigned32 (0..65535)
    MAX-ACCESS read-only
    STATUS     current
    DESCRIPTION
        ""
    ::= { lcosLXStatusWLANManagementRADIUSProfilesEntry 3 }

-- {COLUMN} 13.1.59.105.1.4
lcosLXStatusWLANManagementRADIUSProfilesEntryAccountSecret OBJECT-TYPE
    SYNTAX     OCTET STRING (SIZE(0..64))
    MAX-ACCESS read-only
    STATUS     current
    DESCRIPTION
        ""
    ::= { lcosLXStatusWLANManagementRADIUSProfilesEntry 4 }

-- {COLUMN} 13.1.59.105.1.5
lcosLXStatusWLANManagementRADIUSProfilesEntryAccountLoopback OBJECT-TYPE
    SYNTAX     OCTET STRING (SIZE(0..32))
    MAX-ACCESS read-only
    STATUS     current
    DESCRIPTION
        ""
    ::= { lcosLXStatusWLANManagementRADIUSProfilesEntry 5 }

-- {COLUMN} 13.1.59.105.1.6
lcosLXStatusWLANManagementRADIUSProfilesEntryAccountProtocol OBJECT-TYPE
    SYNTAX     INTEGER {
                  eRADIUS(0),
                  eRADSEC(1)
               }
    MAX-ACCESS read-only
    STATUS     current
    DESCRIPTION
        ""
    ::= { lcosLXStatusWLANManagementRADIUSProfilesEntry 6 }

-- {COLUMN} 13.1.59.105.1.7
lcosLXStatusWLANManagementRADIUSProfilesEntryAccessIP OBJECT-TYPE
    SYNTAX     OCTET STRING (SIZE(0..44))
    MAX-ACCESS read-only
    STATUS     current
    DESCRIPTION
        ""
    ::= { lcosLXStatusWLANManagementRADIUSProfilesEntry 7 }

-- {COLUMN} 13.1.59.105.1.8
lcosLXStatusWLANManagementRADIUSProfilesEntryAccessPort OBJECT-TYPE
    SYNTAX     Unsigned32 (0..65535)
    MAX-ACCESS read-only
    STATUS     current
    DESCRIPTION
        ""
    ::= { lcosLXStatusWLANManagementRADIUSProfilesEntry 8 }

-- {COLUMN} 13.1.59.105.1.9
lcosLXStatusWLANManagementRADIUSProfilesEntryAccessSecret OBJECT-TYPE
    SYNTAX     OCTET STRING (SIZE(0..64))
    MAX-ACCESS read-only
    STATUS     current
    DESCRIPTION
        ""
    ::= { lcosLXStatusWLANManagementRADIUSProfilesEntry 9 }

-- {COLUMN} 13.1.59.105.1.10
lcosLXStatusWLANManagementRADIUSProfilesEntryAccessLoopback OBJECT-TYPE
    SYNTAX     OCTET STRING (SIZE(0..32))
    MAX-ACCESS read-only
    STATUS     current
    DESCRIPTION
        ""
    ::= { lcosLXStatusWLANManagementRADIUSProfilesEntry 10 }

-- {COLUMN} 13.1.59.105.1.11
lcosLXStatusWLANManagementRADIUSProfilesEntryAccessProtocol OBJECT-TYPE
    SYNTAX     INTEGER {
                  eRADIUS(0),
                  eRADSEC(1)
               }
    MAX-ACCESS read-only
    STATUS     current
    DESCRIPTION
        ""
    ::= { lcosLXStatusWLANManagementRADIUSProfilesEntry 11 }

-- {COLUMN} 13.1.59.105.1.12
lcosLXStatusWLANManagementRADIUSProfilesEntryBackup OBJECT-TYPE
    SYNTAX     OCTET STRING (SIZE(0..64))
    MAX-ACCESS read-only
    STATUS     current
    DESCRIPTION
        ""
    ::= { lcosLXStatusWLANManagementRADIUSProfilesEntry 12 }

-- {OID} 13.1.61
lcosLXStatusL2TP OBJECT IDENTIFIER ::= { lcosLXStatus 61 }

-- {TABLE} 13.1.61.1
lcosLXStatusL2TPEndpoints OBJECT-TYPE
    SYNTAX     SEQUENCE OF LcosLXStatusL2TPEndpointsEntry
    MAX-ACCESS not-accessible
    STATUS     current
    DESCRIPTION
        ""
    ::= { lcosLXStatusL2TP 1 }

-- {INDEX} 13.1.61.1
lcosLXStatusL2TPEndpointsEntry OBJECT-TYPE
    SYNTAX     LcosLXStatusL2TPEndpointsEntry
    MAX-ACCESS not-accessible
    STATUS     current
    DESCRIPTION
        ""
    INDEX {
        lcosLXStatusL2TPEndpointsEntryL2TPEndpoint
    }
    ::= { lcosLXStatusL2TPEndpoints 1 }

-- {SEQUENCE} 13.1.61.1
LcosLXStatusL2TPEndpointsEntry ::= SEQUENCE {
    lcosLXStatusL2TPEndpointsEntryL2TPEndpoint OCTET STRING,
    lcosLXStatusL2TPEndpointsEntryState OCTET STRING,
    lcosLXStatusL2TPEndpointsEntryConnStartTimestamp OCTET STRING,
    lcosLXStatusL2TPEndpointsEntryConnstarttime OCTET STRING
}

-- {COLUMN} 13.1.61.1.1.1
lcosLXStatusL2TPEndpointsEntryL2TPEndpoint OBJECT-TYPE
    SYNTAX     OCTET STRING (SIZE(0..32))
    MAX-ACCESS not-accessible
    STATUS     current
    DESCRIPTION
        ""
    ::= { lcosLXStatusL2TPEndpointsEntry 1 }

-- {COLUMN} 13.1.61.1.1.2
lcosLXStatusL2TPEndpointsEntryState OBJECT-TYPE
    SYNTAX     OCTET STRING (SIZE(0..32))
    MAX-ACCESS read-only
    STATUS     current
    DESCRIPTION
        ""
    ::= { lcosLXStatusL2TPEndpointsEntry 2 }

-- {COLUMN} 13.1.61.1.1.3
lcosLXStatusL2TPEndpointsEntryConnStartTimestamp OBJECT-TYPE
    SYNTAX     OCTET STRING (SIZE(0..32))
    MAX-ACCESS read-only
    STATUS     current
    DESCRIPTION
        ""
    ::= { lcosLXStatusL2TPEndpointsEntry 3 }

-- {COLUMN} 13.1.61.1.1.4
lcosLXStatusL2TPEndpointsEntryConnstarttime OBJECT-TYPE
    SYNTAX     OCTET STRING (SIZE(0..64))
    MAX-ACCESS read-only
    STATUS     current
    DESCRIPTION
        ""
    ::= { lcosLXStatusL2TPEndpointsEntry 4 }

-- {TABLE} 13.1.61.2
lcosLXStatusL2TPEthernet OBJECT-TYPE
    SYNTAX     SEQUENCE OF LcosLXStatusL2TPEthernetEntry
    MAX-ACCESS not-accessible
    STATUS     current
    DESCRIPTION
        ""
    ::= { lcosLXStatusL2TP 2 }

-- {INDEX} 13.1.61.2
lcosLXStatusL2TPEthernetEntry OBJECT-TYPE
    SYNTAX     LcosLXStatusL2TPEthernetEntry
    MAX-ACCESS not-accessible
    STATUS     current
    DESCRIPTION
        ""
    INDEX {
        lcosLXStatusL2TPEthernetEntryRemoteEnd,
        lcosLXStatusL2TPEthernetEntryL2TPEndpoint
    }
    ::= { lcosLXStatusL2TPEthernet 1 }

-- {SEQUENCE} 13.1.61.2
LcosLXStatusL2TPEthernetEntry ::= SEQUENCE {
    lcosLXStatusL2TPEthernetEntryRemoteEnd OCTET STRING,
    lcosLXStatusL2TPEthernetEntryL2TPEndpoint OCTET STRING,
    lcosLXStatusL2TPEthernetEntryState OCTET STRING,
    lcosLXStatusL2TPEthernetEntryInterface OCTET STRING,
    lcosLXStatusL2TPEthernetEntryBridgeAddr OCTET STRING,
    lcosLXStatusL2TPEthernetEntryConntimestamp OCTET STRING,
    lcosLXStatusL2TPEthernetEntryConnstarttime OCTET STRING
}

-- {COLUMN} 13.1.61.2.1.1
lcosLXStatusL2TPEthernetEntryRemoteEnd OBJECT-TYPE
    SYNTAX     OCTET STRING (SIZE(0..32))
    MAX-ACCESS not-accessible
    STATUS     current
    DESCRIPTION
        ""
    ::= { lcosLXStatusL2TPEthernetEntry 1 }

-- {COLUMN} 13.1.61.2.1.2
lcosLXStatusL2TPEthernetEntryL2TPEndpoint OBJECT-TYPE
    SYNTAX     OCTET STRING (SIZE(0..32))
    MAX-ACCESS not-accessible
    STATUS     current
    DESCRIPTION
        ""
    ::= { lcosLXStatusL2TPEthernetEntry 2 }

-- {COLUMN} 13.1.61.2.1.3
lcosLXStatusL2TPEthernetEntryState OBJECT-TYPE
    SYNTAX     OCTET STRING (SIZE(0..32))
    MAX-ACCESS read-only
    STATUS     current
    DESCRIPTION
        ""
    ::= { lcosLXStatusL2TPEthernetEntry 3 }

-- {COLUMN} 13.1.61.2.1.4
lcosLXStatusL2TPEthernetEntryInterface OBJECT-TYPE
    SYNTAX     OCTET STRING (SIZE(0..32))
    MAX-ACCESS read-only
    STATUS     current
    DESCRIPTION
        ""
    ::= { lcosLXStatusL2TPEthernetEntry 4 }

-- {COLUMN} 13.1.61.2.1.5
lcosLXStatusL2TPEthernetEntryBridgeAddr OBJECT-TYPE
    SYNTAX     OCTET STRING (SIZE(0..32))
    MAX-ACCESS read-only
    STATUS     current
    DESCRIPTION
        ""
    ::= { lcosLXStatusL2TPEthernetEntry 5 }

-- {COLUMN} 13.1.61.2.1.6
lcosLXStatusL2TPEthernetEntryConntimestamp OBJECT-TYPE
    SYNTAX     OCTET STRING (SIZE(0..32))
    MAX-ACCESS read-only
    STATUS     current
    DESCRIPTION
        ""
    ::= { lcosLXStatusL2TPEthernetEntry 6 }

-- {COLUMN} 13.1.61.2.1.7
lcosLXStatusL2TPEthernetEntryConnstarttime OBJECT-TYPE
    SYNTAX     OCTET STRING (SIZE(0..64))
    MAX-ACCESS read-only
    STATUS     current
    DESCRIPTION
        ""
    ::= { lcosLXStatusL2TPEthernetEntry 7 }

-- {OID} 13.1.62
lcosLXStatusSyslog OBJECT IDENTIFIER ::= { lcosLXStatus 62 }

-- {OID} 13.1.70
lcosLXStatusIPConfiguration OBJECT IDENTIFIER ::= { lcosLXStatus 70 }

-- {TABLE} 13.1.70.1
lcosLXStatusIPConfigurationAddresses OBJECT-TYPE
    SYNTAX     SEQUENCE OF LcosLXStatusIPConfigurationAddressesEntry
    MAX-ACCESS not-accessible
    STATUS     current
    DESCRIPTION
        ""
    ::= { lcosLXStatusIPConfiguration 1 }

-- {INDEX} 13.1.70.1
lcosLXStatusIPConfigurationAddressesEntry OBJECT-TYPE
    SYNTAX     LcosLXStatusIPConfigurationAddressesEntry
    MAX-ACCESS not-accessible
    STATUS     current
    DESCRIPTION
        ""
    INDEX {
        lcosLXStatusIPConfigurationAddressesEntryInterfaceName,
        lcosLXStatusIPConfigurationAddressesEntryIPVersion,
        lcosLXStatusIPConfigurationAddressesEntryAddressSource,
        lcosLXStatusIPConfigurationAddressesEntryAddress
    }
    ::= { lcosLXStatusIPConfigurationAddresses 1 }

-- {SEQUENCE} 13.1.70.1
LcosLXStatusIPConfigurationAddressesEntry ::= SEQUENCE {
    lcosLXStatusIPConfigurationAddressesEntryInterfaceName OCTET STRING,
    lcosLXStatusIPConfigurationAddressesEntryIPVersion INTEGER,
    lcosLXStatusIPConfigurationAddressesEntryAddressSource INTEGER,
    lcosLXStatusIPConfigurationAddressesEntryAddress OCTET STRING,
    lcosLXStatusIPConfigurationAddressesEntryGateway OCTET STRING
}

-- {COLUMN} 13.1.70.1.1.1
lcosLXStatusIPConfigurationAddressesEntryInterfaceName OBJECT-TYPE
    SYNTAX     OCTET STRING (SIZE(0..64))
    MAX-ACCESS not-accessible
    STATUS     current
    DESCRIPTION
        ""
    ::= { lcosLXStatusIPConfigurationAddressesEntry 1 }

-- {COLUMN} 13.1.70.1.1.2
lcosLXStatusIPConfigurationAddressesEntryIPVersion OBJECT-TYPE
    SYNTAX     INTEGER {
                  eIPv4(1),
                  eIPv6(2)
               }
    MAX-ACCESS not-accessible
    STATUS     current
    DESCRIPTION
        ""
    ::= { lcosLXStatusIPConfigurationAddressesEntry 2 }

-- {COLUMN} 13.1.70.1.1.3
lcosLXStatusIPConfigurationAddressesEntryAddressSource OBJECT-TYPE
    SYNTAX     INTEGER {
                  eRouterAdvertisement(1),
                  eLinkLocal(2),
                  eDHCPv6(3),
                  eDHCP(4),
                  estatic(5)
               }
    MAX-ACCESS not-accessible
    STATUS     current
    DESCRIPTION
        ""
    ::= { lcosLXStatusIPConfigurationAddressesEntry 3 }

-- {COLUMN} 13.1.70.1.1.4
lcosLXStatusIPConfigurationAddressesEntryAddress OBJECT-TYPE
    SYNTAX     OCTET STRING (SIZE(0..50))
    MAX-ACCESS not-accessible
    STATUS     current
    DESCRIPTION
        ""
    ::= { lcosLXStatusIPConfigurationAddressesEntry 4 }

-- {COLUMN} 13.1.70.1.1.5
lcosLXStatusIPConfigurationAddressesEntryGateway OBJECT-TYPE
    SYNTAX     OCTET STRING (SIZE(0..44))
    MAX-ACCESS read-only
    STATUS     current
    DESCRIPTION
        ""
    ::= { lcosLXStatusIPConfigurationAddressesEntry 5 }

-- {OID} 13.1.77
lcosLXStatusUSB OBJECT IDENTIFIER ::= { lcosLXStatus 77 }

-- {TABLE} 13.1.77.1
lcosLXStatusUSBDevices OBJECT-TYPE
    SYNTAX     SEQUENCE OF LcosLXStatusUSBDevicesEntry
    MAX-ACCESS not-accessible
    STATUS     current
    DESCRIPTION
        ""
    ::= { lcosLXStatusUSB 1 }

-- {INDEX} 13.1.77.1
lcosLXStatusUSBDevicesEntry OBJECT-TYPE
    SYNTAX     LcosLXStatusUSBDevicesEntry
    MAX-ACCESS not-accessible
    STATUS     current
    DESCRIPTION
        ""
    INDEX {
        lcosLXStatusUSBDevicesEntryBusNumber,
        lcosLXStatusUSBDevicesEntryDevNumber
    }
    ::= { lcosLXStatusUSBDevices 1 }

-- {SEQUENCE} 13.1.77.1
LcosLXStatusUSBDevicesEntry ::= SEQUENCE {
    lcosLXStatusUSBDevicesEntryBusNumber Unsigned32,
    lcosLXStatusUSBDevicesEntryDevNumber Unsigned32,
    lcosLXStatusUSBDevicesEntryVendorID OCTET STRING,
    lcosLXStatusUSBDevicesEntryProductID OCTET STRING,
    lcosLXStatusUSBDevicesEntryProduct OCTET STRING,
    lcosLXStatusUSBDevicesEntryManufacturer OCTET STRING
}

-- {COLUMN} 13.1.77.1.1.1
lcosLXStatusUSBDevicesEntryBusNumber OBJECT-TYPE
    SYNTAX     Unsigned32 (0..255)
    MAX-ACCESS not-accessible
    STATUS     current
    DESCRIPTION
        ""
    ::= { lcosLXStatusUSBDevicesEntry 1 }

-- {COLUMN} 13.1.77.1.1.2
lcosLXStatusUSBDevicesEntryDevNumber OBJECT-TYPE
    SYNTAX     Unsigned32 (0..255)
    MAX-ACCESS not-accessible
    STATUS     current
    DESCRIPTION
        ""
    ::= { lcosLXStatusUSBDevicesEntry 2 }

-- {COLUMN} 13.1.77.1.1.3
lcosLXStatusUSBDevicesEntryVendorID OBJECT-TYPE
    SYNTAX     OCTET STRING (SIZE(0..16))
    MAX-ACCESS read-only
    STATUS     current
    DESCRIPTION
        ""
    ::= { lcosLXStatusUSBDevicesEntry 3 }

-- {COLUMN} 13.1.77.1.1.4
lcosLXStatusUSBDevicesEntryProductID OBJECT-TYPE
    SYNTAX     OCTET STRING (SIZE(0..16))
    MAX-ACCESS read-only
    STATUS     current
    DESCRIPTION
        ""
    ::= { lcosLXStatusUSBDevicesEntry 4 }

-- {COLUMN} 13.1.77.1.1.5
lcosLXStatusUSBDevicesEntryProduct OBJECT-TYPE
    SYNTAX     OCTET STRING (SIZE(0..64))
    MAX-ACCESS read-only
    STATUS     current
    DESCRIPTION
        ""
    ::= { lcosLXStatusUSBDevicesEntry 5 }

-- {COLUMN} 13.1.77.1.1.6
lcosLXStatusUSBDevicesEntryManufacturer OBJECT-TYPE
    SYNTAX     OCTET STRING (SIZE(0..64))
    MAX-ACCESS read-only
    STATUS     current
    DESCRIPTION
        ""
    ::= { lcosLXStatusUSBDevicesEntry 6 }

-- {OID} 13.1.91
lcosLXStatusRolloutAgent OBJECT IDENTIFIER ::= { lcosLXStatus 91 }

-- {SCALAR} 13.1.91.1
lcosLXStatusRolloutAgentHeartbeatURL OBJECT-TYPE
    SYNTAX     OCTET STRING (SIZE(0..255))
    MAX-ACCESS read-only
    STATUS     current
    DESCRIPTION
        ""
    ::= { lcosLXStatusRolloutAgent 1 }

-- {SCALAR} 13.1.91.2
lcosLXStatusRolloutAgentProjectID OBJECT-TYPE
    SYNTAX     OCTET STRING (SIZE(0..36))
    MAX-ACCESS read-only
    STATUS     current
    DESCRIPTION
        ""
    ::= { lcosLXStatusRolloutAgent 2 }

-- {SCALAR} 13.1.91.3
lcosLXStatusRolloutAgentDeviceID OBJECT-TYPE
    SYNTAX     OCTET STRING (SIZE(0..36))
    MAX-ACCESS read-only
    STATUS     current
    DESCRIPTION
        ""
    ::= { lcosLXStatusRolloutAgent 3 }

-- {SCALAR} 13.1.91.4
lcosLXStatusRolloutAgentActiveTAN OBJECT-TYPE
    SYNTAX     OCTET STRING (SIZE(0..36))
    MAX-ACCESS read-only
    STATUS     current
    DESCRIPTION
        ""
    ::= { lcosLXStatusRolloutAgent 4 }

-- {SCALAR} 13.1.91.5
lcosLXStatusRolloutAgentTimestamp OBJECT-TYPE
    SYNTAX     OCTET STRING (SIZE(0..20))
    MAX-ACCESS read-only
    STATUS     current
    DESCRIPTION
        ""
    ::= { lcosLXStatusRolloutAgent 5 }

-- {SCALAR} 13.1.91.6
lcosLXStatusRolloutAgentLastStatus OBJECT-TYPE
    SYNTAX     OCTET STRING (SIZE(0..20))
    MAX-ACCESS read-only
    STATUS     current
    DESCRIPTION
        ""
    ::= { lcosLXStatusRolloutAgent 6 }

-- {OID} 13.1.98
lcosLXStatusLMC OBJECT IDENTIFIER ::= { lcosLXStatus 98 }

-- {TABLE} 13.1.98.1
lcosLXStatusLMCTransportStatus OBJECT-TYPE
    SYNTAX     SEQUENCE OF LcosLXStatusLMCTransportStatusEntry
    MAX-ACCESS not-accessible
    STATUS     current
    DESCRIPTION
        ""
    ::= { lcosLXStatusLMC 1 }

-- {INDEX} 13.1.98.1
lcosLXStatusLMCTransportStatusEntry OBJECT-TYPE
    SYNTAX     LcosLXStatusLMCTransportStatusEntry
    MAX-ACCESS not-accessible
    STATUS     current
    DESCRIPTION
        ""
    INDEX {
        lcosLXStatusLMCTransportStatusEntryServiceName
    }
    ::= { lcosLXStatusLMCTransportStatus 1 }

-- {SEQUENCE} 13.1.98.1
LcosLXStatusLMCTransportStatusEntry ::= SEQUENCE {
    lcosLXStatusLMCTransportStatusEntryServiceName OCTET STRING,
    lcosLXStatusLMCTransportStatusEntryHTTPRequests Counter64,
    lcosLXStatusLMCTransportStatusEntryHTTPRequestErrors Counter64,
    lcosLXStatusLMCTransportStatusEntryTxBytes Counter64,
    lcosLXStatusLMCTransportStatusEntryRxBytes Counter64
}

-- {COLUMN} 13.1.98.1.1.1
lcosLXStatusLMCTransportStatusEntryServiceName OBJECT-TYPE
    SYNTAX     OCTET STRING (SIZE(0..16))
    MAX-ACCESS not-accessible
    STATUS     current
    DESCRIPTION
        ""
    ::= { lcosLXStatusLMCTransportStatusEntry 1 }

-- {COLUMN} 13.1.98.1.1.2
lcosLXStatusLMCTransportStatusEntryHTTPRequests OBJECT-TYPE
    SYNTAX     Counter64
    MAX-ACCESS read-only
    STATUS     current
    DESCRIPTION
        ""
    ::= { lcosLXStatusLMCTransportStatusEntry 2 }

-- {COLUMN} 13.1.98.1.1.3
lcosLXStatusLMCTransportStatusEntryHTTPRequestErrors OBJECT-TYPE
    SYNTAX     Counter64
    MAX-ACCESS read-only
    STATUS     current
    DESCRIPTION
        ""
    ::= { lcosLXStatusLMCTransportStatusEntry 3 }

-- {COLUMN} 13.1.98.1.1.4
lcosLXStatusLMCTransportStatusEntryTxBytes OBJECT-TYPE
    SYNTAX     Counter64
    MAX-ACCESS read-only
    STATUS     current
    DESCRIPTION
        ""
    ::= { lcosLXStatusLMCTransportStatusEntry 4 }

-- {COLUMN} 13.1.98.1.1.6
lcosLXStatusLMCTransportStatusEntryRxBytes OBJECT-TYPE
    SYNTAX     Counter64
    MAX-ACCESS read-only
    STATUS     current
    DESCRIPTION
        ""
    ::= { lcosLXStatusLMCTransportStatusEntry 6 }

-- {SCALAR} 13.1.98.5
lcosLXStatusLMCCustomerDeviceID OBJECT-TYPE
    SYNTAX     OCTET STRING (SIZE(0..100))
    MAX-ACCESS read-only
    STATUS     current
    DESCRIPTION
        ""
    ::= { lcosLXStatusLMC 5 }

-- {SCALAR} 13.1.98.6
lcosLXStatusLMCRoundTripTime OBJECT-TYPE
    SYNTAX     Unsigned32 (0..4294967295)
    MAX-ACCESS read-only
    STATUS     current
    DESCRIPTION
        ""
    ::= { lcosLXStatusLMC 6 }

-- {SCALAR} 13.1.98.7
lcosLXStatusLMCManagementStatus OBJECT-TYPE
    SYNTAX     INTEGER {
                  eNotAuthenticatedwithLMCnoCloudManagement(0),
                  eAuthenticatedwithLMCCloudManagementinactive(1),
                  eDisabled(2),
                  eDisabledByWLC(3),
                  eOperating(4),
                  eHTTPProtocolError(5),
                  eHTTPConnectionError(6),
                  eDNSError(7),
                  eMemoryError(8),
                  eWaitingNotYet(9),
                  eRedirect(10),
                  eAuthenticationError(11),
                  eGenericError(12),
                  eCertificateStorageFailed(13),
                  eAuthenticatedwithLMCCloudManagementactive(14),
                  eCertificateGenerationAborted(15),
                  eNoActivationCode(16)
               }
    MAX-ACCESS read-only
    STATUS     current
    DESCRIPTION
        ""
    ::= { lcosLXStatusLMC 7 }

-- {SCALAR} 13.1.98.9
lcosLXStatusLMCControlStatus OBJECT-TYPE
    SYNTAX     INTEGER {
                  eNotAuthenticatedwithLMCnoCloudManagement(0),
                  eAuthenticatedwithLMCCloudManagementinactive(1),
                  eDisabled(2),
                  eDisabledByWLC(3),
                  eOperating(4),
                  eHTTPProtocolError(5),
                  eHTTPConnectionError(6),
                  eDNSError(7),
                  eMemoryError(8),
                  eWaitingNotYet(9),
                  eRedirect(10),
                  eAuthenticationError(11),
                  eGenericError(12),
                  eCertificateStorageFailed(13),
                  eAuthenticatedwithLMCCloudManagementactive(14),
                  eCertificateGenerationAborted(15),
                  eNoActivationCode(16)
               }
    MAX-ACCESS read-only
    STATUS     current
    DESCRIPTION
        ""
    ::= { lcosLXStatusLMC 9 }

-- {SCALAR} 13.1.98.10
lcosLXStatusLMCMonitorStatus OBJECT-TYPE
    SYNTAX     INTEGER {
                  eNotAuthenticatedwithLMCnoCloudManagement(0),
                  eAuthenticatedwithLMCCloudManagementinactive(1),
                  eDisabled(2),
                  eDisabledByWLC(3),
                  eOperating(4),
                  eHTTPProtocolError(5),
                  eHTTPConnectionError(6),
                  eDNSError(7),
                  eMemoryError(8),
                  eWaitingNotYet(9),
                  eRedirect(10),
                  eAuthenticationError(11),
                  eGenericError(12),
                  eCertificateStorageFailed(13),
                  eAuthenticatedwithLMCCloudManagementactive(14),
                  eCertificateGenerationAborted(15),
                  eNoActivationCode(16)
               }
    MAX-ACCESS read-only
    STATUS     current
    DESCRIPTION
        ""
    ::= { lcosLXStatusLMC 10 }

-- {SCALAR} 13.1.98.12
lcosLXStatusLMCZeroTouchSupport OBJECT-TYPE
    SYNTAX     INTEGER {
                  eNo(0),
                  eYes(1)
               }
    MAX-ACCESS read-only
    STATUS     current
    DESCRIPTION
        ""
    ::= { lcosLXStatusLMC 12 }

-- {SCALAR} 13.1.98.13
lcosLXStatusLMCPairingTokenPresent OBJECT-TYPE
    SYNTAX     INTEGER {
                  eNo(0),
                  eYes(1)
               }
    MAX-ACCESS read-only
    STATUS     current
    DESCRIPTION
        ""
    ::= { lcosLXStatusLMC 13 }

-- {SCALAR} 13.1.98.15
lcosLXStatusLMCConfigModified OBJECT-TYPE
    SYNTAX     INTEGER {
                  eNo(0),
                  eYes(1)
               }
    MAX-ACCESS read-only
    STATUS     current
    DESCRIPTION
        ""
    ::= { lcosLXStatusLMC 15 }

-- {SCALAR} 13.1.98.16
lcosLXStatusLMCLMCDomain OBJECT-TYPE
    SYNTAX     OCTET STRING (SIZE(0..254))
    MAX-ACCESS read-only
    STATUS     current
    DESCRIPTION
        ""
    ::= { lcosLXStatusLMC 16 }

-- {OID} 13.1.99
lcosLXStatusLBS OBJECT IDENTIFIER ::= { lcosLXStatus 99 }

-- {TABLE} 13.1.99.4
lcosLXStatusLBSBLEScanResults OBJECT-TYPE
    SYNTAX     SEQUENCE OF LcosLXStatusLBSBLEScanResultsEntry
    MAX-ACCESS not-accessible
    STATUS     current
    DESCRIPTION
        ""
    ::= { lcosLXStatusLBS 4 }

-- {INDEX} 13.1.99.4
lcosLXStatusLBSBLEScanResultsEntry OBJECT-TYPE
    SYNTAX     LcosLXStatusLBSBLEScanResultsEntry
    MAX-ACCESS not-accessible
    STATUS     current
    DESCRIPTION
        ""
    INDEX {
        lcosLXStatusLBSBLEScanResultsEntryDeviceAddress
    }
    ::= { lcosLXStatusLBSBLEScanResults 1 }

-- {SEQUENCE} 13.1.99.4
LcosLXStatusLBSBLEScanResultsEntry ::= SEQUENCE {
    lcosLXStatusLBSBLEScanResultsEntryDeviceAddress OCTET STRING,
    lcosLXStatusLBSBLEScanResultsEntryAddressType OCTET STRING,
    lcosLXStatusLBSBLEScanResultsEntryRSSI Integer32,
    lcosLXStatusLBSBLEScanResultsEntryLastSeen OCTET STRING,
    lcosLXStatusLBSBLEScanResultsEntryAdvertisingData OCTET STRING,
    lcosLXStatusLBSBLEScanResultsEntryScanResponseData OCTET STRING,
    lcosLXStatusLBSBLEScanResultsEntryManufacturer OCTET STRING,
    lcosLXStatusLBSBLEScanResultsEntryLocalNameType INTEGER,
    lcosLXStatusLBSBLEScanResultsEntryASCIILocalName OCTET STRING
}

-- {COLUMN} 13.1.99.4.1.1
lcosLXStatusLBSBLEScanResultsEntryDeviceAddress OBJECT-TYPE
    SYNTAX     OCTET STRING (SIZE(0..20))
    MAX-ACCESS not-accessible
    STATUS     current
    DESCRIPTION
        ""
    ::= { lcosLXStatusLBSBLEScanResultsEntry 1 }

-- {COLUMN} 13.1.99.4.1.2
lcosLXStatusLBSBLEScanResultsEntryAddressType OBJECT-TYPE
    SYNTAX     OCTET STRING (SIZE(0..10))
    MAX-ACCESS read-only
    STATUS     current
    DESCRIPTION
        ""
    ::= { lcosLXStatusLBSBLEScanResultsEntry 2 }

-- {COLUMN} 13.1.99.4.1.3
lcosLXStatusLBSBLEScanResultsEntryRSSI OBJECT-TYPE
    SYNTAX     Integer32 (-128..127)
    MAX-ACCESS read-only
    STATUS     current
    DESCRIPTION
        ""
    ::= { lcosLXStatusLBSBLEScanResultsEntry 3 }

-- {COLUMN} 13.1.99.4.1.4
lcosLXStatusLBSBLEScanResultsEntryLastSeen OBJECT-TYPE
    SYNTAX     OCTET STRING (SIZE(0..32))
    MAX-ACCESS read-only
    STATUS     current
    DESCRIPTION
        ""
    ::= { lcosLXStatusLBSBLEScanResultsEntry 4 }

-- {COLUMN} 13.1.99.4.1.5
lcosLXStatusLBSBLEScanResultsEntryAdvertisingData OBJECT-TYPE
    SYNTAX     OCTET STRING (SIZE(0..64))
    MAX-ACCESS read-only
    STATUS     current
    DESCRIPTION
        ""
    ::= { lcosLXStatusLBSBLEScanResultsEntry 5 }

-- {COLUMN} 13.1.99.4.1.6
lcosLXStatusLBSBLEScanResultsEntryScanResponseData OBJECT-TYPE
    SYNTAX     OCTET STRING (SIZE(0..64))
    MAX-ACCESS read-only
    STATUS     current
    DESCRIPTION
        ""
    ::= { lcosLXStatusLBSBLEScanResultsEntry 6 }

-- {COLUMN} 13.1.99.4.1.7
lcosLXStatusLBSBLEScanResultsEntryManufacturer OBJECT-TYPE
    SYNTAX     OCTET STRING (SIZE(0..30))
    MAX-ACCESS read-only
    STATUS     current
    DESCRIPTION
        ""
    ::= { lcosLXStatusLBSBLEScanResultsEntry 7 }

-- {COLUMN} 13.1.99.4.1.8
lcosLXStatusLBSBLEScanResultsEntryLocalNameType OBJECT-TYPE
    SYNTAX     INTEGER {
                  eNone(0),
                  eShortened(1),
                  eComplete(2)
               }
    MAX-ACCESS read-only
    STATUS     current
    DESCRIPTION
        ""
    ::= { lcosLXStatusLBSBLEScanResultsEntry 8 }

-- {COLUMN} 13.1.99.4.1.9
lcosLXStatusLBSBLEScanResultsEntryASCIILocalName OBJECT-TYPE
    SYNTAX     OCTET STRING (SIZE(0..30))
    MAX-ACCESS read-only
    STATUS     current
    DESCRIPTION
        ""
    ::= { lcosLXStatusLBSBLEScanResultsEntry 9 }

-- {SCALAR} 13.1.99.5
lcosLXStatusLBSCACertinfo OBJECT-TYPE
    SYNTAX     OCTET STRING (SIZE(0..255))
    MAX-ACCESS read-only
    STATUS     current
    DESCRIPTION
        ""
    ::= { lcosLXStatusLBS 5 }

-- {OID} 13.1.100
lcosLXStatusSniffer OBJECT IDENTIFIER ::= { lcosLXStatus 100 }

-- {TABLE} 13.1.100.1
lcosLXStatusSnifferProtocols OBJECT-TYPE
    SYNTAX     SEQUENCE OF LcosLXStatusSnifferProtocolsEntry
    MAX-ACCESS not-accessible
    STATUS     current
    DESCRIPTION
        ""
    ::= { lcosLXStatusSniffer 1 }

-- {INDEX} 13.1.100.1
lcosLXStatusSnifferProtocolsEntry OBJECT-TYPE
    SYNTAX     LcosLXStatusSnifferProtocolsEntry
    MAX-ACCESS not-accessible
    STATUS     current
    DESCRIPTION
        ""
    INDEX {
        lcosLXStatusSnifferProtocolsEntryProtocol,
        lcosLXStatusSnifferProtocolsEntrySender
    }
    ::= { lcosLXStatusSnifferProtocols 1 }

-- {SEQUENCE} 13.1.100.1
LcosLXStatusSnifferProtocolsEntry ::= SEQUENCE {
    lcosLXStatusSnifferProtocolsEntryProtocol INTEGER,
    lcosLXStatusSnifferProtocolsEntrySender OCTET STRING,
    lcosLXStatusSnifferProtocolsEntryTotal Counter64,
    lcosLXStatusSnifferProtocolsEntryCountperMinute Unsigned32,
    lcosLXStatusSnifferProtocolsEntryLastSeen OCTET STRING
}

-- {COLUMN} 13.1.100.1.1.1
lcosLXStatusSnifferProtocolsEntryProtocol OBJECT-TYPE
    SYNTAX     INTEGER {
                  eARP(1),
                  eICMP(2),
                  eICMPv6(3)
               }
    MAX-ACCESS not-accessible
    STATUS     current
    DESCRIPTION
        ""
    ::= { lcosLXStatusSnifferProtocolsEntry 1 }

-- {COLUMN} 13.1.100.1.1.2
lcosLXStatusSnifferProtocolsEntrySender OBJECT-TYPE
    SYNTAX     OCTET STRING (SIZE(0..64))
    MAX-ACCESS not-accessible
    STATUS     current
    DESCRIPTION
        ""
    ::= { lcosLXStatusSnifferProtocolsEntry 2 }

-- {COLUMN} 13.1.100.1.1.3
lcosLXStatusSnifferProtocolsEntryTotal OBJECT-TYPE
    SYNTAX     Counter64
    MAX-ACCESS read-only
    STATUS     current
    DESCRIPTION
        ""
    ::= { lcosLXStatusSnifferProtocolsEntry 3 }

-- {COLUMN} 13.1.100.1.1.4
lcosLXStatusSnifferProtocolsEntryCountperMinute OBJECT-TYPE
    SYNTAX     Unsigned32 (0..4294967295)
    MAX-ACCESS read-only
    STATUS     current
    DESCRIPTION
        ""
    ::= { lcosLXStatusSnifferProtocolsEntry 4 }

-- {COLUMN} 13.1.100.1.1.5
lcosLXStatusSnifferProtocolsEntryLastSeen OBJECT-TYPE
    SYNTAX     OCTET STRING (SIZE(0..32))
    MAX-ACCESS read-only
    STATUS     current
    DESCRIPTION
        ""
    ::= { lcosLXStatusSnifferProtocolsEntry 5 }

-- {OID} 13.1.107
lcosLXStatusAutomaticFirmwareUpdate OBJECT IDENTIFIER ::= { lcosLXStatus 107 }

-- {SCALAR} 13.1.107.1
lcosLXStatusAutomaticFirmwareUpdateMode OBJECT-TYPE
    SYNTAX     INTEGER {
                  emanual(0),
                  echeck(1),
                  echeckandupdate(2)
               }
    MAX-ACCESS read-only
    STATUS     current
    DESCRIPTION
        ""
    ::= { lcosLXStatusAutomaticFirmwareUpdate 1 }

-- {SCALAR} 13.1.107.2
lcosLXStatusAutomaticFirmwareUpdateLastCheck OBJECT-TYPE
    SYNTAX     OCTET STRING (SIZE(0..36))
    MAX-ACCESS read-only
    STATUS     current
    DESCRIPTION
        ""
    ::= { lcosLXStatusAutomaticFirmwareUpdate 2 }

-- {SCALAR} 13.1.107.3
lcosLXStatusAutomaticFirmwareUpdateNextCheck OBJECT-TYPE
    SYNTAX     OCTET STRING (SIZE(0..36))
    MAX-ACCESS read-only
    STATUS     current
    DESCRIPTION
        ""
    ::= { lcosLXStatusAutomaticFirmwareUpdate 3 }

-- {SCALAR} 13.1.107.4
lcosLXStatusAutomaticFirmwareUpdateUpdateCandidate OBJECT-TYPE
    SYNTAX     OCTET STRING (SIZE(0..36))
    MAX-ACCESS read-only
    STATUS     current
    DESCRIPTION
        ""
    ::= { lcosLXStatusAutomaticFirmwareUpdate 4 }

-- {SCALAR} 13.1.107.5
lcosLXStatusAutomaticFirmwareUpdateState OBJECT-TYPE
    SYNTAX     INTEGER {
                  eclosed(0),
                  eclosing(1),
                  ecancel(2),
                  eidle(3),
                  einitializing(4),
                  eworking(5),
                  etesting(6),
                  erequesting(7),
                  econtactingupdateserver(8),
                  eprocessingresponse(9),
                  edownloading(10),
                  everifyingdownload(11),
                  einstalling(12),
                  ereboot(13),
                  econtinueinstallation(14),
                  eprepareverifyinginstallation(15),
                  everifyinginstallation(16),
                  eresetting(17),
                  ewaiting(18),
                  ewaitingforinstallation(19)
               }
    MAX-ACCESS read-only
    STATUS     current
    DESCRIPTION
        ""
    ::= { lcosLXStatusAutomaticFirmwareUpdate 5 }

-- {SCALAR} 13.1.107.6
lcosLXStatusAutomaticFirmwareUpdateCurrentAction OBJECT-TYPE
    SYNTAX     INTEGER {
                  enone(0),
                  estartup(1),
                  eautomaticupdatecheck(2),
                  emanualupdatecheck(3),
                  eautomaticupdate(4),
                  emanualupdate(5),
                  ereset(6)
               }
    MAX-ACCESS read-only
    STATUS     current
    DESCRIPTION
        ""
    ::= { lcosLXStatusAutomaticFirmwareUpdate 6 }

-- {SCALAR} 13.1.107.7
lcosLXStatusAutomaticFirmwareUpdateLastResult OBJECT-TYPE
    SYNTAX     INTEGER {
                  eOK(0),
                  eunknownerroroccured(30),
                  eactioncancelledbyuser(31),
                  efailedtoloadupdateserverresponse(32),
                  einvalidupdateserverresponse(33),
                  eupdateservererror(34),
                  einternallogicerror(35),
                  einternalmissingdataerror(36),
                  einternalprocessingerror(37),
                  eupdatefilechecksuminvalid(38),
                  eupdateinstallationfailed(39),
                  esystemrebootedunexpectedly(40),
                  ewrongactionhasbeendetectedwithingivencontext(41),
                  ewrongstatehasbeendetectedwithingivencontext(42),
                  eupdateserverofferedblacklistedfirmware(43),
                  efirmwareverificationfailedretrying(44),
                  efirmwareverificationfailed(45),
                  efirmwareinstallationfailed(46),
                  erepeatedupdatesearchhasfailed(47),
                  eupdateserverunavailable(48),
                  eupdateserverbusyrepeating(49),
                  eupdateserverrepeatedlybusy(50),
                  eupdateserverbusyretrylater(51),
                  eactioncancelledoutoftimerange(52),
                  eactioncancelledbyupdateinstallation(53),
                  eactioncancelledbyrequest(54),
                  efailedtoqueueaction(55),
                  efirmwarefallback(56),
                  eactioncancelledbyconfigchange(57),
                  eactioncancelledbyshutdown(58),
                  eunknowndownloaderroroccured(300),
                  eserverurlinvalid(301),
                  edownloadfailedinvalidtarget(302),
                  efailedtocreatedownloadtask(303),
                  efailedtorequestdownload(304),
                  efailedtowritedownloadtofile(305),
                  efailedtoopendownloadfile(306),
                  edownloadcancelled(307),
                  edownloadtimeout(308),
                  efailedtoconnecttotheserver(309),
                  edownloadprotocolerror(310),
                  ednserror(311),
                  eoutofmemory(312),
                  etoomanyconnections(313),
                  etruststorenotavailable(314),
                  esecureconnectionfailed(315),
                  efailedtoattachdownloadeventhandles(316),
                  efailedtoreaddownloadstream(317),
                  eupdateserveremptyerror(401),
                  eserverresponsemismatchesinitialrequest(402),
                  eserverresponseidmismatch(403),
                  eserverresponseheaderincomplete(404),
                  eserverresponsehasinvalidstructure(405),
                  eserverresponseinvalid(406),
                  eserverresponsebodyincomplete(407),
                  einternalparametererror(408),
                  eunsupportedfirmwaretypeprovided(409),
                  ewritingmainconfigurationhasfailed(501),
                  einvalidmainconfiguration(502),
                  emodifyingmainconfigurationfailed(503),
                  emodifyingblacklistfailed(504)
               }
    MAX-ACCESS read-only
    STATUS     current
    DESCRIPTION
        ""
    ::= { lcosLXStatusAutomaticFirmwareUpdate 7 }

-- {SCALAR} 13.1.107.8
lcosLXStatusAutomaticFirmwareUpdatePlannedInstallation OBJECT-TYPE
    SYNTAX     OCTET STRING (SIZE(0..36))
    MAX-ACCESS read-only
    STATUS     current
    DESCRIPTION
        ""
    ::= { lcosLXStatusAutomaticFirmwareUpdate 8 }

-- {SCALAR} 13.1.107.12
lcosLXStatusAutomaticFirmwareUpdateCurrentVersion OBJECT-TYPE
    SYNTAX     OCTET STRING (SIZE(0..36))
    MAX-ACCESS read-only
    STATUS     current
    DESCRIPTION
        ""
    ::= { lcosLXStatusAutomaticFirmwareUpdate 12 }

-- {SCALAR} 13.1.107.102
lcosLXStatusAutomaticFirmwareUpdateLastCheckEpoch OBJECT-TYPE
    SYNTAX     Unsigned32 (0..4294967295)
    MAX-ACCESS read-only
    STATUS     current
    DESCRIPTION
        ""
    ::= { lcosLXStatusAutomaticFirmwareUpdate 102 }

-- {SCALAR} 13.1.107.103
lcosLXStatusAutomaticFirmwareUpdateNextCheckEpoch OBJECT-TYPE
    SYNTAX     Unsigned32 (0..4294967295)
    MAX-ACCESS read-only
    STATUS     current
    DESCRIPTION
        ""
    ::= { lcosLXStatusAutomaticFirmwareUpdate 103 }

-- {SCALAR} 13.1.107.108
lcosLXStatusAutomaticFirmwareUpdatePlannedInstallationEpoch OBJECT-TYPE
    SYNTAX     Unsigned32 (0..4294967295)
    MAX-ACCESS read-only
    STATUS     current
    DESCRIPTION
        ""
    ::= { lcosLXStatusAutomaticFirmwareUpdate 108 }

-- {OID} 13.1.111
lcosLXStatusIoT OBJECT IDENTIFIER ::= { lcosLXStatus 111 }

-- {OID} 13.1.111.88
lcosLXStatusIoTWirelessePaper OBJECT IDENTIFIER ::= { lcosLXStatusIoT 88 }

-- {SCALAR} 13.1.111.88.1
lcosLXStatusIoTWirelessePaperServerCAInfo OBJECT-TYPE
    SYNTAX     OCTET STRING (SIZE(0..255))
    MAX-ACCESS read-only
    STATUS     current
    DESCRIPTION
        ""
    ::= { lcosLXStatusIoTWirelessePaper 1 }

-- {SCALAR} 13.1.111.88.2
lcosLXStatusIoTWirelessePaperAccessPointID OBJECT-TYPE
    SYNTAX     Unsigned32 (0..4294967295)
    MAX-ACCESS read-only
    STATUS     current
    DESCRIPTION
        ""
    ::= { lcosLXStatusIoTWirelessePaper 2 }

-- {SCALAR} 13.1.111.88.3
lcosLXStatusIoTWirelessePaperConnectedServer OBJECT-TYPE
    SYNTAX     OCTET STRING (SIZE(0..64))
    MAX-ACCESS read-only
    STATUS     current
    DESCRIPTION
        ""
    ::= { lcosLXStatusIoTWirelessePaper 3 }

-- {SCALAR} 13.1.111.88.4
lcosLXStatusIoTWirelessePaperCurrentChannel OBJECT-TYPE
    SYNTAX     INTEGER {
                  e2404MHz(0),
                  e2410MHz(1),
                  e2422MHz(2),
                  e2425MHz(3),
                  e2442MHz(4),
                  e2450MHz(5),
                  e2462MHz(6),
                  e2470MHz(7),
                  e2474MHz(8),
                  e2477MHz(9),
                  e2480MHz(10),
                  eNone(255)
               }
    MAX-ACCESS read-only
    STATUS     current
    DESCRIPTION
        ""
    ::= { lcosLXStatusIoTWirelessePaper 4 }

-- {SCALAR} 13.1.111.88.5
lcosLXStatusIoTWirelessePaperFirmwareVersion OBJECT-TYPE
    SYNTAX     OCTET STRING (SIZE(0..64))
    MAX-ACCESS read-only
    STATUS     current
    DESCRIPTION
        ""
    ::= { lcosLXStatusIoTWirelessePaper 5 }

-- {SCALAR} 13.1.111.88.6
lcosLXStatusIoTWirelessePaperClaimID OBJECT-TYPE
    SYNTAX     OCTET STRING (SIZE(0..16))
    MAX-ACCESS read-only
    STATUS     current
    DESCRIPTION
        ""
    ::= { lcosLXStatusIoTWirelessePaper 6 }

-- {OID} 13.2
lcosLXSetup OBJECT IDENTIFIER ::= { lcosLX 2 }

-- {SCALAR} 13.2.1
lcosLXSetupName OBJECT-TYPE
    SYNTAX     OCTET STRING (SIZE(0..64))
    MAX-ACCESS read-only
    STATUS     current
    DESCRIPTION
        ""
    ::= { lcosLXSetup 1 }

-- {OID} 13.2.11
lcosLXSetupConfig OBJECT IDENTIFIER ::= { lcosLXSetup 11 }

-- {SCALAR} 13.2.11.1
lcosLXSetupConfigComment1 OBJECT-TYPE
    SYNTAX     OCTET STRING (SIZE(0..255))
    MAX-ACCESS read-only
    STATUS     current
    DESCRIPTION
        ""
    ::= { lcosLXSetupConfig 1 }

-- {SCALAR} 13.2.11.2
lcosLXSetupConfigComment2 OBJECT-TYPE
    SYNTAX     OCTET STRING (SIZE(0..255))
    MAX-ACCESS read-only
    STATUS     current
    DESCRIPTION
        ""
    ::= { lcosLXSetupConfig 2 }

-- {SCALAR} 13.2.11.3
lcosLXSetupConfigComment3 OBJECT-TYPE
    SYNTAX     OCTET STRING (SIZE(0..255))
    MAX-ACCESS read-only
    STATUS     current
    DESCRIPTION
        ""
    ::= { lcosLXSetupConfig 3 }

-- {SCALAR} 13.2.11.4
lcosLXSetupConfigComment4 OBJECT-TYPE
    SYNTAX     OCTET STRING (SIZE(0..255))
    MAX-ACCESS read-only
    STATUS     current
    DESCRIPTION
        ""
    ::= { lcosLXSetupConfig 4 }

-- {SCALAR} 13.2.11.5
lcosLXSetupConfigComment5 OBJECT-TYPE
    SYNTAX     OCTET STRING (SIZE(0..255))
    MAX-ACCESS read-only
    STATUS     current
    DESCRIPTION
        ""
    ::= { lcosLXSetupConfig 5 }

-- {SCALAR} 13.2.11.6
lcosLXSetupConfigComment6 OBJECT-TYPE
    SYNTAX     OCTET STRING (SIZE(0..255))
    MAX-ACCESS read-only
    STATUS     current
    DESCRIPTION
        ""
    ::= { lcosLXSetupConfig 6 }

-- {SCALAR} 13.2.11.7
lcosLXSetupConfigComment7 OBJECT-TYPE
    SYNTAX     OCTET STRING (SIZE(0..255))
    MAX-ACCESS read-only
    STATUS     current
    DESCRIPTION
        ""
    ::= { lcosLXSetupConfig 7 }

-- {SCALAR} 13.2.11.8
lcosLXSetupConfigComment8 OBJECT-TYPE
    SYNTAX     OCTET STRING (SIZE(0..255))
    MAX-ACCESS read-only
    STATUS     current
    DESCRIPTION
        ""
    ::= { lcosLXSetupConfig 8 }

-- {SCALAR} 13.2.11.9
lcosLXSetupConfigLocation OBJECT-TYPE
    SYNTAX     OCTET STRING (SIZE(0..255))
    MAX-ACCESS read-only
    STATUS     current
    DESCRIPTION
        ""
    ::= { lcosLXSetupConfig 9 }

-- {SCALAR} 13.2.11.10
lcosLXSetupConfigAdministrator OBJECT-TYPE
    SYNTAX     OCTET STRING (SIZE(0..255))
    MAX-ACCESS read-only
    STATUS     current
    DESCRIPTION
        ""
    ::= { lcosLXSetupConfig 10 }

-- {SCALAR} 13.2.11.11
lcosLXSetupConfigConfigAgingMinutes OBJECT-TYPE
    SYNTAX     Unsigned32 (0..65535)
    MAX-ACCESS read-only
    STATUS     current
    DESCRIPTION
        ""
    ::= { lcosLXSetupConfig 11 }

-- {SCALAR} 13.2.11.12
lcosLXSetupConfigIAPPAnnouncementInterval OBJECT-TYPE
    SYNTAX     Unsigned32 (0..65535)
    MAX-ACCESS read-only
    STATUS     current
    DESCRIPTION
        ""
    ::= { lcosLXSetupConfig 12 }

-- {TABLE} 13.2.11.13
lcosLXSetupConfigServices OBJECT-TYPE
    SYNTAX     SEQUENCE OF LcosLXSetupConfigServicesEntry
    MAX-ACCESS not-accessible
    STATUS     current
    DESCRIPTION
        ""
    ::= { lcosLXSetupConfig 13 }

-- {INDEX} 13.2.11.13
lcosLXSetupConfigServicesEntry OBJECT-TYPE
    SYNTAX     LcosLXSetupConfigServicesEntry
    MAX-ACCESS not-accessible
    STATUS     current
    DESCRIPTION
        ""
    INDEX {
        lcosLXSetupConfigServicesEntryName
    }
    ::= { lcosLXSetupConfigServices 1 }

-- {SEQUENCE} 13.2.11.13
LcosLXSetupConfigServicesEntry ::= SEQUENCE {
    lcosLXSetupConfigServicesEntryName INTEGER,
    lcosLXSetupConfigServicesEntryOperating INTEGER
}

-- {COLUMN} 13.2.11.13.1.1
lcosLXSetupConfigServicesEntryName OBJECT-TYPE
    SYNTAX     INTEGER {
                  eHTTPS(0),
                  eSSH(1)
               }
    MAX-ACCESS not-accessible
    STATUS     current
    DESCRIPTION
        ""
    ::= { lcosLXSetupConfigServicesEntry 1 }

-- {COLUMN} 13.2.11.13.1.2
lcosLXSetupConfigServicesEntryOperating OBJECT-TYPE
    SYNTAX     INTEGER {
                  eNo(0),
                  eYes(1)
               }
    MAX-ACCESS read-only
    STATUS     current
    DESCRIPTION
        ""
    ::= { lcosLXSetupConfigServicesEntry 2 }

-- {SCALAR} 13.2.11.18
lcosLXSetupConfigLEDMode OBJECT-TYPE
    SYNTAX     INTEGER {
                  eOn(0),
                  eOff(1),
                  eTimedOff(2)
               }
    MAX-ACCESS read-only
    STATUS     current
    DESCRIPTION
        ""
    ::= { lcosLXSetupConfig 18 }

-- {TABLE} 13.2.11.21
lcosLXSetupConfigAdmins OBJECT-TYPE
    SYNTAX     SEQUENCE OF LcosLXSetupConfigAdminsEntry
    MAX-ACCESS not-accessible
    STATUS     current
    DESCRIPTION
        ""
    ::= { lcosLXSetupConfig 21 }

-- {INDEX} 13.2.11.21
lcosLXSetupConfigAdminsEntry OBJECT-TYPE
    SYNTAX     LcosLXSetupConfigAdminsEntry
    MAX-ACCESS not-accessible
    STATUS     current
    DESCRIPTION
        ""
    INDEX {
        lcosLXSetupConfigAdminsEntryAdministrator
    }
    ::= { lcosLXSetupConfigAdmins 1 }

-- {SEQUENCE} 13.2.11.21
LcosLXSetupConfigAdminsEntry ::= SEQUENCE {
    lcosLXSetupConfigAdminsEntryAdministrator OCTET STRING,
    lcosLXSetupConfigAdminsEntryFunctionRights BITS,
    lcosLXSetupConfigAdminsEntryRights INTEGER,
    lcosLXSetupConfigAdminsEntryHashedPassword OCTET STRING
}

-- {COLUMN} 13.2.11.21.1.1
lcosLXSetupConfigAdminsEntryAdministrator OBJECT-TYPE
    SYNTAX     OCTET STRING (SIZE(0..16))
    MAX-ACCESS not-accessible
    STATUS     current
    DESCRIPTION
        ""
    ::= { lcosLXSetupConfigAdminsEntry 1 }

-- {COLUMN} 13.2.11.21.1.3
lcosLXSetupConfigAdminsEntryFunctionRights OBJECT-TYPE
    SYNTAX     BITS {
                  eBasic(0),
                  eAdminManagement(31)
               }
    MAX-ACCESS read-only
    STATUS     current
    DESCRIPTION
        ""
    ::= { lcosLXSetupConfigAdminsEntry 3 }

-- {COLUMN} 13.2.11.21.1.5
lcosLXSetupConfigAdminsEntryRights OBJECT-TYPE
    SYNTAX     INTEGER {
                  eNone(0),
                  eAdminROLimit(1),
                  eAdminRWLimit(2),
                  eAdminRO(3),
                  eAdminRW(4),
                  eSupervisor(5)
               }
    MAX-ACCESS read-only
    STATUS     current
    DESCRIPTION
        ""
    ::= { lcosLXSetupConfigAdminsEntry 5 }

-- {COLUMN} 13.2.11.21.1.6
lcosLXSetupConfigAdminsEntryHashedPassword OBJECT-TYPE
    SYNTAX     OCTET STRING (SIZE(0..255))
    MAX-ACCESS read-only
    STATUS     current
    DESCRIPTION
        ""
    ::= { lcosLXSetupConfigAdminsEntry 6 }

-- {OID} 13.2.11.50
lcosLXSetupConfigLL2M OBJECT IDENTIFIER ::= { lcosLXSetupConfig 50 }

-- {SCALAR} 13.2.11.50.1
lcosLXSetupConfigLL2MOperating OBJECT-TYPE
    SYNTAX     INTEGER {
                  eNo(0),
                  eYes(1)
               }
    MAX-ACCESS read-only
    STATUS     current
    DESCRIPTION
        ""
    ::= { lcosLXSetupConfigLL2M 1 }

-- {TABLE} 13.2.11.50.2
lcosLXSetupConfigLL2MInterfaces OBJECT-TYPE
    SYNTAX     SEQUENCE OF LcosLXSetupConfigLL2MInterfacesEntry
    MAX-ACCESS not-accessible
    STATUS     current
    DESCRIPTION
        ""
    ::= { lcosLXSetupConfigLL2M 2 }

-- {INDEX} 13.2.11.50.2
lcosLXSetupConfigLL2MInterfacesEntry OBJECT-TYPE
    SYNTAX     LcosLXSetupConfigLL2MInterfacesEntry
    MAX-ACCESS not-accessible
    STATUS     current
    DESCRIPTION
        ""
    INDEX {
        lcosLXSetupConfigLL2MInterfacesEntryPort
    }
    ::= { lcosLXSetupConfigLL2MInterfaces 1 }

-- {SEQUENCE} 13.2.11.50.2
LcosLXSetupConfigLL2MInterfacesEntry ::= SEQUENCE {
    lcosLXSetupConfigLL2MInterfacesEntryPort OCTET STRING,
    lcosLXSetupConfigLL2MInterfacesEntryActive INTEGER
}

-- {COLUMN} 13.2.11.50.2.1.1
lcosLXSetupConfigLL2MInterfacesEntryPort OBJECT-TYPE
    SYNTAX     OCTET STRING (SIZE(0..5))
    MAX-ACCESS not-accessible
    STATUS     current
    DESCRIPTION
        ""
    ::= { lcosLXSetupConfigLL2MInterfacesEntry 1 }

-- {COLUMN} 13.2.11.50.2.1.2
lcosLXSetupConfigLL2MInterfacesEntryActive OBJECT-TYPE
    SYNTAX     INTEGER {
                  eNo(0),
                  eYes(1)
               }
    MAX-ACCESS read-only
    STATUS     current
    DESCRIPTION
        ""
    ::= { lcosLXSetupConfigLL2MInterfacesEntry 2 }

-- {OID} 13.2.11.51
lcosLXSetupConfigTacacsPlus OBJECT IDENTIFIER ::= { lcosLXSetupConfig 51 }

-- {SCALAR} 13.2.11.51.1
lcosLXSetupConfigTacacsPlusOperating OBJECT-TYPE
    SYNTAX     INTEGER {
                  eNo(0),
                  eYes(1)
               }
    MAX-ACCESS read-only
    STATUS     current
    DESCRIPTION
        ""
    ::= { lcosLXSetupConfigTacacsPlus 1 }

-- {SCALAR} 13.2.11.51.2
lcosLXSetupConfigTacacsPlusInternalfallbackallowed OBJECT-TYPE
    SYNTAX     INTEGER {
                  eNo(0),
                  eYes(1)
               }
    MAX-ACCESS read-only
    STATUS     current
    DESCRIPTION
        ""
    ::= { lcosLXSetupConfigTacacsPlus 2 }

-- {SCALAR} 13.2.11.51.10
lcosLXSetupConfigTacacsPlusServerAddress OBJECT-TYPE
    SYNTAX     OCTET STRING (SIZE(0..64))
    MAX-ACCESS read-only
    STATUS     current
    DESCRIPTION
        ""
    ::= { lcosLXSetupConfigTacacsPlus 10 }

-- {SCALAR} 13.2.11.51.11
lcosLXSetupConfigTacacsPlusServerPort OBJECT-TYPE
    SYNTAX     Unsigned32 (0..65535)
    MAX-ACCESS read-only
    STATUS     current
    DESCRIPTION
        ""
    ::= { lcosLXSetupConfigTacacsPlus 11 }

-- {SCALAR} 13.2.11.51.12
lcosLXSetupConfigTacacsPlusServerSecret OBJECT-TYPE
    SYNTAX     OCTET STRING (SIZE(0..64))
    MAX-ACCESS read-only
    STATUS     current
    DESCRIPTION
        ""
    ::= { lcosLXSetupConfigTacacsPlus 12 }

-- {SCALAR} 13.2.11.51.20
lcosLXSetupConfigTacacsPlusSpareServerAddress OBJECT-TYPE
    SYNTAX     OCTET STRING (SIZE(0..64))
    MAX-ACCESS read-only
    STATUS     current
    DESCRIPTION
        ""
    ::= { lcosLXSetupConfigTacacsPlus 20 }

-- {SCALAR} 13.2.11.51.21
lcosLXSetupConfigTacacsPlusSpareServerPort OBJECT-TYPE
    SYNTAX     Unsigned32 (0..65535)
    MAX-ACCESS read-only
    STATUS     current
    DESCRIPTION
        ""
    ::= { lcosLXSetupConfigTacacsPlus 21 }

-- {SCALAR} 13.2.11.51.22
lcosLXSetupConfigTacacsPlusSpareServerSecret OBJECT-TYPE
    SYNTAX     OCTET STRING (SIZE(0..64))
    MAX-ACCESS read-only
    STATUS     current
    DESCRIPTION
        ""
    ::= { lcosLXSetupConfigTacacsPlus 22 }

-- {OID} 13.2.11.52
lcosLXSetupConfigSSH OBJECT IDENTIFIER ::= { lcosLXSetupConfig 52 }

-- {SCALAR} 13.2.11.52.1
lcosLXSetupConfigSSHRSAHostkeyLength OBJECT-TYPE
    SYNTAX     INTEGER {
                  e2048Bits(2048),
                  e4096Bits(4096)
               }
    MAX-ACCESS read-only
    STATUS     current
    DESCRIPTION
        ""
    ::= { lcosLXSetupConfigSSH 1 }

-- {SCALAR} 13.2.11.52.2
lcosLXSetupConfigSSHBruteForceTimeWindow OBJECT-TYPE
    SYNTAX     Unsigned32 (0..4294967295)
    MAX-ACCESS read-only
    STATUS     current
    DESCRIPTION
        ""
    ::= { lcosLXSetupConfigSSH 2 }

-- {SCALAR} 13.2.11.52.3
lcosLXSetupConfigSSHMaxAttempts OBJECT-TYPE
    SYNTAX     Unsigned32 (0..255)
    MAX-ACCESS read-only
    STATUS     current
    DESCRIPTION
        ""
    ::= { lcosLXSetupConfigSSH 3 }

-- {SCALAR} 13.2.11.52.4
lcosLXSetupConfigSSHRateLimiting OBJECT-TYPE
    SYNTAX     INTEGER {
                  eNo(0),
                  eYes(1)
               }
    MAX-ACCESS read-only
    STATUS     current
    DESCRIPTION
        ""
    ::= { lcosLXSetupConfigSSH 4 }

-- {SCALAR} 13.2.11.90
lcosLXSetupConfigLEDOffSeconds OBJECT-TYPE
    SYNTAX     Unsigned32 (0..65535)
    MAX-ACCESS read-only
    STATUS     current
    DESCRIPTION
        ""
    ::= { lcosLXSetupConfig 90 }

-- {SCALAR} 13.2.11.91
lcosLXSetupConfigLEDTest OBJECT-TYPE
    SYNTAX     INTEGER {
                  eOff(0),
                  eRed(1),
                  eGreen(2),
                  eBlue(3),
                  eAll(4),
                  eNoTest(255)
               }
    MAX-ACCESS read-only
    STATUS     current
    DESCRIPTION
        ""
    ::= { lcosLXSetupConfig 91 }

-- {SCALAR} 13.2.11.92
lcosLXSetupConfigRolloutAgentOperating OBJECT-TYPE
    SYNTAX     INTEGER {
                  eNo(0),
                  eYes(1),
                  eOnlyunconfigured(2)
               }
    MAX-ACCESS read-only
    STATUS     current
    DESCRIPTION
        ""
    ::= { lcosLXSetupConfig 92 }

-- {OID} 13.2.14
lcosLXSetupTime OBJECT IDENTIFIER ::= { lcosLXSetup 14 }

-- {SCALAR} 13.2.14.20
lcosLXSetupTimeTimezone OBJECT-TYPE
    SYNTAX     INTEGER {
                  eUTC(0),
                  eEuropeBerlin(1),
                  eEuropeVienna(2),
                  eEuropeZurich(3),
                  eEuropeLondon(4),
                  eEuropePrague(5),
                  eEuropeWarsaw(6),
                  eEuropeZagreb(7),
                  eEuropeCopenhagen(8),
                  eEuropeParis(9),
                  eEuropeHelsinki(10),
                  eEuropeTallinn(11),
                  eEuropeAthens(12),
                  eEuropeBudapest(13),
                  eEuropeDublin(14),
                  eEuropeRome(15),
                  eEuropeRiga(16),
                  eEuropeVilnius(17),
                  eEuropeLuxembourg(18),
                  eEuropeMalta(19),
                  eEuropeAmsterdam(20),
                  eEuropeNicosia(21),
                  eEuropeLisbon(22),
                  eEuropeBucharest(23),
                  eEuropeBratislava(24),
                  eEuropeLjubljana(25),
                  eEuropeMadrid(26),
                  eEuropeStockholm(27),
                  eEuropeBrussels(28),
                  eEuropeSofia(29),
                  eUSAlaska(30),
                  eUSPacific(31),
                  eUSMountain(32),
                  eUSCentral(33),
                  eUSEastern(34),
                  ePacificAuckland(35),
                  ePacificHonolulu(36),
                  eAustraliaBrisbane(37),
                  eAustraliaSydney(38),
                  eAustraliaPerth(39),
                  eAustraliaDarwin(40),
                  eAustraliaAdelaide(41)
               }
    MAX-ACCESS read-only
    STATUS     current
    DESCRIPTION
        ""
    ::= { lcosLXSetupTime 20 }

-- {OID} 13.2.14.21
lcosLXSetupTimeNTP OBJECT IDENTIFIER ::= { lcosLXSetupTime 21 }

-- {SCALAR} 13.2.14.21.1
lcosLXSetupTimeNTPOperating OBJECT-TYPE
    SYNTAX     INTEGER {
                  eNo(0),
                  eYes(1)
               }
    MAX-ACCESS read-only
    STATUS     current
    DESCRIPTION
        ""
    ::= { lcosLXSetupTimeNTP 1 }

-- {TABLE} 13.2.14.21.3
lcosLXSetupTimeNTPServers OBJECT-TYPE
    SYNTAX     SEQUENCE OF LcosLXSetupTimeNTPServersEntry
    MAX-ACCESS not-accessible
    STATUS     current
    DESCRIPTION
        ""
    ::= { lcosLXSetupTimeNTP 3 }

-- {INDEX} 13.2.14.21.3
lcosLXSetupTimeNTPServersEntry OBJECT-TYPE
    SYNTAX     LcosLXSetupTimeNTPServersEntry
    MAX-ACCESS not-accessible
    STATUS     current
    DESCRIPTION
        ""
    INDEX {
        lcosLXSetupTimeNTPServersEntryName
    }
    ::= { lcosLXSetupTimeNTPServers 1 }

-- {SEQUENCE} 13.2.14.21.3
LcosLXSetupTimeNTPServersEntry ::= SEQUENCE {
    lcosLXSetupTimeNTPServersEntryName OCTET STRING,
    lcosLXSetupTimeNTPServersEntryActive INTEGER
}

-- {COLUMN} 13.2.14.21.3.1.1
lcosLXSetupTimeNTPServersEntryName OBJECT-TYPE
    SYNTAX     OCTET STRING (SIZE(0..64))
    MAX-ACCESS not-accessible
    STATUS     current
    DESCRIPTION
        ""
    ::= { lcosLXSetupTimeNTPServersEntry 1 }

-- {COLUMN} 13.2.14.21.3.1.2
lcosLXSetupTimeNTPServersEntryActive OBJECT-TYPE
    SYNTAX     INTEGER {
                  eNo(0),
                  eYes(1)
               }
    MAX-ACCESS read-only
    STATUS     current
    DESCRIPTION
        ""
    ::= { lcosLXSetupTimeNTPServersEntry 2 }

-- {OID} 13.2.20
lcosLXSetupWLAN OBJECT IDENTIFIER ::= { lcosLXSetup 20 }

-- {TABLE} 13.2.20.1
lcosLXSetupWLANNetwork OBJECT-TYPE
    SYNTAX     SEQUENCE OF LcosLXSetupWLANNetworkEntry
    MAX-ACCESS not-accessible
    STATUS     current
    DESCRIPTION
        ""
    ::= { lcosLXSetupWLAN 1 }

-- {INDEX} 13.2.20.1
lcosLXSetupWLANNetworkEntry OBJECT-TYPE
    SYNTAX     LcosLXSetupWLANNetworkEntry
    MAX-ACCESS not-accessible
    STATUS     current
    DESCRIPTION
        ""
    INDEX {
        lcosLXSetupWLANNetworkEntryNetworkName
    }
    ::= { lcosLXSetupWLANNetwork 1 }

-- {SEQUENCE} 13.2.20.1
LcosLXSetupWLANNetworkEntry ::= SEQUENCE {
    lcosLXSetupWLANNetworkEntryNetworkName OCTET STRING,
    lcosLXSetupWLANNetworkEntrySSIDName OCTET STRING,
    lcosLXSetupWLANNetworkEntryClosedNetwork INTEGER,
    lcosLXSetupWLANNetworkEntryMaxStations Unsigned32,
    lcosLXSetupWLANNetworkEntryInterStationTraffic INTEGER,
    lcosLXSetupWLANNetworkEntryClientIsolation INTEGER,
    lcosLXSetupWLANNetworkEntryMinClientStrength Unsigned32,
    lcosLXSetupWLANNetworkEntryExcludeFromClientManagement INTEGER,
    lcosLXSetupWLANNetworkEntryTimeframe OCTET STRING,
    lcosLXSetupWLANNetworkEntryHotspot OCTET STRING,
    lcosLXSetupWLANNetworkEntrySummaricTxLimitKbits Unsigned32,
    lcosLXSetupWLANNetworkEntrySummaricRxLimitKbits Unsigned32,
    lcosLXSetupWLANNetworkEntryBlockMulticast INTEGER,
    lcosLXSetupWLANNetworkEntryClientTxLimitKbits Unsigned32,
    lcosLXSetupWLANNetworkEntryClientRxLimitKbits Unsigned32,
    lcosLXSetupWLANNetworkEntryARPHandling INTEGER,
    lcosLXSetupWLANNetworkEntryMulticastToUnicast INTEGER,
    lcosLXSetupWLANNetworkEntryBridge INTEGER,
    lcosLXSetupWLANNetworkEntryWLCContinuationTime Unsigned32,
    lcosLXSetupWLANNetworkEntryWDSLink OCTET STRING,
    lcosLXSetupWLANNetworkEntryUAPSD INTEGER,
    lcosLXSetupWLANNetworkEntryRRM INTEGER,
    lcosLXSetupWLANNetworkEntryDTIMPeriod Unsigned32,
    lcosLXSetupWLANNetworkEntryRTSThreshold Unsigned32,
    lcosLXSetupWLANNetworkEntryNetworkID OCTET STRING,
    lcosLXSetupWLANNetworkEntryMLOMode INTEGER,
    lcosLXSetupWLANNetworkEntryKey OCTET STRING,
    lcosLXSetupWLANNetworkEntryRadios INTEGER,
    lcosLXSetupWLANNetworkEntryEncryptionProfile OCTET STRING,
    lcosLXSetupWLANNetworkEntryIdleTimeout Unsigned32,
    lcosLXSetupWLANNetworkEntryVLANID Unsigned32,
    lcosLXSetupWLANNetworkEntryMobilityDomain OCTET STRING
}

-- {COLUMN} 13.2.20.1.1.1
lcosLXSetupWLANNetworkEntryNetworkName OBJECT-TYPE
    SYNTAX     OCTET STRING (SIZE(0..64))
    MAX-ACCESS not-accessible
    STATUS     current
    DESCRIPTION
        ""
    ::= { lcosLXSetupWLANNetworkEntry 1 }

-- {COLUMN} 13.2.20.1.1.2
lcosLXSetupWLANNetworkEntrySSIDName OBJECT-TYPE
    SYNTAX     OCTET STRING (SIZE(0..32))
    MAX-ACCESS read-only
    STATUS     current
    DESCRIPTION
        ""
    ::= { lcosLXSetupWLANNetworkEntry 2 }

-- {COLUMN} 13.2.20.1.1.4
lcosLXSetupWLANNetworkEntryClosedNetwork OBJECT-TYPE
    SYNTAX     INTEGER {
                  eNo(0),
                  eYes(1)
               }
    MAX-ACCESS read-only
    STATUS     current
    DESCRIPTION
        ""
    ::= { lcosLXSetupWLANNetworkEntry 4 }

-- {COLUMN} 13.2.20.1.1.10
lcosLXSetupWLANNetworkEntryMaxStations OBJECT-TYPE
    SYNTAX     Unsigned32 (0..65535)
    MAX-ACCESS read-only
    STATUS     current
    DESCRIPTION
        ""
    ::= { lcosLXSetupWLANNetworkEntry 10 }

-- {COLUMN} 13.2.20.1.1.13
lcosLXSetupWLANNetworkEntryInterStationTraffic OBJECT-TYPE
    SYNTAX     INTEGER {
                  eNo(0),
                  eYes(1)
               }
    MAX-ACCESS read-only
    STATUS     current
    DESCRIPTION
        ""
    ::= { lcosLXSetupWLANNetworkEntry 13 }

-- {COLUMN} 13.2.20.1.1.14
lcosLXSetupWLANNetworkEntryClientIsolation OBJECT-TYPE
    SYNTAX     INTEGER {
                  eNo(0),
                  eYes(1)
               }
    MAX-ACCESS read-only
    STATUS     current
    DESCRIPTION
        ""
    ::= { lcosLXSetupWLANNetworkEntry 14 }

-- {COLUMN} 13.2.20.1.1.16
lcosLXSetupWLANNetworkEntryMinClientStrength OBJECT-TYPE
    SYNTAX     Unsigned32 (0..255)
    MAX-ACCESS read-only
    STATUS     current
    DESCRIPTION
        ""
    ::= { lcosLXSetupWLANNetworkEntry 16 }

-- {COLUMN} 13.2.20.1.1.17
lcosLXSetupWLANNetworkEntryExcludeFromClientManagement OBJECT-TYPE
    SYNTAX     INTEGER {
                  eNo(0),
                  eYes(1)
               }
    MAX-ACCESS read-only
    STATUS     current
    DESCRIPTION
        ""
    ::= { lcosLXSetupWLANNetworkEntry 17 }

-- {COLUMN} 13.2.20.1.1.18
lcosLXSetupWLANNetworkEntryTimeframe OBJECT-TYPE
    SYNTAX     OCTET STRING (SIZE(0..31))
    MAX-ACCESS read-only
    STATUS     current
    DESCRIPTION
        ""
    ::= { lcosLXSetupWLANNetworkEntry 18 }

-- {COLUMN} 13.2.20.1.1.19
lcosLXSetupWLANNetworkEntryHotspot OBJECT-TYPE
    SYNTAX     OCTET STRING (SIZE(0..32))
    MAX-ACCESS read-only
    STATUS     current
    DESCRIPTION
        ""
    ::= { lcosLXSetupWLANNetworkEntry 19 }

-- {COLUMN} 13.2.20.1.1.20
lcosLXSetupWLANNetworkEntrySummaricTxLimitKbits OBJECT-TYPE
    SYNTAX     Unsigned32 (0..4294967295)
    MAX-ACCESS read-only
    STATUS     current
    DESCRIPTION
        ""
    ::= { lcosLXSetupWLANNetworkEntry 20 }

-- {COLUMN} 13.2.20.1.1.21
lcosLXSetupWLANNetworkEntrySummaricRxLimitKbits OBJECT-TYPE
    SYNTAX     Unsigned32 (0..4294967295)
    MAX-ACCESS read-only
    STATUS     current
    DESCRIPTION
        ""
    ::= { lcosLXSetupWLANNetworkEntry 21 }

-- {COLUMN} 13.2.20.1.1.25
lcosLXSetupWLANNetworkEntryBlockMulticast OBJECT-TYPE
    SYNTAX     INTEGER {
                  eNo(0),
                  eIPv4only(1),
                  eIPv6only(2),
                  eBoth(3)
               }
    MAX-ACCESS read-only
    STATUS     current
    DESCRIPTION
        ""
    ::= { lcosLXSetupWLANNetworkEntry 25 }

-- {COLUMN} 13.2.20.1.1.26
lcosLXSetupWLANNetworkEntryClientTxLimitKbits OBJECT-TYPE
    SYNTAX     Unsigned32 (0..4294967295)
    MAX-ACCESS read-only
    STATUS     current
    DESCRIPTION
        ""
    ::= { lcosLXSetupWLANNetworkEntry 26 }

-- {COLUMN} 13.2.20.1.1.27
lcosLXSetupWLANNetworkEntryClientRxLimitKbits OBJECT-TYPE
    SYNTAX     Unsigned32 (0..4294967295)
    MAX-ACCESS read-only
    STATUS     current
    DESCRIPTION
        ""
    ::= { lcosLXSetupWLANNetworkEntry 27 }

-- {COLUMN} 13.2.20.1.1.28
lcosLXSetupWLANNetworkEntryARPHandling OBJECT-TYPE
    SYNTAX     INTEGER {
                  eOff(0),
                  eOn(1),
                  eStrict(2)
               }
    MAX-ACCESS read-only
    STATUS     current
    DESCRIPTION
        ""
    ::= { lcosLXSetupWLANNetworkEntry 28 }

-- {COLUMN} 13.2.20.1.1.29
lcosLXSetupWLANNetworkEntryMulticastToUnicast OBJECT-TYPE
    SYNTAX     INTEGER {
                  eNo(0),
                  eConvertToUnicast(1),
                  eConvertToAggregate(2)
               }
    MAX-ACCESS read-only
    STATUS     current
    DESCRIPTION
        ""
    ::= { lcosLXSetupWLANNetworkEntry 29 }

-- {COLUMN} 13.2.20.1.1.30
lcosLXSetupWLANNetworkEntryBridge OBJECT-TYPE
    SYNTAX     INTEGER {
                  ebrlan(0),
                  eWLCTunnel1(1),
                  eWLCTunnel2(2),
                  eWLCTunnel3(3),
                  eWLCTunnel4(4),
                  eWLCTunnel5(5),
                  eWLCTunnel6(6),
                  eWLCTunnel7(7),
                  eWLCTunnel8(8),
                  eWLCTunnel9(9),
                  eWLCTunnel10(10),
                  eWLCTunnel11(11),
                  eWLCTunnel12(12),
                  eWLCTunnel13(13),
                  eWLCTunnel14(14),
                  eWLCTunnel15(15),
                  eWLCTunnel16(16),
                  eWLCTunnel17(17),
                  eWLCTunnel18(18),
                  eWLCTunnel19(19),
                  eWLCTunnel20(20),
                  eWLCTunnel21(21),
                  eWLCTunnel22(22),
                  eWLCTunnel23(23),
                  eWLCTunnel24(24),
                  eWLCTunnel25(25),
                  eWLCTunnel26(26),
                  eWLCTunnel27(27),
                  eWLCTunnel28(28),
                  eWLCTunnel29(29),
                  eWLCTunnel30(30),
                  eWLCTunnel31(31),
                  eWLCTunnel32(32),
                  eL2TPTunnel1(34),
                  eL2TPTunnel2(35),
                  eL2TPTunnel3(36),
                  eL2TPTunnel4(37),
                  eL2TPTunnel5(38),
                  eL2TPTunnel6(39),
                  eL2TPTunnel7(40),
                  eL2TPTunnel8(41),
                  eL2TPTunnel9(42),
                  eL2TPTunnel10(43),
                  eL2TPTunnel11(44),
                  eL2TPTunnel12(45),
                  eL2TPTunnel13(46),
                  eL2TPTunnel14(47),
                  eL2TPTunnel15(48),
                  eL2TPTunnel16(49)
               }
    MAX-ACCESS read-only
    STATUS     current
    DESCRIPTION
        ""
    ::= { lcosLXSetupWLANNetworkEntry 30 }

-- {COLUMN} 13.2.20.1.1.31
lcosLXSetupWLANNetworkEntryWLCContinuationTime OBJECT-TYPE
    SYNTAX     Unsigned32 (0..65535)
    MAX-ACCESS read-only
    STATUS     current
    DESCRIPTION
        ""
    ::= { lcosLXSetupWLANNetworkEntry 31 }

-- {COLUMN} 13.2.20.1.1.32
lcosLXSetupWLANNetworkEntryWDSLink OBJECT-TYPE
    SYNTAX     OCTET STRING (SIZE(0..64))
    MAX-ACCESS read-only
    STATUS     current
    DESCRIPTION
        ""
    ::= { lcosLXSetupWLANNetworkEntry 32 }

-- {COLUMN} 13.2.20.1.1.34
lcosLXSetupWLANNetworkEntryUAPSD OBJECT-TYPE
    SYNTAX     INTEGER {
                  eNo(0),
                  eYes(1)
               }
    MAX-ACCESS read-only
    STATUS     current
    DESCRIPTION
        ""
    ::= { lcosLXSetupWLANNetworkEntry 34 }

-- {COLUMN} 13.2.20.1.1.35
lcosLXSetupWLANNetworkEntryRRM OBJECT-TYPE
    SYNTAX     INTEGER {
                  eNo(0),
                  eYes(1)
               }
    MAX-ACCESS read-only
    STATUS     current
    DESCRIPTION
        ""
    ::= { lcosLXSetupWLANNetworkEntry 35 }

-- {COLUMN} 13.2.20.1.1.36
lcosLXSetupWLANNetworkEntryDTIMPeriod OBJECT-TYPE
    SYNTAX     Unsigned32 (0..255)
    MAX-ACCESS read-only
    STATUS     current
    DESCRIPTION
        ""
    ::= { lcosLXSetupWLANNetworkEntry 36 }

-- {COLUMN} 13.2.20.1.1.37
lcosLXSetupWLANNetworkEntryRTSThreshold OBJECT-TYPE
    SYNTAX     Unsigned32 (0..65535)
    MAX-ACCESS read-only
    STATUS     current
    DESCRIPTION
        ""
    ::= { lcosLXSetupWLANNetworkEntry 37 }

-- {COLUMN} 13.2.20.1.1.41
lcosLXSetupWLANNetworkEntryNetworkID OBJECT-TYPE
    SYNTAX     OCTET STRING (SIZE(0..36))
    MAX-ACCESS read-only
    STATUS     current
    DESCRIPTION
        ""
    ::= { lcosLXSetupWLANNetworkEntry 41 }

-- {COLUMN} 13.2.20.1.1.42
lcosLXSetupWLANNetworkEntryMLOMode OBJECT-TYPE
    SYNTAX     INTEGER {
                  eAuto(0),
                  eSingleLink(1),
                  eDisabled(2)
               }
    MAX-ACCESS read-only
    STATUS     current
    DESCRIPTION
        ""
    ::= { lcosLXSetupWLANNetworkEntry 42 }

-- {COLUMN} 13.2.20.1.1.100
lcosLXSetupWLANNetworkEntryKey OBJECT-TYPE
    SYNTAX     OCTET STRING (SIZE(0..63))
    MAX-ACCESS read-only
    STATUS     current
    DESCRIPTION
        ""
    ::= { lcosLXSetupWLANNetworkEntry 100 }

-- {COLUMN} 13.2.20.1.1.101
lcosLXSetupWLANNetworkEntryRadios OBJECT-TYPE
    SYNTAX     INTEGER {
                  e24GHz5GHz(1),
                  e24GHz(2),
                  e5GHz(3),
                  enone(4),
                  e24GHz5GHz6GHz(5),
                  e24GHz6GHz(6),
                  e5GHz6GHz(7),
                  e6GHz(8)
               }
    MAX-ACCESS read-only
    STATUS     current
    DESCRIPTION
        ""
    ::= { lcosLXSetupWLANNetworkEntry 101 }

-- {COLUMN} 13.2.20.1.1.102
lcosLXSetupWLANNetworkEntryEncryptionProfile OBJECT-TYPE
    SYNTAX     OCTET STRING (SIZE(0..128))
    MAX-ACCESS read-only
    STATUS     current
    DESCRIPTION
        ""
    ::= { lcosLXSetupWLANNetworkEntry 102 }

-- {COLUMN} 13.2.20.1.1.103
lcosLXSetupWLANNetworkEntryIdleTimeout OBJECT-TYPE
    SYNTAX     Unsigned32 (0..65535)
    MAX-ACCESS read-only
    STATUS     current
    DESCRIPTION
        ""
    ::= { lcosLXSetupWLANNetworkEntry 103 }

-- {COLUMN} 13.2.20.1.1.200
lcosLXSetupWLANNetworkEntryVLANID OBJECT-TYPE
    SYNTAX     Unsigned32 (0..65535)
    MAX-ACCESS read-only
    STATUS     current
    DESCRIPTION
        ""
    ::= { lcosLXSetupWLANNetworkEntry 200 }

-- {COLUMN} 13.2.20.1.1.990
lcosLXSetupWLANNetworkEntryMobilityDomain OBJECT-TYPE
    SYNTAX     OCTET STRING (SIZE(0..4))
    MAX-ACCESS read-only
    STATUS     current
    DESCRIPTION
        ""
    ::= { lcosLXSetupWLANNetworkEntry 990 }

-- {SCALAR} 13.2.20.2
lcosLXSetupWLANCountry OBJECT-TYPE
    SYNTAX     INTEGER {
                  eAustralia(36),
                  eAustria(40),
                  eBelgium(56),
                  eBosniaHerzegovina(70),
                  eBulgaria(100),
                  eCanada(124),
                  eCroatia(191),
                  eCyprus(196),
                  eCzechRepublic(203),
                  eDenmark(208),
                  eEstonia(233),
                  eFinland(246),
                  eFrance(250),
                  eGermany(276),
                  eGreece(300),
                  eHungary(348),
                  eIreland(372),
                  eItaly(380),
                  eLatvia(428),
                  eLiechtenstein(438),
                  eLithuania(440),
                  eLuxembourg(442),
                  eMalta(470),
                  eMorocco(504),
                  eNetherlands(528),
                  eNewZealand(554),
                  eNorway(578),
                  ePoland(616),
                  ePortugal(620),
                  eRomania(642),
                  eRwanda(646),
                  eSenegal(686),
                  eSerbia(688),
                  eSingapore(702),
                  eSlovakia(703),
                  eSlovenia(705),
                  eSouthAfrica(710),
                  eSpain(724),
                  eSweden(752),
                  eSwitzerland(756),
                  eTurkey(792),
                  eUkraine(804),
                  eUnitedKingdom(826),
                  eUnitedStates(840),
                  eEurope(998)
               }
    MAX-ACCESS read-only
    STATUS     current
    DESCRIPTION
        ""
    ::= { lcosLXSetupWLAN 2 }

-- {TABLE} 13.2.20.3
lcosLXSetupWLANEncryption OBJECT-TYPE
    SYNTAX     SEQUENCE OF LcosLXSetupWLANEncryptionEntry
    MAX-ACCESS not-accessible
    STATUS     current
    DESCRIPTION
        ""
    ::= { lcosLXSetupWLAN 3 }

-- {INDEX} 13.2.20.3
lcosLXSetupWLANEncryptionEntry OBJECT-TYPE
    SYNTAX     LcosLXSetupWLANEncryptionEntry
    MAX-ACCESS not-accessible
    STATUS     current
    DESCRIPTION
        ""
    INDEX {
        lcosLXSetupWLANEncryptionEntryProfileName
    }
    ::= { lcosLXSetupWLANEncryption 1 }

-- {SEQUENCE} 13.2.20.3
LcosLXSetupWLANEncryptionEntry ::= SEQUENCE {
    lcosLXSetupWLANEncryptionEntryProfileName OCTET STRING,
    lcosLXSetupWLANEncryptionEntryEncryption INTEGER,
    lcosLXSetupWLANEncryptionEntryMethod INTEGER,
    lcosLXSetupWLANEncryptionEntryWPAVersion INTEGER,
    lcosLXSetupWLANEncryptionEntryWPARekeyingCycle Unsigned32,
    lcosLXSetupWLANEncryptionEntryWPA1SessionKeytypes INTEGER,
    lcosLXSetupWLANEncryptionEntryWPA23SessionKeytypes BITS,
    lcosLXSetupWLANEncryptionEntryProtMgmtFrames INTEGER,
    lcosLXSetupWLANEncryptionEntryProtBeacons INTEGER,
    lcosLXSetupWLANEncryptionEntryPreAuthentication INTEGER,
    lcosLXSetupWLANEncryptionEntryOKC INTEGER,
    lcosLXSetupWLANEncryptionEntryWPA2KeyManagement INTEGER,
    lcosLXSetupWLANEncryptionEntryPMKIAPPSecret OCTET STRING,
    lcosLXSetupWLANEncryptionEntryRADIUSServerProfile OCTET STRING,
    lcosLXSetupWLANEncryptionEntrySAEOWEGroups BITS,
    lcosLXSetupWLANEncryptionEntryGroupMgmtCipher INTEGER
}

-- {COLUMN} 13.2.20.3.1.1
lcosLXSetupWLANEncryptionEntryProfileName OBJECT-TYPE
    SYNTAX     OCTET STRING (SIZE(0..128))
    MAX-ACCESS not-accessible
    STATUS     current
    DESCRIPTION
        ""
    ::= { lcosLXSetupWLANEncryptionEntry 1 }

-- {COLUMN} 13.2.20.3.1.2
lcosLXSetupWLANEncryptionEntryEncryption OBJECT-TYPE
    SYNTAX     INTEGER {
                  eNo(0),
                  eYes(1)
               }
    MAX-ACCESS read-only
    STATUS     current
    DESCRIPTION
        ""
    ::= { lcosLXSetupWLANEncryptionEntry 2 }

-- {COLUMN} 13.2.20.3.1.4
lcosLXSetupWLANEncryptionEntryMethod OBJECT-TYPE
    SYNTAX     INTEGER {
                  eWEP40Bits(5),
                  eWEP104Bits(13),
                  eWEP128Bits(16),
                  e80211iWPAPSK(32),
                  e80211iWPA8021X(33),
                  eWEP40Bits8021X(34),
                  eWEP104Bits8021X(35),
                  eWEP128Bits8021X(36),
                  eEnhancedOpen(37),
                  e80211iWPA8021X192Bits(38)
               }
    MAX-ACCESS read-only
    STATUS     current
    DESCRIPTION
        ""
    ::= { lcosLXSetupWLANEncryptionEntry 4 }

-- {COLUMN} 13.2.20.3.1.9
lcosLXSetupWLANEncryptionEntryWPAVersion OBJECT-TYPE
    SYNTAX     INTEGER {
                  eWPA1(2),
                  eWPA2(4),
                  eWPA12(6),
                  eWPA3(8),
                  eWPA23(12)
               }
    MAX-ACCESS read-only
    STATUS     current
    DESCRIPTION
        ""
    ::= { lcosLXSetupWLANEncryptionEntry 9 }

-- {COLUMN} 13.2.20.3.1.11
lcosLXSetupWLANEncryptionEntryWPARekeyingCycle OBJECT-TYPE
    SYNTAX     Unsigned32 (0..4294967295)
    MAX-ACCESS read-only
    STATUS     current
    DESCRIPTION
        ""
    ::= { lcosLXSetupWLANEncryptionEntry 11 }

-- {COLUMN} 13.2.20.3.1.12
lcosLXSetupWLANEncryptionEntryWPA1SessionKeytypes OBJECT-TYPE
    SYNTAX     INTEGER {
                  eTKIP(1),
                  eAES(2),
                  eTKIPAES(3)
               }
    MAX-ACCESS read-only
    STATUS     current
    DESCRIPTION
        ""
    ::= { lcosLXSetupWLANEncryptionEntry 12 }

-- {COLUMN} 13.2.20.3.1.13
lcosLXSetupWLANEncryptionEntryWPA23SessionKeytypes OBJECT-TYPE
    SYNTAX     BITS {
                  eTKIP(0),
                  eAESCCMP128(1),
                  eAESCCMP256(2),
                  eAESGCMP128(3),
                  eAESGCMP256(4)
               }
    MAX-ACCESS read-only
    STATUS     current
    DESCRIPTION
        ""
    ::= { lcosLXSetupWLANEncryptionEntry 13 }

-- {COLUMN} 13.2.20.3.1.14
lcosLXSetupWLANEncryptionEntryProtMgmtFrames OBJECT-TYPE
    SYNTAX     INTEGER {
                  eNo(0),
                  eoptional(1),
                  emandatory(2)
               }
    MAX-ACCESS read-only
    STATUS     current
    DESCRIPTION
        ""
    ::= { lcosLXSetupWLANEncryptionEntry 14 }

-- {COLUMN} 13.2.20.3.1.15
lcosLXSetupWLANEncryptionEntryProtBeacons OBJECT-TYPE
    SYNTAX     INTEGER {
                  eNo(0),
                  eYes(1),
                  eAuto(255)
               }
    MAX-ACCESS read-only
    STATUS     current
    DESCRIPTION
        ""
    ::= { lcosLXSetupWLANEncryptionEntry 15 }

-- {COLUMN} 13.2.20.3.1.16
lcosLXSetupWLANEncryptionEntryPreAuthentication OBJECT-TYPE
    SYNTAX     INTEGER {
                  eNo(0),
                  eYes(1)
               }
    MAX-ACCESS read-only
    STATUS     current
    DESCRIPTION
        ""
    ::= { lcosLXSetupWLANEncryptionEntry 16 }

-- {COLUMN} 13.2.20.3.1.17
lcosLXSetupWLANEncryptionEntryOKC OBJECT-TYPE
    SYNTAX     INTEGER {
                  eNo(0),
                  eYes(1)
               }
    MAX-ACCESS read-only
    STATUS     current
    DESCRIPTION
        ""
    ::= { lcosLXSetupWLANEncryptionEntry 17 }

-- {COLUMN} 13.2.20.3.1.19
lcosLXSetupWLANEncryptionEntryWPA2KeyManagement OBJECT-TYPE
    SYNTAX     INTEGER {
                  eStandard(0),
                  eFastRoaming(1),
                  eStandardFastRoaming(2)
               }
    MAX-ACCESS read-only
    STATUS     current
    DESCRIPTION
        ""
    ::= { lcosLXSetupWLANEncryptionEntry 19 }

-- {COLUMN} 13.2.20.3.1.20
lcosLXSetupWLANEncryptionEntryPMKIAPPSecret OBJECT-TYPE
    SYNTAX     OCTET STRING (SIZE(0..64))
    MAX-ACCESS read-only
    STATUS     current
    DESCRIPTION
        ""
    ::= { lcosLXSetupWLANEncryptionEntry 20 }

-- {COLUMN} 13.2.20.3.1.21
lcosLXSetupWLANEncryptionEntryRADIUSServerProfile OBJECT-TYPE
    SYNTAX     OCTET STRING (SIZE(0..64))
    MAX-ACCESS read-only
    STATUS     current
    DESCRIPTION
        ""
    ::= { lcosLXSetupWLANEncryptionEntry 21 }

-- {COLUMN} 13.2.20.3.1.26
lcosLXSetupWLANEncryptionEntrySAEOWEGroups OBJECT-TYPE
    SYNTAX     BITS {
                  eDH19(19),
                  eDH20(20),
                  eDH21(21)
               }
    MAX-ACCESS read-only
    STATUS     current
    DESCRIPTION
        ""
    ::= { lcosLXSetupWLANEncryptionEntry 26 }

-- {COLUMN} 13.2.20.3.1.27
lcosLXSetupWLANEncryptionEntryGroupMgmtCipher OBJECT-TYPE
    SYNTAX     INTEGER {
                  eBIPCMAC128(0),
                  eBIPCMAC256(1),
                  eBIPGMAC128(2),
                  eBIPGMAC256(3)
               }
    MAX-ACCESS read-only
    STATUS     current
    DESCRIPTION
        ""
    ::= { lcosLXSetupWLANEncryptionEntry 27 }

-- {OID} 13.2.20.4
lcosLXSetupWLANMgmt OBJECT IDENTIFIER ::= { lcosLXSetupWLAN 4 }

-- {SCALAR} 13.2.20.4.1
lcosLXSetupWLANMgmtActiveProfile OBJECT-TYPE
    SYNTAX     OCTET STRING (SIZE(0..128))
    MAX-ACCESS read-only
    STATUS     current
    DESCRIPTION
        ""
    ::= { lcosLXSetupWLANMgmt 1 }

-- {TABLE} 13.2.20.4.2
lcosLXSetupWLANMgmtProfiles OBJECT-TYPE
    SYNTAX     SEQUENCE OF LcosLXSetupWLANMgmtProfilesEntry
    MAX-ACCESS not-accessible
    STATUS     current
    DESCRIPTION
        ""
    ::= { lcosLXSetupWLANMgmt 2 }

-- {INDEX} 13.2.20.4.2
lcosLXSetupWLANMgmtProfilesEntry OBJECT-TYPE
    SYNTAX     LcosLXSetupWLANMgmtProfilesEntry
    MAX-ACCESS not-accessible
    STATUS     current
    DESCRIPTION
        ""
    INDEX {
        lcosLXSetupWLANMgmtProfilesEntryProfileName
    }
    ::= { lcosLXSetupWLANMgmtProfiles 1 }

-- {SEQUENCE} 13.2.20.4.2
LcosLXSetupWLANMgmtProfilesEntry ::= SEQUENCE {
    lcosLXSetupWLANMgmtProfilesEntryProfileName OCTET STRING,
    lcosLXSetupWLANMgmtProfilesEntryOperating INTEGER,
    lcosLXSetupWLANMgmtProfilesEntrySteeringMinPHYSignal Unsigned32,
    lcosLXSetupWLANMgmtProfilesEntryUpgradeTXRateThreshold Unsigned32,
    lcosLXSetupWLANMgmtProfilesEntryUpgradePHYSignalThreshold Unsigned32,
    lcosLXSetupWLANMgmtProfilesEntryDowngradeTXRateThreshold Unsigned32,
    lcosLXSetupWLANMgmtProfilesEntryDowngradePHYSignalThreshold Unsigned32,
    lcosLXSetupWLANMgmtProfilesEntry24GHzSubProfile OCTET STRING,
    lcosLXSetupWLANMgmtProfilesEntry5GHzSubProfile OCTET STRING
}

-- {COLUMN} 13.2.20.4.2.1.1
lcosLXSetupWLANMgmtProfilesEntryProfileName OBJECT-TYPE
    SYNTAX     OCTET STRING (SIZE(0..128))
    MAX-ACCESS not-accessible
    STATUS     current
    DESCRIPTION
        ""
    ::= { lcosLXSetupWLANMgmtProfilesEntry 1 }

-- {COLUMN} 13.2.20.4.2.1.2
lcosLXSetupWLANMgmtProfilesEntryOperating OBJECT-TYPE
    SYNTAX     INTEGER {
                  eNo(0),
                  eYes(1)
               }
    MAX-ACCESS read-only
    STATUS     current
    DESCRIPTION
        ""
    ::= { lcosLXSetupWLANMgmtProfilesEntry 2 }

-- {COLUMN} 13.2.20.4.2.1.3
lcosLXSetupWLANMgmtProfilesEntrySteeringMinPHYSignal OBJECT-TYPE
    SYNTAX     Unsigned32 (0..4294967295)
    MAX-ACCESS read-only
    STATUS     current
    DESCRIPTION
        ""
    ::= { lcosLXSetupWLANMgmtProfilesEntry 3 }

-- {COLUMN} 13.2.20.4.2.1.4
lcosLXSetupWLANMgmtProfilesEntryUpgradeTXRateThreshold OBJECT-TYPE
    SYNTAX     Unsigned32 (0..4294967295)
    MAX-ACCESS read-only
    STATUS     current
    DESCRIPTION
        ""
    ::= { lcosLXSetupWLANMgmtProfilesEntry 4 }

-- {COLUMN} 13.2.20.4.2.1.5
lcosLXSetupWLANMgmtProfilesEntryUpgradePHYSignalThreshold OBJECT-TYPE
    SYNTAX     Unsigned32 (0..4294967295)
    MAX-ACCESS read-only
    STATUS     current
    DESCRIPTION
        ""
    ::= { lcosLXSetupWLANMgmtProfilesEntry 5 }

-- {COLUMN} 13.2.20.4.2.1.6
lcosLXSetupWLANMgmtProfilesEntryDowngradeTXRateThreshold OBJECT-TYPE
    SYNTAX     Unsigned32 (0..4294967295)
    MAX-ACCESS read-only
    STATUS     current
    DESCRIPTION
        ""
    ::= { lcosLXSetupWLANMgmtProfilesEntry 6 }

-- {COLUMN} 13.2.20.4.2.1.7
lcosLXSetupWLANMgmtProfilesEntryDowngradePHYSignalThreshold OBJECT-TYPE
    SYNTAX     Unsigned32 (0..4294967295)
    MAX-ACCESS read-only
    STATUS     current
    DESCRIPTION
        ""
    ::= { lcosLXSetupWLANMgmtProfilesEntry 7 }

-- {COLUMN} 13.2.20.4.2.1.8
lcosLXSetupWLANMgmtProfilesEntry24GHzSubProfile OBJECT-TYPE
    SYNTAX     OCTET STRING (SIZE(0..128))
    MAX-ACCESS read-only
    STATUS     current
    DESCRIPTION
        ""
    ::= { lcosLXSetupWLANMgmtProfilesEntry 8 }

-- {COLUMN} 13.2.20.4.2.1.9
lcosLXSetupWLANMgmtProfilesEntry5GHzSubProfile OBJECT-TYPE
    SYNTAX     OCTET STRING (SIZE(0..128))
    MAX-ACCESS read-only
    STATUS     current
    DESCRIPTION
        ""
    ::= { lcosLXSetupWLANMgmtProfilesEntry 9 }

-- {TABLE} 13.2.20.4.3
lcosLXSetupWLANMgmt24GHz OBJECT-TYPE
    SYNTAX     SEQUENCE OF LcosLXSetupWLANMgmt24GHzEntry
    MAX-ACCESS not-accessible
    STATUS     current
    DESCRIPTION
        ""
    ::= { lcosLXSetupWLANMgmt 3 }

-- {INDEX} 13.2.20.4.3
lcosLXSetupWLANMgmt24GHzEntry OBJECT-TYPE
    SYNTAX     LcosLXSetupWLANMgmt24GHzEntry
    MAX-ACCESS not-accessible
    STATUS     current
    DESCRIPTION
        ""
    INDEX {
        lcosLXSetupWLANMgmt24GHzEntryProfileName
    }
    ::= { lcosLXSetupWLANMgmt24GHz 1 }

-- {SEQUENCE} 13.2.20.4.3
LcosLXSetupWLANMgmt24GHzEntry ::= SEQUENCE {
    lcosLXSetupWLANMgmt24GHzEntryProfileName OCTET STRING,
    lcosLXSetupWLANMgmt24GHzEntryUtilizationCheckInterval Unsigned32,
    lcosLXSetupWLANMgmt24GHzEntryUtilizationAveragePeriod Unsigned32,
    lcosLXSetupWLANMgmt24GHzEntryUtilizationOverloadThreshold Unsigned32,
    lcosLXSetupWLANMgmt24GHzEntryUtilizationDeviationThreshold Unsigned32,
    lcosLXSetupWLANMgmt24GHzEntryInterferenceDetection INTEGER,
    lcosLXSetupWLANMgmt24GHzEntryDelayProbePHYSignalThreshold Unsigned32,
    lcosLXSetupWLANMgmt24GHzEntryDelayProbeTimeWindow Unsigned32,
    lcosLXSetupWLANMgmt24GHzEntryDelayProbeMinRequestCount Unsigned32
}

-- {COLUMN} 13.2.20.4.3.1.1
lcosLXSetupWLANMgmt24GHzEntryProfileName OBJECT-TYPE
    SYNTAX     OCTET STRING (SIZE(0..128))
    MAX-ACCESS not-accessible
    STATUS     current
    DESCRIPTION
        ""
    ::= { lcosLXSetupWLANMgmt24GHzEntry 1 }

-- {COLUMN} 13.2.20.4.3.1.2
lcosLXSetupWLANMgmt24GHzEntryUtilizationCheckInterval OBJECT-TYPE
    SYNTAX     Unsigned32 (0..4294967295)
    MAX-ACCESS read-only
    STATUS     current
    DESCRIPTION
        ""
    ::= { lcosLXSetupWLANMgmt24GHzEntry 2 }

-- {COLUMN} 13.2.20.4.3.1.3
lcosLXSetupWLANMgmt24GHzEntryUtilizationAveragePeriod OBJECT-TYPE
    SYNTAX     Unsigned32 (0..4294967295)
    MAX-ACCESS read-only
    STATUS     current
    DESCRIPTION
        ""
    ::= { lcosLXSetupWLANMgmt24GHzEntry 3 }

-- {COLUMN} 13.2.20.4.3.1.4
lcosLXSetupWLANMgmt24GHzEntryUtilizationOverloadThreshold OBJECT-TYPE
    SYNTAX     Unsigned32 (0..4294967295)
    MAX-ACCESS read-only
    STATUS     current
    DESCRIPTION
        ""
    ::= { lcosLXSetupWLANMgmt24GHzEntry 4 }

-- {COLUMN} 13.2.20.4.3.1.5
lcosLXSetupWLANMgmt24GHzEntryUtilizationDeviationThreshold OBJECT-TYPE
    SYNTAX     Unsigned32 (0..4294967295)
    MAX-ACCESS read-only
    STATUS     current
    DESCRIPTION
        ""
    ::= { lcosLXSetupWLANMgmt24GHzEntry 5 }

-- {COLUMN} 13.2.20.4.3.1.6
lcosLXSetupWLANMgmt24GHzEntryInterferenceDetection OBJECT-TYPE
    SYNTAX     INTEGER {
                  eNo(0),
                  eYes(1)
               }
    MAX-ACCESS read-only
    STATUS     current
    DESCRIPTION
        ""
    ::= { lcosLXSetupWLANMgmt24GHzEntry 6 }

-- {COLUMN} 13.2.20.4.3.1.7
lcosLXSetupWLANMgmt24GHzEntryDelayProbePHYSignalThreshold OBJECT-TYPE
    SYNTAX     Unsigned32 (0..4294967295)
    MAX-ACCESS read-only
    STATUS     current
    DESCRIPTION
        ""
    ::= { lcosLXSetupWLANMgmt24GHzEntry 7 }

-- {COLUMN} 13.2.20.4.3.1.8
lcosLXSetupWLANMgmt24GHzEntryDelayProbeTimeWindow OBJECT-TYPE
    SYNTAX     Unsigned32 (0..4294967295)
    MAX-ACCESS read-only
    STATUS     current
    DESCRIPTION
        ""
    ::= { lcosLXSetupWLANMgmt24GHzEntry 8 }

-- {COLUMN} 13.2.20.4.3.1.9
lcosLXSetupWLANMgmt24GHzEntryDelayProbeMinRequestCount OBJECT-TYPE
    SYNTAX     Unsigned32 (0..4294967295)
    MAX-ACCESS read-only
    STATUS     current
    DESCRIPTION
        ""
    ::= { lcosLXSetupWLANMgmt24GHzEntry 9 }

-- {TABLE} 13.2.20.4.4
lcosLXSetupWLANMgmt5GHz OBJECT-TYPE
    SYNTAX     SEQUENCE OF LcosLXSetupWLANMgmt5GHzEntry
    MAX-ACCESS not-accessible
    STATUS     current
    DESCRIPTION
        ""
    ::= { lcosLXSetupWLANMgmt 4 }

-- {INDEX} 13.2.20.4.4
lcosLXSetupWLANMgmt5GHzEntry OBJECT-TYPE
    SYNTAX     LcosLXSetupWLANMgmt5GHzEntry
    MAX-ACCESS not-accessible
    STATUS     current
    DESCRIPTION
        ""
    INDEX {
        lcosLXSetupWLANMgmt5GHzEntryProfileName
    }
    ::= { lcosLXSetupWLANMgmt5GHz 1 }

-- {SEQUENCE} 13.2.20.4.4
LcosLXSetupWLANMgmt5GHzEntry ::= SEQUENCE {
    lcosLXSetupWLANMgmt5GHzEntryProfileName OCTET STRING,
    lcosLXSetupWLANMgmt5GHzEntryUtilizationCheckInterval Unsigned32,
    lcosLXSetupWLANMgmt5GHzEntryUtilizationAveragePeriod Unsigned32,
    lcosLXSetupWLANMgmt5GHzEntryUtilizationOverloadThreshold Unsigned32,
    lcosLXSetupWLANMgmt5GHzEntryUtilizationDeviationThreshold Unsigned32,
    lcosLXSetupWLANMgmt5GHzEntryInterferenceDetection INTEGER
}

-- {COLUMN} 13.2.20.4.4.1.1
lcosLXSetupWLANMgmt5GHzEntryProfileName OBJECT-TYPE
    SYNTAX     OCTET STRING (SIZE(0..128))
    MAX-ACCESS not-accessible
    STATUS     current
    DESCRIPTION
        ""
    ::= { lcosLXSetupWLANMgmt5GHzEntry 1 }

-- {COLUMN} 13.2.20.4.4.1.2
lcosLXSetupWLANMgmt5GHzEntryUtilizationCheckInterval OBJECT-TYPE
    SYNTAX     Unsigned32 (0..4294967295)
    MAX-ACCESS read-only
    STATUS     current
    DESCRIPTION
        ""
    ::= { lcosLXSetupWLANMgmt5GHzEntry 2 }

-- {COLUMN} 13.2.20.4.4.1.3
lcosLXSetupWLANMgmt5GHzEntryUtilizationAveragePeriod OBJECT-TYPE
    SYNTAX     Unsigned32 (0..4294967295)
    MAX-ACCESS read-only
    STATUS     current
    DESCRIPTION
        ""
    ::= { lcosLXSetupWLANMgmt5GHzEntry 3 }

-- {COLUMN} 13.2.20.4.4.1.4
lcosLXSetupWLANMgmt5GHzEntryUtilizationOverloadThreshold OBJECT-TYPE
    SYNTAX     Unsigned32 (0..4294967295)
    MAX-ACCESS read-only
    STATUS     current
    DESCRIPTION
        ""
    ::= { lcosLXSetupWLANMgmt5GHzEntry 4 }

-- {COLUMN} 13.2.20.4.4.1.5
lcosLXSetupWLANMgmt5GHzEntryUtilizationDeviationThreshold OBJECT-TYPE
    SYNTAX     Unsigned32 (0..4294967295)
    MAX-ACCESS read-only
    STATUS     current
    DESCRIPTION
        ""
    ::= { lcosLXSetupWLANMgmt5GHzEntry 5 }

-- {COLUMN} 13.2.20.4.4.1.6
lcosLXSetupWLANMgmt5GHzEntryInterferenceDetection OBJECT-TYPE
    SYNTAX     INTEGER {
                  eNo(0),
                  eYes(1)
               }
    MAX-ACCESS read-only
    STATUS     current
    DESCRIPTION
        ""
    ::= { lcosLXSetupWLANMgmt5GHzEntry 6 }

-- {TABLE} 13.2.20.8
lcosLXSetupWLANRadioSettings OBJECT-TYPE
    SYNTAX     SEQUENCE OF LcosLXSetupWLANRadioSettingsEntry
    MAX-ACCESS not-accessible
    STATUS     current
    DESCRIPTION
        ""
    ::= { lcosLXSetupWLAN 8 }

-- {INDEX} 13.2.20.8
lcosLXSetupWLANRadioSettingsEntry OBJECT-TYPE
    SYNTAX     LcosLXSetupWLANRadioSettingsEntry
    MAX-ACCESS not-accessible
    STATUS     current
    DESCRIPTION
        ""
    INDEX {
        lcosLXSetupWLANRadioSettingsEntryIfc
    }
    ::= { lcosLXSetupWLANRadioSettings 1 }

-- {SEQUENCE} 13.2.20.8
LcosLXSetupWLANRadioSettingsEntry ::= SEQUENCE {
    lcosLXSetupWLANRadioSettingsEntryIfc OCTET STRING,
    lcosLXSetupWLANRadioSettingsEntry5GHzMode INTEGER,
    lcosLXSetupWLANRadioSettingsEntryRadioBand INTEGER,
    lcosLXSetupWLANRadioSettingsEntrySubBand INTEGER,
    lcosLXSetupWLANRadioSettingsEntryChannel Unsigned32,
    lcosLXSetupWLANRadioSettingsEntry24GHzMode INTEGER,
    lcosLXSetupWLANRadioSettingsEntryChannelList OCTET STRING,
    lcosLXSetupWLANRadioSettingsEntryAntennaMask INTEGER,
    lcosLXSetupWLANRadioSettingsEntry6GHzMode INTEGER,
    lcosLXSetupWLANRadioSettingsEntryMaxChannelBandwidth INTEGER,
    lcosLXSetupWLANRadioSettingsEntryExcludeDFSChannels INTEGER,
    lcosLXSetupWLANRadioSettingsEntryPowerSetting INTEGER,
    lcosLXSetupWLANRadioSettingsEntryEIRP Unsigned32,
    lcosLXSetupWLANRadioSettingsEntryIncludeWeatherRadarChannels INTEGER,
    lcosLXSetupWLANRadioSettingsEntryMaxDistance Unsigned32,
    lcosLXSetupWLANRadioSettingsEntryChannelSelection INTEGER
}

-- {COLUMN} 13.2.20.8.1.1
lcosLXSetupWLANRadioSettingsEntryIfc OBJECT-TYPE
    SYNTAX     OCTET STRING (SIZE(0..9))
    MAX-ACCESS not-accessible
    STATUS     current
    DESCRIPTION
        ""
    ::= { lcosLXSetupWLANRadioSettingsEntry 1 }

-- {COLUMN} 13.2.20.8.1.3
lcosLXSetupWLANRadioSettingsEntry5GHzMode OBJECT-TYPE
    SYNTAX     INTEGER {
                  e11anmixed(3),
                  e11anacmixed(7),
                  e11nacmixed(8),
                  e11aconly(9),
                  e11anacaxmixed(10),
                  e11anacaxbemixed(11),
                  eAuto(255)
               }
    MAX-ACCESS read-only
    STATUS     current
    DESCRIPTION
        ""
    ::= { lcosLXSetupWLANRadioSettingsEntry 3 }

-- {COLUMN} 13.2.20.8.1.6
lcosLXSetupWLANRadioSettingsEntryRadioBand OBJECT-TYPE
    SYNTAX     INTEGER {
                  e24GHz(1),
                  e5GHz(2),
                  e6GHz(3)
               }
    MAX-ACCESS read-only
    STATUS     current
    DESCRIPTION
        ""
    ::= { lcosLXSetupWLANRadioSettingsEntry 6 }

-- {COLUMN} 13.2.20.8.1.7
lcosLXSetupWLANRadioSettingsEntrySubBand OBJECT-TYPE
    SYNTAX     INTEGER {
                  eBand1(1),
                  eBand2(2),
                  eBand12(0),
                  eBand5(3)
               }
    MAX-ACCESS read-only
    STATUS     current
    DESCRIPTION
        ""
    ::= { lcosLXSetupWLANRadioSettingsEntry 7 }

-- {COLUMN} 13.2.20.8.1.8
lcosLXSetupWLANRadioSettingsEntryChannel OBJECT-TYPE
    SYNTAX     Unsigned32 (0..255)
    MAX-ACCESS read-only
    STATUS     current
    DESCRIPTION
        ""
    ::= { lcosLXSetupWLANRadioSettingsEntry 8 }

-- {COLUMN} 13.2.20.8.1.9
lcosLXSetupWLANRadioSettingsEntry24GHzMode OBJECT-TYPE
    SYNTAX     INTEGER {
                  e11bgmixed(0),
                  e11gonly(1),
                  e11bgnmixed(5),
                  e11gnmixed(7),
                  e11bgnaxmixed(8),
                  e11gnaxmixed(9),
                  eAuto(255)
               }
    MAX-ACCESS read-only
    STATUS     current
    DESCRIPTION
        ""
    ::= { lcosLXSetupWLANRadioSettingsEntry 9 }

-- {COLUMN} 13.2.20.8.1.13
lcosLXSetupWLANRadioSettingsEntryChannelList OBJECT-TYPE
    SYNTAX     OCTET STRING (SIZE(0..100))
    MAX-ACCESS read-only
    STATUS     current
    DESCRIPTION
        ""
    ::= { lcosLXSetupWLANRadioSettingsEntry 13 }

-- {COLUMN} 13.2.20.8.1.17
lcosLXSetupWLANRadioSettingsEntryAntennaMask OBJECT-TYPE
    SYNTAX     INTEGER {
                  eAll(0),
                  eAntenna1(1),
                  eAntenna2(2),
                  eAntenna12(3),
                  eAntenna3(4),
                  eAntenna13(5),
                  eAntenna23(6),
                  eAntenna123(7),
                  eAntenna4(8),
                  eAntenna14(9),
                  eAntenna24(10),
                  eAntenna124(11),
                  eAntenna34(12),
                  eAntenna134(13),
                  eAntenna234(14),
                  eAntenna1234(15)
               }
    MAX-ACCESS read-only
    STATUS     current
    DESCRIPTION
        ""
    ::= { lcosLXSetupWLANRadioSettingsEntry 17 }

-- {COLUMN} 13.2.20.8.1.19
lcosLXSetupWLANRadioSettingsEntry6GHzMode OBJECT-TYPE
    SYNTAX     INTEGER {
                  e11ax(0),
                  e11axbemixed(1),
                  eAuto(255)
               }
    MAX-ACCESS read-only
    STATUS     current
    DESCRIPTION
        ""
    ::= { lcosLXSetupWLANRadioSettingsEntry 19 }

-- {COLUMN} 13.2.20.8.1.24
lcosLXSetupWLANRadioSettingsEntryMaxChannelBandwidth OBJECT-TYPE
    SYNTAX     INTEGER {
                  e20MHz(0),
                  e40MHz(1),
                  e80MHz(2),
                  e160MHz(3),
                  e320MHz(4),
                  eAuto(255)
               }
    MAX-ACCESS read-only
    STATUS     current
    DESCRIPTION
        ""
    ::= { lcosLXSetupWLANRadioSettingsEntry 24 }

-- {COLUMN} 13.2.20.8.1.29
lcosLXSetupWLANRadioSettingsEntryExcludeDFSChannels OBJECT-TYPE
    SYNTAX     INTEGER {
                  eNo(0),
                  eYes(1)
               }
    MAX-ACCESS read-only
    STATUS     current
    DESCRIPTION
        ""
    ::= { lcosLXSetupWLANRadioSettingsEntry 29 }

-- {COLUMN} 13.2.20.8.1.33
lcosLXSetupWLANRadioSettingsEntryPowerSetting OBJECT-TYPE
    SYNTAX     INTEGER {
                  eAutomatic(0),
                  eManual(1)
               }
    MAX-ACCESS read-only
    STATUS     current
    DESCRIPTION
        ""
    ::= { lcosLXSetupWLANRadioSettingsEntry 33 }

-- {COLUMN} 13.2.20.8.1.34
lcosLXSetupWLANRadioSettingsEntryEIRP OBJECT-TYPE
    SYNTAX     Unsigned32 (0..255)
    MAX-ACCESS read-only
    STATUS     current
    DESCRIPTION
        ""
    ::= { lcosLXSetupWLANRadioSettingsEntry 34 }

-- {COLUMN} 13.2.20.8.1.35
lcosLXSetupWLANRadioSettingsEntryIncludeWeatherRadarChannels OBJECT-TYPE
    SYNTAX     INTEGER {
                  eNo(0),
                  eYes(1)
               }
    MAX-ACCESS read-only
    STATUS     current
    DESCRIPTION
        ""
    ::= { lcosLXSetupWLANRadioSettingsEntry 35 }

-- {COLUMN} 13.2.20.8.1.36
lcosLXSetupWLANRadioSettingsEntryMaxDistance OBJECT-TYPE
    SYNTAX     Unsigned32 (0..255)
    MAX-ACCESS read-only
    STATUS     current
    DESCRIPTION
        ""
    ::= { lcosLXSetupWLANRadioSettingsEntry 36 }

-- {COLUMN} 13.2.20.8.1.37
lcosLXSetupWLANRadioSettingsEntryChannelSelection OBJECT-TYPE
    SYNTAX     INTEGER {
                  eAuto(0),
                  eRandom(1)
               }
    MAX-ACCESS read-only
    STATUS     current
    DESCRIPTION
        ""
    ::= { lcosLXSetupWLANRadioSettingsEntry 37 }

-- {SCALAR} 13.2.20.9
lcosLXSetupWLANAutomaticEnvironmentScanEnabled OBJECT-TYPE
    SYNTAX     INTEGER {
                  eNo(0),
                  eYes(1)
               }
    MAX-ACCESS read-only
    STATUS     current
    DESCRIPTION
        ""
    ::= { lcosLXSetupWLAN 9 }

-- {SCALAR} 13.2.20.10
lcosLXSetupWLANAutomaticEnvironmentScanTimeBegin OBJECT-TYPE
    SYNTAX     OCTET STRING (SIZE(0..5))
    MAX-ACCESS read-only
    STATUS     current
    DESCRIPTION
        ""
    ::= { lcosLXSetupWLAN 10 }

-- {SCALAR} 13.2.20.11
lcosLXSetupWLANAutomaticEnvironmentScanTimeEnd OBJECT-TYPE
    SYNTAX     OCTET STRING (SIZE(0..5))
    MAX-ACCESS read-only
    STATUS     current
    DESCRIPTION
        ""
    ::= { lcosLXSetupWLAN 11 }

-- {OID} 13.2.20.12
lcosLXSetupWLANHotspot OBJECT IDENTIFIER ::= { lcosLXSetupWLAN 12 }

-- {TABLE} 13.2.20.12.1
lcosLXSetupWLANHotspotHotspots OBJECT-TYPE
    SYNTAX     SEQUENCE OF LcosLXSetupWLANHotspotHotspotsEntry
    MAX-ACCESS not-accessible
    STATUS     current
    DESCRIPTION
        ""
    ::= { lcosLXSetupWLANHotspot 1 }

-- {INDEX} 13.2.20.12.1
lcosLXSetupWLANHotspotHotspotsEntry OBJECT-TYPE
    SYNTAX     LcosLXSetupWLANHotspotHotspotsEntry
    MAX-ACCESS not-accessible
    STATUS     current
    DESCRIPTION
        ""
    INDEX {
        lcosLXSetupWLANHotspotHotspotsEntryName
    }
    ::= { lcosLXSetupWLANHotspotHotspots 1 }

-- {SEQUENCE} 13.2.20.12.1
LcosLXSetupWLANHotspotHotspotsEntry ::= SEQUENCE {
    lcosLXSetupWLANHotspotHotspotsEntryName OCTET STRING,
    lcosLXSetupWLANHotspotHotspotsEntryURL OCTET STRING,
    lcosLXSetupWLANHotspotHotspotsEntryRevisionID OCTET STRING,
    lcosLXSetupWLANHotspotHotspotsEntryPrivateNetwork INTEGER,
    lcosLXSetupWLANHotspotHotspotsEntryDHCPRangeStart OCTET STRING,
    lcosLXSetupWLANHotspotHotspotsEntryDHCPRangeEnd OCTET STRING
}

-- {COLUMN} 13.2.20.12.1.1.1
lcosLXSetupWLANHotspotHotspotsEntryName OBJECT-TYPE
    SYNTAX     OCTET STRING (SIZE(0..32))
    MAX-ACCESS not-accessible
    STATUS     current
    DESCRIPTION
        ""
    ::= { lcosLXSetupWLANHotspotHotspotsEntry 1 }

-- {COLUMN} 13.2.20.12.1.1.2
lcosLXSetupWLANHotspotHotspotsEntryURL OBJECT-TYPE
    SYNTAX     OCTET STRING (SIZE(0..255))
    MAX-ACCESS read-only
    STATUS     current
    DESCRIPTION
        ""
    ::= { lcosLXSetupWLANHotspotHotspotsEntry 2 }

-- {COLUMN} 13.2.20.12.1.1.3
lcosLXSetupWLANHotspotHotspotsEntryRevisionID OBJECT-TYPE
    SYNTAX     OCTET STRING (SIZE(0..36))
    MAX-ACCESS read-only
    STATUS     current
    DESCRIPTION
        ""
    ::= { lcosLXSetupWLANHotspotHotspotsEntry 3 }

-- {COLUMN} 13.2.20.12.1.1.4
lcosLXSetupWLANHotspotHotspotsEntryPrivateNetwork OBJECT-TYPE
    SYNTAX     INTEGER {
                  eNo(0),
                  eYes(1)
               }
    MAX-ACCESS read-only
    STATUS     current
    DESCRIPTION
        ""
    ::= { lcosLXSetupWLANHotspotHotspotsEntry 4 }

-- {COLUMN} 13.2.20.12.1.1.5
lcosLXSetupWLANHotspotHotspotsEntryDHCPRangeStart OBJECT-TYPE
    SYNTAX     OCTET STRING (SIZE(0..32))
    MAX-ACCESS read-only
    STATUS     current
    DESCRIPTION
        ""
    ::= { lcosLXSetupWLANHotspotHotspotsEntry 5 }

-- {COLUMN} 13.2.20.12.1.1.6
lcosLXSetupWLANHotspotHotspotsEntryDHCPRangeEnd OBJECT-TYPE
    SYNTAX     OCTET STRING (SIZE(0..32))
    MAX-ACCESS read-only
    STATUS     current
    DESCRIPTION
        ""
    ::= { lcosLXSetupWLANHotspotHotspotsEntry 6 }

-- {TABLE} 13.2.20.12.2
lcosLXSetupWLANHotspotWalledGarden OBJECT-TYPE
    SYNTAX     SEQUENCE OF LcosLXSetupWLANHotspotWalledGardenEntry
    MAX-ACCESS not-accessible
    STATUS     current
    DESCRIPTION
        ""
    ::= { lcosLXSetupWLANHotspot 2 }

-- {INDEX} 13.2.20.12.2
lcosLXSetupWLANHotspotWalledGardenEntry OBJECT-TYPE
    SYNTAX     LcosLXSetupWLANHotspotWalledGardenEntry
    MAX-ACCESS not-accessible
    STATUS     current
    DESCRIPTION
        ""
    INDEX {
        lcosLXSetupWLANHotspotWalledGardenEntryHotspot,
        lcosLXSetupWLANHotspotWalledGardenEntryHostname
    }
    ::= { lcosLXSetupWLANHotspotWalledGarden 1 }

-- {SEQUENCE} 13.2.20.12.2
LcosLXSetupWLANHotspotWalledGardenEntry ::= SEQUENCE {
    lcosLXSetupWLANHotspotWalledGardenEntryHotspot OCTET STRING,
    lcosLXSetupWLANHotspotWalledGardenEntryHostname OCTET STRING,
    lcosLXSetupWLANHotspotWalledGardenEntryLMCunreachableonly INTEGER
}

-- {COLUMN} 13.2.20.12.2.1.1
lcosLXSetupWLANHotspotWalledGardenEntryHotspot OBJECT-TYPE
    SYNTAX     OCTET STRING (SIZE(0..32))
    MAX-ACCESS not-accessible
    STATUS     current
    DESCRIPTION
        ""
    ::= { lcosLXSetupWLANHotspotWalledGardenEntry 1 }

-- {COLUMN} 13.2.20.12.2.1.2
lcosLXSetupWLANHotspotWalledGardenEntryHostname OBJECT-TYPE
    SYNTAX     OCTET STRING (SIZE(0..255))
    MAX-ACCESS not-accessible
    STATUS     current
    DESCRIPTION
        ""
    ::= { lcosLXSetupWLANHotspotWalledGardenEntry 2 }

-- {COLUMN} 13.2.20.12.2.1.3
lcosLXSetupWLANHotspotWalledGardenEntryLMCunreachableonly OBJECT-TYPE
    SYNTAX     INTEGER {
                  eNo(0),
                  eYes(1)
               }
    MAX-ACCESS read-only
    STATUS     current
    DESCRIPTION
        ""
    ::= { lcosLXSetupWLANHotspotWalledGardenEntry 3 }

-- {OID} 13.2.20.13
lcosLXSetupWLANWDS OBJECT IDENTIFIER ::= { lcosLXSetupWLAN 13 }

-- {TABLE} 13.2.20.13.1
lcosLXSetupWLANWDSLinks OBJECT-TYPE
    SYNTAX     SEQUENCE OF LcosLXSetupWLANWDSLinksEntry
    MAX-ACCESS not-accessible
    STATUS     current
    DESCRIPTION
        ""
    ::= { lcosLXSetupWLANWDS 1 }

-- {INDEX} 13.2.20.13.1
lcosLXSetupWLANWDSLinksEntry OBJECT-TYPE
    SYNTAX     LcosLXSetupWLANWDSLinksEntry
    MAX-ACCESS not-accessible
    STATUS     current
    DESCRIPTION
        ""
    INDEX {
        lcosLXSetupWLANWDSLinksEntryLinkName
    }
    ::= { lcosLXSetupWLANWDSLinks 1 }

-- {SEQUENCE} 13.2.20.13.1
LcosLXSetupWLANWDSLinksEntry ::= SEQUENCE {
    lcosLXSetupWLANWDSLinksEntryLinkName OCTET STRING,
    lcosLXSetupWLANWDSLinksEntrySSIDName OCTET STRING,
    lcosLXSetupWLANWDSLinksEntryMode INTEGER,
    lcosLXSetupWLANWDSLinksEntryRadio INTEGER,
    lcosLXSetupWLANWDSLinksEntryEncryptionProfile OCTET STRING,
    lcosLXSetupWLANWDSLinksEntryEncryptionKey OCTET STRING,
    lcosLXSetupWLANWDSLinksEntryAdditionalVLANs OCTET STRING,
    lcosLXSetupWLANWDSLinksEntryLCOSClientBridgeSupport INTEGER,
    lcosLXSetupWLANWDSLinksEntryAdditionalUntaggedVLAN INTEGER,
    lcosLXSetupWLANWDSLinksEntryRoamingProfile OCTET STRING
}

-- {COLUMN} 13.2.20.13.1.1.1
lcosLXSetupWLANWDSLinksEntryLinkName OBJECT-TYPE
    SYNTAX     OCTET STRING (SIZE(0..64))
    MAX-ACCESS not-accessible
    STATUS     current
    DESCRIPTION
        ""
    ::= { lcosLXSetupWLANWDSLinksEntry 1 }

-- {COLUMN} 13.2.20.13.1.1.2
lcosLXSetupWLANWDSLinksEntrySSIDName OBJECT-TYPE
    SYNTAX     OCTET STRING (SIZE(0..32))
    MAX-ACCESS read-only
    STATUS     current
    DESCRIPTION
        ""
    ::= { lcosLXSetupWLANWDSLinksEntry 2 }

-- {COLUMN} 13.2.20.13.1.1.3
lcosLXSetupWLANWDSLinksEntryMode OBJECT-TYPE
    SYNTAX     INTEGER {
                  eAccessPoint(0),
                  eStation(1),
                  eLegacyStation(2)
               }
    MAX-ACCESS read-only
    STATUS     current
    DESCRIPTION
        ""
    ::= { lcosLXSetupWLANWDSLinksEntry 3 }

-- {COLUMN} 13.2.20.13.1.1.4
lcosLXSetupWLANWDSLinksEntryRadio OBJECT-TYPE
    SYNTAX     INTEGER {
                  e24GHz(1),
                  e5GHz(2),
                  e6GHz(3)
               }
    MAX-ACCESS read-only
    STATUS     current
    DESCRIPTION
        ""
    ::= { lcosLXSetupWLANWDSLinksEntry 4 }

-- {COLUMN} 13.2.20.13.1.1.5
lcosLXSetupWLANWDSLinksEntryEncryptionProfile OBJECT-TYPE
    SYNTAX     OCTET STRING (SIZE(0..128))
    MAX-ACCESS read-only
    STATUS     current
    DESCRIPTION
        ""
    ::= { lcosLXSetupWLANWDSLinksEntry 5 }

-- {COLUMN} 13.2.20.13.1.1.6
lcosLXSetupWLANWDSLinksEntryEncryptionKey OBJECT-TYPE
    SYNTAX     OCTET STRING (SIZE(0..63))
    MAX-ACCESS read-only
    STATUS     current
    DESCRIPTION
        ""
    ::= { lcosLXSetupWLANWDSLinksEntry 6 }

-- {COLUMN} 13.2.20.13.1.1.8
lcosLXSetupWLANWDSLinksEntryAdditionalVLANs OBJECT-TYPE
    SYNTAX     OCTET STRING (SIZE(0..128))
    MAX-ACCESS read-only
    STATUS     current
    DESCRIPTION
        ""
    ::= { lcosLXSetupWLANWDSLinksEntry 8 }

-- {COLUMN} 13.2.20.13.1.1.9
lcosLXSetupWLANWDSLinksEntryLCOSClientBridgeSupport OBJECT-TYPE
    SYNTAX     INTEGER {
                  eNo(0),
                  eYes(1)
               }
    MAX-ACCESS read-only
    STATUS     current
    DESCRIPTION
        ""
    ::= { lcosLXSetupWLANWDSLinksEntry 9 }

-- {COLUMN} 13.2.20.13.1.1.10
lcosLXSetupWLANWDSLinksEntryAdditionalUntaggedVLAN OBJECT-TYPE
    SYNTAX     INTEGER {
                  eNo(0),
                  eYes(1)
               }
    MAX-ACCESS read-only
    STATUS     current
    DESCRIPTION
        ""
    ::= { lcosLXSetupWLANWDSLinksEntry 10 }

-- {COLUMN} 13.2.20.13.1.1.11
lcosLXSetupWLANWDSLinksEntryRoamingProfile OBJECT-TYPE
    SYNTAX     OCTET STRING (SIZE(0..128))
    MAX-ACCESS read-only
    STATUS     current
    DESCRIPTION
        ""
    ::= { lcosLXSetupWLANWDSLinksEntry 11 }

-- {TABLE} 13.2.20.13.2
lcosLXSetupWLANWDSEncryption OBJECT-TYPE
    SYNTAX     SEQUENCE OF LcosLXSetupWLANWDSEncryptionEntry
    MAX-ACCESS not-accessible
    STATUS     current
    DESCRIPTION
        ""
    ::= { lcosLXSetupWLANWDS 2 }

-- {INDEX} 13.2.20.13.2
lcosLXSetupWLANWDSEncryptionEntry OBJECT-TYPE
    SYNTAX     LcosLXSetupWLANWDSEncryptionEntry
    MAX-ACCESS not-accessible
    STATUS     current
    DESCRIPTION
        ""
    INDEX {
        lcosLXSetupWLANWDSEncryptionEntryProfileName
    }
    ::= { lcosLXSetupWLANWDSEncryption 1 }

-- {SEQUENCE} 13.2.20.13.2
LcosLXSetupWLANWDSEncryptionEntry ::= SEQUENCE {
    lcosLXSetupWLANWDSEncryptionEntryProfileName OCTET STRING,
    lcosLXSetupWLANWDSEncryptionEntryMethod INTEGER,
    lcosLXSetupWLANWDSEncryptionEntryWPAVersion INTEGER,
    lcosLXSetupWLANWDSEncryptionEntryWPA1SessionKeytypes INTEGER,
    lcosLXSetupWLANWDSEncryptionEntryWPA23SessionKeytypes INTEGER,
    lcosLXSetupWLANWDSEncryptionEntryRADIUSClientProfile OCTET STRING
}

-- {COLUMN} 13.2.20.13.2.1.1
lcosLXSetupWLANWDSEncryptionEntryProfileName OBJECT-TYPE
    SYNTAX     OCTET STRING (SIZE(0..128))
    MAX-ACCESS not-accessible
    STATUS     current
    DESCRIPTION
        ""
    ::= { lcosLXSetupWLANWDSEncryptionEntry 1 }

-- {COLUMN} 13.2.20.13.2.1.2
lcosLXSetupWLANWDSEncryptionEntryMethod OBJECT-TYPE
    SYNTAX     INTEGER {
                  e80211iWPAPSK(32),
                  e80211iWPA8021X(33)
               }
    MAX-ACCESS read-only
    STATUS     current
    DESCRIPTION
        ""
    ::= { lcosLXSetupWLANWDSEncryptionEntry 2 }

-- {COLUMN} 13.2.20.13.2.1.3
lcosLXSetupWLANWDSEncryptionEntryWPAVersion OBJECT-TYPE
    SYNTAX     INTEGER {
                  eWPA1(2),
                  eWPA2(4),
                  eWPA12(6),
                  eWPA3(8),
                  eWPA23(12)
               }
    MAX-ACCESS read-only
    STATUS     current
    DESCRIPTION
        ""
    ::= { lcosLXSetupWLANWDSEncryptionEntry 3 }

-- {COLUMN} 13.2.20.13.2.1.4
lcosLXSetupWLANWDSEncryptionEntryWPA1SessionKeytypes OBJECT-TYPE
    SYNTAX     INTEGER {
                  eTKIP(1),
                  eAES(2),
                  eTKIPAES(3)
               }
    MAX-ACCESS read-only
    STATUS     current
    DESCRIPTION
        ""
    ::= { lcosLXSetupWLANWDSEncryptionEntry 4 }

-- {COLUMN} 13.2.20.13.2.1.5
lcosLXSetupWLANWDSEncryptionEntryWPA23SessionKeytypes OBJECT-TYPE
    SYNTAX     INTEGER {
                  eTKIP(1),
                  eAES(2),
                  eTKIPAES(3)
               }
    MAX-ACCESS read-only
    STATUS     current
    DESCRIPTION
        ""
    ::= { lcosLXSetupWLANWDSEncryptionEntry 5 }

-- {COLUMN} 13.2.20.13.2.1.6
lcosLXSetupWLANWDSEncryptionEntryRADIUSClientProfile OBJECT-TYPE
    SYNTAX     OCTET STRING (SIZE(0..64))
    MAX-ACCESS read-only
    STATUS     current
    DESCRIPTION
        ""
    ::= { lcosLXSetupWLANWDSEncryptionEntry 6 }

-- {TABLE} 13.2.20.13.3
lcosLXSetupWLANWDSRoaming OBJECT-TYPE
    SYNTAX     SEQUENCE OF LcosLXSetupWLANWDSRoamingEntry
    MAX-ACCESS not-accessible
    STATUS     current
    DESCRIPTION
        ""
    ::= { lcosLXSetupWLANWDS 3 }

-- {INDEX} 13.2.20.13.3
lcosLXSetupWLANWDSRoamingEntry OBJECT-TYPE
    SYNTAX     LcosLXSetupWLANWDSRoamingEntry
    MAX-ACCESS not-accessible
    STATUS     current
    DESCRIPTION
        ""
    INDEX {
        lcosLXSetupWLANWDSRoamingEntryProfileName
    }
    ::= { lcosLXSetupWLANWDSRoaming 1 }

-- {SEQUENCE} 13.2.20.13.3
LcosLXSetupWLANWDSRoamingEntry ::= SEQUENCE {
    lcosLXSetupWLANWDSRoamingEntryProfileName OCTET STRING,
    lcosLXSetupWLANWDSRoamingEntrySignalStrengthThreshold Integer32,
    lcosLXSetupWLANWDSRoamingEntryGoodSignalScanInterval Unsigned32,
    lcosLXSetupWLANWDSRoamingEntryBadSignalScanInterval Unsigned32
}

-- {COLUMN} 13.2.20.13.3.1.1
lcosLXSetupWLANWDSRoamingEntryProfileName OBJECT-TYPE
    SYNTAX     OCTET STRING (SIZE(0..128))
    MAX-ACCESS not-accessible
    STATUS     current
    DESCRIPTION
        ""
    ::= { lcosLXSetupWLANWDSRoamingEntry 1 }

-- {COLUMN} 13.2.20.13.3.1.2
lcosLXSetupWLANWDSRoamingEntrySignalStrengthThreshold OBJECT-TYPE
    SYNTAX     Integer32 (-128..127)
    MAX-ACCESS read-only
    STATUS     current
    DESCRIPTION
        ""
    ::= { lcosLXSetupWLANWDSRoamingEntry 2 }

-- {COLUMN} 13.2.20.13.3.1.3
lcosLXSetupWLANWDSRoamingEntryGoodSignalScanInterval OBJECT-TYPE
    SYNTAX     Unsigned32 (0..4294967295)
    MAX-ACCESS read-only
    STATUS     current
    DESCRIPTION
        ""
    ::= { lcosLXSetupWLANWDSRoamingEntry 3 }

-- {COLUMN} 13.2.20.13.3.1.4
lcosLXSetupWLANWDSRoamingEntryBadSignalScanInterval OBJECT-TYPE
    SYNTAX     Unsigned32 (0..4294967295)
    MAX-ACCESS read-only
    STATUS     current
    DESCRIPTION
        ""
    ::= { lcosLXSetupWLANWDSRoamingEntry 4 }

-- {SCALAR} 13.2.20.14
lcosLXSetupWLANIncludeUUID OBJECT-TYPE
    SYNTAX     INTEGER {
                  eNo(0),
                  eYes(1)
               }
    MAX-ACCESS read-only
    STATUS     current
    DESCRIPTION
        ""
    ::= { lcosLXSetupWLAN 14 }

-- {SCALAR} 13.2.20.15
lcosLXSetupWLANPowerSavingMode OBJECT-TYPE
    SYNTAX     INTEGER {
                  eNo(0),
                  eYes(1)
               }
    MAX-ACCESS read-only
    STATUS     current
    DESCRIPTION
        ""
    ::= { lcosLXSetupWLAN 15 }

-- {SCALAR} 13.2.20.16
lcosLXSetupWLANIncludeDevicename OBJECT-TYPE
    SYNTAX     INTEGER {
                  eNo(0),
                  eYes(1)
               }
    MAX-ACCESS read-only
    STATUS     current
    DESCRIPTION
        ""
    ::= { lcosLXSetupWLAN 16 }

-- {SCALAR} 13.2.20.17
lcosLXSetupWLANUseScanRadio OBJECT-TYPE
    SYNTAX     INTEGER {
                  eNo(0),
                  eYes(1)
               }
    MAX-ACCESS read-only
    STATUS     current
    DESCRIPTION
        ""
    ::= { lcosLXSetupWLAN 17 }

-- {OID} 13.2.20.133
lcosLXSetupWLANLEPS OBJECT IDENTIFIER ::= { lcosLXSetupWLAN 133 }

-- {SCALAR} 13.2.20.133.1
lcosLXSetupWLANLEPSOperating OBJECT-TYPE
    SYNTAX     INTEGER {
                  eNo(0),
                  eYes(1)
               }
    MAX-ACCESS read-only
    STATUS     current
    DESCRIPTION
        ""
    ::= { lcosLXSetupWLANLEPS 1 }

-- {TABLE} 13.2.20.133.2
lcosLXSetupWLANLEPSProfiles OBJECT-TYPE
    SYNTAX     SEQUENCE OF LcosLXSetupWLANLEPSProfilesEntry
    MAX-ACCESS not-accessible
    STATUS     current
    DESCRIPTION
        ""
    ::= { lcosLXSetupWLANLEPS 2 }

-- {INDEX} 13.2.20.133.2
lcosLXSetupWLANLEPSProfilesEntry OBJECT-TYPE
    SYNTAX     LcosLXSetupWLANLEPSProfilesEntry
    MAX-ACCESS not-accessible
    STATUS     current
    DESCRIPTION
        ""
    INDEX {
        lcosLXSetupWLANLEPSProfilesEntryName
    }
    ::= { lcosLXSetupWLANLEPSProfiles 1 }

-- {SEQUENCE} 13.2.20.133.2
LcosLXSetupWLANLEPSProfilesEntry ::= SEQUENCE {
    lcosLXSetupWLANLEPSProfilesEntryName OCTET STRING,
    lcosLXSetupWLANLEPSProfilesEntryNetworkName OCTET STRING,
    lcosLXSetupWLANLEPSProfilesEntryMACList INTEGER,
    lcosLXSetupWLANLEPSProfilesEntryVLAN Unsigned32
}

-- {COLUMN} 13.2.20.133.2.1.1
lcosLXSetupWLANLEPSProfilesEntryName OBJECT-TYPE
    SYNTAX     OCTET STRING (SIZE(0..32))
    MAX-ACCESS not-accessible
    STATUS     current
    DESCRIPTION
        ""
    ::= { lcosLXSetupWLANLEPSProfilesEntry 1 }

-- {COLUMN} 13.2.20.133.2.1.2
lcosLXSetupWLANLEPSProfilesEntryNetworkName OBJECT-TYPE
    SYNTAX     OCTET STRING (SIZE(0..64))
    MAX-ACCESS read-only
    STATUS     current
    DESCRIPTION
        ""
    ::= { lcosLXSetupWLANLEPSProfilesEntry 2 }

-- {COLUMN} 13.2.20.133.2.1.3
lcosLXSetupWLANLEPSProfilesEntryMACList OBJECT-TYPE
    SYNTAX     INTEGER {
                  eDisabled(0),
                  eWhitelist(1),
                  eBlacklist(2)
               }
    MAX-ACCESS read-only
    STATUS     current
    DESCRIPTION
        ""
    ::= { lcosLXSetupWLANLEPSProfilesEntry 3 }

-- {COLUMN} 13.2.20.133.2.1.4
lcosLXSetupWLANLEPSProfilesEntryVLAN OBJECT-TYPE
    SYNTAX     Unsigned32 (0..65535)
    MAX-ACCESS read-only
    STATUS     current
    DESCRIPTION
        ""
    ::= { lcosLXSetupWLANLEPSProfilesEntry 4 }

-- {TABLE} 13.2.20.133.3
lcosLXSetupWLANLEPSUsers OBJECT-TYPE
    SYNTAX     SEQUENCE OF LcosLXSetupWLANLEPSUsersEntry
    MAX-ACCESS not-accessible
    STATUS     current
    DESCRIPTION
        ""
    ::= { lcosLXSetupWLANLEPS 3 }

-- {INDEX} 13.2.20.133.3
lcosLXSetupWLANLEPSUsersEntry OBJECT-TYPE
    SYNTAX     LcosLXSetupWLANLEPSUsersEntry
    MAX-ACCESS not-accessible
    STATUS     current
    DESCRIPTION
        ""
    INDEX {
        lcosLXSetupWLANLEPSUsersEntryName
    }
    ::= { lcosLXSetupWLANLEPSUsers 1 }

-- {SEQUENCE} 13.2.20.133.3
LcosLXSetupWLANLEPSUsersEntry ::= SEQUENCE {
    lcosLXSetupWLANLEPSUsersEntryName OCTET STRING,
    lcosLXSetupWLANLEPSUsersEntryProfile OCTET STRING,
    lcosLXSetupWLANLEPSUsersEntryWPAPassphrase OCTET STRING,
    lcosLXSetupWLANLEPSUsersEntryVLAN Unsigned32,
    lcosLXSetupWLANLEPSUsersEntryMACAddress MacAddress
}

-- {COLUMN} 13.2.20.133.3.1.1
lcosLXSetupWLANLEPSUsersEntryName OBJECT-TYPE
    SYNTAX     OCTET STRING (SIZE(0..31))
    MAX-ACCESS not-accessible
    STATUS     current
    DESCRIPTION
        ""
    ::= { lcosLXSetupWLANLEPSUsersEntry 1 }

-- {COLUMN} 13.2.20.133.3.1.2
lcosLXSetupWLANLEPSUsersEntryProfile OBJECT-TYPE
    SYNTAX     OCTET STRING (SIZE(0..32))
    MAX-ACCESS read-only
    STATUS     current
    DESCRIPTION
        ""
    ::= { lcosLXSetupWLANLEPSUsersEntry 2 }

-- {COLUMN} 13.2.20.133.3.1.3
lcosLXSetupWLANLEPSUsersEntryWPAPassphrase OBJECT-TYPE
    SYNTAX     OCTET STRING (SIZE(0..63))
    MAX-ACCESS read-only
    STATUS     current
    DESCRIPTION
        ""
    ::= { lcosLXSetupWLANLEPSUsersEntry 3 }

-- {COLUMN} 13.2.20.133.3.1.4
lcosLXSetupWLANLEPSUsersEntryVLAN OBJECT-TYPE
    SYNTAX     Unsigned32 (0..65535)
    MAX-ACCESS read-only
    STATUS     current
    DESCRIPTION
        ""
    ::= { lcosLXSetupWLANLEPSUsersEntry 4 }

-- {COLUMN} 13.2.20.133.3.1.7
lcosLXSetupWLANLEPSUsersEntryMACAddress OBJECT-TYPE
    SYNTAX     MacAddress
    MAX-ACCESS read-only
    STATUS     current
    DESCRIPTION
        ""
    ::= { lcosLXSetupWLANLEPSUsersEntry 7 }

-- {TABLE} 13.2.20.1111
lcosLXSetupWLANRateSelection OBJECT-TYPE
    SYNTAX     SEQUENCE OF LcosLXSetupWLANRateSelectionEntry
    MAX-ACCESS not-accessible
    STATUS     current
    DESCRIPTION
        ""
    ::= { lcosLXSetupWLAN 1111 }

-- {INDEX} 13.2.20.1111
lcosLXSetupWLANRateSelectionEntry OBJECT-TYPE
    SYNTAX     LcosLXSetupWLANRateSelectionEntry
    MAX-ACCESS not-accessible
    STATUS     current
    DESCRIPTION
        ""
    INDEX {
        lcosLXSetupWLANRateSelectionEntryNetworkName,
        lcosLXSetupWLANRateSelectionEntryRadioband
    }
    ::= { lcosLXSetupWLANRateSelection 1 }

-- {SEQUENCE} 13.2.20.1111
LcosLXSetupWLANRateSelectionEntry ::= SEQUENCE {
    lcosLXSetupWLANRateSelectionEntryNetworkName OCTET STRING,
    lcosLXSetupWLANRateSelectionEntryBroadcastRate INTEGER,
    lcosLXSetupWLANRateSelectionEntryMulticastRate INTEGER,
    lcosLXSetupWLANRateSelectionEntryBeaconRate INTEGER,
    lcosLXSetupWLANRateSelectionEntryBasicRates BITS,
    lcosLXSetupWLANRateSelectionEntrySupportedRates BITS,
    lcosLXSetupWLANRateSelectionEntryRadioband INTEGER
}

-- {COLUMN} 13.2.20.1111.1.1
lcosLXSetupWLANRateSelectionEntryNetworkName OBJECT-TYPE
    SYNTAX     OCTET STRING (SIZE(0..64))
    MAX-ACCESS not-accessible
    STATUS     current
    DESCRIPTION
        ""
    ::= { lcosLXSetupWLANRateSelectionEntry 1 }

-- {COLUMN} 13.2.20.1111.1.23
lcosLXSetupWLANRateSelectionEntryBroadcastRate OBJECT-TYPE
    SYNTAX     INTEGER {
                  edefault(0),
                  e1Mbps(1000),
                  e2Mbps(2000),
                  e55Mbps(5500),
                  e11Mbps(11000),
                  e6Mbps(6000),
                  e9Mbps(9000),
                  e12Mbps(12000),
                  e18Mbps(18000),
                  e24Mbps(24000),
                  e36Mbps(36000),
                  e48Mbps(48000),
                  e54Mbps(54000)
               }
    MAX-ACCESS read-only
    STATUS     current
    DESCRIPTION
        ""
    ::= { lcosLXSetupWLANRateSelectionEntry 23 }

-- {COLUMN} 13.2.20.1111.1.24
lcosLXSetupWLANRateSelectionEntryMulticastRate OBJECT-TYPE
    SYNTAX     INTEGER {
                  edefault(0),
                  e1Mbps(1000),
                  e2Mbps(2000),
                  e55Mbps(5500),
                  e11Mbps(11000),
                  e6Mbps(6000),
                  e9Mbps(9000),
                  e12Mbps(12000),
                  e18Mbps(18000),
                  e24Mbps(24000),
                  e36Mbps(36000),
                  e48Mbps(48000),
                  e54Mbps(54000)
               }
    MAX-ACCESS read-only
    STATUS     current
    DESCRIPTION
        ""
    ::= { lcosLXSetupWLANRateSelectionEntry 24 }

-- {COLUMN} 13.2.20.1111.1.25
lcosLXSetupWLANRateSelectionEntryBeaconRate OBJECT-TYPE
    SYNTAX     INTEGER {
                  edefault(0),
                  e1Mbps(1000),
                  e2Mbps(2000),
                  e55Mbps(5500),
                  e11Mbps(11000),
                  e6Mbps(6000),
                  e9Mbps(9000),
                  e12Mbps(12000),
                  e18Mbps(18000),
                  e24Mbps(24000),
                  e36Mbps(36000),
                  e48Mbps(48000),
                  e54Mbps(54000)
               }
    MAX-ACCESS read-only
    STATUS     current
    DESCRIPTION
        ""
    ::= { lcosLXSetupWLANRateSelectionEntry 25 }

-- {COLUMN} 13.2.20.1111.1.26
lcosLXSetupWLANRateSelectionEntryBasicRates OBJECT-TYPE
    SYNTAX     BITS {
                  e1Mbps(0),
                  e2Mbps(1),
                  e55Mbps(2),
                  e11Mbps(3),
                  e6Mbps(4),
                  e9Mbps(5),
                  e12Mbps(6),
                  e18Mbps(7),
                  e24Mbps(8),
                  e36Mbps(9),
                  e48Mbps(10),
                  e54Mbps(11)
               }
    MAX-ACCESS read-only
    STATUS     current
    DESCRIPTION
        ""
    ::= { lcosLXSetupWLANRateSelectionEntry 26 }

-- {COLUMN} 13.2.20.1111.1.27
lcosLXSetupWLANRateSelectionEntrySupportedRates OBJECT-TYPE
    SYNTAX     BITS {
                  e1Mbps(0),
                  e2Mbps(1),
                  e55Mbps(2),
                  e11Mbps(3),
                  e6Mbps(4),
                  e9Mbps(5),
                  e12Mbps(6),
                  e18Mbps(7),
                  e24Mbps(8),
                  e36Mbps(9),
                  e48Mbps(10),
                  e54Mbps(11)
               }
    MAX-ACCESS read-only
    STATUS     current
    DESCRIPTION
        ""
    ::= { lcosLXSetupWLANRateSelectionEntry 27 }

-- {COLUMN} 13.2.20.1111.1.101
lcosLXSetupWLANRateSelectionEntryRadioband OBJECT-TYPE
    SYNTAX     INTEGER {
                  e24GHz5GHz(1),
                  e24GHz(2),
                  e5GHz(3),
                  enone(4),
                  e24GHz5GHz6GHz(5),
                  e24GHz6GHz(6),
                  e5GHz6GHz(7),
                  e6GHz(8)
               }
    MAX-ACCESS not-accessible
    STATUS     current
    DESCRIPTION
        ""
    ::= { lcosLXSetupWLANRateSelectionEntry 101 }

-- {OID} 13.2.22
lcosLXSetupSyslog OBJECT IDENTIFIER ::= { lcosLXSetup 22 }

-- {TABLE} 13.2.22.2
lcosLXSetupSyslogServer OBJECT-TYPE
    SYNTAX     SEQUENCE OF LcosLXSetupSyslogServerEntry
    MAX-ACCESS not-accessible
    STATUS     current
    DESCRIPTION
        ""
    ::= { lcosLXSetupSyslog 2 }

-- {INDEX} 13.2.22.2
lcosLXSetupSyslogServerEntry OBJECT-TYPE
    SYNTAX     LcosLXSetupSyslogServerEntry
    MAX-ACCESS not-accessible
    STATUS     current
    DESCRIPTION
        ""
    INDEX {
        lcosLXSetupSyslogServerEntryName
    }
    ::= { lcosLXSetupSyslogServer 1 }

-- {SEQUENCE} 13.2.22.2
LcosLXSetupSyslogServerEntry ::= SEQUENCE {
    lcosLXSetupSyslogServerEntryName OCTET STRING,
    lcosLXSetupSyslogServerEntryIPAddress OCTET STRING,
    lcosLXSetupSyslogServerEntryPort Unsigned32,
    lcosLXSetupSyslogServerEntryProtocol INTEGER
}

-- {COLUMN} 13.2.22.2.1.1
lcosLXSetupSyslogServerEntryName OBJECT-TYPE
    SYNTAX     OCTET STRING (SIZE(0..32))
    MAX-ACCESS not-accessible
    STATUS     current
    DESCRIPTION
        ""
    ::= { lcosLXSetupSyslogServerEntry 1 }

-- {COLUMN} 13.2.22.2.1.7
lcosLXSetupSyslogServerEntryIPAddress OBJECT-TYPE
    SYNTAX     OCTET STRING (SIZE(0..64))
    MAX-ACCESS read-only
    STATUS     current
    DESCRIPTION
        ""
    ::= { lcosLXSetupSyslogServerEntry 7 }

-- {COLUMN} 13.2.22.2.1.8
lcosLXSetupSyslogServerEntryPort OBJECT-TYPE
    SYNTAX     Unsigned32 (0..65535)
    MAX-ACCESS read-only
    STATUS     current
    DESCRIPTION
        ""
    ::= { lcosLXSetupSyslogServerEntry 8 }

-- {COLUMN} 13.2.22.2.1.9
lcosLXSetupSyslogServerEntryProtocol OBJECT-TYPE
    SYNTAX     INTEGER {
                  eTCP(1),
                  eUDP(2)
               }
    MAX-ACCESS read-only
    STATUS     current
    DESCRIPTION
        ""
    ::= { lcosLXSetupSyslogServerEntry 9 }

-- {OID} 13.2.30
lcosLXSetupRADIUS OBJECT IDENTIFIER ::= { lcosLXSetup 30 }

-- {TABLE} 13.2.30.3
lcosLXSetupRADIUSRADIUSServer OBJECT-TYPE
    SYNTAX     SEQUENCE OF LcosLXSetupRADIUSRADIUSServerEntry
    MAX-ACCESS not-accessible
    STATUS     current
    DESCRIPTION
        ""
    ::= { lcosLXSetupRADIUS 3 }

-- {INDEX} 13.2.30.3
lcosLXSetupRADIUSRADIUSServerEntry OBJECT-TYPE
    SYNTAX     LcosLXSetupRADIUSRADIUSServerEntry
    MAX-ACCESS not-accessible
    STATUS     current
    DESCRIPTION
        ""
    INDEX {
        lcosLXSetupRADIUSRADIUSServerEntryName
    }
    ::= { lcosLXSetupRADIUSRADIUSServer 1 }

-- {SEQUENCE} 13.2.30.3
LcosLXSetupRADIUSRADIUSServerEntry ::= SEQUENCE {
    lcosLXSetupRADIUSRADIUSServerEntryName OCTET STRING,
    lcosLXSetupRADIUSRADIUSServerEntryPort Unsigned32,
    lcosLXSetupRADIUSRADIUSServerEntrySecret OCTET STRING,
    lcosLXSetupRADIUSRADIUSServerEntryBackup OCTET STRING,
    lcosLXSetupRADIUSRADIUSServerEntryServerIPAddress OCTET STRING,
    lcosLXSetupRADIUSRADIUSServerEntryAccountingPort Unsigned32,
    lcosLXSetupRADIUSRADIUSServerEntryAccountingIPAddress OCTET STRING,
    lcosLXSetupRADIUSRADIUSServerEntryMACCheck INTEGER,
    lcosLXSetupRADIUSRADIUSServerEntryFallbackDynamicVLANID Unsigned32,
    lcosLXSetupRADIUSRADIUSServerEntryRequireMessageAuthenticator INTEGER
}

-- {COLUMN} 13.2.30.3.1.1
lcosLXSetupRADIUSRADIUSServerEntryName OBJECT-TYPE
    SYNTAX     OCTET STRING (SIZE(0..64))
    MAX-ACCESS not-accessible
    STATUS     current
    DESCRIPTION
        ""
    ::= { lcosLXSetupRADIUSRADIUSServerEntry 1 }

-- {COLUMN} 13.2.30.3.1.3
lcosLXSetupRADIUSRADIUSServerEntryPort OBJECT-TYPE
    SYNTAX     Unsigned32 (0..65535)
    MAX-ACCESS read-only
    STATUS     current
    DESCRIPTION
        ""
    ::= { lcosLXSetupRADIUSRADIUSServerEntry 3 }

-- {COLUMN} 13.2.30.3.1.4
lcosLXSetupRADIUSRADIUSServerEntrySecret OBJECT-TYPE
    SYNTAX     OCTET STRING (SIZE(0..64))
    MAX-ACCESS read-only
    STATUS     current
    DESCRIPTION
        ""
    ::= { lcosLXSetupRADIUSRADIUSServerEntry 4 }

-- {COLUMN} 13.2.30.3.1.5
lcosLXSetupRADIUSRADIUSServerEntryBackup OBJECT-TYPE
    SYNTAX     OCTET STRING (SIZE(0..64))
    MAX-ACCESS read-only
    STATUS     current
    DESCRIPTION
        ""
    ::= { lcosLXSetupRADIUSRADIUSServerEntry 5 }

-- {COLUMN} 13.2.30.3.1.8
lcosLXSetupRADIUSRADIUSServerEntryServerIPAddress OBJECT-TYPE
    SYNTAX     OCTET STRING (SIZE(0..64))
    MAX-ACCESS read-only
    STATUS     current
    DESCRIPTION
        ""
    ::= { lcosLXSetupRADIUSRADIUSServerEntry 8 }

-- {COLUMN} 13.2.30.3.1.9
lcosLXSetupRADIUSRADIUSServerEntryAccountingPort OBJECT-TYPE
    SYNTAX     Unsigned32 (0..65535)
    MAX-ACCESS read-only
    STATUS     current
    DESCRIPTION
        ""
    ::= { lcosLXSetupRADIUSRADIUSServerEntry 9 }

-- {COLUMN} 13.2.30.3.1.14
lcosLXSetupRADIUSRADIUSServerEntryAccountingIPAddress OBJECT-TYPE
    SYNTAX     OCTET STRING (SIZE(0..64))
    MAX-ACCESS read-only
    STATUS     current
    DESCRIPTION
        ""
    ::= { lcosLXSetupRADIUSRADIUSServerEntry 14 }

-- {COLUMN} 13.2.30.3.1.15
lcosLXSetupRADIUSRADIUSServerEntryMACCheck OBJECT-TYPE
    SYNTAX     INTEGER {
                  eNo(0),
                  eYes(1)
               }
    MAX-ACCESS read-only
    STATUS     current
    DESCRIPTION
        ""
    ::= { lcosLXSetupRADIUSRADIUSServerEntry 15 }

-- {COLUMN} 13.2.30.3.1.16
lcosLXSetupRADIUSRADIUSServerEntryFallbackDynamicVLANID OBJECT-TYPE
    SYNTAX     Unsigned32 (0..65535)
    MAX-ACCESS read-only
    STATUS     current
    DESCRIPTION
        ""
    ::= { lcosLXSetupRADIUSRADIUSServerEntry 16 }

-- {COLUMN} 13.2.30.3.1.17
lcosLXSetupRADIUSRADIUSServerEntryRequireMessageAuthenticator OBJECT-TYPE
    SYNTAX     INTEGER {
                  eNo(0),
                  eYes(1)
               }
    MAX-ACCESS read-only
    STATUS     current
    DESCRIPTION
        ""
    ::= { lcosLXSetupRADIUSRADIUSServerEntry 17 }

-- {TABLE} 13.2.30.11
lcosLXSetupRADIUSLANSupplicant OBJECT-TYPE
    SYNTAX     SEQUENCE OF LcosLXSetupRADIUSLANSupplicantEntry
    MAX-ACCESS not-accessible
    STATUS     current
    DESCRIPTION
        ""
    ::= { lcosLXSetupRADIUS 11 }

-- {INDEX} 13.2.30.11
lcosLXSetupRADIUSLANSupplicantEntry OBJECT-TYPE
    SYNTAX     LcosLXSetupRADIUSLANSupplicantEntry
    MAX-ACCESS not-accessible
    STATUS     current
    DESCRIPTION
        ""
    INDEX {
        lcosLXSetupRADIUSLANSupplicantEntryInterfaceName
    }
    ::= { lcosLXSetupRADIUSLANSupplicant 1 }

-- {SEQUENCE} 13.2.30.11
LcosLXSetupRADIUSLANSupplicantEntry ::= SEQUENCE {
    lcosLXSetupRADIUSLANSupplicantEntryInterfaceName OCTET STRING,
    lcosLXSetupRADIUSLANSupplicantEntryMethod INTEGER,
    lcosLXSetupRADIUSLANSupplicantEntryUsername OCTET STRING,
    lcosLXSetupRADIUSLANSupplicantEntryPassword OCTET STRING
}

-- {COLUMN} 13.2.30.11.1.1
lcosLXSetupRADIUSLANSupplicantEntryInterfaceName OBJECT-TYPE
    SYNTAX     OCTET STRING (SIZE(0..64))
    MAX-ACCESS not-accessible
    STATUS     current
    DESCRIPTION
        ""
    ::= { lcosLXSetupRADIUSLANSupplicantEntry 1 }

-- {COLUMN} 13.2.30.11.1.2
lcosLXSetupRADIUSLANSupplicantEntryMethod OBJECT-TYPE
    SYNTAX     INTEGER {
                  enone(0),
                  eMD5(1024),
                  eTTLSPAP(5383),
                  eTTLSCHAP(5384),
                  eTTLSMSCHAP(5567),
                  eTTLSMSCHAPv2(5402),
                  eTTLSMD5(5380),
                  ePEAPMSCHAPv2(6426),
                  ePEAPGTC(6406)
               }
    MAX-ACCESS read-only
    STATUS     current
    DESCRIPTION
        ""
    ::= { lcosLXSetupRADIUSLANSupplicantEntry 2 }

-- {COLUMN} 13.2.30.11.1.3
lcosLXSetupRADIUSLANSupplicantEntryUsername OBJECT-TYPE
    SYNTAX     OCTET STRING (SIZE(0..64))
    MAX-ACCESS read-only
    STATUS     current
    DESCRIPTION
        ""
    ::= { lcosLXSetupRADIUSLANSupplicantEntry 3 }

-- {COLUMN} 13.2.30.11.1.4
lcosLXSetupRADIUSLANSupplicantEntryPassword OBJECT-TYPE
    SYNTAX     OCTET STRING (SIZE(0..64))
    MAX-ACCESS read-only
    STATUS     current
    DESCRIPTION
        ""
    ::= { lcosLXSetupRADIUSLANSupplicantEntry 4 }

-- {TABLE} 13.2.30.12
lcosLXSetupRADIUSWLANSupplicant OBJECT-TYPE
    SYNTAX     SEQUENCE OF LcosLXSetupRADIUSWLANSupplicantEntry
    MAX-ACCESS not-accessible
    STATUS     current
    DESCRIPTION
        ""
    ::= { lcosLXSetupRADIUS 12 }

-- {INDEX} 13.2.30.12
lcosLXSetupRADIUSWLANSupplicantEntry OBJECT-TYPE
    SYNTAX     LcosLXSetupRADIUSWLANSupplicantEntry
    MAX-ACCESS not-accessible
    STATUS     current
    DESCRIPTION
        ""
    INDEX {
        lcosLXSetupRADIUSWLANSupplicantEntryProfileName
    }
    ::= { lcosLXSetupRADIUSWLANSupplicant 1 }

-- {SEQUENCE} 13.2.30.12
LcosLXSetupRADIUSWLANSupplicantEntry ::= SEQUENCE {
    lcosLXSetupRADIUSWLANSupplicantEntryProfileName OCTET STRING,
    lcosLXSetupRADIUSWLANSupplicantEntryMethod INTEGER,
    lcosLXSetupRADIUSWLANSupplicantEntryUsername OCTET STRING,
    lcosLXSetupRADIUSWLANSupplicantEntryPassword OCTET STRING,
    lcosLXSetupRADIUSWLANSupplicantEntryCertificate INTEGER
}

-- {COLUMN} 13.2.30.12.1.1
lcosLXSetupRADIUSWLANSupplicantEntryProfileName OBJECT-TYPE
    SYNTAX     OCTET STRING (SIZE(0..64))
    MAX-ACCESS not-accessible
    STATUS     current
    DESCRIPTION
        ""
    ::= { lcosLXSetupRADIUSWLANSupplicantEntry 1 }

-- {COLUMN} 13.2.30.12.1.2
lcosLXSetupRADIUSWLANSupplicantEntryMethod OBJECT-TYPE
    SYNTAX     INTEGER {
                  enone(0),
                  eMD5(1024),
                  eTLS(3328),
                  eTTLSPAP(5383),
                  eTTLSCHAP(5384),
                  eTTLSMSCHAP(5567),
                  eTTLSMSCHAPv2(5402),
                  eTTLSMD5(5380),
                  ePEAPMSCHAPv2(6426),
                  ePEAPGTC(6406)
               }
    MAX-ACCESS read-only
    STATUS     current
    DESCRIPTION
        ""
    ::= { lcosLXSetupRADIUSWLANSupplicantEntry 2 }

-- {COLUMN} 13.2.30.12.1.3
lcosLXSetupRADIUSWLANSupplicantEntryUsername OBJECT-TYPE
    SYNTAX     OCTET STRING (SIZE(0..64))
    MAX-ACCESS read-only
    STATUS     current
    DESCRIPTION
        ""
    ::= { lcosLXSetupRADIUSWLANSupplicantEntry 3 }

-- {COLUMN} 13.2.30.12.1.4
lcosLXSetupRADIUSWLANSupplicantEntryPassword OBJECT-TYPE
    SYNTAX     OCTET STRING (SIZE(0..64))
    MAX-ACCESS read-only
    STATUS     current
    DESCRIPTION
        ""
    ::= { lcosLXSetupRADIUSWLANSupplicantEntry 4 }

-- {COLUMN} 13.2.30.12.1.5
lcosLXSetupRADIUSWLANSupplicantEntryCertificate OBJECT-TYPE
    SYNTAX     INTEGER {
                  eAutoaccept(0),
                  eContainer(1)
               }
    MAX-ACCESS read-only
    STATUS     current
    DESCRIPTION
        ""
    ::= { lcosLXSetupRADIUSWLANSupplicantEntry 5 }

-- {OID} 13.2.40
lcosLXSetupMulticastSnooping OBJECT IDENTIFIER ::= { lcosLXSetup 40 }

-- {OID} 13.2.45
lcosLXSetupBridge OBJECT IDENTIFIER ::= { lcosLXSetup 45 }

-- {TABLE} 13.2.45.1
lcosLXSetupBridgeDHCPSnooping OBJECT-TYPE
    SYNTAX     SEQUENCE OF LcosLXSetupBridgeDHCPSnoopingEntry
    MAX-ACCESS not-accessible
    STATUS     current
    DESCRIPTION
        ""
    ::= { lcosLXSetupBridge 1 }

-- {INDEX} 13.2.45.1
lcosLXSetupBridgeDHCPSnoopingEntry OBJECT-TYPE
    SYNTAX     LcosLXSetupBridgeDHCPSnoopingEntry
    MAX-ACCESS not-accessible
    STATUS     current
    DESCRIPTION
        ""
    INDEX {
        lcosLXSetupBridgeDHCPSnoopingEntryPort
    }
    ::= { lcosLXSetupBridgeDHCPSnooping 1 }

-- {SEQUENCE} 13.2.45.1
LcosLXSetupBridgeDHCPSnoopingEntry ::= SEQUENCE {
    lcosLXSetupBridgeDHCPSnoopingEntryPort OCTET STRING,
    lcosLXSetupBridgeDHCPSnoopingEntryCircuitID OCTET STRING,
    lcosLXSetupBridgeDHCPSnoopingEntryRemoteID OCTET STRING
}

-- {COLUMN} 13.2.45.1.1.1
lcosLXSetupBridgeDHCPSnoopingEntryPort OBJECT-TYPE
    SYNTAX     OCTET STRING (SIZE(0..64))
    MAX-ACCESS not-accessible
    STATUS     current
    DESCRIPTION
        ""
    ::= { lcosLXSetupBridgeDHCPSnoopingEntry 1 }

-- {COLUMN} 13.2.45.1.1.2
lcosLXSetupBridgeDHCPSnoopingEntryCircuitID OBJECT-TYPE
    SYNTAX     OCTET STRING (SIZE(0..64))
    MAX-ACCESS read-only
    STATUS     current
    DESCRIPTION
        ""
    ::= { lcosLXSetupBridgeDHCPSnoopingEntry 2 }

-- {COLUMN} 13.2.45.1.1.3
lcosLXSetupBridgeDHCPSnoopingEntryRemoteID OBJECT-TYPE
    SYNTAX     OCTET STRING (SIZE(0..64))
    MAX-ACCESS read-only
    STATUS     current
    DESCRIPTION
        ""
    ::= { lcosLXSetupBridgeDHCPSnoopingEntry 3 }

-- {OID} 13.2.46
lcosLXSetupmDNSFilter OBJECT IDENTIFIER ::= { lcosLXSetup 46 }

-- {TABLE} 13.2.46.1
lcosLXSetupmDNSFilterServices OBJECT-TYPE
    SYNTAX     SEQUENCE OF LcosLXSetupmDNSFilterServicesEntry
    MAX-ACCESS not-accessible
    STATUS     current
    DESCRIPTION
        ""
    ::= { lcosLXSetupmDNSFilter 1 }

-- {INDEX} 13.2.46.1
lcosLXSetupmDNSFilterServicesEntry OBJECT-TYPE
    SYNTAX     LcosLXSetupmDNSFilterServicesEntry
    MAX-ACCESS not-accessible
    STATUS     current
    DESCRIPTION
        ""
    INDEX {
        lcosLXSetupmDNSFilterServicesEntryName
    }
    ::= { lcosLXSetupmDNSFilterServices 1 }

-- {SEQUENCE} 13.2.46.1
LcosLXSetupmDNSFilterServicesEntry ::= SEQUENCE {
    lcosLXSetupmDNSFilterServicesEntryName OCTET STRING,
    lcosLXSetupmDNSFilterServicesEntryServiceType OCTET STRING,
    lcosLXSetupmDNSFilterServicesEntryComment OCTET STRING
}

-- {COLUMN} 13.2.46.1.1.1
lcosLXSetupmDNSFilterServicesEntryName OBJECT-TYPE
    SYNTAX     OCTET STRING (SIZE(0..32))
    MAX-ACCESS not-accessible
    STATUS     current
    DESCRIPTION
        ""
    ::= { lcosLXSetupmDNSFilterServicesEntry 1 }

-- {COLUMN} 13.2.46.1.1.2
lcosLXSetupmDNSFilterServicesEntryServiceType OBJECT-TYPE
    SYNTAX     OCTET STRING (SIZE(0..128))
    MAX-ACCESS read-only
    STATUS     current
    DESCRIPTION
        ""
    ::= { lcosLXSetupmDNSFilterServicesEntry 2 }

-- {COLUMN} 13.2.46.1.1.3
lcosLXSetupmDNSFilterServicesEntryComment OBJECT-TYPE
    SYNTAX     OCTET STRING (SIZE(0..128))
    MAX-ACCESS read-only
    STATUS     current
    DESCRIPTION
        ""
    ::= { lcosLXSetupmDNSFilterServicesEntry 3 }

-- {TABLE} 13.2.46.2
lcosLXSetupmDNSFilterServicesList OBJECT-TYPE
    SYNTAX     SEQUENCE OF LcosLXSetupmDNSFilterServicesListEntry
    MAX-ACCESS not-accessible
    STATUS     current
    DESCRIPTION
        ""
    ::= { lcosLXSetupmDNSFilter 2 }

-- {INDEX} 13.2.46.2
lcosLXSetupmDNSFilterServicesListEntry OBJECT-TYPE
    SYNTAX     LcosLXSetupmDNSFilterServicesListEntry
    MAX-ACCESS not-accessible
    STATUS     current
    DESCRIPTION
        ""
    INDEX {
        lcosLXSetupmDNSFilterServicesListEntryNetworkName
    }
    ::= { lcosLXSetupmDNSFilterServicesList 1 }

-- {SEQUENCE} 13.2.46.2
LcosLXSetupmDNSFilterServicesListEntry ::= SEQUENCE {
    lcosLXSetupmDNSFilterServicesListEntryNetworkName OCTET STRING,
    lcosLXSetupmDNSFilterServicesListEntryServices OCTET STRING
}

-- {COLUMN} 13.2.46.2.1.1
lcosLXSetupmDNSFilterServicesListEntryNetworkName OBJECT-TYPE
    SYNTAX     OCTET STRING (SIZE(0..64))
    MAX-ACCESS not-accessible
    STATUS     current
    DESCRIPTION
        ""
    ::= { lcosLXSetupmDNSFilterServicesListEntry 1 }

-- {COLUMN} 13.2.46.2.1.2
lcosLXSetupmDNSFilterServicesListEntryServices OBJECT-TYPE
    SYNTAX     OCTET STRING (SIZE(0..255))
    MAX-ACCESS read-only
    STATUS     current
    DESCRIPTION
        ""
    ::= { lcosLXSetupmDNSFilterServicesListEntry 2 }

-- {OID} 13.2.59
lcosLXSetupWLANManagement OBJECT IDENTIFIER ::= { lcosLXSetup 59 }

-- {TABLE} 13.2.59.1
lcosLXSetupWLANManagementStaticWLCConfiguration OBJECT-TYPE
    SYNTAX     SEQUENCE OF LcosLXSetupWLANManagementStaticWLCConfigurationEntry
    MAX-ACCESS not-accessible
    STATUS     current
    DESCRIPTION
        ""
    ::= { lcosLXSetupWLANManagement 1 }

-- {INDEX} 13.2.59.1
lcosLXSetupWLANManagementStaticWLCConfigurationEntry OBJECT-TYPE
    SYNTAX     LcosLXSetupWLANManagementStaticWLCConfigurationEntry
    MAX-ACCESS not-accessible
    STATUS     current
    DESCRIPTION
        ""
    INDEX {
        lcosLXSetupWLANManagementStaticWLCConfigurationEntryIPAddress
    }
    ::= { lcosLXSetupWLANManagementStaticWLCConfiguration 1 }

-- {SEQUENCE} 13.2.59.1
LcosLXSetupWLANManagementStaticWLCConfigurationEntry ::= SEQUENCE {
    lcosLXSetupWLANManagementStaticWLCConfigurationEntryIPAddress OCTET STRING,
    lcosLXSetupWLANManagementStaticWLCConfigurationEntryPort Unsigned32
}

-- {COLUMN} 13.2.59.1.1.1
lcosLXSetupWLANManagementStaticWLCConfigurationEntryIPAddress OBJECT-TYPE
    SYNTAX     OCTET STRING (SIZE(0..44))
    MAX-ACCESS not-accessible
    STATUS     current
    DESCRIPTION
        ""
    ::= { lcosLXSetupWLANManagementStaticWLCConfigurationEntry 1 }

-- {COLUMN} 13.2.59.1.1.2
lcosLXSetupWLANManagementStaticWLCConfigurationEntryPort OBJECT-TYPE
    SYNTAX     Unsigned32 (0..65535)
    MAX-ACCESS read-only
    STATUS     current
    DESCRIPTION
        ""
    ::= { lcosLXSetupWLANManagementStaticWLCConfigurationEntry 2 }

-- {SCALAR} 13.2.59.2
lcosLXSetupWLANManagementOperating OBJECT-TYPE
    SYNTAX     INTEGER {
                  eNo(0),
                  eYes(1)
               }
    MAX-ACCESS read-only
    STATUS     current
    DESCRIPTION
        ""
    ::= { lcosLXSetupWLANManagement 2 }

-- {SCALAR} 13.2.59.3
lcosLXSetupWLANManagementUpdateCertBefore OBJECT-TYPE
    SYNTAX     Unsigned32 (0..65535)
    MAX-ACCESS read-only
    STATUS     current
    DESCRIPTION
        ""
    ::= { lcosLXSetupWLANManagement 3 }

-- {SCALAR} 13.2.59.4
lcosLXSetupWLANManagementCapwapPort OBJECT-TYPE
    SYNTAX     Unsigned32 (0..65535)
    MAX-ACCESS read-only
    STATUS     current
    DESCRIPTION
        ""
    ::= { lcosLXSetupWLANManagement 4 }

-- {OID} 13.2.60
lcosLXSetupPower OBJECT IDENTIFIER ::= { lcosLXSetup 60 }

-- {SCALAR} 13.2.60.1
lcosLXSetupPowerDualPoEMode OBJECT-TYPE
    SYNTAX     INTEGER {
                  eHitlessFailover(0),
                  eLoadBalancing(1)
               }
    MAX-ACCESS read-only
    STATUS     current
    DESCRIPTION
        ""
    ::= { lcosLXSetupPower 1 }

-- {OID} 13.2.61
lcosLXSetupL2TP OBJECT IDENTIFIER ::= { lcosLXSetup 61 }

-- {TABLE} 13.2.61.1
lcosLXSetupL2TPEndpoints OBJECT-TYPE
    SYNTAX     SEQUENCE OF LcosLXSetupL2TPEndpointsEntry
    MAX-ACCESS not-accessible
    STATUS     current
    DESCRIPTION
        ""
    ::= { lcosLXSetupL2TP 1 }

-- {INDEX} 13.2.61.1
lcosLXSetupL2TPEndpointsEntry OBJECT-TYPE
    SYNTAX     LcosLXSetupL2TPEndpointsEntry
    MAX-ACCESS not-accessible
    STATUS     current
    DESCRIPTION
        ""
    INDEX {
        lcosLXSetupL2TPEndpointsEntryTunnelID
    }
    ::= { lcosLXSetupL2TPEndpoints 1 }

-- {SEQUENCE} 13.2.61.1
LcosLXSetupL2TPEndpointsEntry ::= SEQUENCE {
    lcosLXSetupL2TPEndpointsEntryTunnelID OCTET STRING,
    lcosLXSetupL2TPEndpointsEntryIPAddress OCTET STRING,
    lcosLXSetupL2TPEndpointsEntryPort Unsigned32,
    lcosLXSetupL2TPEndpointsEntryHostname OCTET STRING,
    lcosLXSetupL2TPEndpointsEntryPassword OCTET STRING,
    lcosLXSetupL2TPEndpointsEntryAuthPeer INTEGER,
    lcosLXSetupL2TPEndpointsEntryHide INTEGER,
    lcosLXSetupL2TPEndpointsEntryOperating INTEGER
}

-- {COLUMN} 13.2.61.1.1.1
lcosLXSetupL2TPEndpointsEntryTunnelID OBJECT-TYPE
    SYNTAX     OCTET STRING (SIZE(0..16))
    MAX-ACCESS not-accessible
    STATUS     current
    DESCRIPTION
        ""
    ::= { lcosLXSetupL2TPEndpointsEntry 1 }

-- {COLUMN} 13.2.61.1.1.2
lcosLXSetupL2TPEndpointsEntryIPAddress OBJECT-TYPE
    SYNTAX     OCTET STRING (SIZE(0..64))
    MAX-ACCESS read-only
    STATUS     current
    DESCRIPTION
        ""
    ::= { lcosLXSetupL2TPEndpointsEntry 2 }

-- {COLUMN} 13.2.61.1.1.3
lcosLXSetupL2TPEndpointsEntryPort OBJECT-TYPE
    SYNTAX     Unsigned32 (0..65535)
    MAX-ACCESS read-only
    STATUS     current
    DESCRIPTION
        ""
    ::= { lcosLXSetupL2TPEndpointsEntry 3 }

-- {COLUMN} 13.2.61.1.1.4
lcosLXSetupL2TPEndpointsEntryHostname OBJECT-TYPE
    SYNTAX     OCTET STRING (SIZE(0..64))
    MAX-ACCESS read-only
    STATUS     current
    DESCRIPTION
        ""
    ::= { lcosLXSetupL2TPEndpointsEntry 4 }

-- {COLUMN} 13.2.61.1.1.5
lcosLXSetupL2TPEndpointsEntryPassword OBJECT-TYPE
    SYNTAX     OCTET STRING (SIZE(0..32))
    MAX-ACCESS read-only
    STATUS     current
    DESCRIPTION
        ""
    ::= { lcosLXSetupL2TPEndpointsEntry 5 }

-- {COLUMN} 13.2.61.1.1.6
lcosLXSetupL2TPEndpointsEntryAuthPeer OBJECT-TYPE
    SYNTAX     INTEGER {
                  eNo(0),
                  eYes(1)
               }
    MAX-ACCESS read-only
    STATUS     current
    DESCRIPTION
        ""
    ::= { lcosLXSetupL2TPEndpointsEntry 6 }

-- {COLUMN} 13.2.61.1.1.7
lcosLXSetupL2TPEndpointsEntryHide OBJECT-TYPE
    SYNTAX     INTEGER {
                  eNo(0),
                  eYes(1)
               }
    MAX-ACCESS read-only
    STATUS     current
    DESCRIPTION
        ""
    ::= { lcosLXSetupL2TPEndpointsEntry 7 }

-- {COLUMN} 13.2.61.1.1.8
lcosLXSetupL2TPEndpointsEntryOperating OBJECT-TYPE
    SYNTAX     INTEGER {
                  eNo(0),
                  eYes(1)
               }
    MAX-ACCESS read-only
    STATUS     current
    DESCRIPTION
        ""
    ::= { lcosLXSetupL2TPEndpointsEntry 8 }

-- {TABLE} 13.2.61.2
lcosLXSetupL2TPEthernet OBJECT-TYPE
    SYNTAX     SEQUENCE OF LcosLXSetupL2TPEthernetEntry
    MAX-ACCESS not-accessible
    STATUS     current
    DESCRIPTION
        ""
    ::= { lcosLXSetupL2TP 2 }

-- {INDEX} 13.2.61.2
lcosLXSetupL2TPEthernetEntry OBJECT-TYPE
    SYNTAX     LcosLXSetupL2TPEthernetEntry
    MAX-ACCESS not-accessible
    STATUS     current
    DESCRIPTION
        ""
    INDEX {
        lcosLXSetupL2TPEthernetEntryL2TPEndpoint,
        lcosLXSetupL2TPEthernetEntryRemoteEnd
    }
    ::= { lcosLXSetupL2TPEthernet 1 }

-- {SEQUENCE} 13.2.61.2
LcosLXSetupL2TPEthernetEntry ::= SEQUENCE {
    lcosLXSetupL2TPEthernetEntryL2TPEndpoint OCTET STRING,
    lcosLXSetupL2TPEthernetEntryRemoteEnd OCTET STRING,
    lcosLXSetupL2TPEthernetEntryInterfaceName INTEGER,
    lcosLXSetupL2TPEthernetEntryMTU Unsigned32
}

-- {COLUMN} 13.2.61.2.1.1
lcosLXSetupL2TPEthernetEntryL2TPEndpoint OBJECT-TYPE
    SYNTAX     OCTET STRING (SIZE(0..16))
    MAX-ACCESS not-accessible
    STATUS     current
    DESCRIPTION
        ""
    ::= { lcosLXSetupL2TPEthernetEntry 1 }

-- {COLUMN} 13.2.61.2.1.2
lcosLXSetupL2TPEthernetEntryRemoteEnd OBJECT-TYPE
    SYNTAX     OCTET STRING (SIZE(0..32))
    MAX-ACCESS not-accessible
    STATUS     current
    DESCRIPTION
        ""
    ::= { lcosLXSetupL2TPEthernetEntry 2 }

-- {COLUMN} 13.2.61.2.1.3
lcosLXSetupL2TPEthernetEntryInterfaceName OBJECT-TYPE
    SYNTAX     INTEGER {
                  eL2TPTunnel1(0),
                  eL2TPTunnel2(1),
                  eL2TPTunnel3(2),
                  eL2TPTunnel4(3),
                  eL2TPTunnel5(4),
                  eL2TPTunnel6(5),
                  eL2TPTunnel7(6),
                  eL2TPTunnel8(7),
                  eL2TPTunnel9(8),
                  eL2TPTunnel10(9),
                  eL2TPTunnel11(10),
                  eL2TPTunnel12(11),
                  eL2TPTunnel13(12),
                  eL2TPTunnel14(13),
                  eL2TPTunnel15(14),
                  eL2TPTunnel16(15)
               }
    MAX-ACCESS read-only
    STATUS     current
    DESCRIPTION
        ""
    ::= { lcosLXSetupL2TPEthernetEntry 3 }

-- {COLUMN} 13.2.61.2.1.4
lcosLXSetupL2TPEthernetEntryMTU OBJECT-TYPE
    SYNTAX     Unsigned32 (0..65535)
    MAX-ACCESS read-only
    STATUS     current
    DESCRIPTION
        ""
    ::= { lcosLXSetupL2TPEthernetEntry 4 }

-- {OID} 13.2.62
lcosLXSetupLAN OBJECT IDENTIFIER ::= { lcosLXSetup 62 }

-- {TABLE} 13.2.62.1
lcosLXSetupLANLACP OBJECT-TYPE
    SYNTAX     SEQUENCE OF LcosLXSetupLANLACPEntry
    MAX-ACCESS not-accessible
    STATUS     current
    DESCRIPTION
        ""
    ::= { lcosLXSetupLAN 1 }

-- {INDEX} 13.2.62.1
lcosLXSetupLANLACPEntry OBJECT-TYPE
    SYNTAX     LcosLXSetupLANLACPEntry
    MAX-ACCESS not-accessible
    STATUS     current
    DESCRIPTION
        ""
    INDEX {
        lcosLXSetupLANLACPEntryName
    }
    ::= { lcosLXSetupLANLACP 1 }

-- {SEQUENCE} 13.2.62.1
LcosLXSetupLANLACPEntry ::= SEQUENCE {
    lcosLXSetupLANLACPEntryName OCTET STRING,
    lcosLXSetupLANLACPEntryOperating INTEGER,
    lcosLXSetupLANLACPEntryPriority Unsigned32,
    lcosLXSetupLANLACPEntryDistributionPolicy INTEGER,
    lcosLXSetupLANLACPEntryPortsUNUSED OCTET STRING
}

-- {COLUMN} 13.2.62.1.1.1
lcosLXSetupLANLACPEntryName OBJECT-TYPE
    SYNTAX     OCTET STRING (SIZE(0..9))
    MAX-ACCESS not-accessible
    STATUS     current
    DESCRIPTION
        ""
    ::= { lcosLXSetupLANLACPEntry 1 }

-- {COLUMN} 13.2.62.1.1.2
lcosLXSetupLANLACPEntryOperating OBJECT-TYPE
    SYNTAX     INTEGER {
                  eNo(0),
                  eYes(1)
               }
    MAX-ACCESS read-only
    STATUS     current
    DESCRIPTION
        ""
    ::= { lcosLXSetupLANLACPEntry 2 }

-- {COLUMN} 13.2.62.1.1.3
lcosLXSetupLANLACPEntryPriority OBJECT-TYPE
    SYNTAX     Unsigned32 (0..65535)
    MAX-ACCESS read-only
    STATUS     current
    DESCRIPTION
        ""
    ::= { lcosLXSetupLANLACPEntry 3 }

-- {COLUMN} 13.2.62.1.1.4
lcosLXSetupLANLACPEntryDistributionPolicy OBJECT-TYPE
    SYNTAX     INTEGER {
                  elayer2(0),
                  elayer23(1),
                  elayer34(2),
                  eencap23(3),
                  eencap34(4)
               }
    MAX-ACCESS read-only
    STATUS     current
    DESCRIPTION
        ""
    ::= { lcosLXSetupLANLACPEntry 4 }

-- {COLUMN} 13.2.62.1.1.5
lcosLXSetupLANLACPEntryPortsUNUSED OBJECT-TYPE
    SYNTAX     OCTET STRING (SIZE(0..16))
    MAX-ACCESS read-only
    STATUS     current
    DESCRIPTION
        ""
    ::= { lcosLXSetupLANLACPEntry 5 }

-- {TABLE} 13.2.62.2
lcosLXSetupLANEthernetPorts OBJECT-TYPE
    SYNTAX     SEQUENCE OF LcosLXSetupLANEthernetPortsEntry
    MAX-ACCESS not-accessible
    STATUS     current
    DESCRIPTION
        ""
    ::= { lcosLXSetupLAN 2 }

-- {INDEX} 13.2.62.2
lcosLXSetupLANEthernetPortsEntry OBJECT-TYPE
    SYNTAX     LcosLXSetupLANEthernetPortsEntry
    MAX-ACCESS not-accessible
    STATUS     current
    DESCRIPTION
        ""
    INDEX {
        lcosLXSetupLANEthernetPortsEntryPort
    }
    ::= { lcosLXSetupLANEthernetPorts 1 }

-- {SEQUENCE} 13.2.62.2
LcosLXSetupLANEthernetPortsEntry ::= SEQUENCE {
    lcosLXSetupLANEthernetPortsEntryPort OCTET STRING,
    lcosLXSetupLANEthernetPortsEntryAdvertisedRates BITS,
    lcosLXSetupLANEthernetPortsEntryPowerSaving INTEGER
}

-- {COLUMN} 13.2.62.2.1.1
lcosLXSetupLANEthernetPortsEntryPort OBJECT-TYPE
    SYNTAX     OCTET STRING (SIZE(0..10))
    MAX-ACCESS not-accessible
    STATUS     current
    DESCRIPTION
        ""
    ::= { lcosLXSetupLANEthernetPortsEntry 1 }

-- {COLUMN} 13.2.62.2.1.2
lcosLXSetupLANEthernetPortsEntryAdvertisedRates OBJECT-TYPE
    SYNTAX     BITS {
                  e100HDX(2),
                  e100FDX(3),
                  e1000FDX(5),
                  e10000FDX(12)
               }
    MAX-ACCESS read-only
    STATUS     current
    DESCRIPTION
        ""
    ::= { lcosLXSetupLANEthernetPortsEntry 2 }

-- {COLUMN} 13.2.62.2.1.3
lcosLXSetupLANEthernetPortsEntryPowerSaving OBJECT-TYPE
    SYNTAX     INTEGER {
                  eNo(0),
                  eYes(1)
               }
    MAX-ACCESS read-only
    STATUS     current
    DESCRIPTION
        ""
    ::= { lcosLXSetupLANEthernetPortsEntry 3 }

-- {OID} 13.2.62.3
lcosLXSetupLANSpanningTree OBJECT IDENTIFIER ::= { lcosLXSetupLAN 3 }

-- {SCALAR} 13.2.62.3.1
lcosLXSetupLANSpanningTreeOperating OBJECT-TYPE
    SYNTAX     INTEGER {
                  eNo(0),
                  eYes(1)
               }
    MAX-ACCESS read-only
    STATUS     current
    DESCRIPTION
        ""
    ::= { lcosLXSetupLANSpanningTree 1 }

-- {TABLE} 13.2.62.3.2
lcosLXSetupLANSpanningTreePortData OBJECT-TYPE
    SYNTAX     SEQUENCE OF LcosLXSetupLANSpanningTreePortDataEntry
    MAX-ACCESS not-accessible
    STATUS     current
    DESCRIPTION
        ""
    ::= { lcosLXSetupLANSpanningTree 2 }

-- {INDEX} 13.2.62.3.2
lcosLXSetupLANSpanningTreePortDataEntry OBJECT-TYPE
    SYNTAX     LcosLXSetupLANSpanningTreePortDataEntry
    MAX-ACCESS not-accessible
    STATUS     current
    DESCRIPTION
        ""
    INDEX {
        lcosLXSetupLANSpanningTreePortDataEntryPort
    }
    ::= { lcosLXSetupLANSpanningTreePortData 1 }

-- {SEQUENCE} 13.2.62.3.2
LcosLXSetupLANSpanningTreePortDataEntry ::= SEQUENCE {
    lcosLXSetupLANSpanningTreePortDataEntryPort OCTET STRING,
    lcosLXSetupLANSpanningTreePortDataEntryPriority INTEGER,
    lcosLXSetupLANSpanningTreePortDataEntryEdgePort INTEGER,
    lcosLXSetupLANSpanningTreePortDataEntryPathCostOverride Unsigned32
}

-- {COLUMN} 13.2.62.3.2.1.1
lcosLXSetupLANSpanningTreePortDataEntryPort OBJECT-TYPE
    SYNTAX     OCTET STRING (SIZE(0..64))
    MAX-ACCESS not-accessible
    STATUS     current
    DESCRIPTION
        ""
    ::= { lcosLXSetupLANSpanningTreePortDataEntry 1 }

-- {COLUMN} 13.2.62.3.2.1.2
lcosLXSetupLANSpanningTreePortDataEntryPriority OBJECT-TYPE
    SYNTAX     INTEGER {
                  e0(0),
                  e16(1),
                  e32(2),
                  e48(3),
                  e64(4),
                  e80(5),
                  e96(6),
                  e112(7),
                  e128(8),
                  e144(9),
                  e160(10),
                  e176(11),
                  e192(12),
                  e208(13),
                  e224(14),
                  e240(15)
               }
    MAX-ACCESS read-only
    STATUS     current
    DESCRIPTION
        ""
    ::= { lcosLXSetupLANSpanningTreePortDataEntry 2 }

-- {COLUMN} 13.2.62.3.2.1.3
lcosLXSetupLANSpanningTreePortDataEntryEdgePort OBJECT-TYPE
    SYNTAX     INTEGER {
                  eNo(0),
                  eYes(1)
               }
    MAX-ACCESS read-only
    STATUS     current
    DESCRIPTION
        ""
    ::= { lcosLXSetupLANSpanningTreePortDataEntry 3 }

-- {COLUMN} 13.2.62.3.2.1.4
lcosLXSetupLANSpanningTreePortDataEntryPathCostOverride OBJECT-TYPE
    SYNTAX     Unsigned32 (0..4294967295)
    MAX-ACCESS read-only
    STATUS     current
    DESCRIPTION
        ""
    ::= { lcosLXSetupLANSpanningTreePortDataEntry 4 }

-- {SCALAR} 13.2.62.3.3
lcosLXSetupLANSpanningTreeBridgePriority OBJECT-TYPE
    SYNTAX     INTEGER {
                  e0(0),
                  e4096(1),
                  e8192(2),
                  e12288(3),
                  e16384(4),
                  e20480(5),
                  e24576(6),
                  e28672(7),
                  e32768(8),
                  e36864(9),
                  e40960(10),
                  e45056(11),
                  e49152(12),
                  e53248(13),
                  e57344(14),
                  e61440(15)
               }
    MAX-ACCESS read-only
    STATUS     current
    DESCRIPTION
        ""
    ::= { lcosLXSetupLANSpanningTree 3 }

-- {SCALAR} 13.2.62.3.4
lcosLXSetupLANSpanningTreeProtocolVersion OBJECT-TYPE
    SYNTAX     INTEGER {
                  eClassic(0),
                  eRapid(1)
               }
    MAX-ACCESS read-only
    STATUS     current
    DESCRIPTION
        ""
    ::= { lcosLXSetupLANSpanningTree 4 }

-- {SCALAR} 13.2.62.3.5
lcosLXSetupLANSpanningTreeForwardDelay OBJECT-TYPE
    SYNTAX     Unsigned32 (0..255)
    MAX-ACCESS read-only
    STATUS     current
    DESCRIPTION
        ""
    ::= { lcosLXSetupLANSpanningTree 5 }

-- {SCALAR} 13.2.62.3.6
lcosLXSetupLANSpanningTreeHelloTime OBJECT-TYPE
    SYNTAX     Unsigned32 (0..255)
    MAX-ACCESS read-only
    STATUS     current
    DESCRIPTION
        ""
    ::= { lcosLXSetupLANSpanningTree 6 }

-- {SCALAR} 13.2.62.3.7
lcosLXSetupLANSpanningTreeMaxAge OBJECT-TYPE
    SYNTAX     Unsigned32 (0..255)
    MAX-ACCESS read-only
    STATUS     current
    DESCRIPTION
        ""
    ::= { lcosLXSetupLANSpanningTree 7 }

-- {SCALAR} 13.2.62.3.8
lcosLXSetupLANSpanningTreeTransmitHoldCount OBJECT-TYPE
    SYNTAX     Unsigned32 (0..255)
    MAX-ACCESS read-only
    STATUS     current
    DESCRIPTION
        ""
    ::= { lcosLXSetupLANSpanningTree 8 }

-- {OID} 13.2.70
lcosLXSetupIPConfiguration OBJECT IDENTIFIER ::= { lcosLXSetup 70 }

-- {TABLE} 13.2.70.4
lcosLXSetupIPConfigurationStaticParameters OBJECT-TYPE
    SYNTAX     SEQUENCE OF LcosLXSetupIPConfigurationStaticParametersEntry
    MAX-ACCESS not-accessible
    STATUS     current
    DESCRIPTION
        ""
    ::= { lcosLXSetupIPConfiguration 4 }

-- {INDEX} 13.2.70.4
lcosLXSetupIPConfigurationStaticParametersEntry OBJECT-TYPE
    SYNTAX     LcosLXSetupIPConfigurationStaticParametersEntry
    MAX-ACCESS not-accessible
    STATUS     current
    DESCRIPTION
        ""
    INDEX {
        lcosLXSetupIPConfigurationStaticParametersEntryInterfaceName
    }
    ::= { lcosLXSetupIPConfigurationStaticParameters 1 }

-- {SEQUENCE} 13.2.70.4
LcosLXSetupIPConfigurationStaticParametersEntry ::= SEQUENCE {
    lcosLXSetupIPConfigurationStaticParametersEntryInterfaceName OCTET STRING,
    lcosLXSetupIPConfigurationStaticParametersEntryIPv4Gateway IpAddress,
    lcosLXSetupIPConfigurationStaticParametersEntryIPv6Gateway OCTET STRING,
    lcosLXSetupIPConfigurationStaticParametersEntryPrimaryIPv4DNS IpAddress,
    lcosLXSetupIPConfigurationStaticParametersEntrySecondaryIPv4DNS IpAddress,
    lcosLXSetupIPConfigurationStaticParametersEntryPrimaryIPv6DNS OCTET STRING,
    lcosLXSetupIPConfigurationStaticParametersEntrySecondaryIPv6DNS OCTET STRING
}

-- {COLUMN} 13.2.70.4.1.1
lcosLXSetupIPConfigurationStaticParametersEntryInterfaceName OBJECT-TYPE
    SYNTAX     OCTET STRING (SIZE(0..64))
    MAX-ACCESS not-accessible
    STATUS     current
    DESCRIPTION
        ""
    ::= { lcosLXSetupIPConfigurationStaticParametersEntry 1 }

-- {COLUMN} 13.2.70.4.1.2
lcosLXSetupIPConfigurationStaticParametersEntryIPv4Gateway OBJECT-TYPE
    SYNTAX     IpAddress
    MAX-ACCESS read-only
    STATUS     current
    DESCRIPTION
        ""
    ::= { lcosLXSetupIPConfigurationStaticParametersEntry 2 }

-- {COLUMN} 13.2.70.4.1.3
lcosLXSetupIPConfigurationStaticParametersEntryIPv6Gateway OBJECT-TYPE
    SYNTAX     OCTET STRING (SIZE(0..44))
    MAX-ACCESS read-only
    STATUS     current
    DESCRIPTION
        ""
    ::= { lcosLXSetupIPConfigurationStaticParametersEntry 3 }

-- {COLUMN} 13.2.70.4.1.4
lcosLXSetupIPConfigurationStaticParametersEntryPrimaryIPv4DNS OBJECT-TYPE
    SYNTAX     IpAddress
    MAX-ACCESS read-only
    STATUS     current
    DESCRIPTION
        ""
    ::= { lcosLXSetupIPConfigurationStaticParametersEntry 4 }

-- {COLUMN} 13.2.70.4.1.5
lcosLXSetupIPConfigurationStaticParametersEntrySecondaryIPv4DNS OBJECT-TYPE
    SYNTAX     IpAddress
    MAX-ACCESS read-only
    STATUS     current
    DESCRIPTION
        ""
    ::= { lcosLXSetupIPConfigurationStaticParametersEntry 5 }

-- {COLUMN} 13.2.70.4.1.6
lcosLXSetupIPConfigurationStaticParametersEntryPrimaryIPv6DNS OBJECT-TYPE
    SYNTAX     OCTET STRING (SIZE(0..44))
    MAX-ACCESS read-only
    STATUS     current
    DESCRIPTION
        ""
    ::= { lcosLXSetupIPConfigurationStaticParametersEntry 6 }

-- {COLUMN} 13.2.70.4.1.7
lcosLXSetupIPConfigurationStaticParametersEntrySecondaryIPv6DNS OBJECT-TYPE
    SYNTAX     OCTET STRING (SIZE(0..44))
    MAX-ACCESS read-only
    STATUS     current
    DESCRIPTION
        ""
    ::= { lcosLXSetupIPConfigurationStaticParametersEntry 7 }

-- {TABLE} 13.2.70.6
lcosLXSetupIPConfigurationLANInterfaces OBJECT-TYPE
    SYNTAX     SEQUENCE OF LcosLXSetupIPConfigurationLANInterfacesEntry
    MAX-ACCESS not-accessible
    STATUS     current
    DESCRIPTION
        ""
    ::= { lcosLXSetupIPConfiguration 6 }

-- {INDEX} 13.2.70.6
lcosLXSetupIPConfigurationLANInterfacesEntry OBJECT-TYPE
    SYNTAX     LcosLXSetupIPConfigurationLANInterfacesEntry
    MAX-ACCESS not-accessible
    STATUS     current
    DESCRIPTION
        ""
    INDEX {
        lcosLXSetupIPConfigurationLANInterfacesEntryInterfaceName
    }
    ::= { lcosLXSetupIPConfigurationLANInterfaces 1 }

-- {SEQUENCE} 13.2.70.6
LcosLXSetupIPConfigurationLANInterfacesEntry ::= SEQUENCE {
    lcosLXSetupIPConfigurationLANInterfacesEntryInterfaceName OCTET STRING,
    lcosLXSetupIPConfigurationLANInterfacesEntryInterfaceID OCTET STRING,
    lcosLXSetupIPConfigurationLANInterfacesEntryVLANID Unsigned32,
    lcosLXSetupIPConfigurationLANInterfacesEntryIPv4AddressSource INTEGER,
    lcosLXSetupIPConfigurationLANInterfacesEntryIPv6AddressSource INTEGER,
    lcosLXSetupIPConfigurationLANInterfacesEntryStaticIPv4Address OCTET STRING,
    lcosLXSetupIPConfigurationLANInterfacesEntryStaticIPv6Address OCTET STRING,
    lcosLXSetupIPConfigurationLANInterfacesEntryComment OCTET STRING
}

-- {COLUMN} 13.2.70.6.1.1
lcosLXSetupIPConfigurationLANInterfacesEntryInterfaceName OBJECT-TYPE
    SYNTAX     OCTET STRING (SIZE(0..64))
    MAX-ACCESS not-accessible
    STATUS     current
    DESCRIPTION
        ""
    ::= { lcosLXSetupIPConfigurationLANInterfacesEntry 1 }

-- {COLUMN} 13.2.70.6.1.2
lcosLXSetupIPConfigurationLANInterfacesEntryInterfaceID OBJECT-TYPE
    SYNTAX     OCTET STRING (SIZE(0..16))
    MAX-ACCESS read-only
    STATUS     current
    DESCRIPTION
        ""
    ::= { lcosLXSetupIPConfigurationLANInterfacesEntry 2 }

-- {COLUMN} 13.2.70.6.1.3
lcosLXSetupIPConfigurationLANInterfacesEntryVLANID OBJECT-TYPE
    SYNTAX     Unsigned32 (0..65535)
    MAX-ACCESS read-only
    STATUS     current
    DESCRIPTION
        ""
    ::= { lcosLXSetupIPConfigurationLANInterfacesEntry 3 }

-- {COLUMN} 13.2.70.6.1.4
lcosLXSetupIPConfigurationLANInterfacesEntryIPv4AddressSource OBJECT-TYPE
    SYNTAX     INTEGER {
                  eDHCP(1),
                  estatic(2)
               }
    MAX-ACCESS read-only
    STATUS     current
    DESCRIPTION
        ""
    ::= { lcosLXSetupIPConfigurationLANInterfacesEntry 4 }

-- {COLUMN} 13.2.70.6.1.5
lcosLXSetupIPConfigurationLANInterfacesEntryIPv6AddressSource OBJECT-TYPE
    SYNTAX     INTEGER {
                  eRouterAdvertisement(1),
                  eDHCPv6(2),
                  estatic(3)
               }
    MAX-ACCESS read-only
    STATUS     current
    DESCRIPTION
        ""
    ::= { lcosLXSetupIPConfigurationLANInterfacesEntry 5 }

-- {COLUMN} 13.2.70.6.1.6
lcosLXSetupIPConfigurationLANInterfacesEntryStaticIPv4Address OBJECT-TYPE
    SYNTAX     OCTET STRING (SIZE(0..19))
    MAX-ACCESS read-only
    STATUS     current
    DESCRIPTION
        ""
    ::= { lcosLXSetupIPConfigurationLANInterfacesEntry 6 }

-- {COLUMN} 13.2.70.6.1.7
lcosLXSetupIPConfigurationLANInterfacesEntryStaticIPv6Address OBJECT-TYPE
    SYNTAX     OCTET STRING (SIZE(0..44))
    MAX-ACCESS read-only
    STATUS     current
    DESCRIPTION
        ""
    ::= { lcosLXSetupIPConfigurationLANInterfacesEntry 7 }

-- {COLUMN} 13.2.70.6.1.9
lcosLXSetupIPConfigurationLANInterfacesEntryComment OBJECT-TYPE
    SYNTAX     OCTET STRING (SIZE(0..32))
    MAX-ACCESS read-only
    STATUS     current
    DESCRIPTION
        ""
    ::= { lcosLXSetupIPConfigurationLANInterfacesEntry 9 }

-- {OID} 13.2.99
lcosLXSetupLBS OBJECT IDENTIFIER ::= { lcosLXSetup 99 }

-- {TABLE} 13.2.99.1
lcosLXSetupLBSHTTPServer OBJECT-TYPE
    SYNTAX     SEQUENCE OF LcosLXSetupLBSHTTPServerEntry
    MAX-ACCESS not-accessible
    STATUS     current
    DESCRIPTION
        ""
    ::= { lcosLXSetupLBS 1 }

-- {INDEX} 13.2.99.1
lcosLXSetupLBSHTTPServerEntry OBJECT-TYPE
    SYNTAX     LcosLXSetupLBSHTTPServerEntry
    MAX-ACCESS not-accessible
    STATUS     current
    DESCRIPTION
        ""
    INDEX {
        lcosLXSetupLBSHTTPServerEntryURL
    }
    ::= { lcosLXSetupLBSHTTPServer 1 }

-- {SEQUENCE} 13.2.99.1
LcosLXSetupLBSHTTPServerEntry ::= SEQUENCE {
    lcosLXSetupLBSHTTPServerEntryURL OCTET STRING,
    lcosLXSetupLBSHTTPServerEntrySecret OCTET STRING,
    lcosLXSetupLBSHTTPServerEntryDataSources BITS,
    lcosLXSetupLBSHTTPServerEntryBLEMeasurementsFields BITS,
    lcosLXSetupLBSHTTPServerEntryBufferingTimeout Unsigned32,
    lcosLXSetupLBSHTTPServerEntryBufferSize Unsigned32
}

-- {COLUMN} 13.2.99.1.1.1
lcosLXSetupLBSHTTPServerEntryURL OBJECT-TYPE
    SYNTAX     OCTET STRING (SIZE(0..251))
    MAX-ACCESS not-accessible
    STATUS     current
    DESCRIPTION
        ""
    ::= { lcosLXSetupLBSHTTPServerEntry 1 }

-- {COLUMN} 13.2.99.1.1.3
lcosLXSetupLBSHTTPServerEntrySecret OBJECT-TYPE
    SYNTAX     OCTET STRING (SIZE(0..64))
    MAX-ACCESS read-only
    STATUS     current
    DESCRIPTION
        ""
    ::= { lcosLXSetupLBSHTTPServerEntry 3 }

-- {COLUMN} 13.2.99.1.1.4
lcosLXSetupLBSHTTPServerEntryDataSources OBJECT-TYPE
    SYNTAX     BITS {
                  eBLE(1)
               }
    MAX-ACCESS read-only
    STATUS     current
    DESCRIPTION
        ""
    ::= { lcosLXSetupLBSHTTPServerEntry 4 }

-- {COLUMN} 13.2.99.1.1.5
lcosLXSetupLBSHTTPServerEntryBLEMeasurementsFields OBJECT-TYPE
    SYNTAX     BITS {
                  eBLEAddressTypeTransmit(0),
                  eBLEAdvertisingDataTransmit(1),
                  eBLENameTransmit(2),
                  eBLERSSITransmit(3),
                  eBLEScanResponseDataTransmit(4)
               }
    MAX-ACCESS read-only
    STATUS     current
    DESCRIPTION
        ""
    ::= { lcosLXSetupLBSHTTPServerEntry 5 }

-- {COLUMN} 13.2.99.1.1.6
lcosLXSetupLBSHTTPServerEntryBufferingTimeout OBJECT-TYPE
    SYNTAX     Unsigned32 (0..65535)
    MAX-ACCESS read-only
    STATUS     current
    DESCRIPTION
        ""
    ::= { lcosLXSetupLBSHTTPServerEntry 6 }

-- {COLUMN} 13.2.99.1.1.7
lcosLXSetupLBSHTTPServerEntryBufferSize OBJECT-TYPE
    SYNTAX     Unsigned32 (0..65535)
    MAX-ACCESS read-only
    STATUS     current
    DESCRIPTION
        ""
    ::= { lcosLXSetupLBSHTTPServerEntry 7 }

-- {SCALAR} 13.2.99.2
lcosLXSetupLBSOperating OBJECT-TYPE
    SYNTAX     INTEGER {
                  eNo(0),
                  eYes(1)
               }
    MAX-ACCESS read-only
    STATUS     current
    DESCRIPTION
        ""
    ::= { lcosLXSetupLBS 2 }

-- {SCALAR} 13.2.99.3
lcosLXSetupLBSLBSServerType OBJECT-TYPE
    SYNTAX     INTEGER {
                  eHTTPJSON(1)
               }
    MAX-ACCESS read-only
    STATUS     current
    DESCRIPTION
        ""
    ::= { lcosLXSetupLBS 3 }

-- {SCALAR} 13.2.99.4
lcosLXSetupLBSBLEScanType OBJECT-TYPE
    SYNTAX     INTEGER {
                  ePassive(1),
                  eActive(2)
               }
    MAX-ACCESS read-only
    STATUS     current
    DESCRIPTION
        ""
    ::= { lcosLXSetupLBS 4 }

-- {OID} 13.2.102
lcosLXSetupLMC OBJECT IDENTIFIER ::= { lcosLXSetup 102 }

-- {SCALAR} 13.2.102.1
lcosLXSetupLMCOperating OBJECT-TYPE
    SYNTAX     INTEGER {
                  eNo(0),
                  eYes(1),
                  eOnlyWithoutWLC(2)
               }
    MAX-ACCESS read-only
    STATUS     current
    DESCRIPTION
        ""
    ::= { lcosLXSetupLMC 1 }

-- {OID} 13.2.102.2
lcosLXSetupLMCProxy OBJECT IDENTIFIER ::= { lcosLXSetupLMC 2 }

-- {SCALAR} 13.2.102.2.1
lcosLXSetupLMCProxyURL OBJECT-TYPE
    SYNTAX     OCTET STRING (SIZE(0..255))
    MAX-ACCESS read-only
    STATUS     current
    DESCRIPTION
        ""
    ::= { lcosLXSetupLMCProxy 1 }

-- {SCALAR} 13.2.102.2.2
lcosLXSetupLMCProxyUsername OBJECT-TYPE
    SYNTAX     OCTET STRING (SIZE(0..64))
    MAX-ACCESS read-only
    STATUS     current
    DESCRIPTION
        ""
    ::= { lcosLXSetupLMCProxy 2 }

-- {SCALAR} 13.2.102.2.3
lcosLXSetupLMCProxyPassword OBJECT-TYPE
    SYNTAX     OCTET STRING (SIZE(0..64))
    MAX-ACCESS read-only
    STATUS     current
    DESCRIPTION
        ""
    ::= { lcosLXSetupLMCProxy 3 }

-- {SCALAR} 13.2.102.2.4
lcosLXSetupLMCProxyTunnel OBJECT-TYPE
    SYNTAX     INTEGER {
                  eNo(0),
                  eYes(1)
               }
    MAX-ACCESS read-only
    STATUS     current
    DESCRIPTION
        ""
    ::= { lcosLXSetupLMCProxy 4 }

-- {SCALAR} 13.2.102.8
lcosLXSetupLMCDHCPClientAutoRenew OBJECT-TYPE
    SYNTAX     INTEGER {
                  eNo(0),
                  eYes(1)
               }
    MAX-ACCESS read-only
    STATUS     current
    DESCRIPTION
        ""
    ::= { lcosLXSetupLMC 8 }

-- {SCALAR} 13.2.102.13
lcosLXSetupLMCConfigurationViaDHCP OBJECT-TYPE
    SYNTAX     INTEGER {
                  eNo(0),
                  eYes(1)
               }
    MAX-ACCESS read-only
    STATUS     current
    DESCRIPTION
        ""
    ::= { lcosLXSetupLMC 13 }

-- {SCALAR} 13.2.102.15
lcosLXSetupLMCLMCDomain OBJECT-TYPE
    SYNTAX     OCTET STRING (SIZE(0..255))
    MAX-ACCESS read-only
    STATUS     current
    DESCRIPTION
        ""
    ::= { lcosLXSetupLMC 15 }

-- {SCALAR} 13.2.102.16
lcosLXSetupLMCRolloutProjectID OBJECT-TYPE
    SYNTAX     OCTET STRING (SIZE(0..36))
    MAX-ACCESS read-only
    STATUS     current
    DESCRIPTION
        ""
    ::= { lcosLXSetupLMC 16 }

-- {SCALAR} 13.2.102.17
lcosLXSetupLMCRolloutLocationID OBJECT-TYPE
    SYNTAX     OCTET STRING (SIZE(0..36))
    MAX-ACCESS read-only
    STATUS     current
    DESCRIPTION
        ""
    ::= { lcosLXSetupLMC 17 }

-- {SCALAR} 13.2.102.18
lcosLXSetupLMCRolloutDeviceRole OBJECT-TYPE
    SYNTAX     OCTET STRING (SIZE(0..36))
    MAX-ACCESS read-only
    STATUS     current
    DESCRIPTION
        ""
    ::= { lcosLXSetupLMC 18 }

-- {SCALAR} 13.2.102.200
lcosLXSetupLMCPairingToken OBJECT-TYPE
    SYNTAX     OCTET STRING (SIZE(0..36))
    MAX-ACCESS read-only
    STATUS     current
    DESCRIPTION
        ""
    ::= { lcosLXSetupLMC 200 }

-- {OID} 13.2.107
lcosLXSetupAutomaticFirmwareUpdate OBJECT IDENTIFIER ::= { lcosLXSetup 107 }

-- {SCALAR} 13.2.107.1
lcosLXSetupAutomaticFirmwareUpdateMode OBJECT-TYPE
    SYNTAX     INTEGER {
                  emanual(0),
                  echeck(1),
                  echeckandupdate(2)
               }
    MAX-ACCESS read-only
    STATUS     current
    DESCRIPTION
        ""
    ::= { lcosLXSetupAutomaticFirmwareUpdate 1 }

-- {SCALAR} 13.2.107.6
lcosLXSetupAutomaticFirmwareUpdateBaseURL OBJECT-TYPE
    SYNTAX     OCTET STRING (SIZE(0..252))
    MAX-ACCESS read-only
    STATUS     current
    DESCRIPTION
        ""
    ::= { lcosLXSetupAutomaticFirmwareUpdate 6 }

-- {SCALAR} 13.2.107.7
lcosLXSetupAutomaticFirmwareUpdateCheckInterval OBJECT-TYPE
    SYNTAX     INTEGER {
                  edaily(0),
                  eweekly(1)
               }
    MAX-ACCESS read-only
    STATUS     current
    DESCRIPTION
        ""
    ::= { lcosLXSetupAutomaticFirmwareUpdate 7 }

-- {SCALAR} 13.2.107.8
lcosLXSetupAutomaticFirmwareUpdateVersionPolicy OBJECT-TYPE
    SYNTAX     INTEGER {
                  elatest(0),
                  ecurrent(1),
                  esecurityupdatesonly(2),
                  elatestwithoutREL(3)
               }
    MAX-ACCESS read-only
    STATUS     current
    DESCRIPTION
        ""
    ::= { lcosLXSetupAutomaticFirmwareUpdate 8 }

-- {SCALAR} 13.2.107.10
lcosLXSetupAutomaticFirmwareUpdateCheckTimeBegin OBJECT-TYPE
    SYNTAX     Unsigned32 (0..255)
    MAX-ACCESS read-only
    STATUS     current
    DESCRIPTION
        ""
    ::= { lcosLXSetupAutomaticFirmwareUpdate 10 }

-- {SCALAR} 13.2.107.11
lcosLXSetupAutomaticFirmwareUpdateCheckTimeEnd OBJECT-TYPE
    SYNTAX     Unsigned32 (0..255)
    MAX-ACCESS read-only
    STATUS     current
    DESCRIPTION
        ""
    ::= { lcosLXSetupAutomaticFirmwareUpdate 11 }

-- {SCALAR} 13.2.107.12
lcosLXSetupAutomaticFirmwareUpdateInstallTimeBegin OBJECT-TYPE
    SYNTAX     Unsigned32 (0..255)
    MAX-ACCESS read-only
    STATUS     current
    DESCRIPTION
        ""
    ::= { lcosLXSetupAutomaticFirmwareUpdate 12 }

-- {SCALAR} 13.2.107.13
lcosLXSetupAutomaticFirmwareUpdateInstallTimeEnd OBJECT-TYPE
    SYNTAX     Unsigned32 (0..255)
    MAX-ACCESS read-only
    STATUS     current
    DESCRIPTION
        ""
    ::= { lcosLXSetupAutomaticFirmwareUpdate 13 }

-- {OID} 13.2.111
lcosLXSetupIoT OBJECT IDENTIFIER ::= { lcosLXSetup 111 }

-- {OID} 13.2.111.1
lcosLXSetupIoTUSB OBJECT IDENTIFIER ::= { lcosLXSetupIoT 1 }

-- {OID} 13.2.111.1.1
lcosLXSetupIoTUSBCDCEEMSupport OBJECT IDENTIFIER ::= { lcosLXSetupIoTUSB 1 }

-- {OID} 13.2.111.88
lcosLXSetupIoTWirelessePaper OBJECT IDENTIFIER ::= { lcosLXSetupIoT 88 }

-- {TABLE} 13.2.111.88.20
lcosLXSetupIoTWirelessePaperIPInterface OBJECT-TYPE
    SYNTAX     SEQUENCE OF LcosLXSetupIoTWirelessePaperIPInterfaceEntry
    MAX-ACCESS not-accessible
    STATUS     current
    DESCRIPTION
        ""
    ::= { lcosLXSetupIoTWirelessePaper 20 }

-- {INDEX} 13.2.111.88.20
lcosLXSetupIoTWirelessePaperIPInterfaceEntry OBJECT-TYPE
    SYNTAX     LcosLXSetupIoTWirelessePaperIPInterfaceEntry
    MAX-ACCESS not-accessible
    STATUS     current
    DESCRIPTION
        ""
    INDEX {
        lcosLXSetupIoTWirelessePaperIPInterfaceEntryInterfaceName
    }
    ::= { lcosLXSetupIoTWirelessePaperIPInterface 1 }

-- {SEQUENCE} 13.2.111.88.20
LcosLXSetupIoTWirelessePaperIPInterfaceEntry ::= SEQUENCE {
    lcosLXSetupIoTWirelessePaperIPInterfaceEntryInterfaceName OCTET STRING,
    lcosLXSetupIoTWirelessePaperIPInterfaceEntryInterfaceID OCTET STRING,
    lcosLXSetupIoTWirelessePaperIPInterfaceEntryVLANID Unsigned32,
    lcosLXSetupIoTWirelessePaperIPInterfaceEntryIPv4AddressSource INTEGER,
    lcosLXSetupIoTWirelessePaperIPInterfaceEntryIPv6AddressSource INTEGER,
    lcosLXSetupIoTWirelessePaperIPInterfaceEntryStaticIPv4Address OCTET STRING,
    lcosLXSetupIoTWirelessePaperIPInterfaceEntryStaticIPv6Address OCTET STRING
}

-- {COLUMN} 13.2.111.88.20.1.1
lcosLXSetupIoTWirelessePaperIPInterfaceEntryInterfaceName OBJECT-TYPE
    SYNTAX     OCTET STRING (SIZE(0..64))
    MAX-ACCESS not-accessible
    STATUS     current
    DESCRIPTION
        ""
    ::= { lcosLXSetupIoTWirelessePaperIPInterfaceEntry 1 }

-- {COLUMN} 13.2.111.88.20.1.2
lcosLXSetupIoTWirelessePaperIPInterfaceEntryInterfaceID OBJECT-TYPE
    SYNTAX     OCTET STRING (SIZE(0..16))
    MAX-ACCESS read-only
    STATUS     current
    DESCRIPTION
        ""
    ::= { lcosLXSetupIoTWirelessePaperIPInterfaceEntry 2 }

-- {COLUMN} 13.2.111.88.20.1.3
lcosLXSetupIoTWirelessePaperIPInterfaceEntryVLANID OBJECT-TYPE
    SYNTAX     Unsigned32 (0..65535)
    MAX-ACCESS read-only
    STATUS     current
    DESCRIPTION
        ""
    ::= { lcosLXSetupIoTWirelessePaperIPInterfaceEntry 3 }

-- {COLUMN} 13.2.111.88.20.1.4
lcosLXSetupIoTWirelessePaperIPInterfaceEntryIPv4AddressSource OBJECT-TYPE
    SYNTAX     INTEGER {
                  eDHCP(1),
                  estatic(2)
               }
    MAX-ACCESS read-only
    STATUS     current
    DESCRIPTION
        ""
    ::= { lcosLXSetupIoTWirelessePaperIPInterfaceEntry 4 }

-- {COLUMN} 13.2.111.88.20.1.5
lcosLXSetupIoTWirelessePaperIPInterfaceEntryIPv6AddressSource OBJECT-TYPE
    SYNTAX     INTEGER {
                  eRouterAdvertisement(1),
                  eDHCPv6(2),
                  estatic(3)
               }
    MAX-ACCESS read-only
    STATUS     current
    DESCRIPTION
        ""
    ::= { lcosLXSetupIoTWirelessePaperIPInterfaceEntry 5 }

-- {COLUMN} 13.2.111.88.20.1.6
lcosLXSetupIoTWirelessePaperIPInterfaceEntryStaticIPv4Address OBJECT-TYPE
    SYNTAX     OCTET STRING (SIZE(0..19))
    MAX-ACCESS read-only
    STATUS     current
    DESCRIPTION
        ""
    ::= { lcosLXSetupIoTWirelessePaperIPInterfaceEntry 6 }

-- {COLUMN} 13.2.111.88.20.1.7
lcosLXSetupIoTWirelessePaperIPInterfaceEntryStaticIPv6Address OBJECT-TYPE
    SYNTAX     OCTET STRING (SIZE(0..44))
    MAX-ACCESS read-only
    STATUS     current
    DESCRIPTION
        ""
    ::= { lcosLXSetupIoTWirelessePaperIPInterfaceEntry 7 }

-- {TABLE} 13.2.111.88.30
lcosLXSetupIoTWirelessePaperStatic OBJECT-TYPE
    SYNTAX     SEQUENCE OF LcosLXSetupIoTWirelessePaperStaticEntry
    MAX-ACCESS not-accessible
    STATUS     current
    DESCRIPTION
        ""
    ::= { lcosLXSetupIoTWirelessePaper 30 }

-- {INDEX} 13.2.111.88.30
lcosLXSetupIoTWirelessePaperStaticEntry OBJECT-TYPE
    SYNTAX     LcosLXSetupIoTWirelessePaperStaticEntry
    MAX-ACCESS not-accessible
    STATUS     current
    DESCRIPTION
        ""
    INDEX {
        lcosLXSetupIoTWirelessePaperStaticEntryInterfaceName
    }
    ::= { lcosLXSetupIoTWirelessePaperStatic 1 }

-- {SEQUENCE} 13.2.111.88.30
LcosLXSetupIoTWirelessePaperStaticEntry ::= SEQUENCE {
    lcosLXSetupIoTWirelessePaperStaticEntryInterfaceName OCTET STRING,
    lcosLXSetupIoTWirelessePaperStaticEntryIPv4Gateway IpAddress,
    lcosLXSetupIoTWirelessePaperStaticEntryIPv6Gateway OCTET STRING,
    lcosLXSetupIoTWirelessePaperStaticEntryPrimaryIPv4DNS IpAddress,
    lcosLXSetupIoTWirelessePaperStaticEntrySecondaryIPv4DNS IpAddress,
    lcosLXSetupIoTWirelessePaperStaticEntryPrimaryIPv6DNS OCTET STRING,
    lcosLXSetupIoTWirelessePaperStaticEntrySecondaryIPv6DNS OCTET STRING
}

-- {COLUMN} 13.2.111.88.30.1.1
lcosLXSetupIoTWirelessePaperStaticEntryInterfaceName OBJECT-TYPE
    SYNTAX     OCTET STRING (SIZE(0..64))
    MAX-ACCESS not-accessible
    STATUS     current
    DESCRIPTION
        ""
    ::= { lcosLXSetupIoTWirelessePaperStaticEntry 1 }

-- {COLUMN} 13.2.111.88.30.1.2
lcosLXSetupIoTWirelessePaperStaticEntryIPv4Gateway OBJECT-TYPE
    SYNTAX     IpAddress
    MAX-ACCESS read-only
    STATUS     current
    DESCRIPTION
        ""
    ::= { lcosLXSetupIoTWirelessePaperStaticEntry 2 }

-- {COLUMN} 13.2.111.88.30.1.3
lcosLXSetupIoTWirelessePaperStaticEntryIPv6Gateway OBJECT-TYPE
    SYNTAX     OCTET STRING (SIZE(0..44))
    MAX-ACCESS read-only
    STATUS     current
    DESCRIPTION
        ""
    ::= { lcosLXSetupIoTWirelessePaperStaticEntry 3 }

-- {COLUMN} 13.2.111.88.30.1.4
lcosLXSetupIoTWirelessePaperStaticEntryPrimaryIPv4DNS OBJECT-TYPE
    SYNTAX     IpAddress
    MAX-ACCESS read-only
    STATUS     current
    DESCRIPTION
        ""
    ::= { lcosLXSetupIoTWirelessePaperStaticEntry 4 }

-- {COLUMN} 13.2.111.88.30.1.5
lcosLXSetupIoTWirelessePaperStaticEntrySecondaryIPv4DNS OBJECT-TYPE
    SYNTAX     IpAddress
    MAX-ACCESS read-only
    STATUS     current
    DESCRIPTION
        ""
    ::= { lcosLXSetupIoTWirelessePaperStaticEntry 5 }

-- {COLUMN} 13.2.111.88.30.1.6
lcosLXSetupIoTWirelessePaperStaticEntryPrimaryIPv6DNS OBJECT-TYPE
    SYNTAX     OCTET STRING (SIZE(0..44))
    MAX-ACCESS read-only
    STATUS     current
    DESCRIPTION
        ""
    ::= { lcosLXSetupIoTWirelessePaperStaticEntry 6 }

-- {COLUMN} 13.2.111.88.30.1.7
lcosLXSetupIoTWirelessePaperStaticEntrySecondaryIPv6DNS OBJECT-TYPE
    SYNTAX     OCTET STRING (SIZE(0..44))
    MAX-ACCESS read-only
    STATUS     current
    DESCRIPTION
        ""
    ::= { lcosLXSetupIoTWirelessePaperStaticEntry 7 }

-- {OID} 13.3
lcosLXFirmware OBJECT IDENTIFIER ::= { lcosLX 3 }

-- {SCALAR} 13.3.10
lcosLXFirmwareBootcount OBJECT-TYPE
    SYNTAX     Unsigned32 (0..255)
    MAX-ACCESS read-only
    STATUS     current
    DESCRIPTION
        ""
    ::= { lcosLXFirmware 10 }

-- {OID} 13.4
lcosLXOther OBJECT IDENTIFIER ::= { lcosLX 4 }

-- {OID} 13.8
lcosLXProducts OBJECT IDENTIFIER ::= { lcosLX 8 }

-- {OID} 13.8.0
lcosLXProductsAccessPoints OBJECT IDENTIFIER ::= { lcosLXProducts 0 }

-- {OID} 13.8.0.16
lcosLXProductsAccessPointsLX7500 OBJECT IDENTIFIER ::= { lcosLXProductsAccessPoints 16 }



-- {NOTIFICATION} 13.0.0.1
lcosLXWifiTrapAuthStation NOTIFICATION-TYPE
    OBJECTS {
            lcosLXStatusSNMPEventEntryCount,
            lcosLXStatusWLANStationEntryIdentification
           }
    STATUS current
    DESCRIPTION
            ""
    ::= { lcosLXWifiTraps 1 }

-- {NOTIFICATION} 13.0.0.2
lcosLXWifiTrapDeAuthStation NOTIFICATION-TYPE
    OBJECTS {
            lcosLXStatusSNMPEventEntryCount,
            lcosLXStatusWLANStationEntryIdentification
           }
    STATUS current
    DESCRIPTION
            ""
    ::= { lcosLXWifiTraps 2 }

-- {NOTIFICATION} 13.0.0.3
lcosLXWifiTrapAssStation NOTIFICATION-TYPE
    OBJECTS {
            lcosLXStatusSNMPEventEntryCount,
            lcosLXStatusWLANStationEntryIdentification
           }
    STATUS current
    DESCRIPTION
            ""
    ::= { lcosLXWifiTraps 3 }

-- {NOTIFICATION} 13.0.0.4
lcosLXWifiTrapReAssStation NOTIFICATION-TYPE
    OBJECTS {
            lcosLXStatusSNMPEventEntryCount,
            lcosLXStatusWLANStationEntryIdentification
           }
    STATUS current
    DESCRIPTION
            ""
    ::= { lcosLXWifiTraps 4 }

-- {NOTIFICATION} 13.0.0.5
lcosLXWifiTrapDisAssStation NOTIFICATION-TYPE
    OBJECTS {
            lcosLXStatusSNMPEventEntryCount,
            lcosLXStatusWLANStationEntryIdentification
           }
    STATUS current
    DESCRIPTION
            ""
    ::= { lcosLXWifiTraps 5 }

-- {NOTIFICATION} 13.0.0.6
lcosLXWifiTrapAssRej NOTIFICATION-TYPE
    OBJECTS {
            lcosLXStatusSNMPEventEntryCount,
            lcosLXStatusWLANStationEntryIdentification
           }
    STATUS current
    DESCRIPTION
            ""
    ::= { lcosLXWifiTraps 6 }

-- {NOTIFICATION} 13.0.0.7
lcosLXWifiTrapConnected NOTIFICATION-TYPE
    OBJECTS {
            lcosLXStatusSNMPEventEntryCount,
            lcosLXStatusWLANStationEntryIdentification
           }
    STATUS current
    DESCRIPTION
            ""
    ::= { lcosLXWifiTraps 7 }

END
